GWAPIMIB DEFINITIONS ::= BEGIN

IMPORTS
        Counter, TimeTicks, Gauge, enterprises  FROM RFC1155-SMI
        DisplayString                           FROM RFC1213-MIB
        TRAP-TYPE                               FROM RFC-1215
        OBJECT-TYPE                             FROM RFC-1212;

wpcorp          OBJECT IDENTIFIER   ::= { enterprises 922 }
gateways        OBJECT IDENTIFIER   ::= { wpcorp        2 }
ngwAPI         OBJECT IDENTIFIER   ::= { gateways      8 }
ngwAPIInfo     OBJECT IDENTIFIER   ::= { ngwAPI       1 }
ngwAPITrapInfo OBJECT IDENTIFIER   ::= { ngwAPI       2 }


-- ====================================== NGWAPI Get/Set Variables =========
ngwAPIGatewayName OBJECT-TYPE
       SYNTAX  DisplayString (SIZE (0..255))
       ACCESS  read-only
       STATUS  mandatory
       DESCRIPTION
       "The GroupWise API Gateway name."
   ::= { ngwAPIInfo 1 }
 
ngwAPIUptime OBJECT-TYPE
       SYNTAX  TimeTicks
       ACCESS  read-only
       STATUS  mandatory
       DESCRIPTION
      "Uptime of the GroupWise API Gateway."
   ::= { ngwAPIInfo 2 }

ngwAPIGroupWiseLink OBJECT-TYPE
       SYNTAX  DisplayString (SIZE (0..5))
       ACCESS  read-only
       STATUS  mandatory
       DESCRIPTION
      "GroupWise API Gateway Link: UP or DOWN"
   ::= { ngwAPIInfo 3 }

ngwAPIFrgnLink OBJECT-TYPE
       SYNTAX  DisplayString (SIZE (0..5))
       ACCESS  read-only
       STATUS  mandatory
       DESCRIPTION
      "GroupWise API Gateway Foreign Link: UP or DOWN"
   ::= { ngwAPIInfo 4 }

ngwAPIOutBytes OBJECT-TYPE
       SYNTAX  Counter
       ACCESS  read-only
       STATUS  mandatory
       DESCRIPTION
      "The number of message bytes sent to GroupWise API."
   ::= { ngwAPIInfo 5 }
 
ngwAPIInBytes OBJECT-TYPE
       SYNTAX  Counter
       ACCESS  read-only
       STATUS  mandatory
       DESCRIPTION
      "The number of message bytes received from GroupWise API."
   ::= { ngwAPIInfo 6 }
 
ngwAPIOutMsgs OBJECT-TYPE
       SYNTAX  Counter
       ACCESS  read-only
       STATUS  mandatory
       DESCRIPTION
      "The number of messages sent to GroupWise API."
   ::= { ngwAPIInfo 7 }
 
ngwAPIInMsgs OBJECT-TYPE
       SYNTAX  Counter
       ACCESS  read-only
       STATUS  mandatory
       DESCRIPTION
      "The number of messages received from API."
   ::= { ngwAPIInfo 8 }
 
ngwAPIOutStatuses OBJECT-TYPE
       SYNTAX  Counter
       ACCESS  read-only
       STATUS  mandatory
       DESCRIPTION
      "The number of statuses sent to API."
   ::= { ngwAPIInfo 9 }
 
ngwAPIInStatuses OBJECT-TYPE
       SYNTAX  Counter
       ACCESS  read-only
       STATUS  mandatory
       DESCRIPTION
      "The number of statuses received from API."
   ::= { ngwAPIInfo 10 }
 
ngwAPIOutErrors OBJECT-TYPE
       SYNTAX  Counter
       ACCESS  read-only
       STATUS  mandatory
       DESCRIPTION
      "The number of failed transfers to API."
   ::= { ngwAPIInfo 11 }
 
ngwAPIInErrors OBJECT-TYPE
       SYNTAX  Counter
       ACCESS  read-only
       STATUS  mandatory
       DESCRIPTION
      "The number of failed transfers from API."
   ::= { ngwAPIInfo 12 }

-- ================================================== ngwAPITrapInfo ========
-- The ngwAPITrapInfo group
-- These objects are used only in traps produced by NGWAPI
 
ngwAPITrapTime OBJECT-TYPE
		SYNTAX  INTEGER
		ACCESS  not-accessible
		STATUS  mandatory
		DESCRIPTION "The time the trap occurred. Seconds since Jan 1, 1970 (GMT)"
	::= { ngwAPITrapInfo 1 }

-- ================================================== NGWAPI Traps =========
ngwAPIStartTrap TRAP-TYPE
		ENTERPRISE    ngwAPIInfo
		VARIABLES     {ngwAPITrapTime, ngwAPIGatewayName}
		DESCRIPTION   "GroupWise API Gateway start."
		--NMS Trap annotation
		--#TYPE       "GroupWise API Gateway start."
		--#SUMMARY    "GroupWise API Gateway %s has started."
		--#ARGUMENTS  {1}
		--#SEVERITY   INFORMATIONAL
		--#TIMEINDEX  0
		--#HELP       "NGWALARM.HLP"
		--#HELPTAG    101		
		--#STATE      OPERATIONAL
		::= 1

ngwAPIStopTrap TRAP-TYPE
		ENTERPRISE    ngwAPIInfo
		VARIABLES     {ngwAPITrapTime, ngwAPIGatewayName}
		DESCRIPTION   "GroupWise API Gateway stop."
		--NMS Trap annotation
		--#TYPE       "GroupWise API Gateway stop."
		--#SUMMARY    "GroupWise API Gateway %s has stopped."
		--#ARGUMENTS  {1}
		--#SEVERITY   CRITICAL
		--#TIMEINDEX  0
		--#HELP       "NGWALARM.HLP"
		--#HELPTAG    102		
		--#STATE      NONOPERATIONAL
		::= 2

ngwAPIRestartTrap TRAP-TYPE
		ENTERPRISE    ngwAPIInfo
		VARIABLES     {ngwAPITrapTime, ngwAPIGatewayName}
		DESCRIPTION   "GroupWise API Gateway restart."
		--NMS Trap annotation
		--#TYPE       "GroupWise API Gateway restart."
		--#SUMMARY    "GroupWise API Gateway %s has been restarted."
		--#ARGUMENTS  {1}
		--#SEVERITY   INFORMATIONAL
		--#TIMEINDEX  0
		--#HELP       "NGWALARM.HLP"
		--#HELPTAG    503		
		--#STATE      OPERATIONAL
		::= 3
 
ngwAPIGroupWiseLinkTrap TRAP-TYPE
		ENTERPRISE    ngwAPIInfo
		VARIABLES     {ngwAPITrapTime, ngwAPIGatewayName}
		DESCRIPTION   "GroupWise Link lost by GroupWise API Gateway"
		--NMS Trap annotation
		--#TYPE       "GroupWise Link lost by GroupWise API Gateway"
		--#SUMMARY    "GroupWise API Gateway %s has lost its GroupWise Link"
		--#ARGUMENTS  {1}
		--#SEVERITY   INFORMATIONAL
		--#TIMEINDEX  0
		--#HELP       "NGWALARM.HLP"
		--#HELPTAG    504		
		--#STATE      OPERATIONAL
		::= 4

ngwAPIFgnLinkTrap TRAP-TYPE
		ENTERPRISE    ngwAPIInfo
		VARIABLES     {ngwAPITrapTime, ngwAPIGatewayName}
		DESCRIPTION   "API Link lost by GroupWise API Gateway"
		--NMS Trap annotation
		--#TYPE       "API Link lost by GroupWise API Gateway"
		--#SUMMARY    "GroupWise API Gateway %s has lost its API Link"
		--#ARGUMENTS  {1}
		--#SEVERITY   INFORMATIONAL
		--#TIMEINDEX  0
		--#HELP       "NGWALARM.HLP"
		--#HELPTAG    505		
		--#STATE      OPERATIONAL
		::= 5


END
