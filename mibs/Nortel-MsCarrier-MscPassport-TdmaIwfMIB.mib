Nortel-MsCarrier-MscPassport-TdmaIwfMIB
DEFINITIONS ::= BEGIN



IMPORTS

      OBJECT-TYPE
   FROM RFC-1212

      IpAddress
   FROM RFC1155-SMI

      mscPassportMIBs,
      mscComponents
   FROM Nortel-MsCarrier-MscPassport-UsefulDefinitionsMIB

      Counter32,
      RowPointer,
      DisplayString,
      StorageType,
      RowStatus,
      Gauge32,
      Integer32,
      Unsigned32
   FROM Nortel-MsCarrier-MscPassport-StandardTextualConventionsMIB

      AsciiString,
      NonReplicated,
      Link,
      FixedPoint2
   FROM Nortel-MsCarrier-MscPassport-TextualConventionsMIB;




-- LAST-UPDATED   "9909010000Z"
-- ORGANIZATION   "Nortel Networks"
-- CONTACT-INFO   "
--         Nortel Carrier Data Network Management
--         
--         Postal:       P.O. Box 3511, Station C 
--                       Ottawa, Ontario 
--                       Canada  K1Y 4H7
--         
--         via the WEB:  http://www.nortelnetworks.com  
--                       select 'Contact Us' from the menu
--          
--         via phone:    1-800-4NORTEL"
-- DESCRIPTION
--    "The module describing the Nortel MsCarrier MscPassport
--     TdmaIwf Enterprise MIB."

tdmaIwfMIB OBJECT IDENTIFIER ::= { mscPassportMIBs 140 }










-- TdmaCs/<csIndex>
-- The TdmaIwfCallServer component represents an instance of a call 
-- manager for Mobile Telephone eXchange communications (MTX) 
-- InterWorking Function (IWF) calls on this node. The 
-- TdmaIwfCallServer provides a mechanism to segregate call 
-- resources (TdmaIwfBearerChannels) and maintenance activities for 
-- the TdmaIwfBearerChannel(s) associated with that 
-- TdmaIwfCallServer. The csIndex bears no particular significance 
-- and is arbitrary.
-- 
-- This component is specific to the tdmaIwfCallServer feature of the 
-- tdmaIwf application.

mscTdmaCs OBJECT IDENTIFIER ::= { mscComponents 135 }



mscTdmaCsRowStatusTable OBJECT-TYPE
   SYNTAX     SEQUENCE OF MscTdmaCsRowStatusEntry
   ACCESS     not-accessible
   STATUS     mandatory
   DESCRIPTION
     "This entry controls the addition and deletion of 
      mscTdmaCs components."
::= { mscTdmaCs 1 }

mscTdmaCsRowStatusEntry OBJECT-TYPE
   SYNTAX     MscTdmaCsRowStatusEntry
   ACCESS     not-accessible
   STATUS     mandatory
   DESCRIPTION
     "A single entry in the table represents a single 
      mscTdmaCs component."
   INDEX {
      mscTdmaCsCsIndex }
::= { mscTdmaCsRowStatusTable 1 }

MscTdmaCsRowStatusEntry ::= SEQUENCE {
   mscTdmaCsRowStatus
      RowStatus,
   mscTdmaCsComponentName
      DisplayString,
   mscTdmaCsStorageType
      StorageType,
   mscTdmaCsCsIndex
      Integer32 }

mscTdmaCsRowStatus OBJECT-TYPE
   SYNTAX     RowStatus 
   ACCESS     read-write
   STATUS     mandatory
   DESCRIPTION
     "This variable is used as the basis for SNMP naming of
      mscTdmaCs components.
      These components can be added and deleted."
::= { mscTdmaCsRowStatusEntry 1 }

mscTdmaCsComponentName OBJECT-TYPE
   SYNTAX     DisplayString 
   ACCESS     read-only
   STATUS     mandatory
   DESCRIPTION
     "This variable provides the component's string name for
      use with the ASCII Console Interface"
::= { mscTdmaCsRowStatusEntry 2 }

mscTdmaCsStorageType OBJECT-TYPE
   SYNTAX     StorageType 
   ACCESS     read-only
   STATUS     mandatory
   DESCRIPTION
     "This variable represents the storage type value for the
      mscTdmaCs tables."
::= { mscTdmaCsRowStatusEntry 4 }

mscTdmaCsCsIndex OBJECT-TYPE
   SYNTAX     Integer32 (1..10)
   ACCESS     not-accessible
   STATUS     mandatory
   DESCRIPTION
     "This variable represents the index for the mscTdmaCs tables."
::= { mscTdmaCsRowStatusEntry 10 }

mscTdmaCsServProvTable OBJECT-TYPE
   SYNTAX     SEQUENCE OF MscTdmaCsServProvEntry
   ACCESS     not-accessible
   STATUS     mandatory
   DESCRIPTION
     "This group contains all the necessary timers for call setup and call 
      clearing scenarios on the IWF."
::= { mscTdmaCs 100 }

mscTdmaCsServProvEntry OBJECT-TYPE
   SYNTAX     MscTdmaCsServProvEntry
   ACCESS     not-accessible
   STATUS     mandatory
   DESCRIPTION
     "An entry in the mscTdmaCsServProvTable."
   INDEX {
      mscTdmaCsCsIndex }
::= { mscTdmaCsServProvTable 1 }

MscTdmaCsServProvEntry ::= SEQUENCE {
   mscTdmaCsTIwf1
      Unsigned32,
   mscTdmaCsTIwf2
      Unsigned32,
   mscTdmaCsT303
      Unsigned32,
   mscTdmaCsT305
      Unsigned32,
   mscTdmaCsT308
      Unsigned32,
   mscTdmaCsT313
      Unsigned32,
   mscTdmaCsT999
      Unsigned32,
   mscTdmaCsSupportedTechnology
      INTEGER,
   mscTdmaCsSupportedService
      INTEGER }

mscTdmaCsTIwf1 OBJECT-TYPE
   SYNTAX     Unsigned32 (0..3600)
   ACCESS     read-write
   STATUS     mandatory
   DESCRIPTION
     "This is an internal timer to the call server of the IWF and is used 
      during call setup for ensuring the MIT protocol stack and the NIT 
      modem for a new call have been allocated and initialized."
   DEFVAL     { 4 }
::= { mscTdmaCsServProvEntry 1 }

mscTdmaCsTIwf2 OBJECT-TYPE
   SYNTAX     Unsigned32 (0..3600)
   ACCESS     read-write
   STATUS     mandatory
   DESCRIPTION
     "This is an internal timer to the call server of the IWF and is used 
      during call clearing for ensuring the MIT protocol stack and NIT 
      modem for a call have been deallocated correctly."
   DEFVAL     { 4 }
::= { mscTdmaCsServProvEntry 2 }

mscTdmaCsT303 OBJECT-TYPE
   SYNTAX     Unsigned32 (0..3600)
   ACCESS     read-write
   STATUS     mandatory
   DESCRIPTION
     "This timer is a call setup timer and is used for ensuring a 
      CallProceeding message is received for a Setup message that has 
      been sent by the IWF to the MTX."
   DEFVAL     { 4 }
::= { mscTdmaCsServProvEntry 3 }

mscTdmaCsT305 OBJECT-TYPE
   SYNTAX     Unsigned32 (0..3600)
   ACCESS     read-write
   STATUS     mandatory
   DESCRIPTION
     "This timer is a call clearing timer and is used for ensuring a Release 
      message is received for a Disconnect message the IWF has sent to 
      the MTX."
   DEFVAL     { 30 }
::= { mscTdmaCsServProvEntry 4 }

mscTdmaCsT308 OBJECT-TYPE
   SYNTAX     Unsigned32 (0..3600)
   ACCESS     read-write
   STATUS     mandatory
   DESCRIPTION
     "This timer is a call clearing timer and is used for ensuring a 
      ReleaseComplete message is received for the Release message the 
      IWF has sent to the MTX."
   DEFVAL     { 4 }
::= { mscTdmaCsServProvEntry 5 }

mscTdmaCsT313 OBJECT-TYPE
   SYNTAX     Unsigned32 (0..3600)
   ACCESS     read-write
   STATUS     mandatory
   DESCRIPTION
     "This is a call setup timer and is used for ensuring a ConnectAck 
      message is received in response for the Connect message the IWF 
      has sent to the MTX."
   DEFVAL     { 4 }
::= { mscTdmaCsServProvEntry 6 }

mscTdmaCsT999 OBJECT-TYPE
   SYNTAX     Unsigned32 (0..3600)
   ACCESS     read-write
   STATUS     mandatory
   DESCRIPTION
     "This timer is used during a mobile termination call setup and is used 
      for ensuring the Setup message is received from the MTX."
   DEFVAL     { 300 }
::= { mscTdmaCsServProvEntry 7 }

mscTdmaCsSupportedTechnology OBJECT-TYPE
   SYNTAX     INTEGER  {
                 tdmaOnly(0),
                 cdmaOnly(1),
                 tdmaAndCdma(2) }
   ACCESS     read-write
   STATUS     mandatory
   DESCRIPTION
     "This attribute specifies the wireless technology that is supported for 
      data calls on this IWF."
   DEFVAL     { tdmaOnly }
::= { mscTdmaCsServProvEntry 8 }

mscTdmaCsSupportedService OBJECT-TYPE
   SYNTAX     INTEGER  {
                 asyncDataOnly(0),
                 g3FaxOnly(1),
                 analogFaxOnly(2),
                 packetOnly(3),
                 asyncDataAndG3Fax(4),
                 asyncDataAndAnalogFax(5),
                 asyncDataAndPacket(6),
                 asyncDataG3FaxAndPacket(7),
                 asyncDataAFaxAndPacket(8) }
   ACCESS     read-write
   STATUS     mandatory
   DESCRIPTION
     "This attribute specifies the type(s) of data calls this IWF supports."
   DEFVAL     { asyncDataOnly }
::= { mscTdmaCsServProvEntry 9 }

mscTdmaCsMiscProvTable OBJECT-TYPE
   SYNTAX     SEQUENCE OF MscTdmaCsMiscProvEntry
   ACCESS     not-accessible
   STATUS     mandatory
   DESCRIPTION
     "This group contains general provisioning data for the 
      TdmaIwfCallServer that does not fit within other provisioning 
      groups."
::= { mscTdmaCs 101 }

mscTdmaCsMiscProvEntry OBJECT-TYPE
   SYNTAX     MscTdmaCsMiscProvEntry
   ACCESS     not-accessible
   STATUS     mandatory
   DESCRIPTION
     "An entry in the mscTdmaCsMiscProvTable."
   INDEX {
      mscTdmaCsCsIndex }
::= { mscTdmaCsMiscProvTable 1 }

MscTdmaCsMiscProvEntry ::= SEQUENCE {
   mscTdmaCsCommentText
      AsciiString,
   mscTdmaCsMscIpAddress
      IpAddress,
   mscTdmaCsVirtualRouterName
      RowPointer,
   mscTdmaCsVoiceLaw
      INTEGER }

mscTdmaCsCommentText OBJECT-TYPE
   SYNTAX     AsciiString (SIZE (0..40))
   ACCESS     read-write
   STATUS     mandatory
   DESCRIPTION
     "Use of this attribute is at the discretion of the system administrator. 
      Typically, this attribute is used to specify the name of the DMS-
      MTX configured for this TdmaIwfCallServer plus any other 
      commentary information."
   DEFVAL     { ''H }  -- ""
::= { mscTdmaCsMiscProvEntry 1 }

mscTdmaCsMscIpAddress OBJECT-TYPE
   SYNTAX     IpAddress 
   ACCESS     read-write
   STATUS     mandatory
   DESCRIPTION
     "This attribute specifies the Internet Protocol (IP) Address of the 
      Mobile Telephone Exchange (MTX) that is permitted to set up 
      MTX InterWorking Function (IWF) data calls using this 
      TdmaIwfCallServer. This address must be specified in order for this 
      TdmaIwfCallServer to provide service.
      If call setups are attempted from an MSC which does not have this 
      address, those calls are rejected. The callsRequested statistic of this 
      TdmaIwfCallServer is incremented and appropriate call failure logs 
      are generated at the MSC."
   DEFVAL     { '00000000'H }  -- "0.0.0.0"
::= { mscTdmaCsMiscProvEntry 2 }

mscTdmaCsVirtualRouterName OBJECT-TYPE
   SYNTAX     RowPointer 
   ACCESS     read-write
   STATUS     mandatory
   DESCRIPTION
     "This attribute specifies the virtual router that this 
      TdmaIwfCallServer uses for transmitting and receiving signaling 
      messages to and from the DMS-MTX."
::= { mscTdmaCsMiscProvEntry 3 }

mscTdmaCsVoiceLaw OBJECT-TYPE
   SYNTAX     INTEGER  {
                 aLaw(0),
                 muLaw(1) }
   ACCESS     read-write
   STATUS     mandatory
   DESCRIPTION
     "This attribute specifies the voice law to be established for the IWF 
      to PSTN modem link for calls established by this 
      TdmaIwfCallServer. This attribute has one of the following values:
      aLaw: A protocol for encoding voice-band audio, Pulse Code 
      Modulation (PCM).
      muLaw: A protocol for encoding voice-band audio, PCM. 
      Note that this value must match the voice law used at the DMS-
      MTX connected to this TdmaIwfCallServer."
::= { mscTdmaCsMiscProvEntry 4 }

mscTdmaCsCidDataTable OBJECT-TYPE
   SYNTAX     SEQUENCE OF MscTdmaCsCidDataEntry
   ACCESS     not-accessible
   STATUS     mandatory
   DESCRIPTION
     "This group contains the attribute for a component's Customer 
      Identifier (CID). Refer to the attribute description for a detailed 
      explanation of CIDs."
::= { mscTdmaCs 103 }

mscTdmaCsCidDataEntry OBJECT-TYPE
   SYNTAX     MscTdmaCsCidDataEntry
   ACCESS     not-accessible
   STATUS     mandatory
   DESCRIPTION
     "An entry in the mscTdmaCsCidDataTable."
   INDEX {
      mscTdmaCsCsIndex }
::= { mscTdmaCsCidDataTable 1 }

MscTdmaCsCidDataEntry ::= SEQUENCE {
   mscTdmaCsCustomerIdentifier
      Unsigned32 }

mscTdmaCsCustomerIdentifier OBJECT-TYPE
   SYNTAX     Unsigned32 (0 | 1..8191)
   ACCESS     read-write
   STATUS     mandatory
   DESCRIPTION
     "This attribute holds the Customer Identifier (CID).
      
      Every component has a CID. If a component has a cid attribute, the 
      component's CID is the provisioned value of that attribute; 
      otherwise the component inherits the CID of its parent. The top-
      level component has a CID of 0.
      
      Every operator session also has a CID, which is the CID 
      provisioned for the operator's user ID. An operator will see only the 
      stream data for components having a matching CID. Also, the 
      operator will be allowed to issue commands for only those 
      components which have a matching CID.
      
      An operator CID of 0 is used to identify the Network Manager 
      (referred to as 'NetMan' in DPN). This CID matches the CID of 
      any component. Values 1 to 8191 inclusive (equivalent to 'basic 
      CIDs' in DPN) may be assigned to specific customers."
   DEFVAL     { 0 }
::= { mscTdmaCsCidDataEntry 1 }

mscTdmaCsStateTable OBJECT-TYPE
   SYNTAX     SEQUENCE OF MscTdmaCsStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { mscTdmaCs 104 }

mscTdmaCsStateEntry OBJECT-TYPE
   SYNTAX     MscTdmaCsStateEntry
   ACCESS     not-accessible
   STATUS     mandatory
   DESCRIPTION
     "An entry in the mscTdmaCsStateTable."
   INDEX {
      mscTdmaCsCsIndex }
::= { mscTdmaCsStateTable 1 }

MscTdmaCsStateEntry ::= SEQUENCE {
   mscTdmaCsAdminState
      INTEGER,
   mscTdmaCsOperationalState
      INTEGER,
   mscTdmaCsUsageState
      INTEGER }

mscTdmaCsAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { mscTdmaCsStateEntry 1 }

mscTdmaCsOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { mscTdmaCsStateEntry 2 }

mscTdmaCsUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { mscTdmaCsStateEntry 3 }

mscTdmaCsStatsTable OBJECT-TYPE
   SYNTAX     SEQUENCE OF MscTdmaCsStatsEntry
   ACCESS     not-accessible
   STATUS     mandatory
   DESCRIPTION
     "This group contains operational attributes that measure the 
      performance used for the calls set up by this particular 
      TdmaIwfCallServer."
::= { mscTdmaCs 121 }

mscTdmaCsStatsEntry OBJECT-TYPE
   SYNTAX     MscTdmaCsStatsEntry
   ACCESS     not-accessible
   STATUS     mandatory
   DESCRIPTION
     "An entry in the mscTdmaCsStatsTable."
   INDEX {
      mscTdmaCsCsIndex }
::= { mscTdmaCsStatsTable 1 }

MscTdmaCsStatsEntry ::= SEQUENCE {
   mscTdmaCsCurrentCalls
      Gauge32,
   mscTdmaCsCallsRequested
      Counter32,
   mscTdmaCsCallsSetUp
      Counter32,
   mscTdmaCsCallsReleasedNormal
      Counter32,
   mscTdmaCsCallsReleasedAbnormal
      Counter32,
   mscTdmaCsErroredLFrames
      Counter32 }

mscTdmaCsCurrentCalls OBJECT-TYPE
   SYNTAX     Gauge32 (0..2047)
   ACCESS     read-only
   STATUS     mandatory
   DESCRIPTION
     "This attribute indicates the number of active calls currently serviced 
      by this particular TdmaIwfCallServer."
   DEFVAL     { 0 }
::= { mscTdmaCsStatsEntry 1 }

mscTdmaCsCallsRequested OBJECT-TYPE
   SYNTAX     Counter32 
   ACCESS     read-only
   STATUS     mandatory
   DESCRIPTION
     "This attribute counts the number of IWF call setup requests received 
      at this particular TdmaIwfCallServer from the DMS-MTX. The 
      counter wraps when it exceeds the maximum value."
::= { mscTdmaCsStatsEntry 2 }

mscTdmaCsCallsSetUp OBJECT-TYPE
   SYNTAX     Counter32 
   ACCESS     read-only
   STATUS     mandatory
   DESCRIPTION
     "This attribute counts the number of IWF calls successfully setup by 
      this particular TdmaIwfCallServer. A call is considered setup when 
      the IWF-Setup-Request message is received, indicating a request 
      for a data communications service, and the IWF has successfully 
      allocated the necessary resources to fulfill the request. The counter 
      wraps when it exceeds the maximum value."
::= { mscTdmaCsStatsEntry 3 }

mscTdmaCsCallsReleasedNormal OBJECT-TYPE
   SYNTAX     Counter32 
   ACCESS     read-only
   STATUS     mandatory
   DESCRIPTION
     "This attribute counts the number of IWF calls that have completed 
      successfully on this particular TdmaIwfCallServer. The counter 
      wraps when it exceeds the maximum value."
::= { mscTdmaCsStatsEntry 4 }

mscTdmaCsCallsReleasedAbnormal OBJECT-TYPE
   SYNTAX     Counter32 
   ACCESS     read-only
   STATUS     mandatory
   DESCRIPTION
     "This attribute counts the number of IWF calls that have been 
      released due to error conditions at this particular 
      TdmaIwfCallServer or one if its TdmaIwfBearerChannel(s). The 
      counter wraps when it exceeds the maximum value."
::= { mscTdmaCsStatsEntry 5 }

mscTdmaCsErroredLFrames OBJECT-TYPE
   SYNTAX     Counter32 
   ACCESS     read-only
   STATUS     mandatory
   DESCRIPTION
     "This attribute counts the number of CM/IWF Control Interface 
      (CCI) messages received from the DMS-MTX that have an 
      incorrect format. The counter wraps when it exceeds the maximum 
      value."
::= { mscTdmaCsStatsEntry 6 }


-- TdmaCs/<csIndex> Modem/<modem-type> 
-- This component represents an instance of a particular modem type 
-- that enables support of the various modem protocols on the DMS-
-- MTX IWF.

mscTdmaCsModem OBJECT IDENTIFIER ::= { mscTdmaCs 2 }



mscTdmaCsModemRowStatusTable OBJECT-TYPE
   SYNTAX     SEQUENCE OF MscTdmaCsModemRowStatusEntry
   ACCESS     not-accessible
   STATUS     mandatory
   DESCRIPTION
     "This entry controls the addition and deletion of 
      mscTdmaCsModem components."
::= { mscTdmaCsModem 1 }

mscTdmaCsModemRowStatusEntry OBJECT-TYPE
   SYNTAX     MscTdmaCsModemRowStatusEntry
   ACCESS     not-accessible
   STATUS     mandatory
   DESCRIPTION
     "A single entry in the table represents a single 
      mscTdmaCsModem component."
   INDEX {
      mscTdmaCsCsIndex,
      mscTdmaCsModemIndex }
::= { mscTdmaCsModemRowStatusTable 1 }

MscTdmaCsModemRowStatusEntry ::= SEQUENCE {
   mscTdmaCsModemRowStatus
      RowStatus,
   mscTdmaCsModemComponentName
      DisplayString,
   mscTdmaCsModemStorageType
      StorageType,
   mscTdmaCsModemIndex
      NonReplicated }

mscTdmaCsModemRowStatus OBJECT-TYPE
   SYNTAX     RowStatus 
   ACCESS     read-only
   STATUS     mandatory
   DESCRIPTION
     "This variable is used as the basis for SNMP naming of
      mscTdmaCsModem components.
      These components cannot be added nor deleted."
::= { mscTdmaCsModemRowStatusEntry 1 }

mscTdmaCsModemComponentName OBJECT-TYPE
   SYNTAX     DisplayString 
   ACCESS     read-only
   STATUS     mandatory
   DESCRIPTION
     "This variable provides the component's string name for
      use with the ASCII Console Interface"
::= { mscTdmaCsModemRowStatusEntry 2 }

mscTdmaCsModemStorageType OBJECT-TYPE
   SYNTAX     StorageType 
   ACCESS     read-only
   STATUS     mandatory
   DESCRIPTION
     "This variable represents the storage type value for the
      mscTdmaCsModem tables."
::= { mscTdmaCsModemRowStatusEntry 4 }

mscTdmaCsModemIndex OBJECT-TYPE
   SYNTAX     NonReplicated 
   ACCESS     not-accessible
   STATUS     mandatory
   DESCRIPTION
     "This variable represents the index for the mscTdmaCsModem tables."
::= { mscTdmaCsModemRowStatusEntry 10 }


-- TdmaCs/<csIndex> Fax
-- This component represents an instance of fax attributes. These 
-- specify various default settings for aspects of the fax protocol, 
-- which may be used for a DMS-MTX IWF call.

mscTdmaCsFax OBJECT IDENTIFIER ::= { mscTdmaCs 3 }



mscTdmaCsFaxRowStatusTable OBJECT-TYPE
   SYNTAX     SEQUENCE OF MscTdmaCsFaxRowStatusEntry
   ACCESS     not-accessible
   STATUS     mandatory
   DESCRIPTION
     "This entry controls the addition and deletion of 
      mscTdmaCsFax components."
::= { mscTdmaCsFax 1 }

mscTdmaCsFaxRowStatusEntry OBJECT-TYPE
   SYNTAX     MscTdmaCsFaxRowStatusEntry
   ACCESS     not-accessible
   STATUS     mandatory
   DESCRIPTION
     "A single entry in the table represents a single 
      mscTdmaCsFax component."
   INDEX {
      mscTdmaCsCsIndex,
      mscTdmaCsFaxIndex }
::= { mscTdmaCsFaxRowStatusTable 1 }

MscTdmaCsFaxRowStatusEntry ::= SEQUENCE {
   mscTdmaCsFaxRowStatus
      RowStatus,
   mscTdmaCsFaxComponentName
      DisplayString,
   mscTdmaCsFaxStorageType
      StorageType,
   mscTdmaCsFaxIndex
      NonReplicated }

mscTdmaCsFaxRowStatus OBJECT-TYPE
   SYNTAX     RowStatus 
   ACCESS     read-only
   STATUS     mandatory
   DESCRIPTION
     "This variable is used as the basis for SNMP naming of
      mscTdmaCsFax components.
      These components cannot be added nor deleted."
::= { mscTdmaCsFaxRowStatusEntry 1 }

mscTdmaCsFaxComponentName OBJECT-TYPE
   SYNTAX     DisplayString 
   ACCESS     read-only
   STATUS     mandatory
   DESCRIPTION
     "This variable provides the component's string name for
      use with the ASCII Console Interface"
::= { mscTdmaCsFaxRowStatusEntry 2 }

mscTdmaCsFaxStorageType OBJECT-TYPE
   SYNTAX     StorageType 
   ACCESS     read-only
   STATUS     mandatory
   DESCRIPTION
     "This variable represents the storage type value for the
      mscTdmaCsFax tables."
::= { mscTdmaCsFaxRowStatusEntry 4 }

mscTdmaCsFaxIndex OBJECT-TYPE
   SYNTAX     NonReplicated 
   ACCESS     not-accessible
   STATUS     mandatory
   DESCRIPTION
     "This variable represents the index for the mscTdmaCsFax tables."
::= { mscTdmaCsFaxRowStatusEntry 10 }


-- TdmaCs/<csIndex> Dce
-- This component represents an instance of the Data Circuit-
-- Terminating Equipment (DCE). The DCE represents a layer of the 
-- protocol stack for the network-side connection to the Public 
-- Switched Telephone Network. It is responsible for call control, AT-
-- command handling, user-data transport, online-command signaling, 
-- break signaling, circuit/signal lead transport, and compression 
-- negotiation. The DCE is based on the BMI (BSC, MSC, IWF) 
-- portion of the IS-135 standard.

mscTdmaCsDce OBJECT IDENTIFIER ::= { mscTdmaCs 4 }



mscTdmaCsDceRowStatusTable OBJECT-TYPE
   SYNTAX     SEQUENCE OF MscTdmaCsDceRowStatusEntry
   ACCESS     not-accessible
   STATUS     mandatory
   DESCRIPTION
     "This entry controls the addition and deletion of 
      mscTdmaCsDce components."
::= { mscTdmaCsDce 1 }

mscTdmaCsDceRowStatusEntry OBJECT-TYPE
   SYNTAX     MscTdmaCsDceRowStatusEntry
   ACCESS     not-accessible
   STATUS     mandatory
   DESCRIPTION
     "A single entry in the table represents a single 
      mscTdmaCsDce component."
   INDEX {
      mscTdmaCsCsIndex,
      mscTdmaCsDceIndex }
::= { mscTdmaCsDceRowStatusTable 1 }

MscTdmaCsDceRowStatusEntry ::= SEQUENCE {
   mscTdmaCsDceRowStatus
      RowStatus,
   mscTdmaCsDceComponentName
      DisplayString,
   mscTdmaCsDceStorageType
      StorageType,
   mscTdmaCsDceIndex
      NonReplicated }

mscTdmaCsDceRowStatus OBJECT-TYPE
   SYNTAX     RowStatus 
   ACCESS     read-only
   STATUS     mandatory
   DESCRIPTION
     "This variable is used as the basis for SNMP naming of
      mscTdmaCsDce components.
      These components cannot be added nor deleted."
::= { mscTdmaCsDceRowStatusEntry 1 }

mscTdmaCsDceComponentName OBJECT-TYPE
   SYNTAX     DisplayString 
   ACCESS     read-only
   STATUS     mandatory
   DESCRIPTION
     "This variable provides the component's string name for
      use with the ASCII Console Interface"
::= { mscTdmaCsDceRowStatusEntry 2 }

mscTdmaCsDceStorageType OBJECT-TYPE
   SYNTAX     StorageType 
   ACCESS     read-only
   STATUS     mandatory
   DESCRIPTION
     "This variable represents the storage type value for the
      mscTdmaCsDce tables."
::= { mscTdmaCsDceRowStatusEntry 4 }

mscTdmaCsDceIndex OBJECT-TYPE
   SYNTAX     NonReplicated 
   ACCESS     not-accessible
   STATUS     mandatory
   DESCRIPTION
     "This variable represents the index for the mscTdmaCsDce tables."
::= { mscTdmaCsDceRowStatusEntry 10 }


-- TdmaCs/<csIndex> Dsc
-- This component represents an instance of the Data Service Control 
-- (DSC). The DSC represents a layer of the protocol stack for the 
-- mobile-side connection to the IWF. It is responsible for call control, 
-- AT-command handling, user-data transport, online-command 
-- signaling, break signaling, circuit/signal lead transport, and 
-- compression negotiation. The DSC is based on the BMI (BSC, 
-- MSC, IWF) portion of the IS-135 standard.

mscTdmaCsDsc OBJECT IDENTIFIER ::= { mscTdmaCs 5 }



mscTdmaCsDscRowStatusTable OBJECT-TYPE
   SYNTAX     SEQUENCE OF MscTdmaCsDscRowStatusEntry
   ACCESS     not-accessible
   STATUS     mandatory
   DESCRIPTION
     "This entry controls the addition and deletion of 
      mscTdmaCsDsc components."
::= { mscTdmaCsDsc 1 }

mscTdmaCsDscRowStatusEntry OBJECT-TYPE
   SYNTAX     MscTdmaCsDscRowStatusEntry
   ACCESS     not-accessible
   STATUS     mandatory
   DESCRIPTION
     "A single entry in the table represents a single 
      mscTdmaCsDsc component."
   INDEX {
      mscTdmaCsCsIndex,
      mscTdmaCsDscIndex }
::= { mscTdmaCsDscRowStatusTable 1 }

MscTdmaCsDscRowStatusEntry ::= SEQUENCE {
   mscTdmaCsDscRowStatus
      RowStatus,
   mscTdmaCsDscComponentName
      DisplayString,
   mscTdmaCsDscStorageType
      StorageType,
   mscTdmaCsDscIndex
      NonReplicated }

mscTdmaCsDscRowStatus OBJECT-TYPE
   SYNTAX     RowStatus 
   ACCESS     read-only
   STATUS     mandatory
   DESCRIPTION
     "This variable is used as the basis for SNMP naming of
      mscTdmaCsDsc components.
      These components cannot be added nor deleted."
::= { mscTdmaCsDscRowStatusEntry 1 }

mscTdmaCsDscComponentName OBJECT-TYPE
   SYNTAX     DisplayString 
   ACCESS     read-only
   STATUS     mandatory
   DESCRIPTION
     "This variable provides the component's string name for
      use with the ASCII Console Interface"
::= { mscTdmaCsDscRowStatusEntry 2 }

mscTdmaCsDscStorageType OBJECT-TYPE
   SYNTAX     StorageType 
   ACCESS     read-only
   STATUS     mandatory
   DESCRIPTION
     "This variable represents the storage type value for the
      mscTdmaCsDsc tables."
::= { mscTdmaCsDscRowStatusEntry 4 }

mscTdmaCsDscIndex OBJECT-TYPE
   SYNTAX     NonReplicated 
   ACCESS     not-accessible
   STATUS     mandatory
   DESCRIPTION
     "This variable represents the index for the mscTdmaCsDsc tables."
::= { mscTdmaCsDscRowStatusEntry 10 }

mscTdmaCsDscProvTable OBJECT-TYPE
   SYNTAX     SEQUENCE OF MscTdmaCsDscProvEntry
   ACCESS     not-accessible
   STATUS     mandatory
   DESCRIPTION
     "This group contains the provisionable attributes for Data Service 
      Control Asynchronous Data Service portion of the wireless protocol 
      stack used for the calls set up by this particular TdmaIwfCallServer."
::= { mscTdmaCsDsc 10 }

mscTdmaCsDscProvEntry OBJECT-TYPE
   SYNTAX     MscTdmaCsDscProvEntry
   ACCESS     not-accessible
   STATUS     mandatory
   DESCRIPTION
     "An entry in the mscTdmaCsDscProvTable."
   INDEX {
      mscTdmaCsCsIndex,
      mscTdmaCsDscIndex }
::= { mscTdmaCsDscProvTable 1 }

MscTdmaCsDscProvEntry ::= SEQUENCE {
   mscTdmaCsDscLl0BufferSize
      Unsigned32,
   mscTdmaCsDscLl1BufferSize
      Unsigned32,
   mscTdmaCsDscK0Ll0WindowSize
      Unsigned32,
   mscTdmaCsDscK1Ll1WindowSize
      Unsigned32,
   mscTdmaCsDscP0CompressionDirection
      INTEGER,
   mscTdmaCsDscP1CompressionMaximumCodewords
      Unsigned32,
   mscTdmaCsDscP2CompressionMaximumCharacters
      Unsigned32 }

mscTdmaCsDscLl0BufferSize OBJECT-TYPE
   SYNTAX     Unsigned32 (80..65535)
   ACCESS     read-write
   STATUS     obsolete
   DESCRIPTION
     "This attribute specifies the maximum size of the DSC logical link 0 
      control buffer. Changes impact the amount of memory used (more 
      memory is used when increasing the attribute). The gain in 
      performance obtained from the selection of a larger buffer size may 
      be offset by less memory being available. The customer might wish 
      to increase the buffer size when a degradation in throughput of the 
      system is seen."
   DEFVAL     { 80 }
::= { mscTdmaCsDscProvEntry 1 }

mscTdmaCsDscLl1BufferSize OBJECT-TYPE
   SYNTAX     Unsigned32 (160..65535)
   ACCESS     read-write
   STATUS     obsolete
   DESCRIPTION
     "This attribute specifies the maximum size of the DSC logical link 1 
      data buffer. Changes impact the amount of memory used (more 
      memory is used when increasing the attribute). The gain in 
      performance obtained from the selection of a larger buffer size may 
      be offset by less memory being available. The customer might wish 
      to increase the buffer size when a degradation in throughput of the 
      system is seen."
   DEFVAL     { 160 }
::= { mscTdmaCsDscProvEntry 2 }

mscTdmaCsDscK0Ll0WindowSize OBJECT-TYPE
   SYNTAX     Unsigned32 (1..64)
   ACCESS     read-write
   STATUS     mandatory
   DESCRIPTION
     "This attribute specifies the maximum size of the DSC logical link 0 
      window."
   DEFVAL     { 64 }
::= { mscTdmaCsDscProvEntry 3 }

mscTdmaCsDscK1Ll1WindowSize OBJECT-TYPE
   SYNTAX     Unsigned32 (1..64)
   ACCESS     read-write
   STATUS     mandatory
   DESCRIPTION
     "This attribute specifies the maximum size of the DSC logical link 1 
      window."
   DEFVAL     { 64 }
::= { mscTdmaCsDscProvEntry 4 }

mscTdmaCsDscP0CompressionDirection OBJECT-TYPE
   SYNTAX     INTEGER  {
                 noCompression(0),
                 compInitrResp(1),
                 compRespInitr(2),
                 compBoth(3) }
   ACCESS     read-write
   STATUS     obsolete
   DESCRIPTION
     "This attribute specifies the compression configuration for DSC. This 
      attribute has one of the following values:
      noCompression: No compression.
      compInitrResp: Compression initiator to responder.
      compRespInitr: Compression responder to initiator.
      compBoth: Compression both directions."
   DEFVAL     { noCompression }
::= { mscTdmaCsDscProvEntry 5 }

mscTdmaCsDscP1CompressionMaximumCodewords OBJECT-TYPE
   SYNTAX     Unsigned32 (512..4096)
   ACCESS     read-write
   STATUS     obsolete
   DESCRIPTION
     "This attribute specifies the maximum number of codewords to be 
      used for compression. A codeword is a binary number that 
      represents a string of characters. Changes to this attribute impact the 
      amount of memory used (more memory is used when increasing the 
      attribute). The gain in performance obtained from the selection of a 
      larger dictionary may be offset by the larger codeword size needed, 
      and for certain types of data, better performance may be obtained 
      by using a smaller dictionary.
      Changes to this attribute do not affect existing calls."
   DEFVAL     { 512 }
::= { mscTdmaCsDscProvEntry 6 }

mscTdmaCsDscP2CompressionMaximumCharacters OBJECT-TYPE
   SYNTAX     Unsigned32 (6..150)
   ACCESS     read-write
   STATUS     obsolete
   DESCRIPTION
     "This attribute specifies the maximum number of characters that can 
      be represented by a single codeword to be used for compression 
      from logical link 0."
   DEFVAL     { 6 }
::= { mscTdmaCsDscProvEntry 7 }


-- TdmaCs/<csIndex> Rlp1/<radio-channel-type>
-- This component represents an instance of Radio Link Protocol 1 
-- (RLP1), indexed by radio channel type. Valid radio channel types 
-- are:
-- 
-- halfRate, Half rate channel. 
-- fullRate, Full rate channel.
-- doubleRate, Double rate channel.
-- tripleRate, Triple rate channel.
-- 
-- Many RLP1 attributes are dependent on the frame rate and frame 
-- size, that is dictated by the radio channel type. When a 
-- TdmaIwfCallServer is added, a RadioLinkProtocol1 instance is 
-- added automatically for each possible instance value. The attributes 
-- are set to default values, dependent on the radio channel type of the 
-- component instance.

mscTdmaCsRlp1 OBJECT IDENTIFIER ::= { mscTdmaCs 6 }



mscTdmaCsRlp1RowStatusTable OBJECT-TYPE
   SYNTAX     SEQUENCE OF MscTdmaCsRlp1RowStatusEntry
   ACCESS     not-accessible
   STATUS     mandatory
   DESCRIPTION
     "This entry controls the addition and deletion of 
      mscTdmaCsRlp1 components."
::= { mscTdmaCsRlp1 1 }

mscTdmaCsRlp1RowStatusEntry OBJECT-TYPE
   SYNTAX     MscTdmaCsRlp1RowStatusEntry
   ACCESS     not-accessible
   STATUS     mandatory
   DESCRIPTION
     "A single entry in the table represents a single 
      mscTdmaCsRlp1 component."
   INDEX {
      mscTdmaCsCsIndex,
      mscTdmaCsRlp1Index }
::= { mscTdmaCsRlp1RowStatusTable 1 }

MscTdmaCsRlp1RowStatusEntry ::= SEQUENCE {
   mscTdmaCsRlp1RowStatus
      RowStatus,
   mscTdmaCsRlp1ComponentName
      DisplayString,
   mscTdmaCsRlp1StorageType
      StorageType,
   mscTdmaCsRlp1Index
      INTEGER }

mscTdmaCsRlp1RowStatus OBJECT-TYPE
   SYNTAX     RowStatus 
   ACCESS     read-write
   STATUS     mandatory
   DESCRIPTION
     "This variable is used as the basis for SNMP naming of
      mscTdmaCsRlp1 components.
      These components can be added."
::= { mscTdmaCsRlp1RowStatusEntry 1 }

mscTdmaCsRlp1ComponentName OBJECT-TYPE
   SYNTAX     DisplayString 
   ACCESS     read-only
   STATUS     mandatory
   DESCRIPTION
     "This variable provides the component's string name for
      use with the ASCII Console Interface"
::= { mscTdmaCsRlp1RowStatusEntry 2 }

mscTdmaCsRlp1StorageType OBJECT-TYPE
   SYNTAX     StorageType 
   ACCESS     read-only
   STATUS     mandatory
   DESCRIPTION
     "This variable represents the storage type value for the
      mscTdmaCsRlp1 tables."
::= { mscTdmaCsRlp1RowStatusEntry 4 }

mscTdmaCsRlp1Index OBJECT-TYPE
   SYNTAX     INTEGER  {
                 halfRate(0),
                 fullRate(1),
                 doubleRate(2),
                 tripleRate(3) }
   ACCESS     not-accessible
   STATUS     mandatory
   DESCRIPTION
     "This variable represents the index for the mscTdmaCsRlp1 tables."
::= { mscTdmaCsRlp1RowStatusEntry 10 }

mscTdmaCsRlp1ProvTable OBJECT-TYPE
   SYNTAX     SEQUENCE OF MscTdmaCsRlp1ProvEntry
   ACCESS     not-accessible
   STATUS     mandatory
   DESCRIPTION
     "This group contains provisionable attributes for the Radio Link 
      Protocol 1 (RLP1) parameters used for the calls set up by this 
      particular TdmaIwfCallServer. Changes to these attributes do not 
      affect existing calls."
::= { mscTdmaCsRlp1 10 }

mscTdmaCsRlp1ProvEntry OBJECT-TYPE
   SYNTAX     MscTdmaCsRlp1ProvEntry
   ACCESS     not-accessible
   STATUS     mandatory
   DESCRIPTION
     "An entry in the mscTdmaCsRlp1ProvTable."
   INDEX {
      mscTdmaCsCsIndex,
      mscTdmaCsRlp1Index }
::= { mscTdmaCsRlp1ProvTable 1 }

MscTdmaCsRlp1ProvEntry ::= SEQUENCE {
   mscTdmaCsRlp1T1ResponseTimer
      Unsigned32,
   mscTdmaCsRlp1T2LinkActivityTimer
      Unsigned32,
   mscTdmaCsRlp1T3PeerAckTimer
      Unsigned32 }

mscTdmaCsRlp1T1ResponseTimer OBJECT-TYPE
   SYNTAX     Unsigned32 (5..20)
   ACCESS     read-write
   STATUS     mandatory
   DESCRIPTION
     "This attribute specifies the time the receiving Radio Link Protocol 
      (RLP1) entity shall wait for a response from the peer TIA-136-310 
      (formerly IS-130) application.
      During the Exchange Information (XID) negotiation, both RLP1 
      entities (mobile station and IWF) can agree to use a specific value 
      for this timer (T1). The IWF attempts to negotiate to the value 
      specified by this attribute.
      Changes to this attribute do not affect existing calls."
   DEFVAL     { 5 }
::= { mscTdmaCsRlp1ProvEntry 1 }

mscTdmaCsRlp1T2LinkActivityTimer OBJECT-TYPE
   SYNTAX     Unsigned32 (10..120)
   ACCESS     read-write
   STATUS     mandatory
   DESCRIPTION
     "This attribute specifies the maximum time the receiving Radio Link 
      Protocol (RLP1) entity shall wait for link activity.
      During the Exchange Information (XID) negotiation, both RLP1 
      entities (mobile station and IWF) can agree to use a specific value 
      for this timer (T2). The IWF attempts to negotiate to the value 
      specified by this attribute.
      Changes to this attribute do not affect existing calls."
   DEFVAL     { 10 }
::= { mscTdmaCsRlp1ProvEntry 2 }

mscTdmaCsRlp1T3PeerAckTimer OBJECT-TYPE
   SYNTAX     Unsigned32 (5..20)
   ACCESS     read-write
   STATUS     mandatory
   DESCRIPTION
     "This attribute specifies the maximum time the receiving Radio Link 
      Protocol (RLP1) entity shall wait for the peer to ACK or NAK data.
      During the Exchange Information (XID) negotiation, both RLP1 
      entities (mobile station and IWF) can agree to use a specific value 
      for this timer (T3). The IWF attempts to negotiate to the value 
      specified by this attribute.
      Changes to this attribute do not affect existing calls."
   DEFVAL     { 5 }
::= { mscTdmaCsRlp1ProvEntry 3 }


-- TdmaCs/<csIndex> V42
-- This component represents an instance of ITU-T V.42 error 
-- correcting data link protocol. Its attributes specify various default 
-- settings for aspects of the V.42 protocol, that may be used for an 
-- IWF call for the IWF to PSTN modem link.

mscTdmaCsV42 OBJECT IDENTIFIER ::= { mscTdmaCs 7 }



mscTdmaCsV42RowStatusTable OBJECT-TYPE
   SYNTAX     SEQUENCE OF MscTdmaCsV42RowStatusEntry
   ACCESS     not-accessible
   STATUS     mandatory
   DESCRIPTION
     "This entry controls the addition and deletion of 
      mscTdmaCsV42 components."
::= { mscTdmaCsV42 1 }

mscTdmaCsV42RowStatusEntry OBJECT-TYPE
   SYNTAX     MscTdmaCsV42RowStatusEntry
   ACCESS     not-accessible
   STATUS     mandatory
   DESCRIPTION
     "A single entry in the table represents a single 
      mscTdmaCsV42 component."
   INDEX {
      mscTdmaCsCsIndex,
      mscTdmaCsV42Index }
::= { mscTdmaCsV42RowStatusTable 1 }

MscTdmaCsV42RowStatusEntry ::= SEQUENCE {
   mscTdmaCsV42RowStatus
      RowStatus,
   mscTdmaCsV42ComponentName
      DisplayString,
   mscTdmaCsV42StorageType
      StorageType,
   mscTdmaCsV42Index
      NonReplicated }

mscTdmaCsV42RowStatus OBJECT-TYPE
   SYNTAX     RowStatus 
   ACCESS     read-only
   STATUS     mandatory
   DESCRIPTION
     "This variable is used as the basis for SNMP naming of
      mscTdmaCsV42 components.
      These components cannot be added nor deleted."
::= { mscTdmaCsV42RowStatusEntry 1 }

mscTdmaCsV42ComponentName OBJECT-TYPE
   SYNTAX     DisplayString 
   ACCESS     read-only
   STATUS     mandatory
   DESCRIPTION
     "This variable provides the component's string name for
      use with the ASCII Console Interface"
::= { mscTdmaCsV42RowStatusEntry 2 }

mscTdmaCsV42StorageType OBJECT-TYPE
   SYNTAX     StorageType 
   ACCESS     read-only
   STATUS     mandatory
   DESCRIPTION
     "This variable represents the storage type value for the
      mscTdmaCsV42 tables."
::= { mscTdmaCsV42RowStatusEntry 4 }

mscTdmaCsV42Index OBJECT-TYPE
   SYNTAX     NonReplicated 
   ACCESS     not-accessible
   STATUS     mandatory
   DESCRIPTION
     "This variable represents the index for the mscTdmaCsV42 tables."
::= { mscTdmaCsV42RowStatusEntry 10 }

mscTdmaCsV42ProvTable OBJECT-TYPE
   SYNTAX     SEQUENCE OF MscTdmaCsV42ProvEntry
   ACCESS     not-accessible
   STATUS     mandatory
   DESCRIPTION
     "This group contains the provisionable attributes for the V.42 
      protocol used for the calls set up by this particular IwfCallServer. 
      Changes to these attributes do not affect existing calls."
::= { mscTdmaCsV42 10 }

mscTdmaCsV42ProvEntry OBJECT-TYPE
   SYNTAX     MscTdmaCsV42ProvEntry
   ACCESS     not-accessible
   STATUS     mandatory
   DESCRIPTION
     "An entry in the mscTdmaCsV42ProvTable."
   INDEX {
      mscTdmaCsCsIndex,
      mscTdmaCsV42Index }
::= { mscTdmaCsV42ProvTable 1 }

MscTdmaCsV42ProvEntry ::= SEQUENCE {
   mscTdmaCsV42T400DetectTimer
      FixedPoint2,
   mscTdmaCsV42T401AckTimer
      FixedPoint2,
   mscTdmaCsV42T402AckDelayTimer
      FixedPoint2,
   mscTdmaCsV42T403IdleProbeTimer
      Unsigned32,
   mscTdmaCsV42TxN401FrameSize
      Unsigned32,
   mscTdmaCsV42RxN401FrameSize
      Unsigned32,
   mscTdmaCsV42TxKWindowSize
      Unsigned32,
   mscTdmaCsV42RxKWindowSize
      Unsigned32,
   mscTdmaCsV42N400RetransLimit
      Unsigned32,
   mscTdmaCsV42FcsLength
      INTEGER }

mscTdmaCsV42T400DetectTimer OBJECT-TYPE
   SYNTAX     FixedPoint2 (75..254)
   ACCESS     read-write
   STATUS     mandatory
   DESCRIPTION
     "This attribute specifies the maximum amount of time that the IWF 
      waits for an Originator Detection Pattern (ODP) or Answerer 
      Detection Pattern (ADP). ODP/ADP is a series of special bit 
      patterns used during the call setup procedures.
      If the IWF is the originator of the call, it starts sending ODP 
      patterns and waits for an ADP for the duration of T400 from the 
      answerer at call setup time.
      If the IWF is the answerer of the call, it waits for an ODP for T400 
      seconds from the originator and if it receives during that time it 
      sends an ADP pattern to the originator at the call setup time. Since 
      both sides operate with different values of T400 timer, a higher 
      value increases the chance of a successful call setup.
      Changes to this attribute do not affect existing calls."
   DEFVAL     { 75 }
::= { mscTdmaCsV42ProvEntry 1 }

mscTdmaCsV42T401AckTimer OBJECT-TYPE
   SYNTAX     FixedPoint2 (50..900)
   ACCESS     read-write
   STATUS     mandatory
   DESCRIPTION
     "This attribute specifies the maximum amount of time that the IWF 
      waits for an acknowledgment before retransmitting a frame. Since 
      information about the T401 timer is not carried in the Exchange 
      Identification (XID) negotiations at call setup time, both sides 
      operate with different timer values. The value for T401 depends on 
      many factors, such as propagation delay or frame processing time. 
      A frame is retransmitted up to N400 times if the timer T401 expires 
      before an acknowledgment for a frame is actually received. The 
      performance of the data link layer can be impacted by the value of 
      this timer as retransmissions of frames occur on expiry of timer 
      T401. 
      Changes to this attribute do not affect existing calls."
   DEFVAL     { 400 }
::= { mscTdmaCsV42ProvEntry 2 }

mscTdmaCsV42T402AckDelayTimer OBJECT-TYPE
   SYNTAX     FixedPoint2 (25..450)
   ACCESS     read-write
   STATUS     mandatory
   DESCRIPTION
     "This attribute specifies the maximum amount of time that the IWF 
      may wait following the receipt of any frame requiring a reply before 
      it initiates transmission of an appropriate reply in order to ensure 
      that the reply frame is received by the remote error-correcting entity 
      prior to expiration of the T401 timer of the remote error-correcting 
      entity. Since information about the T402 timer is not carried in the 
      Exchange Identification (XID) negotiations at call setup, both sides 
      operate with different timer values. If this timer expires, then the 
      reply that would have been returned prior to its expiration is not 
      sent. The performance of the data link layer can be impacted by the 
      value of this timer as retransmissions of frames occur on expiry of 
      timer T401. For better performance, a value of t402AckDelayTimer 
      (T402) equal to half the value of t401AckTimer (T401) is 
      recommended.
      Changes to this attribute do not affect existing calls."
   DEFVAL     { 200 }
::= { mscTdmaCsV42ProvEntry 3 }

mscTdmaCsV42T403IdleProbeTimer OBJECT-TYPE
   SYNTAX     Unsigned32 (30..90)
   ACCESS     read-write
   STATUS     mandatory
   DESCRIPTION
     "This attribute specifies the maximum amount of time that the IWF 
      allows to elapse without frames being exchanged. The link is 
      permitted to remain idle with no frames being exchanged on the 
      data link. Upon expiry of this timer, the IWF polls its peer for 
      status. Since information about the T403 timer is not carried in the 
      Exchange Identification (XID) negotiations at call setup time, both 
      sides operate with different timer values. 
      Changes to this attribute do not affect existing calls."
   DEFVAL     { 60 }
::= { mscTdmaCsV42ProvEntry 4 }

mscTdmaCsV42TxN401FrameSize OBJECT-TYPE
   SYNTAX     Unsigned32 (1..255)
   ACCESS     read-write
   STATUS     mandatory
   DESCRIPTION
     "This attribute specifies the maximum number of octets that can be 
      carried in the information field of an Information (I) frame, 
      Exchange Identification (XID) frame, and a Unnumbered 
      Information (UI) frame from the IWF to the remote entity. The 
      default value is 128 octets, and no XID negotiations required for 
      txN401FrameSize. If the value for txN401FrameSize value is set to 
      other than 128 octets, then XID frames are exchanged to negotiate a 
      value. The value provided for txN401FrameSize sets up the bounds 
      during XID negotiations. The IWF performs XID negotiations with 
      this value as a minimum or maximum value. If a value greater than 
      128 is specified, then the IWF negotiates or attempts to negotiate a 
      value between the 128 (as a minimum) and the given value (as a 
      maximum). If a value less than 128 is specified, then the IWF 
      attempts to negotiate a value between the given value (as a 
      minimum) and 128 (as a maximum). Any value can be specified as 
      long as it is within the provisionable limits. However, a value equal 
      to or close to 128 is recommended.
      Changes to this attribute do not affect existing calls."
   DEFVAL     { 128 }
::= { mscTdmaCsV42ProvEntry 5 }

mscTdmaCsV42RxN401FrameSize OBJECT-TYPE
   SYNTAX     Unsigned32 (1..255)
   ACCESS     read-write
   STATUS     mandatory
   DESCRIPTION
     "This attribute specifies the maximum number of octets that can be 
      carried in the information field of an Information (I) frame, 
      Exchange Identification (XID) frame, and a Unnumbered 
      Information (UI) frame from the remote entity to the IWF. The 
      default value is 128 octets, and no XID negotiations are required for 
      rxN401FrameSize. If the value set for rxN401FrameSize is other 
      than 128, XID frames are exchanged to negotiate a value. The value 
      provided for rxN401FrameSize sets up the bounds during XID 
      negotiations. The IWF performs XID negotiations with this value as 
      a minimum or maximum value. If a value greater than 128 is 
      specified, then the IWF attempts to negotiate for a value between 
      128 (as a minimum) and the given value (as a maximum). If a value 
      less than 128 value is specified, then the IWF attempts to negotiate 
      for a value between the given value (as a minimum) and 128 (as a 
      maximum). Any value can be specified as long as it is within the 
      provisionable limits. However, a value equal to or close to the 
      default is recommended.
      Changes to this attribute do not affect existing calls."
   DEFVAL     { 128 }
::= { mscTdmaCsV42ProvEntry 6 }

mscTdmaCsV42TxKWindowSize OBJECT-TYPE
   SYNTAX     Unsigned32 (1..255)
   ACCESS     read-write
   STATUS     mandatory
   DESCRIPTION
     "This attribute specifies the maximum number of outstanding 
      unacknowledged sequenced Information (I) frames from the IWF to 
      the remote entity. The default value is 15 frames, and if this value is 
      used then no Exchange Identification (XID) negotiations are 
      required for txKWindowSize. If the value set for txKWindowSize is 
      other than 15, then XID frames are exchanged to negotiate a value. 
      The value provided for txKWindowSize sets up the bounds during 
      XID negotiations. The IWF performs XID negotiations with this 
      value as a minimum or maximum value. If a value greater than 15 is 
      specified, then the IWF attempts to negotiate a value between 15 (as 
      a minimum) and the given value (as a maximum). If a value less 
      than 15 is specified, then the IWF attempts to negotiate for a value 
      between the given value (as a minimum) and 15 (as a maximum). 
      Any value can be specified as long at it is within the provisionable 
      limits. However, a value equal to or close to the default is 
      recommended.
      Changes to this attribute do not affect existing calls."
   DEFVAL     { 15 }
::= { mscTdmaCsV42ProvEntry 7 }

mscTdmaCsV42RxKWindowSize OBJECT-TYPE
   SYNTAX     Unsigned32 (1..255)
   ACCESS     read-write
   STATUS     mandatory
   DESCRIPTION
     "This attribute specifies the maximum number of outstanding 
      unacknowledged sequenced Information (I) frames from the remote 
      entity to the IWF. The default value is 15 frames, and if this value is 
      used then no Exchange Identification (XID) negotiations are 
      required for rxKWindowSize. If the value set for rxKWindowSize is 
      other than 15, then XID frames are exchanged to negotiate a value. 
      The value provided for rxKWindowSize sets up the bounds during 
      XID negotiations. The IWF performs XID negotiations with this 
      value as a minimum or maximum value. If a value greater than 15 is 
      specified, then the IWF attempts to negotiate a value between 15 (as 
      a minimum) and the given value (as a maximum). If a value less 
      than 15 is specified, then the IWF attempts to negotiate for a value 
      between the given value (as a minimum) and 15 (as a maximum). 
      Any value can be specified as long as it is within the provisionable 
      limits. However, a value equal to or close to the default is 
      recommended.
      Changes to this attribute do not affect existing calls."
   DEFVAL     { 15 }
::= { mscTdmaCsV42ProvEntry 8 }

mscTdmaCsV42N400RetransLimit OBJECT-TYPE
   SYNTAX     Unsigned32 (0..255)
   ACCESS     read-write
   STATUS     mandatory
   DESCRIPTION
     "This attribute specifies the maximum number of times the IWF 
      retransmits a frame upon expiry of t401AckTimer before 
      appropriate recovery action is taken. Information about N400 
      (Retransmission Limit) is not carried in the Exchange Identification 
      (XID) negotiation at call setup time so both sides operate with 
      different N400 values.
      Changes to this attribute do not affect existing calls."
   DEFVAL     { 1 }
::= { mscTdmaCsV42ProvEntry 9 }

mscTdmaCsV42FcsLength OBJECT-TYPE
   SYNTAX     INTEGER  {
                 fcs16(0),
                 fcs32Or16(1),
                 fcs32(2) }
   ACCESS     read-write
   STATUS     mandatory
   DESCRIPTION
     "This attribute specifies whether a 16 bit or a 32 bit Frame Check 
      Sequence (FCS) will be used for the link between the IWF and the 
      far end DCE. This attribute has one of the following values:
      fcs16: Use only a 16 bit FCS.
      fcs32Or16: 32 bit FCS is preferred; Use a 16 bit FCS if needed.
      fcs32Only: Use only a 32 it FCS; If unavailable, drop the 
      connection."
   DEFVAL     { fcs32Or16 }
::= { mscTdmaCsV42ProvEntry 10 }


-- TdmaCs/<csIndex> V42bis
-- This component represents an instance of ITU-T V.42bis data 
-- compression protocol. Its attributes specify various default settings 
-- for aspects of the V.42bis protocol, which may be used in an IWF 
-- call on the mobile station to IWF link or the IWF to PSTN modem 
-- link or both.

mscTdmaCsV42Bis OBJECT IDENTIFIER ::= { mscTdmaCs 8 }



mscTdmaCsV42BisRowStatusTable OBJECT-TYPE
   SYNTAX     SEQUENCE OF MscTdmaCsV42BisRowStatusEntry
   ACCESS     not-accessible
   STATUS     mandatory
   DESCRIPTION
     "This entry controls the addition and deletion of 
      mscTdmaCsV42Bis components."
::= { mscTdmaCsV42Bis 1 }

mscTdmaCsV42BisRowStatusEntry OBJECT-TYPE
   SYNTAX     MscTdmaCsV42BisRowStatusEntry
   ACCESS     not-accessible
   STATUS     mandatory
   DESCRIPTION
     "A single entry in the table represents a single 
      mscTdmaCsV42Bis component."
   INDEX {
      mscTdmaCsCsIndex,
      mscTdmaCsV42BisIndex }
::= { mscTdmaCsV42BisRowStatusTable 1 }

MscTdmaCsV42BisRowStatusEntry ::= SEQUENCE {
   mscTdmaCsV42BisRowStatus
      RowStatus,
   mscTdmaCsV42BisComponentName
      DisplayString,
   mscTdmaCsV42BisStorageType
      StorageType,
   mscTdmaCsV42BisIndex
      NonReplicated }

mscTdmaCsV42BisRowStatus OBJECT-TYPE
   SYNTAX     RowStatus 
   ACCESS     read-only
   STATUS     mandatory
   DESCRIPTION
     "This variable is used as the basis for SNMP naming of
      mscTdmaCsV42Bis components.
      These components cannot be added nor deleted."
::= { mscTdmaCsV42BisRowStatusEntry 1 }

mscTdmaCsV42BisComponentName OBJECT-TYPE
   SYNTAX     DisplayString 
   ACCESS     read-only
   STATUS     mandatory
   DESCRIPTION
     "This variable provides the component's string name for
      use with the ASCII Console Interface"
::= { mscTdmaCsV42BisRowStatusEntry 2 }

mscTdmaCsV42BisStorageType OBJECT-TYPE
   SYNTAX     StorageType 
   ACCESS     read-only
   STATUS     mandatory
   DESCRIPTION
     "This variable represents the storage type value for the
      mscTdmaCsV42Bis tables."
::= { mscTdmaCsV42BisRowStatusEntry 4 }

mscTdmaCsV42BisIndex OBJECT-TYPE
   SYNTAX     NonReplicated 
   ACCESS     not-accessible
   STATUS     mandatory
   DESCRIPTION
     "This variable represents the index for the mscTdmaCsV42Bis tables."
::= { mscTdmaCsV42BisRowStatusEntry 10 }

mscTdmaCsV42BisProvTable OBJECT-TYPE
   SYNTAX     SEQUENCE OF MscTdmaCsV42BisProvEntry
   ACCESS     not-accessible
   STATUS     mandatory
   DESCRIPTION
     "This group contains the provisionable attributes for the V.42bis data 
      compression protocol parameters used for the calls set up by this 
      particular CallServer. Changes to these attributes do not affect 
      existing calls."
::= { mscTdmaCsV42Bis 10 }

mscTdmaCsV42BisProvEntry OBJECT-TYPE
   SYNTAX     MscTdmaCsV42BisProvEntry
   ACCESS     not-accessible
   STATUS     mandatory
   DESCRIPTION
     "An entry in the mscTdmaCsV42BisProvTable."
   INDEX {
      mscTdmaCsCsIndex,
      mscTdmaCsV42BisIndex }
::= { mscTdmaCsV42BisProvTable 1 }

MscTdmaCsV42BisProvEntry ::= SEQUENCE {
   mscTdmaCsV42BisP0CompressionDirection
      INTEGER,
   mscTdmaCsV42BisP1MaximumCodewords
      Unsigned32,
   mscTdmaCsV42BisP2MaximumStringSize
      Unsigned32,
   mscTdmaCsV42BisActionOnError
      INTEGER }

mscTdmaCsV42BisP0CompressionDirection OBJECT-TYPE
   SYNTAX     INTEGER  {
                 noCompression(0),
                 compInitrResp(1),
                 compRespInitr(2),
                 compBoth(3) }
   ACCESS     read-write
   STATUS     mandatory
   DESCRIPTION
     "This attribute specifies the V.42bis data compression direction to be 
      supported. The value for compression direction is negotiated at link 
      setup by the data link protocol by way of the Exchange 
      Identification (XID) negotiation of parameter P0 (compression 
      direction).
      During XID negotiation of parameter P0, both sides (IWF and 
      mobile or IWF and PSTN) agree on the compression direction.
      This attribute has one of the following values:
      noCompression: No compression is present.
      compInitrResp: The data sent by the IWF to the other entity is 
      compressed.
      compRespInitr: The data received by the IWF from the other entity 
      is compressed.
      compBoth: The data sent and received by the IWF is compressed.
      Changes to this attribute do not affect existing calls."
   DEFVAL     { compBoth }
::= { mscTdmaCsV42BisProvEntry 1 }

mscTdmaCsV42BisP1MaximumCodewords OBJECT-TYPE
   SYNTAX     Unsigned32 (512..4096)
   ACCESS     read-write
   STATUS     mandatory
   DESCRIPTION
     "This attribute specifies the maximum number of V.42bis codewords 
      the IWF supports. A codeword is a binary number that represents a 
      string of characters in compressed form. V.42bis keeps a dictionary 
      of codewords for each compression direction. Changes to this 
      attribute impact the compression ratio for the encoder (component 
      TdmaBc V42Bis attribute compRatioEncoder). Changes also impact 
      the amount of memory used (more memory is used when increasing 
      the attribute). The gain in performance obtained from the selection 
      of a larger dictionary may be offset by the larger codeword size 
      needed, and for certain types of data, better performance may be 
      obtained by using a smaller dictionary. 
      Changes to this attribute do not affect existing calls."
   DEFVAL     { 512 }
::= { mscTdmaCsV42BisProvEntry 2 }

mscTdmaCsV42BisP2MaximumStringSize OBJECT-TYPE
   SYNTAX     Unsigned32 (6..250)
   ACCESS     read-write
   STATUS     mandatory
   DESCRIPTION
     "This attribute specifies the maximum number of characters allowed 
      in a string represented by a codeword that the IWF supports. Each 
      codeword in a V.42bis dictionary represents a string of characters. 
      Changes to this attribute impact the compression ratio for the 
      encoder.
      Changes to this attribute do not affect existing calls."
   DEFVAL     { 6 }
::= { mscTdmaCsV42BisProvEntry 3 }

mscTdmaCsV42BisActionOnError OBJECT-TYPE
   SYNTAX     INTEGER  {
                 resetLink(0),
                 takeDownCall(1) }
   ACCESS     read-write
   STATUS     mandatory
   DESCRIPTION
     "This attribute specifies whether or not V.42bis takes down the call 
      or resets the link when any of the following errors occur: 
      1.Receipt of STEPUP (step up codeword size) codeword when it 
      would cause C2 (current code word size) to exceed N1 (maximum 
      code word size).
      2. Receipt of a codeword, at any time, equal to C1 (next empty 
      dictionary entry).
      3. Receipt of a codeword representing an empty dictionary entry.
      4. Receipt of a reserved command code.
      5. Receipt of any other error.
      If the value is resetLink, the error corrected connection and V.42bis 
      dictionaries are reset. Some data is lost but the call continues. If the 
      value is takeDownCall, the call is taken down.
      Changes to this attribute do not affect existing calls."
   DEFVAL     { resetLink }
::= { mscTdmaCsV42BisProvEntry 4 }


-- TdmaCs/<csIndex> Lp/n
-- The TdmaIwfLogicalProcessor component represents an instance of 
-- a TdmaIwfLogicalProcessor that may be linked to this 
-- TdmaIwfCallServer. A TdmaIwfBearerChannel is indirectly linked 
-- to this TdmaIwfLogicalProcessor by way of the TdmaIwfFramer 
-- component. This component must be added to the 
-- TdmaIwfCallServer (and the change activated) prior to adding the 
-- TdmaIwfBearerChannel(s). This component can only be 
-- provisioned for one TdmaIwfCallServer.

mscTdmaCsLp OBJECT IDENTIFIER ::= { mscTdmaCs 9 }



mscTdmaCsLpRowStatusTable OBJECT-TYPE
   SYNTAX     SEQUENCE OF MscTdmaCsLpRowStatusEntry
   ACCESS     not-accessible
   STATUS     mandatory
   DESCRIPTION
     "This entry controls the addition and deletion of 
      mscTdmaCsLp components."
::= { mscTdmaCsLp 1 }

mscTdmaCsLpRowStatusEntry OBJECT-TYPE
   SYNTAX     MscTdmaCsLpRowStatusEntry
   ACCESS     not-accessible
   STATUS     mandatory
   DESCRIPTION
     "A single entry in the table represents a single 
      mscTdmaCsLp component."
   INDEX {
      mscTdmaCsCsIndex,
      mscTdmaCsLpIndex }
::= { mscTdmaCsLpRowStatusTable 1 }

MscTdmaCsLpRowStatusEntry ::= SEQUENCE {
   mscTdmaCsLpRowStatus
      RowStatus,
   mscTdmaCsLpComponentName
      DisplayString,
   mscTdmaCsLpStorageType
      StorageType,
   mscTdmaCsLpIndex
      Integer32 }

mscTdmaCsLpRowStatus OBJECT-TYPE
   SYNTAX     RowStatus 
   ACCESS     read-write
   STATUS     mandatory
   DESCRIPTION
     "This variable is used as the basis for SNMP naming of
      mscTdmaCsLp components.
      These components can be added and deleted."
::= { mscTdmaCsLpRowStatusEntry 1 }

mscTdmaCsLpComponentName OBJECT-TYPE
   SYNTAX     DisplayString 
   ACCESS     read-only
   STATUS     mandatory
   DESCRIPTION
     "This variable provides the component's string name for
      use with the ASCII Console Interface"
::= { mscTdmaCsLpRowStatusEntry 2 }

mscTdmaCsLpStorageType OBJECT-TYPE
   SYNTAX     StorageType 
   ACCESS     read-only
   STATUS     mandatory
   DESCRIPTION
     "This variable represents the storage type value for the
      mscTdmaCsLp tables."
::= { mscTdmaCsLpRowStatusEntry 4 }

mscTdmaCsLpIndex OBJECT-TYPE
   SYNTAX     Integer32 (0..15)
   ACCESS     not-accessible
   STATUS     mandatory
   DESCRIPTION
     "This variable represents the index for the mscTdmaCsLp tables."
::= { mscTdmaCsLpRowStatusEntry 10 }

mscTdmaCsLpOperTable OBJECT-TYPE
   SYNTAX     SEQUENCE OF MscTdmaCsLpOperEntry
   ACCESS     not-accessible
   STATUS     mandatory
   DESCRIPTION
     "This group contains operational attributes pertaining to information 
      about TdmaIwfBearerChannels and TdmaIwfLogicalProcessor 
      associated with a TdmaIwfCallServer from a high-level view."
::= { mscTdmaCsLp 10 }

mscTdmaCsLpOperEntry OBJECT-TYPE
   SYNTAX     MscTdmaCsLpOperEntry
   ACCESS     not-accessible
   STATUS     mandatory
   DESCRIPTION
     "An entry in the mscTdmaCsLpOperTable."
   INDEX {
      mscTdmaCsCsIndex,
      mscTdmaCsLpIndex }
::= { mscTdmaCsLpOperTable 1 }

MscTdmaCsLpOperEntry ::= SEQUENCE {
   mscTdmaCsLpConfiguredBearerChannels
      Unsigned32,
   mscTdmaCsLpActiveCalls
      Gauge32,
   mscTdmaCsLpModemsSupported
      INTEGER }

mscTdmaCsLpConfiguredBearerChannels OBJECT-TYPE
   SYNTAX     Unsigned32 (0..124)
   ACCESS     read-only
   STATUS     mandatory
   DESCRIPTION
     "This attribute indicates the number of TdmaIwfBearerChannel 
      components provisioned for the TdmaIwfLogicalProcessor 
      represented by this component."
::= { mscTdmaCsLpOperEntry 1 }

mscTdmaCsLpActiveCalls OBJECT-TYPE
   SYNTAX     Gauge32 (0..124)
   ACCESS     read-only
   STATUS     mandatory
   DESCRIPTION
     "This attribute indicates the number of calls currently active on this 
      LogicalProcessor."
::= { mscTdmaCsLpOperEntry 2 }

mscTdmaCsLpModemsSupported OBJECT-TYPE
   SYNTAX     INTEGER  {
                 yes(0),
                 no(1) }
   ACCESS     read-only
   STATUS     mandatory
   DESCRIPTION
     "This attribute indicates if modems are supported with this 
      TdmaIwfLogicalProcessor. This attribute has one of the following 
      values:
      yes: Modems are supported with this TdmaIwfLogicalProcessor.
      no: Modems are not supported with this TdmaIwfLogicalProcessor."
::= { mscTdmaCsLpOperEntry 3 }


-- TdmaBc/<csIndex>,<bcIndex>
-- This component represents an individual bearer channel resource 
-- for a given TdmaIwfCallServer. Depending on the call type 
-- requested, the TdmaIwfCallServer links one or more 
-- TdmaIwfBearerChannels in a single DMS-MTX InterWorking 
-- Function (IWF) call. Each TdmaIwfBearerChannel is linked to a 
-- channel on a DS1 or E1 port on a TdmaIwfLogicalProcessor (one 
-- TdmaIwfBearerChannel per channel). 
-- The instance value csIndex is the logical identifier for the DMS-
-- MTX and is used for associating the call server with this 
-- TdmaIwfBearerChannel instance.
-- The instance value bcIndex is the logical identifier for the 
-- TdmaIwfBearerChannel. It and the csIndex together define a unique 
-- TdmaIwfBearerChannel.
-- 
-- This component is specific to the tdmaIwfBearerChannel feature 
-- of the tdmaIwf application.

mscTdmaBc OBJECT IDENTIFIER ::= { mscComponents 136 }



mscTdmaBcRowStatusTable OBJECT-TYPE
   SYNTAX     SEQUENCE OF MscTdmaBcRowStatusEntry
   ACCESS     not-accessible
   STATUS     mandatory
   DESCRIPTION
     "This entry controls the addition and deletion of 
      mscTdmaBc components."
::= { mscTdmaBc 1 }

mscTdmaBcRowStatusEntry OBJECT-TYPE
   SYNTAX     MscTdmaBcRowStatusEntry
   ACCESS     not-accessible
   STATUS     mandatory
   DESCRIPTION
     "A single entry in the table represents a single 
      mscTdmaBc component."
   INDEX {
      mscTdmaBcCsIndex,
      mscTdmaBcBcIndex }
::= { mscTdmaBcRowStatusTable 1 }

MscTdmaBcRowStatusEntry ::= SEQUENCE {
   mscTdmaBcRowStatus
      RowStatus,
   mscTdmaBcComponentName
      DisplayString,
   mscTdmaBcStorageType
      StorageType,
   mscTdmaBcCsIndex
      Integer32,
   mscTdmaBcBcIndex
      Integer32 }

mscTdmaBcRowStatus OBJECT-TYPE
   SYNTAX     RowStatus 
   ACCESS     read-write
   STATUS     mandatory
   DESCRIPTION
     "This variable is used as the basis for SNMP naming of
      mscTdmaBc components.
      These components can be added and deleted."
::= { mscTdmaBcRowStatusEntry 1 }

mscTdmaBcComponentName OBJECT-TYPE
   SYNTAX     DisplayString 
   ACCESS     read-only
   STATUS     mandatory
   DESCRIPTION
     "This variable provides the component's string name for
      use with the ASCII Console Interface"
::= { mscTdmaBcRowStatusEntry 2 }

mscTdmaBcStorageType OBJECT-TYPE
   SYNTAX     StorageType 
   ACCESS     read-only
   STATUS     mandatory
   DESCRIPTION
     "This variable represents the storage type value for the
      mscTdmaBc tables."
::= { mscTdmaBcRowStatusEntry 4 }

mscTdmaBcCsIndex OBJECT-TYPE
   SYNTAX     Integer32 (1..10)
   ACCESS     not-accessible
   STATUS     mandatory
   DESCRIPTION
     "This variable represents an index for the mscTdmaBc tables."
::= { mscTdmaBcRowStatusEntry 10 }

mscTdmaBcBcIndex OBJECT-TYPE
   SYNTAX     Integer32 (1..1024)
   ACCESS     not-accessible
   STATUS     mandatory
   DESCRIPTION
     "This variable represents an index for the mscTdmaBc tables."
::= { mscTdmaBcRowStatusEntry 11 }

mscTdmaBcOperTable OBJECT-TYPE
   SYNTAX     SEQUENCE OF MscTdmaBcOperEntry
   ACCESS     not-accessible
   STATUS     mandatory
   DESCRIPTION
     "This group contains operational attributes concerning the operation 
      of this particular TdmaIwfBearerChannel for the current or most 
      recent call."
::= { mscTdmaBc 101 }

mscTdmaBcOperEntry OBJECT-TYPE
   SYNTAX     MscTdmaBcOperEntry
   ACCESS     not-accessible
   STATUS     mandatory
   DESCRIPTION
     "An entry in the mscTdmaBcOperTable."
   INDEX {
      mscTdmaBcCsIndex,
      mscTdmaBcBcIndex }
::= { mscTdmaBcOperTable 1 }

MscTdmaBcOperEntry ::= SEQUENCE {
   mscTdmaBcState
      INTEGER,
   mscTdmaBcCallType
      INTEGER,
   mscTdmaBcLastResponseCode
      INTEGER,
   mscTdmaBcMateBearerChannel
      RowPointer }

mscTdmaBcState OBJECT-TYPE
   SYNTAX     INTEGER  {
                 idle(0),
                 setup(1),
                 active(2),
                 release(3) }
   ACCESS     read-only
   STATUS     mandatory
   DESCRIPTION
     "This attribute indicates the current state of the MSC/IWF Interface 
      Protocol (MIP) Message Router (MMR) for an IWF element. This 
      attribute has one of the following values:
      idle: Startup state of IWF element.
      setup: This call half is being set up.
      active: This call half has been connected by both the MTX and IWF 
      and is active.
      release: This call half is being released."
::= { mscTdmaBcOperEntry 1 }

mscTdmaBcCallType OBJECT-TYPE
   SYNTAX     INTEGER  {
                 analogSpeech(0),
                 digitalSpeech(1),
                 analogPrefSpeech(2),
                 digitalPrefSpeech(3),
                 asyncData(4),
                 g3Fax(5),
                 rejected(6),
                 stuIII(7),
                 notUsedYet(8) }
   ACCESS     read-only
   STATUS     mandatory
   DESCRIPTION
     "This attribute indicates the current call type. This attribute has one 
      of the following values:
      analogSpeech: Analog speech calls.
      digitalSpeech: Digital speech calls.
      analogPrefSpeech: Analog preferred speech calls.
      digitalPrefSpeech: Digital preferred speech calls.
      asyncData: Asynchronous data service calls.
      g3Fax: Group 3 fax calls.
      rejected: Rejected calls.
      stuIII: STU III calls.
      notUsedYet: Bearer Channel has not been used in a call yet."
::= { mscTdmaBcOperEntry 2 }

mscTdmaBcLastResponseCode OBJECT-TYPE
   SYNTAX     INTEGER  {
                 noCause(0),
                 unassignedNumber(1),
                 noRouteToDest(3),
                 normalClearing(16),
                 userBusy(17),
                 noResponse(18),
                 userNoAnswer(19),
                 invalidNumberFormat(28),
                 unspecNormal(31),
                 temporaryFailure(41),
                 channelUnavailable(44),
                 resourceUnavailable(47),
                 qosUnavailable(49),
                 serviceUnavailable(63),
                 unimplementedOption(79),
                 invalidCallRefValue(81),
                 invalidChannel(82),
                 unspecInvalidMessage(95),
                 missingMandatoryIe(96),
                 invalidMessageType(97),
                 incompatibleMessage(98),
                 timerRecovery(102),
                 unspecProtocolError(111) }
   ACCESS     read-only
   STATUS     mandatory
   DESCRIPTION
     "This attribute indicates the MSC/IWF Interface Protocol (MIP) 
      Message Router (MMR) response code returned for the last call 
      which was active on this particular TdmaIwfBearerChannel. This 
      attribute has one of the following values:
      noCause: No cause available.
      unassignedNumber: Unallocated or unassigned number.
      noRouteToDest: No route to destination.
      normalClearing: The call was terminated normally.
      userBusy: User busy.
      noResponse: No carrier.
      userNoAnswer: No answer from user.
      invalidNumberFormat: Translation or routing problem.
      unspecNormal: Normal, unspecified.
      temporaryFailure: Temporary failure.
      channelUnavailable: Channel unavailable.
      resourceUnavailable: Resources unavailable to handle call.
      qosUnavailabled: Specified rate of call unavailable.
      serviceUnavailable: Service not implemented.
      unimplementedOption: Option not implemented.
      invalidCallRefValue: Invalid call reference value.
      invalidChannel: Identified channel does not exist.
      unspecInvalidMessage: Invalid message, unspecified.
      missingMandatoryIe: Missing mandatory information element.
      invalidMessageType: Message type not implemented.
      incompatibleMessage: Message not compatible with call state.
      timerRecovery: Recovery on timer expiration.
      protocolError: Protocol error, unspecified."
::= { mscTdmaBcOperEntry 3 }

mscTdmaBcMateBearerChannel OBJECT-TYPE
   SYNTAX     RowPointer 
   ACCESS     read-only
   STATUS     mandatory
   DESCRIPTION
     "This attribute contains the name of the mate 
      TdmaIwfBearerChannel that this TdmaIwfBearerChannel is 
      involved with in the currently active call."
::= { mscTdmaBcOperEntry 4 }

mscTdmaBcCidDataTable OBJECT-TYPE
   SYNTAX     SEQUENCE OF MscTdmaBcCidDataEntry
   ACCESS     not-accessible
   STATUS     mandatory
   DESCRIPTION
     "This group contains the attribute for a component's Customer 
      Identifier (CID). Refer to the attribute description for a detailed 
      explanation of CIDs."
::= { mscTdmaBc 103 }

mscTdmaBcCidDataEntry OBJECT-TYPE
   SYNTAX     MscTdmaBcCidDataEntry
   ACCESS     not-accessible
   STATUS     mandatory
   DESCRIPTION
     "An entry in the mscTdmaBcCidDataTable."
   INDEX {
      mscTdmaBcCsIndex,
      mscTdmaBcBcIndex }
::= { mscTdmaBcCidDataTable 1 }

MscTdmaBcCidDataEntry ::= SEQUENCE {
   mscTdmaBcCustomerIdentifier
      Unsigned32 }

mscTdmaBcCustomerIdentifier OBJECT-TYPE
   SYNTAX     Unsigned32 (0 | 1..8191)
   ACCESS     read-write
   STATUS     mandatory
   DESCRIPTION
     "This attribute holds the Customer Identifier (CID).
      
      Every component has a CID. If a component has a cid attribute, the 
      component's CID is the provisioned value of that attribute; 
      otherwise the component inherits the CID of its parent. The top-
      level component has a CID of 0.
      
      Every operator session also has a CID, which is the CID 
      provisioned for the operator's user ID. An operator will see only the 
      stream data for components having a matching CID. Also, the 
      operator will be allowed to issue commands for only those 
      components which have a matching CID.
      
      An operator CID of 0 is used to identify the Network Manager 
      (referred to as 'NetMan' in DPN). This CID matches the CID of 
      any component. Values 1 to 8191 inclusive (equivalent to 'basic 
      CIDs' in DPN) may be assigned to specific customers."
   DEFVAL     { 0 }
::= { mscTdmaBcCidDataEntry 1 }

mscTdmaBcStateTable OBJECT-TYPE
   SYNTAX     SEQUENCE OF MscTdmaBcStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { mscTdmaBc 104 }

mscTdmaBcStateEntry OBJECT-TYPE
   SYNTAX     MscTdmaBcStateEntry
   ACCESS     not-accessible
   STATUS     mandatory
   DESCRIPTION
     "An entry in the mscTdmaBcStateTable."
   INDEX {
      mscTdmaBcCsIndex,
      mscTdmaBcBcIndex }
::= { mscTdmaBcStateTable 1 }

MscTdmaBcStateEntry ::= SEQUENCE {
   mscTdmaBcAdminState
      INTEGER,
   mscTdmaBcOperationalState
      INTEGER,
   mscTdmaBcUsageState
      INTEGER }

mscTdmaBcAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { mscTdmaBcStateEntry 1 }

mscTdmaBcOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { mscTdmaBcStateEntry 2 }

mscTdmaBcUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { mscTdmaBcStateEntry 3 }


-- TdmaBc/<csIndex>,<bcIndex> Framer
-- The TdmaIwfFramer component controls link layer framing for 
-- application components sending and receiving data on a link 
-- interface. The TdmaIwfFramer component provides provisionable 
-- attributes related to datapath aspects of the hardware interface rather 
-- than interface specific attributes which are associated with hardware 
-- components. The TdmaIwfFramer component also provides a 
-- provisionable attribute which binds the application component to a 
-- specific hardware component.

mscTdmaBcFramer OBJECT IDENTIFIER ::= { mscTdmaBc 2 }



mscTdmaBcFramerRowStatusTable OBJECT-TYPE
   SYNTAX     SEQUENCE OF MscTdmaBcFramerRowStatusEntry
   ACCESS     not-accessible
   STATUS     mandatory
   DESCRIPTION
     "This entry controls the addition and deletion of 
      mscTdmaBcFramer components."
::= { mscTdmaBcFramer 1 }

mscTdmaBcFramerRowStatusEntry OBJECT-TYPE
   SYNTAX     MscTdmaBcFramerRowStatusEntry
   ACCESS     not-accessible
   STATUS     mandatory
   DESCRIPTION
     "A single entry in the table represents a single 
      mscTdmaBcFramer component."
   INDEX {
      mscTdmaBcCsIndex,
      mscTdmaBcBcIndex,
      mscTdmaBcFramerIndex }
::= { mscTdmaBcFramerRowStatusTable 1 }

MscTdmaBcFramerRowStatusEntry ::= SEQUENCE {
   mscTdmaBcFramerRowStatus
      RowStatus,
   mscTdmaBcFramerComponentName
      DisplayString,
   mscTdmaBcFramerStorageType
      StorageType,
   mscTdmaBcFramerIndex
      NonReplicated }

mscTdmaBcFramerRowStatus OBJECT-TYPE
   SYNTAX     RowStatus 
   ACCESS     read-only
   STATUS     mandatory
   DESCRIPTION
     "This variable is used as the basis for SNMP naming of
      mscTdmaBcFramer components.
      These components cannot be added nor deleted."
::= { mscTdmaBcFramerRowStatusEntry 1 }

mscTdmaBcFramerComponentName OBJECT-TYPE
   SYNTAX     DisplayString 
   ACCESS     read-only
   STATUS     mandatory
   DESCRIPTION
     "This variable provides the component's string name for
      use with the ASCII Console Interface"
::= { mscTdmaBcFramerRowStatusEntry 2 }

mscTdmaBcFramerStorageType OBJECT-TYPE
   SYNTAX     StorageType 
   ACCESS     read-only
   STATUS     mandatory
   DESCRIPTION
     "This variable represents the storage type value for the
      mscTdmaBcFramer tables."
::= { mscTdmaBcFramerRowStatusEntry 4 }

mscTdmaBcFramerIndex OBJECT-TYPE
   SYNTAX     NonReplicated 
   ACCESS     not-accessible
   STATUS     mandatory
   DESCRIPTION
     "This variable represents the index for the mscTdmaBcFramer tables."
::= { mscTdmaBcFramerRowStatusEntry 10 }

mscTdmaBcFramerProvTable OBJECT-TYPE
   SYNTAX     SEQUENCE OF MscTdmaBcFramerProvEntry
   ACCESS     not-accessible
   STATUS     mandatory
   DESCRIPTION
     "This group contains the base provisioning data for the Framer 
      component. Application or hardware interface specific provisioning 
      data is contained in other provisionable Framer groups."
::= { mscTdmaBcFramer 10 }

mscTdmaBcFramerProvEntry OBJECT-TYPE
   SYNTAX     MscTdmaBcFramerProvEntry
   ACCESS     not-accessible
   STATUS     mandatory
   DESCRIPTION
     "An entry in the mscTdmaBcFramerProvTable."
   INDEX {
      mscTdmaBcCsIndex,
      mscTdmaBcBcIndex,
      mscTdmaBcFramerIndex }
::= { mscTdmaBcFramerProvTable 1 }

MscTdmaBcFramerProvEntry ::= SEQUENCE {
   mscTdmaBcFramerInterfaceName
      Link }

mscTdmaBcFramerInterfaceName OBJECT-TYPE
   SYNTAX     Link 
   ACCESS     read-write
   STATUS     mandatory
   DESCRIPTION
     "This attribute contains a hardware component name.
      
      The attribute associates the application with a specific link. This 
      defines the module processor on which Framer's parent component 
      (as well as Framer itself) will run."
::= { mscTdmaBcFramerProvEntry 1 }

mscTdmaBcFramerStatsTable OBJECT-TYPE
   SYNTAX     SEQUENCE OF MscTdmaBcFramerStatsEntry
   ACCESS     not-accessible
   STATUS     mandatory
   DESCRIPTION
     "This group contains the operational statistics data for a 
      TdmaIwfFramer component."
::= { mscTdmaBcFramer 11 }

mscTdmaBcFramerStatsEntry OBJECT-TYPE
   SYNTAX     MscTdmaBcFramerStatsEntry
   ACCESS     not-accessible
   STATUS     mandatory
   DESCRIPTION
     "An entry in the mscTdmaBcFramerStatsTable."
   INDEX {
      mscTdmaBcCsIndex,
      mscTdmaBcBcIndex,
      mscTdmaBcFramerIndex }
::= { mscTdmaBcFramerStatsTable 1 }

MscTdmaBcFramerStatsEntry ::= SEQUENCE {
   mscTdmaBcFramerTxFrames
      Counter32,
   mscTdmaBcFramerRxFrames
      Counter32,
   mscTdmaBcFramerRxBytes
      Counter32 }

mscTdmaBcFramerTxFrames OBJECT-TYPE
   SYNTAX     Counter32 
   ACCESS     read-only
   STATUS     mandatory
   DESCRIPTION
     "This attribute counts the number of frames transmitted to the link 
      interface by TdmaIwfFramer.
      The counter wraps when it exceeds the maximum value."
::= { mscTdmaBcFramerStatsEntry 1 }

mscTdmaBcFramerRxFrames OBJECT-TYPE
   SYNTAX     Counter32 
   ACCESS     read-only
   STATUS     mandatory
   DESCRIPTION
     "This attribute counts the number of frames received from the link 
      interface by TdmaIwfFramer.
      The counter wraps when it exceeds the maximum value."
::= { mscTdmaBcFramerStatsEntry 2 }

mscTdmaBcFramerRxBytes OBJECT-TYPE
   SYNTAX     Counter32 
   ACCESS     read-only
   STATUS     mandatory
   DESCRIPTION
     "This attribute counts the number of bytes received from the link 
      interface by TdmaIwfFramer.
      The counter wraps when it exceeds the maximum value."
::= { mscTdmaBcFramerStatsEntry 3 }

mscTdmaBcFramerLinkTable OBJECT-TYPE
   SYNTAX     SEQUENCE OF MscTdmaBcFramerLinkEntry
   ACCESS     not-accessible
   STATUS     mandatory
   DESCRIPTION
     "This group contains provisionable attributes for the TdmaIwfFramer 
      which controls link layer framing for application components 
      sending and receiving data on a link interface for this particular 
      TdmaIwfBearerChannel."
::= { mscTdmaBcFramer 12 }

mscTdmaBcFramerLinkEntry OBJECT-TYPE
   SYNTAX     MscTdmaBcFramerLinkEntry
   ACCESS     not-accessible
   STATUS     mandatory
   DESCRIPTION
     "An entry in the mscTdmaBcFramerLinkTable."
   INDEX {
      mscTdmaBcCsIndex,
      mscTdmaBcBcIndex,
      mscTdmaBcFramerIndex }
::= { mscTdmaBcFramerLinkTable 1 }

MscTdmaBcFramerLinkEntry ::= SEQUENCE {
   mscTdmaBcFramerFramingType
      INTEGER }

mscTdmaBcFramerFramingType OBJECT-TYPE
   SYNTAX     INTEGER  {
                 btdsFraming(2),
                 mtxFraming(8) }
   ACCESS     read-write
   STATUS     mandatory
   DESCRIPTION
     "This attribute indicates the type of framing for the link layer data 
      received and transmitted on this channel. This attribute has one of 
      the following values:
      btdsFraming: Bit transparent framing for the 
      TdmaIwfBearerChannel components on MVP cards.
      mtxFraming: DMS-MTX InterSystem Link Protocol (ISLP) 
      framing required for the TdmaIwfBearerChannel components on 
      DS1C/E1C cards."
::= { mscTdmaBcFramerLinkEntry 1 }

mscTdmaBcFramerStateTable OBJECT-TYPE
   SYNTAX     SEQUENCE OF MscTdmaBcFramerStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { mscTdmaBcFramer 13 }

mscTdmaBcFramerStateEntry OBJECT-TYPE
   SYNTAX     MscTdmaBcFramerStateEntry
   ACCESS     not-accessible
   STATUS     mandatory
   DESCRIPTION
     "An entry in the mscTdmaBcFramerStateTable."
   INDEX {
      mscTdmaBcCsIndex,
      mscTdmaBcBcIndex,
      mscTdmaBcFramerIndex }
::= { mscTdmaBcFramerStateTable 1 }

MscTdmaBcFramerStateEntry ::= SEQUENCE {
   mscTdmaBcFramerAdminState
      INTEGER,
   mscTdmaBcFramerOperationalState
      INTEGER,
   mscTdmaBcFramerUsageState
      INTEGER }

mscTdmaBcFramerAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { mscTdmaBcFramerStateEntry 1 }

mscTdmaBcFramerOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { mscTdmaBcFramerStateEntry 2 }

mscTdmaBcFramerUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { mscTdmaBcFramerStateEntry 3 }


-- TdmaBc/<csIndex>,<bcIndex> Modem
-- This component represents the group of measurements for the 
-- modem protocol established for a DMS-MTX IWF call (on the IWF 
-- to PSTN modem link) on this particular TdmaIwfBearerChannel.
-- Note that this component is present only if the current or most 
-- recent call involved this protocol.

mscTdmaBcModem OBJECT IDENTIFIER ::= { mscTdmaBc 3 }



mscTdmaBcModemRowStatusTable OBJECT-TYPE
   SYNTAX     SEQUENCE OF MscTdmaBcModemRowStatusEntry
   ACCESS     not-accessible
   STATUS     mandatory
   DESCRIPTION
     "This entry controls the addition and deletion of 
      mscTdmaBcModem components."
::= { mscTdmaBcModem 1 }

mscTdmaBcModemRowStatusEntry OBJECT-TYPE
   SYNTAX     MscTdmaBcModemRowStatusEntry
   ACCESS     not-accessible
   STATUS     mandatory
   DESCRIPTION
     "A single entry in the table represents a single 
      mscTdmaBcModem component."
   INDEX {
      mscTdmaBcCsIndex,
      mscTdmaBcBcIndex,
      mscTdmaBcModemIndex }
::= { mscTdmaBcModemRowStatusTable 1 }

MscTdmaBcModemRowStatusEntry ::= SEQUENCE {
   mscTdmaBcModemRowStatus
      RowStatus,
   mscTdmaBcModemComponentName
      DisplayString,
   mscTdmaBcModemStorageType
      StorageType,
   mscTdmaBcModemIndex
      NonReplicated }

mscTdmaBcModemRowStatus OBJECT-TYPE
   SYNTAX     RowStatus 
   ACCESS     read-only
   STATUS     mandatory
   DESCRIPTION
     "This variable is used as the basis for SNMP naming of
      mscTdmaBcModem components.
      These components cannot be added nor deleted."
::= { mscTdmaBcModemRowStatusEntry 1 }

mscTdmaBcModemComponentName OBJECT-TYPE
   SYNTAX     DisplayString 
   ACCESS     read-only
   STATUS     mandatory
   DESCRIPTION
     "This variable provides the component's string name for
      use with the ASCII Console Interface"
::= { mscTdmaBcModemRowStatusEntry 2 }

mscTdmaBcModemStorageType OBJECT-TYPE
   SYNTAX     StorageType 
   ACCESS     read-only
   STATUS     mandatory
   DESCRIPTION
     "This variable represents the storage type value for the
      mscTdmaBcModem tables."
::= { mscTdmaBcModemRowStatusEntry 4 }

mscTdmaBcModemIndex OBJECT-TYPE
   SYNTAX     NonReplicated 
   ACCESS     not-accessible
   STATUS     mandatory
   DESCRIPTION
     "This variable represents the index for the mscTdmaBcModem tables."
::= { mscTdmaBcModemRowStatusEntry 10 }

mscTdmaBcModemOperTable OBJECT-TYPE
   SYNTAX     SEQUENCE OF MscTdmaBcModemOperEntry
   ACCESS     not-accessible
   STATUS     mandatory
   DESCRIPTION
     "This group contains operational attributes that measure performance 
      of the modem component for this particular 
      TdmaIwfBearerChannel."
::= { mscTdmaBcModem 10 }

mscTdmaBcModemOperEntry OBJECT-TYPE
   SYNTAX     MscTdmaBcModemOperEntry
   ACCESS     not-accessible
   STATUS     mandatory
   DESCRIPTION
     "An entry in the mscTdmaBcModemOperTable."
   INDEX {
      mscTdmaBcCsIndex,
      mscTdmaBcBcIndex,
      mscTdmaBcModemIndex }
::= { mscTdmaBcModemOperTable 1 }

MscTdmaBcModemOperEntry ::= SEQUENCE {
   mscTdmaBcModemVoiceLaw
      INTEGER,
   mscTdmaBcModemRate
      INTEGER,
   mscTdmaBcModemModemAlgorithmInUse
      OCTET STRING,
   mscTdmaBcModemProtocolState
      INTEGER,
   mscTdmaBcModemMobileSideFlowControlState
      INTEGER,
   mscTdmaBcModemPstnSideFlowControlState
      INTEGER,
   mscTdmaBcModemAsyncMode
      INTEGER,
   mscTdmaBcModemOutbandFlowControl
      INTEGER,
   mscTdmaBcModemOutbandBreak
      INTEGER,
   mscTdmaBcModemAutobaud
      INTEGER }

mscTdmaBcModemVoiceLaw OBJECT-TYPE
   SYNTAX     INTEGER  {
                 aLaw(0),
                 muLaw(1) }
   ACCESS     read-only
   STATUS     mandatory
   DESCRIPTION
     "This attribute indicates the active voice law associated with the 
      modem component. This attribute has one of the following values: 
      aLaw and muLaw. Both protocols are utilized for encoding voice-
      band audio. For additional information on each, refer to ITU-T 
      G.711 'Pulse Code Modulation (PCM) of Voice Frequencies'."
::= { mscTdmaBcModemOperEntry 1 }

mscTdmaBcModemRate OBJECT-TYPE
   SYNTAX     INTEGER  {
                 n50(0),
                 n300(1),
                 n600(2),
                 n1200(3),
                 n2400(4),
                 n4800(5),
                 n7200(6),
                 n9600(7),
                 n12000(8),
                 n14400(9),
                 n16800(10),
                 n19200(11),
                 n21600(12),
                 n24000(13),
                 n26400(14),
                 n28800(15),
                 n31200(16),
                 n32000(17),
                 n33600(18),
                 n38400(19),
                 n43200(20),
                 n48000(21),
                 n56000(22),
                 n57600(23),
                 n64000(24) }
   ACCESS     read-only
   STATUS     mandatory
   DESCRIPTION
     "This attribute indicates the transmission rate of the current modem 
      in use. All rates are the same in both the transmit and receive 
      directions."
::= { mscTdmaBcModemOperEntry 2 }

mscTdmaBcModemModemAlgorithmInUse OBJECT-TYPE
   SYNTAX     OCTET STRING (SIZE (2))
   ACCESS     read-only
   STATUS     mandatory
   DESCRIPTION
     "This attribute indicates the current modem algorithm(s) active for 
      the channel. This attribute has one of the following values:
      t30: T.30 is active. T.30 is the Group 3 fax protocol.
      v17: V.17 is active.V.17 is an ITU-T 14400bit/s modem standard. 
      v21: V.21 is active. V.21 is an ITU-4 300bit/s modem standard. 
      v22: V.22 ia active. V.22 is an ITU-T modem standard that operates 
      at 1200bit/s and 600 baud. 
      v22bis: V.22bis is active. V.22bis is an ITU-T modem standard that 
      operates at 2400bit/s and 600 baud. 
      v27ter: V.27ter is active. V.27ter is an ITU-T 7200bit/s modem 
      standard.
      v29: V.29 is active. V.29 is an ITU-T 9600bit/s modem standard. 
      v32: V.32 is active. V.32 is an ITU-T modem standard that operates 
      at 9600bit/s and 2400 baud. 
      v32bis: V.32bis is an ITU-T modem standard that operates at a 
      speed of 14.4kbit/s.

      Description of bits:
      t30(0)
      v17(1)
      v21(2)
      v22(3)
      v22bis(4)
      v27ter(5)
      v29(6)
      v32(7)
      v32bis(8)"
::= { mscTdmaBcModemOperEntry 3 }

mscTdmaBcModemProtocolState OBJECT-TYPE
   SYNTAX     INTEGER  {
                 idle(0),
                 training(1),
                 connected(2),
                 releasing(3) }
   ACCESS     read-only
   STATUS     mandatory
   DESCRIPTION
     "This attribute indicates the active protocol state of the modem in 
      use.This attribute has one of the following values:
      idle: Modem is in an inactive state and has no current connection 
      established.
      training: Modem is attempting to establish a connection with the 
      far end modem via handshaking.
      connected: Modem has establish a connection with the far end 
      modem.
      releasing: Modem has begun tearing down the connection."
::= { mscTdmaBcModemOperEntry 4 }

mscTdmaBcModemMobileSideFlowControlState OBJECT-TYPE
   SYNTAX     INTEGER  {
                 on(0),
                 off(1) }
   ACCESS     read-only
   STATUS     mandatory
   DESCRIPTION
     "This attribute indicates the state of flow control based on whether 
      flow control was requested by the mobile side of the connection and 
      an indication was sent to an upper layer protocol. This attribute has 
      one of the following values:
      on: Flow control is active towards the mobile side of the call.
      off: Flow control is not active towards the mobile side of the call.
      DESCRIPTION"
::= { mscTdmaBcModemOperEntry 5 }

mscTdmaBcModemPstnSideFlowControlState OBJECT-TYPE
   SYNTAX     INTEGER  {
                 on(0),
                 off(1) }
   ACCESS     read-only
   STATUS     mandatory
   DESCRIPTION
     "This attribute indicates the state of flow control based on whether 
      flow control was requested by the PSTN side of the connection and 
      an indication was sent to the Digital Signal Processor. This attribute 
      has one of the following values:
      on: Flow control is active towards the DSP (PSTN side of the call).
      off: Flow control is not active towards the DSP (PSTN side of the 
      call)."
::= { mscTdmaBcModemOperEntry 6 }

mscTdmaBcModemAsyncMode OBJECT-TYPE
   SYNTAX     INTEGER  {
                 on(0),
                 off(1) }
   ACCESS     read-only
   STATUS     mandatory
   DESCRIPTION
     "This attribute indicates whether conversion between synchronous 
      and asynchronous data format (specifically, the stripping or 
      insertion of start and stop bits) is being performed. The value is on 
      unless the V.42 layer is active or it is a fax call. This attribute has 
      one of the following values:
      on: Conversion between synchronous and asynchronous data is 
      being performed.
      off: Conversion between synchronous and asynchronous data is not 
      being performed."
::= { mscTdmaBcModemOperEntry 7 }

mscTdmaBcModemOutbandFlowControl OBJECT-TYPE
   SYNTAX     INTEGER  {
                 on(0),
                 off(1) }
   ACCESS     read-only
   STATUS     mandatory
   DESCRIPTION
     "This attribute indicates whether outband flow control conversions 
      are being performed. If outband flow control is on, then when the 
      Modem Application Layer (MAL) receives an xon or xoff from the 
      PSTN, the MAL converts the instruction into a primitive and sends 
      it to the Data Service Control (DSC). In the opposite direction with 
      outband flow control on, when the MAL receives a primitive from 
      the DSC, the MAL converts the primitive into an xon or xoff and 
      forwards it to the PSTN. If outband flow control is off, then all flow 
      control is handled inband. The modem performs either inband or 
      outband flow control unless V.42 layer is active, it is a fax call, or 
      no flow control was specified by the DMS-MTX. This attribute has 
      one of the following values:
      on: Conversion to and from out-of-band signaling is enabled.
      off: Conversion to and from out-of-band signaling is disabled."
::= { mscTdmaBcModemOperEntry 8 }

mscTdmaBcModemOutbandBreak OBJECT-TYPE
   SYNTAX     INTEGER  {
                 on(0),
                 off(1) }
   ACCESS     read-only
   STATUS     mandatory
   DESCRIPTION
     "This attribute indicates whether inband or outband break control 
      conversions are being performed. If outband break control is on, 
      when the modem detects a break condition coming from the PSTN, 
      the Modem Application Layer (MAL) converts the instruction into a 
      primitive and forwards it to the Data Service Control (DSC). In the 
      opposite direction with outband break control on, when the MAL 
      receives a primitive from the DSC, the MAL converts the primitive 
      into a break and forwards it to the PSTN. When a break condition is 
      discovered all subsequent incoming data is discarded until a start bit 
      is received."
::= { mscTdmaBcModemOperEntry 9 }

mscTdmaBcModemAutobaud OBJECT-TYPE
   SYNTAX     INTEGER  {
                 on(0),
                 off(1) }
   ACCESS     read-only
   STATUS     mandatory
   DESCRIPTION
     "This attribute indicates whether autobaud is active. 
      The modem is instructed at call setup time by the DMS-MTX on 
      the following:
      (1) the initial modem data rate value, and
      (2) whether a modem is allowed to perform autobauding (on) or not 
      (off).
      With autobauding on, the modem is allowed to connect using a 
      valid modem data rate less than or equal to the initial rate specified 
      to the modem by the DMS-MTX. If a modem cannot perform 
      autobauding and the carrier cannot be established at the initial data 
      rate, the modem is disabled."
::= { mscTdmaBcModemOperEntry 10 }

mscTdmaBcModemStatsTable OBJECT-TYPE
   SYNTAX     SEQUENCE OF MscTdmaBcModemStatsEntry
   ACCESS     not-accessible
   STATUS     mandatory
   DESCRIPTION
     "This group contains operational attributes that measure performance 
      of the modem component for this particular 
      TdmaIwfBearerChannel."
::= { mscTdmaBcModem 11 }

mscTdmaBcModemStatsEntry OBJECT-TYPE
   SYNTAX     MscTdmaBcModemStatsEntry
   ACCESS     not-accessible
   STATUS     mandatory
   DESCRIPTION
     "An entry in the mscTdmaBcModemStatsTable."
   INDEX {
      mscTdmaBcCsIndex,
      mscTdmaBcBcIndex,
      mscTdmaBcModemIndex }
::= { mscTdmaBcModemStatsTable 1 }

MscTdmaBcModemStatsEntry ::= SEQUENCE {
   mscTdmaBcModemTxBytes
      Counter32,
   mscTdmaBcModemRxBytes
      Counter32,
   mscTdmaBcModemFramingErrors
      Counter32 }

mscTdmaBcModemTxBytes OBJECT-TYPE
   SYNTAX     Counter32 
   ACCESS     read-only
   STATUS     mandatory
   DESCRIPTION
     "This attribute counts the number of payload bytes transmitted.
      The counter wraps when it exceeds the maximum value."
::= { mscTdmaBcModemStatsEntry 1 }

mscTdmaBcModemRxBytes OBJECT-TYPE
   SYNTAX     Counter32 
   ACCESS     read-only
   STATUS     mandatory
   DESCRIPTION
     "This attribute counts the number of payload bytes received.
      The counter wraps when it exceeds the maximum value."
::= { mscTdmaBcModemStatsEntry 2 }

mscTdmaBcModemFramingErrors OBJECT-TYPE
   SYNTAX     Counter32 
   ACCESS     read-only
   STATUS     mandatory
   DESCRIPTION
     "This attribute counts the number of framing errors detected by the 
      hardware. This is the absence of a stop bit after a start bit and eight 
      bits of data. All incoming data is discarded until the next start bit is 
      received.
      The counter wraps when it exceeds the maximum value."
::= { mscTdmaBcModemStatsEntry 3 }


-- TdmaBc/<csIndex>,<bcIndex> Fax
-- This component represents the group of measurements for the fax 
-- protocol established for a DMS-MTX IWF call (on the mobile 
-- station to IWF link or the IWF to PSTN fax modem/machine link) 
-- on this particular TdmaIwfBearerChannel.
-- Note that this component is present only if the current or most 
-- recent call involved this protocol.

mscTdmaBcFax OBJECT IDENTIFIER ::= { mscTdmaBc 4 }



mscTdmaBcFaxRowStatusTable OBJECT-TYPE
   SYNTAX     SEQUENCE OF MscTdmaBcFaxRowStatusEntry
   ACCESS     not-accessible
   STATUS     mandatory
   DESCRIPTION
     "This entry controls the addition and deletion of 
      mscTdmaBcFax components."
::= { mscTdmaBcFax 1 }

mscTdmaBcFaxRowStatusEntry OBJECT-TYPE
   SYNTAX     MscTdmaBcFaxRowStatusEntry
   ACCESS     not-accessible
   STATUS     mandatory
   DESCRIPTION
     "A single entry in the table represents a single 
      mscTdmaBcFax component."
   INDEX {
      mscTdmaBcCsIndex,
      mscTdmaBcBcIndex,
      mscTdmaBcFaxIndex }
::= { mscTdmaBcFaxRowStatusTable 1 }

MscTdmaBcFaxRowStatusEntry ::= SEQUENCE {
   mscTdmaBcFaxRowStatus
      RowStatus,
   mscTdmaBcFaxComponentName
      DisplayString,
   mscTdmaBcFaxStorageType
      StorageType,
   mscTdmaBcFaxIndex
      NonReplicated }

mscTdmaBcFaxRowStatus OBJECT-TYPE
   SYNTAX     RowStatus 
   ACCESS     read-only
   STATUS     mandatory
   DESCRIPTION
     "This variable is used as the basis for SNMP naming of
      mscTdmaBcFax components.
      These components cannot be added nor deleted."
::= { mscTdmaBcFaxRowStatusEntry 1 }

mscTdmaBcFaxComponentName OBJECT-TYPE
   SYNTAX     DisplayString 
   ACCESS     read-only
   STATUS     mandatory
   DESCRIPTION
     "This variable provides the component's string name for
      use with the ASCII Console Interface"
::= { mscTdmaBcFaxRowStatusEntry 2 }

mscTdmaBcFaxStorageType OBJECT-TYPE
   SYNTAX     StorageType 
   ACCESS     read-only
   STATUS     mandatory
   DESCRIPTION
     "This variable represents the storage type value for the
      mscTdmaBcFax tables."
::= { mscTdmaBcFaxRowStatusEntry 4 }

mscTdmaBcFaxIndex OBJECT-TYPE
   SYNTAX     NonReplicated 
   ACCESS     not-accessible
   STATUS     mandatory
   DESCRIPTION
     "This variable represents the index for the mscTdmaBcFax tables."
::= { mscTdmaBcFaxRowStatusEntry 10 }

mscTdmaBcFaxOperTable OBJECT-TYPE
   SYNTAX     SEQUENCE OF MscTdmaBcFaxOperEntry
   ACCESS     not-accessible
   STATUS     mandatory
   DESCRIPTION
     "This group contains operational attributes which measure the 
      performance of the fax protocol."
::= { mscTdmaBcFax 10 }

mscTdmaBcFaxOperEntry OBJECT-TYPE
   SYNTAX     MscTdmaBcFaxOperEntry
   ACCESS     not-accessible
   STATUS     mandatory
   DESCRIPTION
     "An entry in the mscTdmaBcFaxOperTable."
   INDEX {
      mscTdmaBcCsIndex,
      mscTdmaBcBcIndex,
      mscTdmaBcFaxIndex }
::= { mscTdmaBcFaxOperTable 1 }

MscTdmaBcFaxOperEntry ::= SEQUENCE {
   mscTdmaBcFaxActiveMode
      INTEGER,
   mscTdmaBcFaxProtocolState
      INTEGER,
   mscTdmaBcFaxMessageRate
      Unsigned32 }

mscTdmaBcFaxActiveMode OBJECT-TYPE
   SYNTAX     INTEGER  {
                 normal(0),
                 ecm(1) }
   ACCESS     read-only
   STATUS     mandatory
   DESCRIPTION
     "This attribute indicates the mode of the fax T.30 protocol, 
      determined during Exchange Identification (XID) negotiations. The 
      following modes are supported:
      normal: Normal T.30 protocol, Error Correction Mode (ECM) not 
      used.
      ecm: Error Correction Mode used. Fax error correction is done 
      using a half-duplex page selective repeat technique."
::= { mscTdmaBcFaxOperEntry 1 }

mscTdmaBcFaxProtocolState OBJECT-TYPE
   SYNTAX     INTEGER  {
                 setup(0),
                 idle(1),
                 bcsRx(2),
                 bcsTx(3),
                 msgRx(4),
                 msgTx(5) }
   ACCESS     read-only
   STATUS     mandatory
   DESCRIPTION
     "This attribute indicates the protocol state of the fax adaptor. This 
      attribute has one of the following values:
      setup: Call setup state.
      idle: Idle state only transmitting Synchronize (SYNC) frames.
      bcsRx: Receiving Binary Coded Signal (BCS) packet from modem.
      bcsTx: Transmitting BCS packet to modem.
      msgRx: Receiving fax message from modem.
      msgTx: Transmitting fax message to modem."
::= { mscTdmaBcFaxOperEntry 2 }

mscTdmaBcFaxMessageRate OBJECT-TYPE
   SYNTAX     Unsigned32 (0..65000)
   ACCESS     read-only
   STATUS     mandatory
   DESCRIPTION
     "This attribute indicates the fax message rate used for sending fax 
      documents."
::= { mscTdmaBcFaxOperEntry 3 }

mscTdmaBcFaxStatsTable OBJECT-TYPE
   SYNTAX     SEQUENCE OF MscTdmaBcFaxStatsEntry
   ACCESS     not-accessible
   STATUS     mandatory
   DESCRIPTION
     "This group contains statistical attributes which measure the 
      performance of the fax protocol."
::= { mscTdmaBcFax 11 }

mscTdmaBcFaxStatsEntry OBJECT-TYPE
   SYNTAX     MscTdmaBcFaxStatsEntry
   ACCESS     not-accessible
   STATUS     mandatory
   DESCRIPTION
     "An entry in the mscTdmaBcFaxStatsTable."
   INDEX {
      mscTdmaBcCsIndex,
      mscTdmaBcBcIndex,
      mscTdmaBcFaxIndex }
::= { mscTdmaBcFaxStatsTable 1 }

MscTdmaBcFaxStatsEntry ::= SEQUENCE {
   mscTdmaBcFaxTxPagesToMobile
      Counter32,
   mscTdmaBcFaxRxPagesFromMobile
      Counter32 }

mscTdmaBcFaxTxPagesToMobile OBJECT-TYPE
   SYNTAX     Counter32 
   ACCESS     read-only
   STATUS     mandatory
   DESCRIPTION
     "The attribute counts the number of fax pages transmitted to the 
      mobile.
      The counter wraps when it exceeds the maximum value."
::= { mscTdmaBcFaxStatsEntry 1 }

mscTdmaBcFaxRxPagesFromMobile OBJECT-TYPE
   SYNTAX     Counter32 
   ACCESS     read-only
   STATUS     mandatory
   DESCRIPTION
     "This attribute counts the number of fax pages received from the 
      mobile.
      The counter wraps when it exceeds the maximum value."
::= { mscTdmaBcFaxStatsEntry 2 }


-- TdmaBc/<csIndex>,<bcIndex> Dce
-- This component represents the group of measurements for the 
-- DMS-MTX DCE Protocol established for a DMS-MTX IWF call 
-- (on the Public Switched Telephone Network to the IWF link) on 
-- this particular TdmaIwfBearerChannel.
-- Note that this component is present only if the current or most 
-- recent call involved this protocol.

mscTdmaBcDce OBJECT IDENTIFIER ::= { mscTdmaBc 5 }



mscTdmaBcDceRowStatusTable OBJECT-TYPE
   SYNTAX     SEQUENCE OF MscTdmaBcDceRowStatusEntry
   ACCESS     not-accessible
   STATUS     mandatory
   DESCRIPTION
     "This entry controls the addition and deletion of 
      mscTdmaBcDce components."
::= { mscTdmaBcDce 1 }

mscTdmaBcDceRowStatusEntry OBJECT-TYPE
   SYNTAX     MscTdmaBcDceRowStatusEntry
   ACCESS     not-accessible
   STATUS     mandatory
   DESCRIPTION
     "A single entry in the table represents a single 
      mscTdmaBcDce component."
   INDEX {
      mscTdmaBcCsIndex,
      mscTdmaBcBcIndex,
      mscTdmaBcDceIndex }
::= { mscTdmaBcDceRowStatusTable 1 }

MscTdmaBcDceRowStatusEntry ::= SEQUENCE {
   mscTdmaBcDceRowStatus
      RowStatus,
   mscTdmaBcDceComponentName
      DisplayString,
   mscTdmaBcDceStorageType
      StorageType,
   mscTdmaBcDceIndex
      NonReplicated }

mscTdmaBcDceRowStatus OBJECT-TYPE
   SYNTAX     RowStatus 
   ACCESS     read-only
   STATUS     mandatory
   DESCRIPTION
     "This variable is used as the basis for SNMP naming of
      mscTdmaBcDce components.
      These components cannot be added nor deleted."
::= { mscTdmaBcDceRowStatusEntry 1 }

mscTdmaBcDceComponentName OBJECT-TYPE
   SYNTAX     DisplayString 
   ACCESS     read-only
   STATUS     mandatory
   DESCRIPTION
     "This variable provides the component's string name for
      use with the ASCII Console Interface"
::= { mscTdmaBcDceRowStatusEntry 2 }

mscTdmaBcDceStorageType OBJECT-TYPE
   SYNTAX     StorageType 
   ACCESS     read-only
   STATUS     mandatory
   DESCRIPTION
     "This variable represents the storage type value for the
      mscTdmaBcDce tables."
::= { mscTdmaBcDceRowStatusEntry 4 }

mscTdmaBcDceIndex OBJECT-TYPE
   SYNTAX     NonReplicated 
   ACCESS     not-accessible
   STATUS     mandatory
   DESCRIPTION
     "This variable represents the index for the mscTdmaBcDce tables."
::= { mscTdmaBcDceRowStatusEntry 10 }


-- TdmaBc/<csIndex>,<bcIndex> Dsc
-- This component represents the group of measurements for the 
-- DMS-MTX DSC Protocol established for a DMS-MTX IWF call 
-- (on the mobile station to the IWF link) on this particular 
-- TdmaIwfBearerChannel.
-- Note that this component is present only if the current or most 
-- recent call involved this protocol.

mscTdmaBcDsc OBJECT IDENTIFIER ::= { mscTdmaBc 6 }



mscTdmaBcDscRowStatusTable OBJECT-TYPE
   SYNTAX     SEQUENCE OF MscTdmaBcDscRowStatusEntry
   ACCESS     not-accessible
   STATUS     mandatory
   DESCRIPTION
     "This entry controls the addition and deletion of 
      mscTdmaBcDsc components."
::= { mscTdmaBcDsc 1 }

mscTdmaBcDscRowStatusEntry OBJECT-TYPE
   SYNTAX     MscTdmaBcDscRowStatusEntry
   ACCESS     not-accessible
   STATUS     mandatory
   DESCRIPTION
     "A single entry in the table represents a single 
      mscTdmaBcDsc component."
   INDEX {
      mscTdmaBcCsIndex,
      mscTdmaBcBcIndex,
      mscTdmaBcDscIndex }
::= { mscTdmaBcDscRowStatusTable 1 }

MscTdmaBcDscRowStatusEntry ::= SEQUENCE {
   mscTdmaBcDscRowStatus
      RowStatus,
   mscTdmaBcDscComponentName
      DisplayString,
   mscTdmaBcDscStorageType
      StorageType,
   mscTdmaBcDscIndex
      NonReplicated }

mscTdmaBcDscRowStatus OBJECT-TYPE
   SYNTAX     RowStatus 
   ACCESS     read-only
   STATUS     mandatory
   DESCRIPTION
     "This variable is used as the basis for SNMP naming of
      mscTdmaBcDsc components.
      These components cannot be added nor deleted."
::= { mscTdmaBcDscRowStatusEntry 1 }

mscTdmaBcDscComponentName OBJECT-TYPE
   SYNTAX     DisplayString 
   ACCESS     read-only
   STATUS     mandatory
   DESCRIPTION
     "This variable provides the component's string name for
      use with the ASCII Console Interface"
::= { mscTdmaBcDscRowStatusEntry 2 }

mscTdmaBcDscStorageType OBJECT-TYPE
   SYNTAX     StorageType 
   ACCESS     read-only
   STATUS     mandatory
   DESCRIPTION
     "This variable represents the storage type value for the
      mscTdmaBcDsc tables."
::= { mscTdmaBcDscRowStatusEntry 4 }

mscTdmaBcDscIndex OBJECT-TYPE
   SYNTAX     NonReplicated 
   ACCESS     not-accessible
   STATUS     mandatory
   DESCRIPTION
     "This variable represents the index for the mscTdmaBcDsc tables."
::= { mscTdmaBcDscRowStatusEntry 10 }

mscTdmaBcDscOperTable OBJECT-TYPE
   SYNTAX     SEQUENCE OF MscTdmaBcDscOperEntry
   ACCESS     not-accessible
   STATUS     mandatory
   DESCRIPTION
     "This group contains operational attributes that measure the 
      performance of the DSC asynchronous data service."
::= { mscTdmaBcDsc 10 }

mscTdmaBcDscOperEntry OBJECT-TYPE
   SYNTAX     MscTdmaBcDscOperEntry
   ACCESS     not-accessible
   STATUS     mandatory
   DESCRIPTION
     "An entry in the mscTdmaBcDscOperTable."
   INDEX {
      mscTdmaBcCsIndex,
      mscTdmaBcBcIndex,
      mscTdmaBcDscIndex }
::= { mscTdmaBcDscOperTable 1 }

MscTdmaBcDscOperEntry ::= SEQUENCE {
   mscTdmaBcDscP0CompressionDirection
      INTEGER,
   mscTdmaBcDscP1CompressionMaximumCodewords
      Unsigned32,
   mscTdmaBcDscP2CompressionMaximumCharacters
      Unsigned32 }

mscTdmaBcDscP0CompressionDirection OBJECT-TYPE
   SYNTAX     INTEGER  {
                 noCompression(0),
                 compInitrResp(1),
                 compRespInitr(2),
                 compBoth(3) }
   ACCESS     read-only
   STATUS     mandatory
   DESCRIPTION
     "This attribute indicates the direction of compression requested from 
      logical link 0 (LL0). This attribute has one of the following values:
      noCpmpression: No data compression.
      compInitrResp: Compression initiator to responder.
      compRespInitr: compression responder to initiator.
      compBoth: compression in both directions."
::= { mscTdmaBcDscOperEntry 1 }

mscTdmaBcDscP1CompressionMaximumCodewords OBJECT-TYPE
   SYNTAX     Unsigned32 (512..65535)
   ACCESS     read-only
   STATUS     mandatory
   DESCRIPTION
     "This attribute indicates the maximum number of codewords to be 
      requested from logical link 0 (LL0) for compression. A codeword is 
      a binary number that represents a string of characters."
::= { mscTdmaBcDscOperEntry 2 }

mscTdmaBcDscP2CompressionMaximumCharacters OBJECT-TYPE
   SYNTAX     Unsigned32 (6..250)
   ACCESS     read-only
   STATUS     mandatory
   DESCRIPTION
     "This attribute indicates the maximum number of characters that can 
      be represented by a single codeword to be requested from logical 
      link 0 (LL0) for compression."
::= { mscTdmaBcDscOperEntry 3 }

mscTdmaBcDscStatsTable OBJECT-TYPE
   SYNTAX     SEQUENCE OF MscTdmaBcDscStatsEntry
   ACCESS     not-accessible
   STATUS     mandatory
   DESCRIPTION
     "This group contains statistical attributes that measure the 
      performance of the DSC asynchronous data service."
::= { mscTdmaBcDsc 11 }

mscTdmaBcDscStatsEntry OBJECT-TYPE
   SYNTAX     MscTdmaBcDscStatsEntry
   ACCESS     not-accessible
   STATUS     mandatory
   DESCRIPTION
     "An entry in the mscTdmaBcDscStatsTable."
   INDEX {
      mscTdmaBcCsIndex,
      mscTdmaBcBcIndex,
      mscTdmaBcDscIndex }
::= { mscTdmaBcDscStatsTable 1 }

MscTdmaBcDscStatsEntry ::= SEQUENCE {
   mscTdmaBcDscTxBytes
      Counter32,
   mscTdmaBcDscRxBytes
      Counter32 }

mscTdmaBcDscTxBytes OBJECT-TYPE
   SYNTAX     Counter32 
   ACCESS     read-only
   STATUS     mandatory
   DESCRIPTION
     "This attribute counts the number of data bytes relayed by DSC in 
      the transmit direction (towards the mobile).
      The counter wraps when it exceeds the maximum value."
::= { mscTdmaBcDscStatsEntry 1 }

mscTdmaBcDscRxBytes OBJECT-TYPE
   SYNTAX     Counter32 
   ACCESS     read-only
   STATUS     mandatory
   DESCRIPTION
     "This attribute counts the number of data bytes relayed by DSC in 
      the receive direction (from the mobile).
      The counter wraps when it exceeds the maximum value."
::= { mscTdmaBcDscStatsEntry 2 }


-- TdmaBc/<csIndex>,<bcIndex> Rlp1
-- This component represents the group of measurements for the 
-- Radio Link Protocol 1 (RLP1) established for a DMS-MTX IWF 
-- call (on the mobile station to IWF link) on this particular 
-- TdmaIwfBearerChannel.
-- Note that this component is present only if the current or most 
-- recent call involved this protocol.

mscTdmaBcRlp1 OBJECT IDENTIFIER ::= { mscTdmaBc 7 }



mscTdmaBcRlp1RowStatusTable OBJECT-TYPE
   SYNTAX     SEQUENCE OF MscTdmaBcRlp1RowStatusEntry
   ACCESS     not-accessible
   STATUS     mandatory
   DESCRIPTION
     "This entry controls the addition and deletion of 
      mscTdmaBcRlp1 components."
::= { mscTdmaBcRlp1 1 }

mscTdmaBcRlp1RowStatusEntry OBJECT-TYPE
   SYNTAX     MscTdmaBcRlp1RowStatusEntry
   ACCESS     not-accessible
   STATUS     mandatory
   DESCRIPTION
     "A single entry in the table represents a single 
      mscTdmaBcRlp1 component."
   INDEX {
      mscTdmaBcCsIndex,
      mscTdmaBcBcIndex,
      mscTdmaBcRlp1Index }
::= { mscTdmaBcRlp1RowStatusTable 1 }

MscTdmaBcRlp1RowStatusEntry ::= SEQUENCE {
   mscTdmaBcRlp1RowStatus
      RowStatus,
   mscTdmaBcRlp1ComponentName
      DisplayString,
   mscTdmaBcRlp1StorageType
      StorageType,
   mscTdmaBcRlp1Index
      NonReplicated }

mscTdmaBcRlp1RowStatus OBJECT-TYPE
   SYNTAX     RowStatus 
   ACCESS     read-only
   STATUS     mandatory
   DESCRIPTION
     "This variable is used as the basis for SNMP naming of
      mscTdmaBcRlp1 components.
      These components cannot be added nor deleted."
::= { mscTdmaBcRlp1RowStatusEntry 1 }

mscTdmaBcRlp1ComponentName OBJECT-TYPE
   SYNTAX     DisplayString 
   ACCESS     read-only
   STATUS     mandatory
   DESCRIPTION
     "This variable provides the component's string name for
      use with the ASCII Console Interface"
::= { mscTdmaBcRlp1RowStatusEntry 2 }

mscTdmaBcRlp1StorageType OBJECT-TYPE
   SYNTAX     StorageType 
   ACCESS     read-only
   STATUS     mandatory
   DESCRIPTION
     "This variable represents the storage type value for the
      mscTdmaBcRlp1 tables."
::= { mscTdmaBcRlp1RowStatusEntry 4 }

mscTdmaBcRlp1Index OBJECT-TYPE
   SYNTAX     NonReplicated 
   ACCESS     not-accessible
   STATUS     mandatory
   DESCRIPTION
     "This variable represents the index for the mscTdmaBcRlp1 tables."
::= { mscTdmaBcRlp1RowStatusEntry 10 }

mscTdmaBcRlp1OperTable OBJECT-TYPE
   SYNTAX     SEQUENCE OF MscTdmaBcRlp1OperEntry
   ACCESS     not-accessible
   STATUS     mandatory
   DESCRIPTION
     "This group contains operational attributes that measure performance 
      of the TdmaIwfBearerChannel."
::= { mscTdmaBcRlp1 10 }

mscTdmaBcRlp1OperEntry OBJECT-TYPE
   SYNTAX     MscTdmaBcRlp1OperEntry
   ACCESS     not-accessible
   STATUS     mandatory
   DESCRIPTION
     "An entry in the mscTdmaBcRlp1OperTable."
   INDEX {
      mscTdmaBcCsIndex,
      mscTdmaBcBcIndex,
      mscTdmaBcRlp1Index }
::= { mscTdmaBcRlp1OperTable 1 }

MscTdmaBcRlp1OperEntry ::= SEQUENCE {
   mscTdmaBcRlp1Layer3L0ReqWinSize
      Unsigned32,
   mscTdmaBcRlp1Layer3L1ReqWinSize1
      Unsigned32,
   mscTdmaBcRlp1T1ResponseTimer
      Unsigned32,
   mscTdmaBcRlp1T2LinkActivityTimer
      Unsigned32,
   mscTdmaBcRlp1T3PeerAckTimer
      Unsigned32 }

mscTdmaBcRlp1Layer3L0ReqWinSize OBJECT-TYPE
   SYNTAX     Unsigned32 (1..64)
   ACCESS     read-only
   STATUS     mandatory
   DESCRIPTION
     "This attribute indicates the window size for Service Access Point 
      (SAP) 0 requested by layer 3. The window size is the maximum 
      number of sequentially numbered Information (I) frames that may 
      be unacknowledged at any given time."
::= { mscTdmaBcRlp1OperEntry 1 }

mscTdmaBcRlp1Layer3L1ReqWinSize1 OBJECT-TYPE
   SYNTAX     Unsigned32 (1..64)
   ACCESS     read-only
   STATUS     mandatory
   DESCRIPTION
     "This attribute indicates the window size for Service Access Point 
      (SAP) 1 requested by layer 3. The window size is the maximum 
      number of sequentially numbered Information (I) frames that may 
      be unacknowledged at any given time."
::= { mscTdmaBcRlp1OperEntry 2 }

mscTdmaBcRlp1T1ResponseTimer OBJECT-TYPE
   SYNTAX     Unsigned32 (5..20)
   ACCESS     read-only
   STATUS     mandatory
   DESCRIPTION
     "This attribute indicates the current T1 timer for Service Access 
      Points (SAP) 0 and 1 negotiated by the Radio Link Protocol 1 
      (RLP1), during Exchange Information (XID). This attribute 
      specifies the time the receiving RLP1 entity shall wait for a 
      response from the peer TIA-136-310 (formerly IS-130) application. 
      The value used for XID negotiations can be provisioned in the 
      TdmaCs/* Rlp1 t1ResponseTimer attribute."
::= { mscTdmaBcRlp1OperEntry 3 }

mscTdmaBcRlp1T2LinkActivityTimer OBJECT-TYPE
   SYNTAX     Unsigned32 (10..120)
   ACCESS     read-only
   STATUS     mandatory
   DESCRIPTION
     "This attribute indicates the current T2 timer for Service Access 
      Points (SAP) 0 and 1 negotiated by the Radio Link Protocol 1 
      (RLP1), during Exchange Information (XID). This attribute 
      specifies the maximum time the receiving RLP1 entity shall wait for 
      link activity. The value used for XID negotiations can be 
      provisioned in the TdmaCs/* Rlp1 t2LinkActivityTimer attribute."
::= { mscTdmaBcRlp1OperEntry 4 }

mscTdmaBcRlp1T3PeerAckTimer OBJECT-TYPE
   SYNTAX     Unsigned32 (5..20)
   ACCESS     read-only
   STATUS     mandatory
   DESCRIPTION
     "This attribute indicates the current T2 timer for Service Access 
      Points (SAP) 0 and 1 negotiated by the Radio Link Protocol 1 
      (RLP1), during Exchange Information (XID). The attribute specifies 
      the maximum time the receiving RLP1 entity shall wait for the peer 
      to ACK or NAK data. The value used for XID negotiations can be 
      provisioned in the TdmaCs/* Rlp1 t3PeerAckTimer attribute."
::= { mscTdmaBcRlp1OperEntry 5 }

mscTdmaBcRlp1StatsTable OBJECT-TYPE
   SYNTAX     SEQUENCE OF MscTdmaBcRlp1StatsEntry
   ACCESS     not-accessible
   STATUS     mandatory
   DESCRIPTION
     "This group contains operational attributes that measure performance 
      of the TdmaIwfBearerChannel."
::= { mscTdmaBcRlp1 11 }

mscTdmaBcRlp1StatsEntry OBJECT-TYPE
   SYNTAX     MscTdmaBcRlp1StatsEntry
   ACCESS     not-accessible
   STATUS     mandatory
   DESCRIPTION
     "An entry in the mscTdmaBcRlp1StatsTable."
   INDEX {
      mscTdmaBcCsIndex,
      mscTdmaBcBcIndex,
      mscTdmaBcRlp1Index }
::= { mscTdmaBcRlp1StatsTable 1 }

MscTdmaBcRlp1StatsEntry ::= SEQUENCE {
   mscTdmaBcRlp1TxFrames
      Counter32,
   mscTdmaBcRlp1RxFrames
      Counter32,
   mscTdmaBcRlp1BadRxFrames
      Counter32 }

mscTdmaBcRlp1TxFrames OBJECT-TYPE
   SYNTAX     Counter32 
   ACCESS     read-only
   STATUS     mandatory
   DESCRIPTION
     "This attribute counts the number of valid frames transmitted to the 
      mobile.
      The counter wraps when it exceeds the maximum value."
::= { mscTdmaBcRlp1StatsEntry 1 }

mscTdmaBcRlp1RxFrames OBJECT-TYPE
   SYNTAX     Counter32 
   ACCESS     read-only
   STATUS     mandatory
   DESCRIPTION
     "This attributes counts the number of valid frames received from the 
      mobile.
      The counter wraps when it exceeds the maximum value."
::= { mscTdmaBcRlp1StatsEntry 2 }

mscTdmaBcRlp1BadRxFrames OBJECT-TYPE
   SYNTAX     Counter32 
   ACCESS     read-only
   STATUS     mandatory
   DESCRIPTION
     "This attribute count the total number of bad RLP1 frames received 
      from the mobile.
      The counter wraps when it exceeds the maximum value."
::= { mscTdmaBcRlp1StatsEntry 3 }


-- TdmaBc/<csIndex>,<bcIndex> V42
-- This component represents the group of measurements for the ITU-
-- T V.42 error correcting protocol established for a DMS-MTX IWF 
-- call (on the IWF to PSTN modem link) on this particular 
-- TdmaIwfBearerChannel. 
-- Note that this component is present only if the current or most 
-- recent call involved this protocol.

mscTdmaBcV42 OBJECT IDENTIFIER ::= { mscTdmaBc 8 }



mscTdmaBcV42RowStatusTable OBJECT-TYPE
   SYNTAX     SEQUENCE OF MscTdmaBcV42RowStatusEntry
   ACCESS     not-accessible
   STATUS     mandatory
   DESCRIPTION
     "This entry controls the addition and deletion of 
      mscTdmaBcV42 components."
::= { mscTdmaBcV42 1 }

mscTdmaBcV42RowStatusEntry OBJECT-TYPE
   SYNTAX     MscTdmaBcV42RowStatusEntry
   ACCESS     not-accessible
   STATUS     mandatory
   DESCRIPTION
     "A single entry in the table represents a single 
      mscTdmaBcV42 component."
   INDEX {
      mscTdmaBcCsIndex,
      mscTdmaBcBcIndex,
      mscTdmaBcV42Index }
::= { mscTdmaBcV42RowStatusTable 1 }

MscTdmaBcV42RowStatusEntry ::= SEQUENCE {
   mscTdmaBcV42RowStatus
      RowStatus,
   mscTdmaBcV42ComponentName
      DisplayString,
   mscTdmaBcV42StorageType
      StorageType,
   mscTdmaBcV42Index
      NonReplicated }

mscTdmaBcV42RowStatus OBJECT-TYPE
   SYNTAX     RowStatus 
   ACCESS     read-only
   STATUS     mandatory
   DESCRIPTION
     "This variable is used as the basis for SNMP naming of
      mscTdmaBcV42 components.
      These components cannot be added nor deleted."
::= { mscTdmaBcV42RowStatusEntry 1 }

mscTdmaBcV42ComponentName OBJECT-TYPE
   SYNTAX     DisplayString 
   ACCESS     read-only
   STATUS     mandatory
   DESCRIPTION
     "This variable provides the component's string name for
      use with the ASCII Console Interface"
::= { mscTdmaBcV42RowStatusEntry 2 }

mscTdmaBcV42StorageType OBJECT-TYPE
   SYNTAX     StorageType 
   ACCESS     read-only
   STATUS     mandatory
   DESCRIPTION
     "This variable represents the storage type value for the
      mscTdmaBcV42 tables."
::= { mscTdmaBcV42RowStatusEntry 4 }

mscTdmaBcV42Index OBJECT-TYPE
   SYNTAX     NonReplicated 
   ACCESS     not-accessible
   STATUS     mandatory
   DESCRIPTION
     "This variable represents the index for the mscTdmaBcV42 tables."
::= { mscTdmaBcV42RowStatusEntry 10 }

mscTdmaBcV42OperTable OBJECT-TYPE
   SYNTAX     SEQUENCE OF MscTdmaBcV42OperEntry
   ACCESS     not-accessible
   STATUS     mandatory
   DESCRIPTION
     "This group contains operational attributes which measure V.42 error 
      detection and correction performance."
::= { mscTdmaBcV42 10 }

mscTdmaBcV42OperEntry OBJECT-TYPE
   SYNTAX     MscTdmaBcV42OperEntry
   ACCESS     not-accessible
   STATUS     mandatory
   DESCRIPTION
     "An entry in the mscTdmaBcV42OperTable."
   INDEX {
      mscTdmaBcCsIndex,
      mscTdmaBcBcIndex,
      mscTdmaBcV42Index }
::= { mscTdmaBcV42OperTable 1 }

MscTdmaBcV42OperEntry ::= SEQUENCE {
   mscTdmaBcV42ProtocolState
      INTEGER,
   mscTdmaBcV42TxN401FrameSize
      Unsigned32,
   mscTdmaBcV42RxN401FrameSize
      Unsigned32,
   mscTdmaBcV42TxKWindowSize
      Unsigned32,
   mscTdmaBcV42RxKWindowSize
      Unsigned32,
   mscTdmaBcV42V42ActiveInCall
      INTEGER,
   mscTdmaBcV42V42BisActiveInCall
      INTEGER }

mscTdmaBcV42ProtocolState OBJECT-TYPE
   SYNTAX     INTEGER  {
                 notActive(0),
                 disconnected(1),
                 linkSetup(2),
                 frameReject(3),
                 disconnectRequest(4),
                 informationTransfer(5),
                 waitingAck(6) }
   ACCESS     read-only
   STATUS     mandatory
   DESCRIPTION
     "This attribute indicates the state of V.42. Valid states are:
      
      notActive: The V.42 link connection with the PSTN modem is not 
      established. None of the V.42 functions including the error 
      detection, error correction, and flow control is provided to the data 
      call. This is the initial state of V.42.
      disconnected: This means that the V42 link is disconnected.
      linkSetup: The V.42 operation enters this state from the 
      disconnected state after the V.42 sends to the PSTN modem a Set 
      Asynchronous Balanced Mode Extended (SABME) frame in an 
      attempt to establish the error control connection with the PSTN 
      modem.
      frameReject: The V.42 operation enters into this state after it 
      identifies an invalid frame sent by the peer and it sends back a frame 
      reject (FRMR) frame to the peer.
      disconnectRequest: The V.42 operation enters into this state after it 
      sends to the peer a disconnect (DISC) frame with the attempt to 
      disconnect the V.42 error control link.
      informationTransfer: The V.42 enters into this state after it receives 
      a UA (unnumbered acknowledgment) frame which the peer sent 
      upon receipt of the SAMBE frame from IWF V.42. Once in this 
      state, the V.42 can exchange data and supervisory information with 
      its peer.
      waitingAck: The V.42 enters this state after it sends polling enquiry 
      to its peer. The V.42 sends the polling enquiry when it receives a 
      reject frame (REJ) from its peer or either its acknowledgment timer 
      or inactivity timer timed out on the information frames sent out."
::= { mscTdmaBcV42OperEntry 1 }

mscTdmaBcV42TxN401FrameSize OBJECT-TYPE
   SYNTAX     Unsigned32 (0..65355)
   ACCESS     read-only
   STATUS     mandatory
   DESCRIPTION
     "This attribute indicates the current value of parameter N401 for 
      V.42 which is negotiated during Exchange Information (XID). This 
      is the maximum number of octets that can be carried in the 
      information field of an information frame that the IWF V.42 
      transmits to the PSTN modem. The IWF V.42 puts this or even 
      smaller size of data into the outgoing information frame. The value 
      used for XID negotiations can be provisioned via TdmaCs/* V42."
::= { mscTdmaBcV42OperEntry 2 }

mscTdmaBcV42RxN401FrameSize OBJECT-TYPE
   SYNTAX     Unsigned32 (1..255)
   ACCESS     read-only
   STATUS     mandatory
   DESCRIPTION
     "This attribute indicates the current value of N401, that is negotiated 
      during Exchange Identification (XID). This is the maximum number 
      of octets that can be carried in the information field of an 
      information frame received from the PSTN modem. An incoming 
      information frame carrying data octets more than this size shall be 
      rejected by the IWF V.42. The value used for XID negotiations can 
      be provisioned via TdmaCs/* V42."
::= { mscTdmaBcV42OperEntry 3 }

mscTdmaBcV42TxKWindowSize OBJECT-TYPE
   SYNTAX     Unsigned32 (0..127)
   ACCESS     read-only
   STATUS     mandatory
   DESCRIPTION
     "This attribute indicates the current value of k, that is negotiated 
      during Exchange Identification (XID). This is the size of flow 
      control sliding window used for the information frames that the 
      V.42 transmits to the PSTN modem. This size governs the 
      maximum number of information frames that the IWF V.42 error-
      correcting entity can have outstanding (that is, unacknowledged). 
      The value used for XID negotiations can be provisioned via 
      TdmaCs/* V42."
::= { mscTdmaBcV42OperEntry 4 }

mscTdmaBcV42RxKWindowSize OBJECT-TYPE
   SYNTAX     Unsigned32 (1..127)
   ACCESS     read-only
   STATUS     mandatory
   DESCRIPTION
     "This attribute indicates the current value of k that is negotiated 
      during Exchange Identification (XID). This is the size of flow 
      control sliding window used for information frames transmitted 
      from the PSTN modem. This size governs the maximum number of 
      information frames that the peer of the IWF V.42 error-correcting 
      entity can have outstanding (that is, unacknowledged). The value 
      used for XID negotiations can be provisioned via TdmaCs/* V42."
::= { mscTdmaBcV42OperEntry 5 }

mscTdmaBcV42V42ActiveInCall OBJECT-TYPE
   SYNTAX     INTEGER  {
                 notActiveInCall(0),
                 activeInCall(1) }
   ACCESS     read-only
   STATUS     mandatory
   DESCRIPTION
     "This attribute indicates whether V42 is really being used in this data 
      call."
   DEFVAL     { notActiveInCall }
::= { mscTdmaBcV42OperEntry 6 }

mscTdmaBcV42V42BisActiveInCall OBJECT-TYPE
   SYNTAX     INTEGER  {
                 notActiveInCall(0),
                 activeInCall(1) }
   ACCESS     read-only
   STATUS     mandatory
   DESCRIPTION
     "This attribute indicates whether V42bis is really being used in this 
      data call."
   DEFVAL     { notActiveInCall }
::= { mscTdmaBcV42OperEntry 7 }

mscTdmaBcV42StatsTable OBJECT-TYPE
   SYNTAX     SEQUENCE OF MscTdmaBcV42StatsEntry
   ACCESS     not-accessible
   STATUS     mandatory
   DESCRIPTION
     "This group contains statistical attributes that measure the V.42 error 
      detection and correction performance."
::= { mscTdmaBcV42 11 }

mscTdmaBcV42StatsEntry OBJECT-TYPE
   SYNTAX     MscTdmaBcV42StatsEntry
   ACCESS     not-accessible
   STATUS     mandatory
   DESCRIPTION
     "An entry in the mscTdmaBcV42StatsTable."
   INDEX {
      mscTdmaBcCsIndex,
      mscTdmaBcBcIndex,
      mscTdmaBcV42Index }
::= { mscTdmaBcV42StatsTable 1 }

MscTdmaBcV42StatsEntry ::= SEQUENCE {
   mscTdmaBcV42RxIBytes
      Counter32,
   mscTdmaBcV42TxIBytes
      Counter32,
   mscTdmaBcV42RxIFrames
      Counter32,
   mscTdmaBcV42TxIFrames
      Counter32,
   mscTdmaBcV42RetransmittedFrames
      Counter32,
   mscTdmaBcV42T1AckTimeouts
      Counter32,
   mscTdmaBcV42RemoteBusyIndications
      Counter32,
   mscTdmaBcV42LocalBusyIndications
      Counter32,
   mscTdmaBcV42BadFramesRx
      Counter32,
   mscTdmaBcV42CrcErrorsRx
      Counter32 }

mscTdmaBcV42RxIBytes OBJECT-TYPE
   SYNTAX     Counter32 
   ACCESS     read-only
   STATUS     mandatory
   DESCRIPTION
     "This attribute counts the total number of bytes that the V.42 actually 
      received from the PSTN modem in a data call.
      The counter wraps when it exceeds the maximum value."
::= { mscTdmaBcV42StatsEntry 1 }

mscTdmaBcV42TxIBytes OBJECT-TYPE
   SYNTAX     Counter32 
   ACCESS     read-only
   STATUS     mandatory
   DESCRIPTION
     "This attribute counts the total number of bytes that the V.42 
      transmitted to the PSTN modem in a data call.
      The counter wraps when it exceeds the maximum value."
::= { mscTdmaBcV42StatsEntry 2 }

mscTdmaBcV42RxIFrames OBJECT-TYPE
   SYNTAX     Counter32 
   ACCESS     read-only
   STATUS     mandatory
   DESCRIPTION
     "This attribute counts the total number of Information (I) frames that 
      the V.42 received from the PSTN modem in a data call.
      The counter wraps when it exceeds the maximum value."
::= { mscTdmaBcV42StatsEntry 3 }

mscTdmaBcV42TxIFrames OBJECT-TYPE
   SYNTAX     Counter32 
   ACCESS     read-only
   STATUS     mandatory
   DESCRIPTION
     "This attribute counts the total number of information frames that the 
      V.42 transmitted to the PSTN modem in a data call.
      The counter wraps when it exceeds the maximum value."
::= { mscTdmaBcV42StatsEntry 4 }

mscTdmaBcV42RetransmittedFrames OBJECT-TYPE
   SYNTAX     Counter32 
   ACCESS     read-only
   STATUS     mandatory
   DESCRIPTION
     "This attribute counts the total number of frames retransmitted by the 
      IWF V.42 entity in a data call. The V.42 retransmits the same frame 
      when the associated T401 acknowledgment timer timeouts or when 
      a Reject (REJ) supervisory frame has been received from the PSTN 
      modem.
      The counter wraps when it exceeds the maximum value."
::= { mscTdmaBcV42StatsEntry 5 }

mscTdmaBcV42T1AckTimeouts OBJECT-TYPE
   SYNTAX     Counter32 
   ACCESS     read-only
   STATUS     mandatory
   DESCRIPTION
     "This attribute counts the total number of times that the T401 timer 
      has timed out within a data call. If this timer times-out frequently, 
      the operator may need to adjust the provisioned parameter T401 
      acknowledgment timer to a larger time amount, since every time 
      that V.42 sends out a frame it sets the T401 timer to wait for the 
      peer's acknowledgment of the frame. When the timer times-out and 
      no acknowledgment has been received, the V.42 sends the same 
      frame to its peer.
      The counter wraps when it exceeds the maximum value."
::= { mscTdmaBcV42StatsEntry 6 }

mscTdmaBcV42RemoteBusyIndications OBJECT-TYPE
   SYNTAX     Counter32 
   ACCESS     read-only
   STATUS     mandatory
   DESCRIPTION
     "This attribute counts the total number of times the PSTN modem 
      enters a busy state (the IWF has received a Receive Not Ready 
      message) and asks the IWF V.42 not to send Information (I) frames 
      to it until it is ready to receive information frames again (indicated 
      by receipt of a Receive Ready message or a data message).
      The counter wraps when it exceeds the maximum value."
::= { mscTdmaBcV42StatsEntry 7 }

mscTdmaBcV42LocalBusyIndications OBJECT-TYPE
   SYNTAX     Counter32 
   ACCESS     read-only
   STATUS     mandatory
   DESCRIPTION
     "This attribute counts the total number of times the IWF V.42 enters 
      in a busy condition and asks the peer to stop sending information 
      frames until it has cleared up from the busy condition. The V.42 
      enters busy condition when its data buffer is about to be overflowed 
      by the incoming Information (I) frames.
      The counter wraps when it exceeds the maximum value."
::= { mscTdmaBcV42StatsEntry 8 }

mscTdmaBcV42BadFramesRx OBJECT-TYPE
   SYNTAX     Counter32 
   ACCESS     read-only
   STATUS     mandatory
   DESCRIPTION
     "This attribute counts the total number of bad frames the IWF V.42 
      has received from the PSTN remote modem within the data call. In 
      this instance, 'bad frames' refer to the V.42 protocol error frames 
      other than the check sequence error frames.
      The counter wraps when it exceeds the maximum value."
::= { mscTdmaBcV42StatsEntry 9 }

mscTdmaBcV42CrcErrorsRx OBJECT-TYPE
   SYNTAX     Counter32 
   ACCESS     read-only
   STATUS     mandatory
   DESCRIPTION
     "This attribute counts the total number of frames received from the 
      remote PSTN modem that contain incorrect frame check sequence. 
      A high value signifies the condition of the physical medium is poor.
      The counter wraps when it exceeds the maximum value."
::= { mscTdmaBcV42StatsEntry 10 }


-- TdmaBc/<csIndex>,<bcIndex> V42bis
-- This component represents the group of measurements for the ITU-
-- T V.42bis data compression protocol established for an IWF call (on 
-- the mobile station to the IWF link or the IWF to PSTN fax modem 
-- link) on this particular TdmaIwfBearerChannel.
-- Note that this component is present only if the current or most 
-- recent call involved this protocol. 

mscTdmaBcV42Bis OBJECT IDENTIFIER ::= { mscTdmaBc 9 }



mscTdmaBcV42BisRowStatusTable OBJECT-TYPE
   SYNTAX     SEQUENCE OF MscTdmaBcV42BisRowStatusEntry
   ACCESS     not-accessible
   STATUS     mandatory
   DESCRIPTION
     "This entry controls the addition and deletion of 
      mscTdmaBcV42Bis components."
::= { mscTdmaBcV42Bis 1 }

mscTdmaBcV42BisRowStatusEntry OBJECT-TYPE
   SYNTAX     MscTdmaBcV42BisRowStatusEntry
   ACCESS     not-accessible
   STATUS     mandatory
   DESCRIPTION
     "A single entry in the table represents a single 
      mscTdmaBcV42Bis component."
   INDEX {
      mscTdmaBcCsIndex,
      mscTdmaBcBcIndex,
      mscTdmaBcV42BisIndex }
::= { mscTdmaBcV42BisRowStatusTable 1 }

MscTdmaBcV42BisRowStatusEntry ::= SEQUENCE {
   mscTdmaBcV42BisRowStatus
      RowStatus,
   mscTdmaBcV42BisComponentName
      DisplayString,
   mscTdmaBcV42BisStorageType
      StorageType,
   mscTdmaBcV42BisIndex
      NonReplicated }

mscTdmaBcV42BisRowStatus OBJECT-TYPE
   SYNTAX     RowStatus 
   ACCESS     read-only
   STATUS     mandatory
   DESCRIPTION
     "This variable is used as the basis for SNMP naming of
      mscTdmaBcV42Bis components.
      These components cannot be added nor deleted."
::= { mscTdmaBcV42BisRowStatusEntry 1 }

mscTdmaBcV42BisComponentName OBJECT-TYPE
   SYNTAX     DisplayString 
   ACCESS     read-only
   STATUS     mandatory
   DESCRIPTION
     "This variable provides the component's string name for
      use with the ASCII Console Interface"
::= { mscTdmaBcV42BisRowStatusEntry 2 }

mscTdmaBcV42BisStorageType OBJECT-TYPE
   SYNTAX     StorageType 
   ACCESS     read-only
   STATUS     mandatory
   DESCRIPTION
     "This variable represents the storage type value for the
      mscTdmaBcV42Bis tables."
::= { mscTdmaBcV42BisRowStatusEntry 4 }

mscTdmaBcV42BisIndex OBJECT-TYPE
   SYNTAX     NonReplicated 
   ACCESS     not-accessible
   STATUS     mandatory
   DESCRIPTION
     "This variable represents the index for the mscTdmaBcV42Bis tables."
::= { mscTdmaBcV42BisRowStatusEntry 10 }

mscTdmaBcV42BisOperTable OBJECT-TYPE
   SYNTAX     SEQUENCE OF MscTdmaBcV42BisOperEntry
   ACCESS     not-accessible
   STATUS     mandatory
   DESCRIPTION
     "This group contains operational attributes that measure the 
      performance of IwfV42bis."
::= { mscTdmaBcV42Bis 10 }

mscTdmaBcV42BisOperEntry OBJECT-TYPE
   SYNTAX     MscTdmaBcV42BisOperEntry
   ACCESS     not-accessible
   STATUS     mandatory
   DESCRIPTION
     "An entry in the mscTdmaBcV42BisOperTable."
   INDEX {
      mscTdmaBcCsIndex,
      mscTdmaBcBcIndex,
      mscTdmaBcV42BisIndex }
::= { mscTdmaBcV42BisOperTable 1 }

MscTdmaBcV42BisOperEntry ::= SEQUENCE {
   mscTdmaBcV42BisProtocolModeEncoder
      INTEGER,
   mscTdmaBcV42BisProtocolModeDecoder
      INTEGER,
   mscTdmaBcV42BisP0CompressionDirection
      INTEGER,
   mscTdmaBcV42BisP1MaximumCodewords
      Unsigned32,
   mscTdmaBcV42BisP2MaximumStringSize
      Unsigned32,
   mscTdmaBcV42BisLastDecodeError
      INTEGER,
   mscTdmaBcV42BisCompRatioEncoder
      FixedPoint2,
   mscTdmaBcV42BisCompRatioDecoder
      FixedPoint2 }

mscTdmaBcV42BisProtocolModeEncoder OBJECT-TYPE
   SYNTAX     INTEGER  {
                 transparent(0),
                 compressed(1) }
   ACCESS     read-only
   STATUS     mandatory
   DESCRIPTION
     "This attribute indicates the current mode of the IwfV42bis encoder. 
      This mode can be either:
      transparent: A mode of operation in which compression has been 
      selected but data is being transmitted in uncompressed form. 
      Transparent mode command sequences may be inserted into the 
      data stream. 
      compressed: A mode of operation in which data is transmitted in 
      codewords.
      The encoder switches between the two modes depending on 
      whether the data coming from the Date Terminal Equipment (DTE) 
      is suitable for compression. The data compression function 
      periodically determines the compressibility of the data based on a 
      comparison of the number of bits required to represent a segment of 
      the data stream before and after compression."
::= { mscTdmaBcV42BisOperEntry 1 }

mscTdmaBcV42BisProtocolModeDecoder OBJECT-TYPE
   SYNTAX     INTEGER  {
                 transparent(0),
                 compressed(1) }
   ACCESS     read-only
   STATUS     mandatory
   DESCRIPTION
     "This attribute indicates the current mode of the V.42bis decoder. 
      This mode can be either: 
      transparent: A mode of operation in which compression has been 
      selected but data is being transmitted in uncompressed form. 
      Transparent mode command sequences may be inserted into the 
      data stream.
      compressed: A mode of operation in which data is transmitted in 
      codewords.
      The encoder (at the mobile or PSTN) switches between the two 
      modes depending on whether the data coming from the Date 
      Terminal Equipment (DTE) is suitable for compression. The data 
      compression function periodically determines the compressibility of 
      the data based on a comparison of the number of bits required to 
      represent a segment of the data stream before and after 
      compression."
::= { mscTdmaBcV42BisOperEntry 2 }

mscTdmaBcV42BisP0CompressionDirection OBJECT-TYPE
   SYNTAX     INTEGER  {
                 noCompression(0),
                 compInitrResp(1),
                 compRespInitr(2),
                 compBoth(3) }
   ACCESS     read-only
   STATUS     mandatory
   DESCRIPTION
     "This attribute indicates the direction in which V.42bis is active, 
      negotiated at link setup by the data link protocol through Exchange 
      Identification (XID) negotiation of parameter P0 (compression 
      direction). The value used for XID negotiations can be provisioned 
      via TdmaCs/* V42bis. This attribute has one of the following 
      values:
      noCompression: No data compression.
      compInitrResp: The data sent by the IWF to the other entity is 
      compressed.
      compRespInitr: The data received by the IWF from the other entity 
      is compressed.
      compBoth: compression in both directions."
::= { mscTdmaBcV42BisOperEntry 3 }

mscTdmaBcV42BisP1MaximumCodewords OBJECT-TYPE
   SYNTAX     Unsigned32 (0..4096)
   ACCESS     read-only
   STATUS     mandatory
   DESCRIPTION
     "This attribute indicates the maximum number of codewords in the 
      dictionary negotiated at link setup by the data link protocol by way 
      of the Exchange Identification (XID) negotiation of parameter P1 
      (number of codewords). The value used for XID negotiations can be 
      provisioned via TdmaCs/* V42bis."
::= { mscTdmaBcV42BisOperEntry 4 }

mscTdmaBcV42BisP2MaximumStringSize OBJECT-TYPE
   SYNTAX     Unsigned32 (6..250)
   ACCESS     read-only
   STATUS     mandatory
   DESCRIPTION
     "This attribute indicates the maximum number of characters allowed 
      in a string represented by a codeword negotiated at link setup by the 
      data link protocol by way of the Exchange Identification (XID) 
      negotiation of parameter P2 (maximum string size). The value used 
      for XID negotiations can be provisioned via TdmaCs/* V42bis."
::= { mscTdmaBcV42BisOperEntry 5 }

mscTdmaBcV42BisLastDecodeError OBJECT-TYPE
   SYNTAX     INTEGER  {
                 none(0),
                 badStepup(1),
                 codewordEqC1(2),
                 emptyCodeword(3),
                 rsvdCommand(4),
                 generalError(5) }
   ACCESS     read-only
   STATUS     mandatory
   DESCRIPTION
     "This attribute indicates last error found by the decoder. This 
      attribute has one of the following values:
      none: No errors found.
      badStepup: Receipt of STEPUP (step up codeword size) codeword 
      when it would cause C2 (current code word size) to exceed N1 
      (maximum code word size).
      codewordEqC1: Receipt of a codeword, at any time, equal to C1 
      (next empty dictionary entry).
      emptyCodeword: Receipt of a codeword representing an empty 
      dictionary entry. 
      reservedCommand: Receipt of a reserved command code.
      generalError: Receipt of any other error.
      The action taken by V.42bis on detecting an error is provisioned via 
      TdmaCs/* V42bis."
   DEFVAL     { none }
::= { mscTdmaBcV42BisOperEntry 6 }

mscTdmaBcV42BisCompRatioEncoder OBJECT-TYPE
   SYNTAX     FixedPoint2 (0..30000)
   ACCESS     read-only
   STATUS     mandatory
   DESCRIPTION
     "This attribute indicates the number of uncompressed bytes divided 
      by the number of compressed bytes. A value greater than one means 
      that the data is being compressed. This is the compression ratio 
      achieved by the V.42bis encoder running on the Passport. This 
      attribute is relevant for both protocol modes transparent and 
      compressed as the encoder switches between the two modes."
::= { mscTdmaBcV42BisOperEntry 7 }

mscTdmaBcV42BisCompRatioDecoder OBJECT-TYPE
   SYNTAX     FixedPoint2 (0..30000)
   ACCESS     read-only
   STATUS     mandatory
   DESCRIPTION
     "This attribute indicates the number of uncompressed bytes divided 
      by the number of compressed bytes. A value greater than one means 
      that the data is being compressed. This is the compression ratio 
      achieved by the V.42bis encoder at the mobile or PSTN. This 
      attribute is relevant for both protocol modes transparent and 
      compressed as the encoder switches between the two modes."
::= { mscTdmaBcV42BisOperEntry 8 }

mscTdmaBcV42BisStatsTable OBJECT-TYPE
   SYNTAX     SEQUENCE OF MscTdmaBcV42BisStatsEntry
   ACCESS     not-accessible
   STATUS     mandatory
   DESCRIPTION
     "This group contains statistical attributes that measure the 
      performance of IwfV42bis."
::= { mscTdmaBcV42Bis 11 }

mscTdmaBcV42BisStatsEntry OBJECT-TYPE
   SYNTAX     MscTdmaBcV42BisStatsEntry
   ACCESS     not-accessible
   STATUS     mandatory
   DESCRIPTION
     "An entry in the mscTdmaBcV42BisStatsTable."
   INDEX {
      mscTdmaBcCsIndex,
      mscTdmaBcBcIndex,
      mscTdmaBcV42BisIndex }
::= { mscTdmaBcV42BisStatsTable 1 }

MscTdmaBcV42BisStatsEntry ::= SEQUENCE {
   mscTdmaBcV42BisModeChangesEncode
      Counter32,
   mscTdmaBcV42BisModeChangesDecode
      Counter32,
   mscTdmaBcV42BisResetsEncode
      Counter32,
   mscTdmaBcV42BisResetsDecode
      Counter32,
   mscTdmaBcV42BisReinitializations
      Counter32,
   mscTdmaBcV42BisErrorsInDecode
      Counter32 }

mscTdmaBcV42BisModeChangesEncode OBJECT-TYPE
   SYNTAX     Counter32 
   ACCESS     read-only
   STATUS     mandatory
   DESCRIPTION
     "This attribute counts the number of mode changes (from transparent 
      to compressed or from compressed to transparent) by the encoder.
      The counter wraps when it exceeds the maximum value."
::= { mscTdmaBcV42BisStatsEntry 1 }

mscTdmaBcV42BisModeChangesDecode OBJECT-TYPE
   SYNTAX     Counter32 
   ACCESS     read-only
   STATUS     mandatory
   DESCRIPTION
     "This attribute counts the number of mode changes (from transparent 
      to compressed or from compressed to transparent) by the decoder. 
      The mode changes are determined by the encoder at the mobile or 
      the PSTN.
      The counter wraps when it exceeds the maximum value."
::= { mscTdmaBcV42BisStatsEntry 2 }

mscTdmaBcV42BisResetsEncode OBJECT-TYPE
   SYNTAX     Counter32 
   ACCESS     read-only
   STATUS     mandatory
   DESCRIPTION
     "This attribute counts the number of resets sent by the encoder. A 
      reset is a command code sent by the encoder to force dictionary 
      reinitialization.
      The counter wraps when it exceeds the maximum value."
::= { mscTdmaBcV42BisStatsEntry 3 }

mscTdmaBcV42BisResetsDecode OBJECT-TYPE
   SYNTAX     Counter32 
   ACCESS     read-only
   STATUS     mandatory
   DESCRIPTION
     "This attribute counts the number of resets received by the decoder. 
      A reset is a command code sent by the encoder to force dictionary 
      reinitialization. The resets of the decoder are determined by the 
      encoder at the mobile or PSTN.
      The counter wraps when it exceeds the maximum value."
::= { mscTdmaBcV42BisStatsEntry 4 }

mscTdmaBcV42BisReinitializations OBJECT-TYPE
   SYNTAX     Counter32 
   ACCESS     read-only
   STATUS     mandatory
   DESCRIPTION
     "This attribute counts the number of times V.42bis is reinitialized 
      because of a destructive break (a destructive break is a break that 
      causes data to be discarded) occurring on the error-corrected 
      connection initiated by either the mobile or PSTN.
      The counter wraps when it exceeds the maximum value."
::= { mscTdmaBcV42BisStatsEntry 5 }

mscTdmaBcV42BisErrorsInDecode OBJECT-TYPE
   SYNTAX     Counter32 
   ACCESS     read-only
   STATUS     mandatory
   DESCRIPTION
     "This attribute counts the number of errors found by the decoder. 
      The errors could be any of the following:
      1.Receipt of STEPUP (step up codeword size) codeword when it 
      would cause C2 (current code word size) to exceed N1 (maximum 
      code word size).
      2. Receipt of a codeword, at any time, equal to C1 (next empty 
      dictionary entry).
      3. Receipt of a codeword representing an empty dictionary entry.
      4. Receipt of a reserved command code.
      5. Receipt of any other error.
      The counter wraps when it exceeds the maximum value.
      The action taken by V.42bis on detecting any of these errors is 
      provisioned via TdmaCs/* V42bis."
::= { mscTdmaBcV42BisStatsEntry 6 }


-- TdmaBc/<csIndex>,<bcIndex> UpperRelay
-- This component represents the group of measurements for the 
-- Upper Relay function established for each half of a DMS-MTX 
-- IWF asynchronous data or fax call (internally between the two 
-- TdmaIwfBearerChannels involved in a call) from this particular 
-- TdmaIwfBearerChannel perspective.

mscTdmaBcUr OBJECT IDENTIFIER ::= { mscTdmaBc 10 }



mscTdmaBcUrRowStatusTable OBJECT-TYPE
   SYNTAX     SEQUENCE OF MscTdmaBcUrRowStatusEntry
   ACCESS     not-accessible
   STATUS     mandatory
   DESCRIPTION
     "This entry controls the addition and deletion of 
      mscTdmaBcUr components."
::= { mscTdmaBcUr 1 }

mscTdmaBcUrRowStatusEntry OBJECT-TYPE
   SYNTAX     MscTdmaBcUrRowStatusEntry
   ACCESS     not-accessible
   STATUS     mandatory
   DESCRIPTION
     "A single entry in the table represents a single 
      mscTdmaBcUr component."
   INDEX {
      mscTdmaBcCsIndex,
      mscTdmaBcBcIndex,
      mscTdmaBcUrIndex }
::= { mscTdmaBcUrRowStatusTable 1 }

MscTdmaBcUrRowStatusEntry ::= SEQUENCE {
   mscTdmaBcUrRowStatus
      RowStatus,
   mscTdmaBcUrComponentName
      DisplayString,
   mscTdmaBcUrStorageType
      StorageType,
   mscTdmaBcUrIndex
      NonReplicated }

mscTdmaBcUrRowStatus OBJECT-TYPE
   SYNTAX     RowStatus 
   ACCESS     read-only
   STATUS     mandatory
   DESCRIPTION
     "This variable is used as the basis for SNMP naming of
      mscTdmaBcUr components.
      These components cannot be added nor deleted."
::= { mscTdmaBcUrRowStatusEntry 1 }

mscTdmaBcUrComponentName OBJECT-TYPE
   SYNTAX     DisplayString 
   ACCESS     read-only
   STATUS     mandatory
   DESCRIPTION
     "This variable provides the component's string name for
      use with the ASCII Console Interface"
::= { mscTdmaBcUrRowStatusEntry 2 }

mscTdmaBcUrStorageType OBJECT-TYPE
   SYNTAX     StorageType 
   ACCESS     read-only
   STATUS     mandatory
   DESCRIPTION
     "This variable represents the storage type value for the
      mscTdmaBcUr tables."
::= { mscTdmaBcUrRowStatusEntry 4 }

mscTdmaBcUrIndex OBJECT-TYPE
   SYNTAX     NonReplicated 
   ACCESS     not-accessible
   STATUS     mandatory
   DESCRIPTION
     "This variable represents the index for the mscTdmaBcUr tables."
::= { mscTdmaBcUrRowStatusEntry 10 }

mscTdmaBcUrOperTable OBJECT-TYPE
   SYNTAX     SEQUENCE OF MscTdmaBcUrOperEntry
   ACCESS     not-accessible
   STATUS     mandatory
   DESCRIPTION
     "This group contains operational attributes that measure the 
      performance of the UpperRelay."
::= { mscTdmaBcUr 10 }

mscTdmaBcUrOperEntry OBJECT-TYPE
   SYNTAX     MscTdmaBcUrOperEntry
   ACCESS     not-accessible
   STATUS     mandatory
   DESCRIPTION
     "An entry in the mscTdmaBcUrOperTable."
   INDEX {
      mscTdmaBcCsIndex,
      mscTdmaBcBcIndex,
      mscTdmaBcUrIndex }
::= { mscTdmaBcUrOperTable 1 }

MscTdmaBcUrOperEntry ::= SEQUENCE {
   mscTdmaBcUrRxBufferSize
      Unsigned32,
   mscTdmaBcUrTxFlowControlState
      INTEGER,
   mscTdmaBcUrRxFlowControlState
      INTEGER }

mscTdmaBcUrRxBufferSize OBJECT-TYPE
   SYNTAX     Unsigned32 (0..65535)
   ACCESS     read-only
   STATUS     mandatory
   DESCRIPTION
     "This attribute indicates the size of the receive flow control buffer.
      This attribute may be viewed via TdmaBc/*,*,*,* UpperRelay."
::= { mscTdmaBcUrOperEntry 1 }

mscTdmaBcUrTxFlowControlState OBJECT-TYPE
   SYNTAX     INTEGER  {
                 active(0),
                 inactive(1) }
   ACCESS     read-only
   STATUS     mandatory
   DESCRIPTION
     "This attribute indicates whether the transmit flow control is active or 
      not. This attribute has one of the following values:
      active: The transmit flow control is active.
      inactive: The transmit flow control is inactive.
      This attribute may be viewed via TdmaBc/*,*,*,* UpperRelay."
::= { mscTdmaBcUrOperEntry 2 }

mscTdmaBcUrRxFlowControlState OBJECT-TYPE
   SYNTAX     INTEGER  {
                 active(0),
                 inactive(1) }
   ACCESS     read-only
   STATUS     mandatory
   DESCRIPTION
     "This attribute indicates whether the receive flow control is active or 
      not. This attribute has one of the following values:
      active: The receive flow control is active.
      inactive: The receive flow control is inactive.
      This attribute may be viewed via TdmaBc/*,*,*,* UpperRelay."
::= { mscTdmaBcUrOperEntry 3 }

mscTdmaBcUrStatsTable OBJECT-TYPE
   SYNTAX     SEQUENCE OF MscTdmaBcUrStatsEntry
   ACCESS     not-accessible
   STATUS     mandatory
   DESCRIPTION
     "This group contains operational attributes that measure the 
      performance of the UpperRelay."
::= { mscTdmaBcUr 11 }

mscTdmaBcUrStatsEntry OBJECT-TYPE
   SYNTAX     MscTdmaBcUrStatsEntry
   ACCESS     not-accessible
   STATUS     mandatory
   DESCRIPTION
     "An entry in the mscTdmaBcUrStatsTable."
   INDEX {
      mscTdmaBcCsIndex,
      mscTdmaBcBcIndex,
      mscTdmaBcUrIndex }
::= { mscTdmaBcUrStatsTable 1 }

MscTdmaBcUrStatsEntry ::= SEQUENCE {
   mscTdmaBcUrTxFrames
      Counter32,
   mscTdmaBcUrRxFrames
      Counter32,
   mscTdmaBcUrUnacknowledgedFrames
      Counter32,
   mscTdmaBcUrCumUnacknowledgedFrames
      Counter32 }

mscTdmaBcUrTxFrames OBJECT-TYPE
   SYNTAX     Counter32 
   ACCESS     read-only
   STATUS     mandatory
   DESCRIPTION
     "This attribute counts the number of frames that are sent in the 
      transmit direction. The counter wraps when it exceeds the 
      maximum value.
      The counter wraps when it exceeds the maximum value."
::= { mscTdmaBcUrStatsEntry 1 }

mscTdmaBcUrRxFrames OBJECT-TYPE
   SYNTAX     Counter32 
   ACCESS     read-only
   STATUS     mandatory
   DESCRIPTION
     "This attribute counts the number of frames that are sent in the 
      receive direction.
      The counter wraps when it exceeds the maximum value."
::= { mscTdmaBcUrStatsEntry 2 }

mscTdmaBcUrUnacknowledgedFrames OBJECT-TYPE
   SYNTAX     Counter32 
   ACCESS     read-only
   STATUS     mandatory
   DESCRIPTION
     "This attribute indicates the current number of frames sent that have 
      not been acknowledged for this instance of the UpperRelay.
      The counter wraps when it exceeds the maximum value."
::= { mscTdmaBcUrStatsEntry 3 }

mscTdmaBcUrCumUnacknowledgedFrames OBJECT-TYPE
   SYNTAX     Counter32 
   ACCESS     read-only
   STATUS     mandatory
   DESCRIPTION
     "This attribute is the total number of unacknowledged frames for this 
      instance of the UpperRelay. It is not reset when a new call starts."
::= { mscTdmaBcUrStatsEntry 4 }




-- 
-- Version and Compliance statements
-- 



-- Object-Group Statement:
-- A list of all current accessible leaf objects.

-- OBJECTS { mscTdmaBcV42BisErrorsInDecode,
--           mscTdmaCsModemComponentName,
--           mscTdmaCsV42StorageType,
--           mscTdmaCsOperationalState,
--           mscTdmaBcV42ComponentName,
--           mscTdmaBcRlp1BadRxFrames,
--           mscTdmaCsErroredLFrames,
--           mscTdmaBcV42RemoteBusyIndications,
--           mscTdmaCsRlp1T1ResponseTimer,
--           mscTdmaCsV42BisStorageType,
--           mscTdmaBcFramerAdminState,
--           mscTdmaBcDscP2CompressionMaximumCharacters,
--           mscTdmaBcFaxTxPagesToMobile,
--           mscTdmaBcV42RetransmittedFrames,
--           mscTdmaBcModemOutbandBreak,
--           mscTdmaBcAdminState,
--           mscTdmaBcUrStorageType,
--           mscTdmaBcFramerRowStatus,
--           mscTdmaBcUrTxFrames,
--           mscTdmaCsV42BisP0CompressionDirection,
--           mscTdmaBcModemOutbandFlowControl,
--           mscTdmaBcRowStatus,
--           mscTdmaBcV42BisP0CompressionDirection,
--           mscTdmaBcUrUnacknowledgedFrames,
--           mscTdmaBcCustomerIdentifier,
--           mscTdmaCsVirtualRouterName,
--           mscTdmaCsLpStorageType,
--           mscTdmaBcFramerUsageState,
--           mscTdmaBcV42CrcErrorsRx,
--           mscTdmaBcUrRxFrames,
--           mscTdmaCsV42TxN401FrameSize,
--           mscTdmaCsFaxStorageType,
--           mscTdmaCsV42BisRowStatus,
--           mscTdmaCsCallsSetUp,
--           mscTdmaBcUsageState,
--           mscTdmaBcRlp1RowStatus,
--           mscTdmaBcFaxComponentName,
--           mscTdmaBcModemTxBytes,
--           mscTdmaBcV42BisModeChangesEncode,
--           mscTdmaBcFramerInterfaceName,
--           mscTdmaBcRlp1T1ResponseTimer,
--           mscTdmaCsDscK1Ll1WindowSize,
--           mscTdmaCsSupportedService,
--           mscTdmaBcV42BisCompRatioDecoder,
--           mscTdmaCsV42TxKWindowSize,
--           mscTdmaBcFramerOperationalState,
--           mscTdmaCsV42ComponentName,
--           mscTdmaBcModemComponentName,
--           mscTdmaCsV42FcsLength,
--           mscTdmaBcFaxMessageRate,
--           mscTdmaBcModemRxBytes,
--           mscTdmaCsModemStorageType,
--           mscTdmaCsDscComponentName,
--           mscTdmaCsLpRowStatus,
--           mscTdmaBcFramerFramingType,
--           mscTdmaBcModemFramingErrors,
--           mscTdmaCsLpModemsSupported,
--           mscTdmaBcV42BisProtocolModeDecoder,
--           mscTdmaBcModemVoiceLaw,
--           mscTdmaCsDceComponentName,
--           mscTdmaBcOperationalState,
--           mscTdmaBcUrComponentName,
--           mscTdmaCsCallsReleasedAbnormal,
--           mscTdmaBcV42ProtocolState,
--           mscTdmaBcDscP0CompressionDirection,
--           mscTdmaBcModemModemAlgorithmInUse,
--           mscTdmaBcLastResponseCode,
--           mscTdmaCsCurrentCalls,
--           mscTdmaBcV42BisModeChangesDecode,
--           mscTdmaCsDscK0Ll0WindowSize,
--           mscTdmaBcV42BisStorageType,
--           mscTdmaCsT999,
--           mscTdmaCsV42RxKWindowSize,
--           mscTdmaCsModemRowStatus,
--           mscTdmaBcRlp1T2LinkActivityTimer,
--           mscTdmaBcModemMobileSideFlowControlState,
--           mscTdmaBcRlp1Layer3L1ReqWinSize1,
--           mscTdmaCsRlp1T3PeerAckTimer,
--           mscTdmaCsLpActiveCalls,
--           mscTdmaBcV42BisReinitializations,
--           mscTdmaBcV42TxN401FrameSize,
--           mscTdmaBcFaxStorageType,
--           mscTdmaBcV42BisRowStatus,
--           mscTdmaCsComponentName,
--           mscTdmaCsV42BisP1MaximumCodewords,
--           mscTdmaCsCustomerIdentifier,
--           mscTdmaBcCallType,
--           mscTdmaBcRlp1TxFrames,
--           mscTdmaBcDscTxBytes,
--           mscTdmaBcV42V42BisActiveInCall,
--           mscTdmaBcV42BisLastDecodeError,
--           mscTdmaBcV42TxKWindowSize,
--           mscTdmaCsVoiceLaw,
--           mscTdmaCsV42BisActionOnError,
--           mscTdmaBcV42TxIFrames,
--           mscTdmaBcDscP1CompressionMaximumCodewords,
--           mscTdmaCsRlp1ComponentName,
--           mscTdmaBcModemStorageType,
--           mscTdmaBcDscComponentName,
--           mscTdmaCsMscIpAddress,
--           mscTdmaBcUrTxFlowControlState,
--           mscTdmaCsTIwf2,
--           mscTdmaCsDscStorageType,
--           mscTdmaBcFramerTxFrames,
--           mscTdmaBcV42LocalBusyIndications,
--           mscTdmaBcV42BisProtocolModeEncoder,
--           mscTdmaCsV42T402AckDelayTimer,
--           mscTdmaBcFaxRowStatus,
--           mscTdmaCsT308,
--           mscTdmaBcRlp1StorageType,
--           mscTdmaBcFaxRxPagesFromMobile,
--           mscTdmaCsV42T400DetectTimer,
--           mscTdmaCsDceStorageType,
--           mscTdmaCsCommentText,
--           mscTdmaBcV42RxIBytes,
--           mscTdmaCsV42N400RetransLimit,
--           mscTdmaCsRlp1T2LinkActivityTimer,
--           mscTdmaCsTIwf1,
--           mscTdmaBcUrRowStatus,
--           mscTdmaBcRlp1RxFrames,
--           mscTdmaBcDscRxBytes,
--           mscTdmaBcV42BisP2MaximumStringSize,
--           mscTdmaBcDceComponentName,
--           mscTdmaBcModemAutobaud,
--           mscTdmaCsV42RowStatus,
--           mscTdmaBcModemRowStatus,
--           mscTdmaBcFaxActiveMode,
--           mscTdmaBcV42RxN401FrameSize,
--           mscTdmaCsV42BisP2MaximumStringSize,
--           mscTdmaBcState,
--           mscTdmaCsDscRowStatus,
--           mscTdmaBcV42TxIBytes,
--           mscTdmaBcFramerComponentName,
--           mscTdmaBcUrRxFlowControlState,
--           mscTdmaBcFramerRxFrames,
--           mscTdmaBcV42RxKWindowSize,
--           mscTdmaBcComponentName,
--           mscTdmaCsDceRowStatus,
--           mscTdmaBcModemRate,
--           mscTdmaBcV42BisP1MaximumCodewords,
--           mscTdmaCsStorageType,
--           mscTdmaBcV42StorageType,
--           mscTdmaCsCallsRequested,
--           mscTdmaBcRlp1Layer3L0ReqWinSize,
--           mscTdmaBcV42BadFramesRx,
--           mscTdmaCsLpConfiguredBearerChannels,
--           mscTdmaBcUrRxBufferSize,
--           mscTdmaCsV42BisComponentName,
--           mscTdmaBcRlp1T3PeerAckTimer,
--           mscTdmaCsFaxRowStatus,
--           mscTdmaBcFramerRxBytes,
--           mscTdmaCsSupportedTechnology,
--           mscTdmaCsT305,
--           mscTdmaBcDscRowStatus,
--           mscTdmaCsRlp1StorageType,
--           mscTdmaBcDscStorageType,
--           mscTdmaBcV42BisResetsDecode,
--           mscTdmaCsAdminState,
--           mscTdmaBcV42V42ActiveInCall,
--           mscTdmaBcV42T1AckTimeouts,
--           mscTdmaBcUrCumUnacknowledgedFrames,
--           mscTdmaCsV42RxN401FrameSize,
--           mscTdmaBcRlp1ComponentName,
--           mscTdmaBcDceStorageType,
--           mscTdmaBcV42BisCompRatioEncoder,
--           mscTdmaCsRowStatus,
--           mscTdmaBcFaxProtocolState,
--           mscTdmaCsT313,
--           mscTdmaCsLpComponentName,
--           mscTdmaCsV42T401AckTimer,
--           mscTdmaBcV42RxIFrames,
--           mscTdmaBcModemAsyncMode,
--           mscTdmaCsFaxComponentName,
--           mscTdmaBcV42BisComponentName,
--           mscTdmaCsCallsReleasedNormal,
--           mscTdmaBcV42RowStatus,
--           mscTdmaBcStorageType,
--           mscTdmaCsUsageState,
--           mscTdmaCsRlp1RowStatus,
--           mscTdmaBcMateBearerChannel,
--           mscTdmaBcModemPstnSideFlowControlState,
--           mscTdmaCsT303,
--           mscTdmaBcModemProtocolState,
--           mscTdmaCsV42T403IdleProbeTimer,
--           mscTdmaBcFramerStorageType,
--           mscTdmaBcV42BisResetsEncode,
--           mscTdmaBcDceRowStatus }
-- STATUS  mandatory
-- DESCRIPTION
--   "A list of all current accessible leaf objects."

tdmaIwfGroup OBJECT IDENTIFIER ::= { tdmaIwfMIB 1 }
tdmaIwfGroupCA OBJECT IDENTIFIER ::= { tdmaIwfGroup 1 }
tdmaIwfGroupCA02 OBJECT IDENTIFIER ::= { tdmaIwfGroupCA 3 }
tdmaIwfGroupCA02A OBJECT IDENTIFIER ::= { tdmaIwfGroupCA02 2 }



-- Agent-Capabilities Statement:

-- PRODUCT-RELEASE "MscPassport Release 1.2 TdmaIwf."
-- STATUS          mandatory
-- DESCRIPTION     "Carrier Passport TdmaIwf MIB: MIB Version CA02A,
--                  Software Version CA02S9C."
-- SUPPORTS        Nortel-MsCarrier-MscPassport-TdmaIwfMIB
--    INCLUDES     { tdmaIwfGroupCA02A }

tdmaIwfCapabilities OBJECT IDENTIFIER ::= { tdmaIwfMIB 3 }
tdmaIwfCapabilitiesCA OBJECT IDENTIFIER ::= { tdmaIwfCapabilities 1 }
tdmaIwfCapabilitiesCA02 OBJECT IDENTIFIER ::= { tdmaIwfCapabilitiesCA 3 }
tdmaIwfCapabilitiesCA02A OBJECT IDENTIFIER ::= { tdmaIwfCapabilitiesCA02 2 }





END
