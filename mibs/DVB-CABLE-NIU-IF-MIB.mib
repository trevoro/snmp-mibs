-- extracted from draft-ietf-ipcdn-dvbniuif-mib-00.txt
-- at Thu Feb 15 06:04:08 2001

   DVB-CABLE-NIU-IF-MIB DEFINITIONS ::= BEGIN 
    
    
   IMPORTS 
       MODULE-IDENTITY, 
       OBJECT-TYPE, 
       Counter32, 
       Integer32, 
  
 
       Gauge32, 
       transmission 
           FROM SNMPv2-SMI 
       TruthValue
           FROM SNMPv2-TC 
       SnmpAdminString 
           FROM SNMP-FRAMEWORK-MIB 
       OBJECT-GROUP, 
       MODULE-COMPLIANCE 
           FROM SNMPv2-CONF 
       ifIndex 
           FROM IF-MIB; 
    
   dvbNiuIf MODULE-IDENTITY 
       LAST-UPDATED    "9912030000Z" 
       ORGANIZATION    "IETF IPCDN Working Group 
                        DVB/DAVIC Interoperability Consortium Technical 
                        Working Group" 
       CONTACT-INFO 
              "        Andrew Valentine 
               Postal: Engineering Design Centre 
                       Hughes Network Systems Ltd 
                       Saxon Street, 
                       Linford Wood, 
                       Milton Keynes. 
                       MK14 6LD 
                       ENGLAND 
    
                  Tel: +44 1908 221122 
                  Fax: +44 1908 221127 
               E-mail: a.valentine@eu.hns.com 
    
               IETF IPCDN Working Group 
               General Discussion: ipcdn@ietf.org 
               Subscribe: http://www.ietf.org/mailman/listinfo/ipcdn 
               Archive: ftp://ftp.ietf.org/ietf-mail-archive/ipcdn 
               Co-chairs: Richard Woundy, rwoundy@cisco.com 
                          Andrew Valentine, a.valentine@eu.hns.com" 
    
       DESCRIPTION     "The information module for the DVB interfaces 
                        found in an EuroModem." 
    
       REVISION        "9912030000Z" 
       DESCRIPTION     "The mib has been modified to incorporate the  
                        MAC states from dvbNiuOperStatus.  These are 
                        in dvbNiuMacStatStatus.  The compliance  
                        section has been fixed." 
    
    
       REVISION        "9910010000Z" 
       DESCRIPTION     "The mib has been modified to incorporate the  
                        comments made by the WGT during the  
                        27/28 Sep 1999 meeting.  The main areas 
  
 
                        affected are dvbNiuMacStatsTable and 
                        dvbNiuDsRfObjects" 
    
       REVISION        "9907281500Z" 
       DESCRIPTION     "The initial version of the MIB" 
   ::= {transmission 1} 
    
    
   dvbNiuMacObjects   OBJECT IDENTIFIER ::= {dvbNiuIf 1} 
   dvbNiuDsRfObjects  OBJECT IDENTIFIER ::= {dvbNiuIf 2} 
   dvbNiuUsRfObjects  OBJECT IDENTIFIER ::= {dvbNiuIf 3} 
   dvbNiuDvbIfConform OBJECT IDENTIFIER ::= {dvbNiuIf 4} 
    
   -- Define groups under dvbNiuMacObjects 
   dvbNiuMacCap     OBJECT IDENTIFIER ::= {dvbNiuMacObjects 1} 
   dvbNiuMacStats   OBJECT IDENTIFIER ::= {dvbNiuMacObjects 2} 
    
   -- Define groups under dvbNiuDsRfObjects 
   dvbNiuDsRfParam  OBJECT IDENTIFIER ::= {dvbNiuDsRfObjects 1} 
    
   -- Define groups under dvbNiuUsRfObjects 
   dvbNiuUsRfParam  OBJECT IDENTIFIER ::= {dvbNiuUsRfObjects 1} 
    
   --Define identifiers under dvbNiuDvbIfConform 
   dvbNiuIfCompliances  OBJECT IDENTIFIER ::= {dvbNiuDvbIfConform 1} 
   dvbNiuIfGroups       OBJECT IDENTIFIER ::= {dvbNiuDvbIfConform 2} 
    
    
   -- Definition of MIB objects 
    
   -- =============================================================== 
   -- =  Mac Capabilities Group                                     = 
   -- =============================================================== 
    
   -- MAC Capabilities table 
    
   dvbNiuMacCapTable OBJECT-TYPE 
       SYNTAX      SEQUENCE OF DvbNiuMacCapEntry 
       MAX-ACCESS  not-accessible 
       STATUS      current 
       DESCRIPTION 
           "This table contains all available MAC capabilites specified 
            in ETS 300 800 (8/3/1999) and identifies whether they are 
            supported on the MAC interface." 
   ::= { dvbNiuMacCap 1 } 
    
   dvbNiuMacCapEntry OBJECT-TYPE 
       SYNTAX      DvbNiuMacCapEntry 
       MAX-ACCESS  not-accessible 
       STATUS      current 
       DESCRIPTION 
           "A row provides the supported capabilities for a single MAC 
            interface.  An entry in this table exists for each ifEntry 
  
 
            with an ifType of dvbRccMacLayer." 
       INDEX { ifIndex } 
   ::= { dvbNiuMacCapTable 1 } 
    
   DvbNiuMacCapEntry ::= SEQUENCE {  
       dvbNiuMacCapVer          INTEGER, 
       dvbNiuMacCapEncap        BITS, 
       dvbNiuMacCapResReqCap    TruthValue, 
       dvbNiuMacCapFragMacMess  TruthValue, 
       dvbNiuMacCapSecSupp      TruthValue, 
       dvbNiuMacCapMinislots    TruthValue, 
       dvbNiuMacCapIbSig        TruthValue, 
       dvbNiuMacCapOobSig       TruthValue, 
       dvbNiuMacCapDsOobBr      BITS, 
       dvbNiuMacCapUsBr         BITS, 
       dvbNiuMacCapMaxConn      Gauge32, 
       dvbNiuMacCapOperation    INTEGER 
   } 
    
   dvbNiuMacCapVer OBJECT-TYPE 
       SYNTAX      INTEGER { 
                       davic11(1), 
                       davic12(2), 
                       en301199(20), 
                       ets300800v2(29), 
                       ets300800v1(30) 
                   } 
       MAX-ACCESS  read-only 
       STATUS      current 
       DESCRIPTION 
           "The mac protocol version." 
   ::= { dvbNiuMacCapEntry 1 } 
    
   dvbNiuMacCapEncap OBJECT-TYPE 
       SYNTAX      BITS { 
                       directIp(0), 
                       ethernetMacBridge(1), 
                       ppp(2) 
                   } 
       MAX-ACCESS  read-only 
       STATUS      current 
       DESCRIPTION 
           "This field is used to identify the encapsulation 
            types supported.  These can be direct IP, Ethernet MAC 
            bridging and PPP." 
   ::= { dvbNiuMacCapEntry 2 } 
    
    
   dvbNiuMacCapResReqCap OBJECT-TYPE 
       SYNTAX      TruthValue 
       MAX-ACCESS  read-only 
       STATUS      current 
       DESCRIPTION 
  
 
           "True if the NIU is able to send MAC Resource Request 
            Messages." 
   ::= { dvbNiuMacCapEntry 3 } 
    
   dvbNiuMacCapFragMacMess OBJECT-TYPE 
       SYNTAX      TruthValue 
       MAX-ACCESS  read-only 
       STATUS      current 
       DESCRIPTION 
           "True if the NIU supports fragemented MAC messages." 
   ::= { dvbNiuMacCapEntry 4 } 
    
   dvbNiuMacCapSecSupp OBJECT-TYPE 
       SYNTAX      TruthValue 
       MAX-ACCESS  read-only 
       STATUS      current 
       DESCRIPTION 
           "True if the NIU supports the security extensions defined 
            in ETS 300 800." 
   ::= { dvbNiuMacCapEntry 5 } 
    
   dvbNiuMacCapMinislots OBJECT-TYPE 
       SYNTAX      TruthValue 
       MAX-ACCESS  read-only 
       STATUS      current 
       DESCRIPTION 
           "True if the NIU is capable of utilising minislots." 
   ::= { dvbNiuMacCapEntry 6 } 
    
   dvbNiuMacCapIbSig OBJECT-TYPE 
       SYNTAX      TruthValue 
       MAX-ACCESS  read-only 
       STATUS      current 
       DESCRIPTION 
           "True if the NIU is capable of utilising in band  
            signalling." 
   ::= { dvbNiuMacCapEntry 7 } 
    
   dvbNiuMacCapOobSig OBJECT-TYPE 
       SYNTAX      TruthValue 
       MAX-ACCESS  read-only 
       STATUS      current 
       DESCRIPTION 
           "True if the NIU is capable of utilising out of band  
            signalling." 
   ::= { dvbNiuMacCapEntry 8 } 
    
   dvbNiuMacCapDsOobBr OBJECT-TYPE 
       SYNTAX      BITS { 
                       d1o544Mbit(0), 
                       d3o088Mbit(1)                     
                   } 
       MAX-ACCESS  read-only 
  
 
       STATUS      current 
       DESCRIPTION 
           "This field is used to identify the downstream out of band 
            bit rates supported. These are 1.544Mbit/s and 3.088Mbit/s. 
            If dvbNiuMacCapOobSig is false then the value of this  
            Object will be zero." 
   ::= { dvbNiuMacCapEntry 9 } 
    
   dvbNiuMacCapUsBr OBJECT-TYPE 
       SYNTAX      BITS { 
                       u256kbit(0), 
                       u1o544Mbit(1), 
                       u3o88Mbit(2), 
                       u6o176Mbit(3)                     
                   } 
       MAX-ACCESS  read-only 
       STATUS      current 
       DESCRIPTION 
           "This field is used to identify the upstream bit rates 
            supported.  These are 256kbit/s, 1.544Mbit/s, 3.088Mbit/s  
            and 6.176Mbit/s." 
   ::= { dvbNiuMacCapEntry 10 } 
    
   dvbNiuMacCapMaxConn OBJECT-TYPE 
       SYNTAX      Gauge32 
       MAX-ACCESS  read-only 
       STATUS      current 
       DESCRIPTION 
           "The maximum number of connections supported by the NIU." 
   ::= { dvbNiuMacCapEntry 11 } 
    
   dvbNiuMacCapOperation OBJECT-TYPE 
       SYNTAX      INTEGER { 
                       one-way(1), 
                       two-way(2) 
                   } 
       MAX-ACCESS  read-only 
       STATUS      current 
       DESCRIPTION 
           "The operational mode of the NIU, this can be either 
            one-way or two-way." 
   ::= { dvbNiuMacCapEntry 12 } 
    
   -- End of MAC capabilities table 
    
   -- =============================================================== 
   -- =  Mac Statistics Group                                       = 
   -- =============================================================== 
    
   -- MAC Statistics table 
    
   dvbNiuMacStatsTable OBJECT-TYPE 
       SYNTAX      SEQUENCE OF DvbNiuMacStatsEntry 
  
 
       MAX-ACCESS  not-accessible 
       STATUS      current 
       DESCRIPTION 
           "This table contains statistics/status associated with the  
            MAC interface.  Reading these statistics does not cause 
            the values to be reset.  If the statistics are read via a  
            MAC message they will be reset!   
    
            Note: The error statistics are represented by only 16 bits, 
            this is because the status message only uses 16 bits for  
            the values." 
   ::= { dvbNiuMacStats 1 } 
    
   dvbNiuMacStatsEntry OBJECT-TYPE 
       SYNTAX      DvbNiuMacStatsEntry 
       MAX-ACCESS  not-accessible 
       STATUS      current 
       DESCRIPTION 
           "A row provides the statistics/status for a single MAC 
            interface.  An entry in this table exists for each ifEntry 
            with an ifType of dvbRccMacLayer." 
       INDEX { ifIndex } 
   ::= { dvbNiuMacStatsTable 1 } 
    
   DvbNiuMacStatsEntry ::= SEQUENCE {  
       dvbNiuMacHwVer                SnmpAdminString, 
       dvbNiuMacStatStatus           INTEGER, 
       dvbNiuMacStatSlotCfgCrcErrs   Gauge32, 
       dvbNiuMacStatRsCorrErrs       Gauge32, 
       dvbNiuMacStatATMPacketLosses  Gauge32, 
       dvbNiuMacStatSlotConfigCount  Gauge32, 
       dvbNiuMacStatSlEsfCrcErrs     Gauge32, 
       dvbNiuMacStatRsErrCorrFrms    Gauge32, 
       dvbNiuMacStatRsErrNonCorrFrms Gauge32, 
       dvbNiuMacStatSlEsfFrameCount  Gauge32, 
       dvbNiuMacStatConCount         Gauge32
   } 
    
   dvbNiuMacHwVer OBJECT-TYPE 
       SYNTAX      SnmpAdminString 
       MAX-ACCESS  read-only 
       STATUS      current 
       DESCRIPTION 
           "The hardware version of the MAC interface.  The is a free 
            format text field." 
   ::= { dvbNiuMacStatsEntry 1 } 
    
   dvbNiuMacStatStatus OBJECT-TYPE 
       SYNTAX      INTEGER { 
                       scanningForCarrier(1), 
                       provisioning(2), 
                       invalidSTBNIU(3), 
                       timingRangingError(4), 
  
 
                       powerRangingError(5), 
                       running(6), 
                       stopped(7), 
                       none(8),                    
                       other(9) 
                   } 
       MAX-ACCESS  read-only 
       STATUS      current 
       DESCRIPTION 
           "The operational status of the NIU.  The statuses 1-8 are 
            from ETS 300 800.  The status other(9) is used for any case 
            that is not explicitly identified"     
   ::= { dvbNiuMacStatsEntry 2 } 
    
   dvbNiuMacStatSlotCfgCrcErrs OBJECT-TYPE 
       SYNTAX      Gauge32 (0..65535) 
       MAX-ACCESS  read-only 
       STATUS      current 
       DESCRIPTION 
           "Counts the number of errors in Slot_Configuration_Count 
            R bytes, as found by the CRC decoder.  This object is 
            initialized to 0 at boot and is reset only upon reboot or  
            by a MAC Status message." 
   ::= { dvbNiuMacStatsEntry 3 } 
    
   dvbNiuMacStatRsCorrErrs OBJECT-TYPE 
       SYNTAX      Gauge32 (0..65535) 
       MAX-ACCESS  read-only 
       STATUS      current 
       DESCRIPTION 
           "Counts the number of errors as corrected by the Reed  
            Solomon decoder.  This object is initialized to 0 at boot  
            and is reset only upon reboot or by a MAC Status message." 
   ::= { dvbNiuMacStatsEntry 4 } 
    
   dvbNiuMacStatATMPacketLosses OBJECT-TYPE 
       SYNTAX      Gauge32 (0..65535) 
       MAX-ACCESS  read-only 
       STATUS      current 
       DESCRIPTION 
           "Counts the number of received ATM cells that were lost,  
            either due to unrecoverable Reed Solomon errors or because 
            of an erroneous HEC of the ATM cells header.  This object 
            is initialized to 0 at boot and is reset only upon reboot  
            or by a MAC Status message." 
   ::= { dvbNiuMacStatsEntry 5 } 
    
   dvbNiuMacStatSlotConfigCount OBJECT-TYPE 
       SYNTAX      Gauge32 (0..65535) 
       MAX-ACCESS  read-only 
       STATUS      current 
       DESCRIPTION 
           "This refers to the number of R-byte sets (Rxa-Rxc) used to 
  
 
            calculate Slot_Configuration_CRC_Error_Count." 
   ::= { dvbNiuMacStatsEntry 6 } 
    
   dvbNiuMacStatSlEsfCrcErrs OBJECT-TYPE 
       SYNTAX      Gauge32 (0..65535) 
       MAX-ACCESS  read-only 
       STATUS      current 
       DESCRIPTION 
           "Counts the number of CRC errrors found in consecutive  
            C1-C6. 
            This object is initialized to 0 at boot and is reset only  
            upon reboot or by a MAC Status message." 
   ::= { dvbNiuMacStatsEntry 7 } 
    
   dvbNiuMacStatRsErrCorrFrms OBJECT-TYPE 
       SYNTAX      Gauge32 (0..65535) 
       MAX-ACCESS  read-only 
       STATUS      current 
       DESCRIPTION 
           "Counts the number of MPEG frames received with correctable 
            Reed Solomon errors (IB only).  This object is initialized 
            to 0 at boot and is reset only upon reboot or by a MAC  
            Status message." 
   ::= { dvbNiuMacStatsEntry 8 } 
    
   dvbNiuMacStatRsErrNonCorrFrms OBJECT-TYPE 
       SYNTAX      Gauge32 (0..65535) 
       MAX-ACCESS  read-only 
       STATUS      current 
       DESCRIPTION 
           "Counts the number of MPEG frames received with non  
            correctable Reed Solomon errors (IB only).  This object is 
            initialized to 0 at boot and is reset only upon reboot or 
            by a MAC Status message." 
   ::= { dvbNiuMacStatsEntry 9 } 
    
   dvbNiuMacStatSlEsfFrameCount OBJECT-TYPE 
       SYNTAX      Gauge32 (0..65535) 
       MAX-ACCESS  read-only 
       STATUS      current 
       DESCRIPTION 
           "This is the number of frames the statistics in this message 
            apply on." 
   ::= { dvbNiuMacStatsEntry 10 } 
    
   dvbNiuMacStatConCount OBJECT-TYPE 
       SYNTAX      Gauge32 
       MAX-ACCESS  read-only 
       STATUS      current 
       DESCRIPTION 
           "The number of active connections." 
   ::= { dvbNiuMacStatsEntry 11 } 
    
  
 
   -- End of MAC statistics table 
    
   -- =============================================================== 
   -- =  Downstream RF Parameters Group                             = 
   -- =============================================================== 
    
   -- Downstream RF parameters table 
    
   dvbNiuRfDsTable OBJECT-TYPE 
       SYNTAX      SEQUENCE OF DvbNiuRfDsEntry 
       MAX-ACCESS  not-accessible 
       STATUS      current 
       DESCRIPTION 
           "This table contains RF characteristcs and counters for the  
            downstream interfaces.  " 
   ::= { dvbNiuDsRfParam 1 } 
    
   dvbNiuRfDsEntry OBJECT-TYPE 
       SYNTAX      DvbNiuRfDsEntry 
       MAX-ACCESS  not-accessible 
       STATUS      current 
       DESCRIPTION 
           "A row provides the RF characteristcs, counters and possible 
            frequencies to use when locating a downstream channel for a  
            single downstream RF interface.  An entry in this 
            table exists for each ifEntry with an ifType of  
            dvbRccDownstream" 
       INDEX { ifIndex } 
   ::= { dvbNiuRfDsTable 1 } 
    
   DvbNiuRfDsEntry ::= SEQUENCE {  
       dvbNiuRfDsHwVer        SnmpAdminString, 
       dvbNiuRfDsLastGoodFreq Integer32, 
       dvbNiuRfDsBackupFreq   Integer32, 
       dvbNiuRfDsLowScanFreq  Integer32, 
       dvbNiuRfDsHighScanFreq Integer32, 
       dvbNiuRfDsScanStep     Integer32, 
       dvbNiuRfDsOobFreq      Integer32, 
       dvbNiuRfDsIbFreq       Integer32, 
       dvbNiuRfDsModType      INTEGER, 
       dvbNiuRfDsSnrEst       Integer32, 
       dvbNiuRfDsPwrLevelEst  Integer32 
   } 
    
   dvbNiuRfDsHwVer OBJECT-TYPE 
       SYNTAX      SnmpAdminString 
       MAX-ACCESS  read-only 
       STATUS      current 
       DESCRIPTION 
           "The hardware version of the downstream RF interface.  The  
            is a free format text field." 
   ::= { dvbNiuRfDsEntry 1 } 
    
  
 
   dvbNiuRfDsLastGoodFreq OBJECT-TYPE 
       SYNTAX      Integer32 (47000000..1000000000) 
       UNITS       "Hz" 
       MAX-ACCESS  read-only 
       STATUS      current 
       DESCRIPTION 
           "This is the last known good frequency for a downstream  
            channel and is used to locate the channel on power up or  
            reset.  If a downstream channel cannot be found at the 
            frequency held by this object then dvbNiuRfDsBackupFreq 
            is tried.  If dvbNiuRfDsBackupFreq fails then a frequency 
            scan is performed between dvbNiuRfDsMinScanFreq and  
            dvbNiuRfDsMaxScanFreq with a step size of  
            dvbNiuRfDsScanStep 
            This object will be updated with the freguency of the  
            channel found using the alternative frequencies." 
       DEFVAL      { 650000000 } 
   ::= { dvbNiuRfDsEntry 2 } 
    
   dvbNiuRfDsBackupFreq OBJECT-TYPE 
       SYNTAX      Integer32 (47000000..1000000000) 
       UNITS       "Hz" 
       MAX-ACCESS  read-write 
       STATUS      current 
       DESCRIPTION 
           "This is a backup frequency for the downstream channel.   
            This will be used if dvbNiuRfDsLastGoodFreq fails.  If this 
            frequency is successfully used then dvbNiuRfDsLastGoodFreq  
            is updated to contain it.  If dvbNiuRfDsBackupFreq fails 
            then a frequency scan is performed between  
            dvbNiuRfDsMinScanFreq and dvbNiuRfDsMaxScanFreq with a step 
            size of dvbNiuRfDsScanStep." 
       DEFVAL      { 450000000 } 
   ::= { dvbNiuRfDsEntry 3 } 
    
   dvbNiuRfDsLowScanFreq OBJECT-TYPE 
       SYNTAX      Integer32 (47000000..1000000000) 
       UNITS       "Hz" 
       MAX-ACCESS  read-write 
       STATUS      current 
       DESCRIPTION 
           "This is the start of the frequency range to be used 
            for scanning to find a downstream channel. If a downstream 
            channel is found then dvbNiuRfDsLastGoodFreq is updated to 
            contain the new frequency and the scan is terminated. 
            The step size used for the scan is dvbNiuRfDsScanStep." 
       DEFVAL      { 110000000 } 
   ::= { dvbNiuRfDsEntry 4 } 
    
   dvbNiuRfDsHighScanFreq OBJECT-TYPE 
       SYNTAX      Integer32 (47000000..1000000000) 
       UNITS       "Hz" 
       MAX-ACCESS  read-write 
  
 
       STATUS      current 
       DESCRIPTION 
           "This is the end of the frequency range to be used for  
            scanningscan to find a downstream channel.  If a downstream 
            channel is found then dvbNiuRfDsLastGoodFreq is updated to 
            contain the new frequency and the scan is terminated. 
            The step size used for the scan is dvbNiuRfDsScanStep." 
       DEFVAL      { 862000000 } 
   ::= { dvbNiuRfDsEntry 5 } 
    
   dvbNiuRfDsScanStep OBJECT-TYPE 
       SYNTAX      Integer32 (47000000..1000000000) 
       UNITS       "Hz" 
       MAX-ACCESS  read-write 
       STATUS      current 
       DESCRIPTION 
           "This is the step size to be used when scanning for a  
            downstream channel." 
       DEFVAL      { 62500 } 
   ::= { dvbNiuRfDsEntry 6 } 
    
    
   dvbNiuRfDsOobFreq OBJECT-TYPE 
       SYNTAX      Integer32 (47000000..1000000000) 
       UNITS       "Hz" 
       MAX-ACCESS  read-only 
       STATUS      current 
       DESCRIPTION 
           "The frequency of the current downstream out of band 
   channel." 
   ::= { dvbNiuRfDsEntry 7 } 
    
   dvbNiuRfDsIbFreq OBJECT-TYPE 
       SYNTAX      Integer32 (47000000..1000000000) 
       UNITS       "Hz" 
       MAX-ACCESS  read-only 
       STATUS      current 
       DESCRIPTION 
           "The frequency of the current downstream in band channel." 
   ::= { dvbNiuRfDsEntry 8 } 
    
    
   dvbNiuRfDsModType OBJECT-TYPE 
       SYNTAX INTEGER { 
           qpsk(2), 
           qam8(3), 
           qam16(4), 
           qam32(5), 
           qam64(6), 
           qam128(7), 
           qam256(8) 
       } 
       MAX-ACCESS  read-only 
  
 
       STATUS      current 
       DESCRIPTION 
           "The modulation type of the downstream channel." 
   ::= { dvbNiuRfDsEntry 9 } 
    
   dvbNiuRfDsSnrEst OBJECT-TYPE 
       SYNTAX      Integer32 (0..255) 
       UNITS       "dB*2" 
       MAX-ACCESS  read-only 
       STATUS      current 
       DESCRIPTION 
           "The estimated signal to noise ratio of the downstream 
            carrying MAC messages.  If the SNR cannot be estinmated 
            it will be 0." 
   ::= { dvbNiuRfDsEntry 10 } 
    
   dvbNiuRfDsPwrLevelEst OBJECT-TYPE 
       SYNTAX      Integer32 (0..255) 
       UNITS       "dBuV*2" 
       MAX-ACCESS  read-only 
       STATUS      current 
       DESCRIPTION 
           "The estimated power level of the downstream carrying 
            MAC messages.  If the power level cannot be estinmated 
            it will be 0." 
   ::= { dvbNiuRfDsEntry 11 } 
    
   -- End of downstream parameters table 
    
   -- =============================================================== 
   -- =  Upstream RF Parameters Group                               = 
   -- =============================================================== 
    
   -- Upstream RF parameters table 
    
   dvbNiuRfUsTable OBJECT-TYPE 
       SYNTAX      SEQUENCE OF DvbNiuRfUsEntry 
       MAX-ACCESS  not-accessible 
       STATUS      current 
       DESCRIPTION 
           "This table contains RF characteristcs and counters for the  
            upstream interfaces." 
   ::= { dvbNiuUsRfParam 1 } 
    
   dvbNiuRfUsEntry OBJECT-TYPE 
       SYNTAX      DvbNiuRfUsEntry 
       MAX-ACCESS  not-accessible 
       STATUS      current 
       DESCRIPTION 
           "A row provides the RF characteristcs and counters for a  
            single upstream RF interface.  An entry in this table 
            exists for each ifEntry with an ifType of dvbRccUpstream" 
       INDEX { ifIndex } 
  
 
   ::= { dvbNiuRfUsTable 1 } 
    
   DvbNiuRfUsEntry ::= SEQUENCE {  
       dvbNiuRfUsHwVer           SnmpAdminString, 
       dvbNiuRfUsFreq            Integer32, 
       dvbNiuRfUsPwrCtrlSetting  Integer32, 
       dvbNiuRfUsTimeOffsetValue Integer32 
   } 
    
   dvbNiuRfUsHwVer OBJECT-TYPE 
       SYNTAX      SnmpAdminString 
       MAX-ACCESS  read-only 
       STATUS      current 
       DESCRIPTION 
           "The hardware version of the upstream RF interface.  The  
            is a free format text field." 
   ::= { dvbNiuRfUsEntry 1 } 
    
   dvbNiuRfUsFreq OBJECT-TYPE 
       SYNTAX      Integer32 (5000000..65000000) 
       UNITS       "Hz" 
       MAX-ACCESS  read-only 
       STATUS      current 
       DESCRIPTION 
           "The frequency of the upstream channel." 
   ::= { dvbNiuRfUsEntry 2 } 
    
   dvbNiuRfUsPwrCtrlSetting OBJECT-TYPE 
       SYNTAX      Integer32 (0..255) 
       UNITS       "dBuV*2" 
       MAX-ACCESS  read-only 
       STATUS      current 
       DESCRIPTION 
           "The actual power used for the upstream transmission.  The 
            unit of measure is 0.5dBuV" 
   ::= { dvbNiuRfUsEntry 3 } 
    
   dvbNiuRfUsTimeOffsetValue OBJECT-TYPE 
       SYNTAX      Integer32 (-32768..32767) 
       UNITS       "100nsec" 
       MAX-ACCESS  read-only 
       STATUS      current 
       DESCRIPTION 
           "This represents a relative offset of the upstream  
            transmission timing.  A negative value indicates an 
            adjustment forward in time.  A positive value indicates 
            an adjustment back in time.  The unit of measure is 100  
            nsec" 
   ::= { dvbNiuRfUsEntry 4 } 
    
   -- End of upstream parameters table 
    
   -- Conformance statements  
  
 
    
   dvbNiuIfCompliance MODULE-COMPLIANCE 
       STATUS      current 
       DESCRIPTION 
           "The compliance statement for EuroModem NIUs  
            which implement the DVB-CABLE-NIU-IF-MIB MIB." 
       MODULE  -- dvbNiuIf 
           MANDATORY-GROUPS { dvbNiuMacGroup, 
                              dvbNiuDsRfParamGroup, 
                              dvbNiuUsRfParamGroup 
                            } 
   ::= { dvbNiuIfCompliances 1 } 
    
   dvbNiuMacGroup OBJECT-GROUP 
       OBJECTS     { 
                     dvbNiuMacHwVer, 
                     dvbNiuMacStatStatus, 
                     dvbNiuMacStatSlotCfgCrcErrs, 
                     dvbNiuMacStatRsCorrErrs, 
                     dvbNiuMacStatATMPacketLosses, 
                     dvbNiuMacStatSlotConfigCount, 
                     dvbNiuMacStatSlEsfCrcErrs, 
                     dvbNiuMacStatRsErrCorrFrms, 
                     dvbNiuMacStatRsErrNonCorrFrms, 
                     dvbNiuMacStatSlEsfFrameCount, 
                     dvbNiuMacStatConCount, 
                     dvbNiuMacCapOobSig, 
                     dvbNiuMacCapVer, 
                     dvbNiuMacCapEncap, 
                     dvbNiuMacCapMaxConn, 
                     dvbNiuMacCapUsBr, 
                     dvbNiuMacCapOperation, 
                     dvbNiuMacCapDsOobBr, 
                     dvbNiuMacCapResReqCap, 
                     dvbNiuMacCapFragMacMess, 
                     dvbNiuMacCapSecSupp, 
                     dvbNiuMacCapMinislots, 
                     dvbNiuMacCapIbSig 
                   } 
       STATUS      current 
       DESCRIPTION 
           "A collection of objects providing capabilities and 
            statistics for the MAC layer." 
   ::= { dvbNiuIfGroups 1 } 
    
   dvbNiuDsRfGroup OBJECT-GROUP 
       OBJECTS     { 
                     dvbNiuRfDsHwVer, 
                     dvbNiuRfDsLastGoodFreq, 
                     dvbNiuRfDsBackupFreq, 
                     dvbNiuRfDsLowScanFreq, 
                     dvbNiuRfDsHighScanFreg, 
                     dvbNiuRfDsScanStep, 
  
 
                     dvbNiuRfDsOobFreq, 
                     dvbNiuRfDsIbFreq, 
                     dvbNiuRfDsModType, 
                     dvbNiuRfDsSnrEst, 
                     dvbNiuRfDsPwrLevelEst 
                   } 
       STATUS      current 
       DESCRIPTION 
           "A collection of objects providing capabilities and 
            statistics for the downstream RF interface." 
   ::= { dvbNiuIfGroups 2 } 
    
   dvbNiuUsRfGroup OBJECT-GROUP 
       OBJECTS     { 
                     dvbNiuRfUsHwVer, 
                     dvbNiuRfUsFreq, 
                     dvbNiuRfUsPwrCtrlSetting, 
                     dvbNiuRfUsTimeOffsetValue 
                   } 
       STATUS      current 
       DESCRIPTION 
           "A collection of objects providing capabilities and 
            statistics for the upstream RF interface." 
   ::= { dvbNiuIfGroups 3 } 
    
    
   END 

--     
--      Copyright (C) The Internet Society (2000).  All Rights Reserved. 
--     
--    This document and translations of it may be copied and furnished to 
--    others, and derivative works that comment on or otherwise explain it 
--    or assist in its implementation may be prepared, copied, published 
--    and distributed, in whole or in part, without restriction of any 
--    kind, provided that the above copyright notice and this paragraph 
--    are included on all such copies and derivative works.  However, this 
--    document itself may not be modified in any way, such as by removing 
--    the copyright notice or references to the Internet Society or other 
--    Internet organizations, except as needed for the purpose of 
--    developing Internet standards in which case the procedures for 
--    copyrights defined in the Internet Standards process must be 
--    followed, or as required to translate it into languages other than 
--    English. 
--  
--    The limited permissions granted above are perpetual and will not be 
--    revoked by the Internet Society or its successors or assigns. 
--     
--    This document and the information contained herein is provided on an 
--    "AS IS" basis and THE INTERNET SOCIETY AND THE INTERNET ENGINEERING 
--    TASK FORCE DISCLAIMS ALL WARRANTIES, EXPRESS OR IMPLIED, INCLUDING 
--    BUT NOT LIMITED TO ANY WARRANTY THAT THE USE OF THE INFORMATION 
--    HEREIN WILL NOT INFRINGE ANY RIGHTS OR ANY IMPLIED WARRANTIES OF 
--    MERCHANTABILITY OR FITNESS FOR A PARTICULAR PURPOSE. 
--
