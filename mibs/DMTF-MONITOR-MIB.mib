DMTF-MONITOR-MIB DEFINITIONS ::= BEGIN

IMPORTS
	OBJECT-TYPE, NOTIFICATION-TYPE,
	MODULE-IDENTITY, enterprises, Counter32, Counter64, Gauge32, Integer32
		FROM SNMPv2-SMI
	DmiString,
	dmiEventDateTime,dmiCompId,dmiEventSeverity,
	dmiEventStateKey,dmiEventAssociatedGroup,
	dmiEventSystem,dmiEventSubSystem
		FROM DMTF-DMI-MIB;

DmiCounter		::= Counter32
DmiCounter64		::= Counter64
DmiGauge		::= Gauge32
DmiInteger		::= Integer32
DmiOctetstring		::= OCTET STRING
DmiCompId		::= INTEGER
DmiGroupId		::= INTEGER

dmtf                	OBJECT IDENTIFIER ::= { enterprises 412 }
dmtfStdMifs         	OBJECT IDENTIFIER ::= { dmtf 2 }
dmtfDynOids         	OBJECT IDENTIFIER ::= { dmtf 3 }

dmtfMonitorMIF MODULE-IDENTITY
     LAST-UPDATED "9710221800Z"
     ORGANIZATION "Desktop Management Task Force"
     CONTACT-INFO
          "         DMTF Technical Advisory Committee

		    Mailstop JF2-53
                    2111 N.E. 25th Avenue
                    Hillsboro, OR 97124

		    Phone: +1 503 264-9300
                    Email: dmtf-info@dmtf.org
          "
     DESCRIPTION
          "This MIB is a translation of the DMTF Monitor MIF
          based on the translation rules defined by the
          DMTF DMI to SNMP Mapping Standard, Version 1.0.

	  DMI-based systems running a DMI-to-SNMP Mapping
          Agent provide the ability to access DMI component
          instrumentation via SNMP protocol operations.
          "
::= { dmtfStdMifs 6 }

SdmtfMonitorAdditionalInformations ::= SEQUENCE {
	assetTag	DmiString,
	monitorLocation	DmiString,
	monitorPrimaryUserName	DmiString,
	monitorPrimaryUserPhone	DmiString
}

dmtfMonitorAdditionalInformationsTable OBJECT-TYPE
	SYNTAX		SEQUENCE OF SdmtfMonitorAdditionalInformations
	MAX-ACCESS	not-accessible
	STATUS		current
	DESCRIPTION	"This group gives more informations about this monitor."
	::= { dmtfMonitorMIF 1 }

dmtfMonitorAdditionalInformationsEntry OBJECT-TYPE
	SYNTAX		SdmtfMonitorAdditionalInformations
	MAX-ACCESS	not-accessible
	STATUS		current
	DESCRIPTION	"This group gives more informations about this monitor."
	INDEX		{ DmiCompId,DmiGroupId }
	::= { dmtfMonitorAdditionalInformationsTable 1 }


assetTag OBJECT-TYPE
	SYNTAX		DmiString
	MAX-ACCESS	read-write
	STATUS		current
	DESCRIPTION	"The monitor asset tag number"
	REFERENCE "'DMTF|Monitor Additional Informations|001' 1"
	::= { dmtfMonitorAdditionalInformationsEntry 1 }

monitorLocation OBJECT-TYPE
	SYNTAX		DmiString
	MAX-ACCESS	read-write
	STATUS		current
	DESCRIPTION	"The physical location of this monitor"
	REFERENCE "'DMTF|Monitor Additional Informations|001' 2"
	::= { dmtfMonitorAdditionalInformationsEntry 2 }

monitorPrimaryUserName OBJECT-TYPE
	SYNTAX		DmiString
	MAX-ACCESS	read-write
	STATUS		current
	DESCRIPTION	"The name of the primary user or owner of this monitor"
	REFERENCE "'DMTF|Monitor Additional Informations|001' 3"
	::= { dmtfMonitorAdditionalInformationsEntry 3 }

monitorPrimaryUserPhone OBJECT-TYPE
	SYNTAX		DmiString
	MAX-ACCESS	read-write
	STATUS		current
	DESCRIPTION	"the phone number of the primary user of this monitor"
	REFERENCE "'DMTF|Monitor Additional Informations|001' 4"
	::= { dmtfMonitorAdditionalInformationsEntry 4 }

SdmtfMonitorResolutions ::= SEQUENCE {
	dmtfMonitorResolutionsState INTEGER,
	monitorResolutionIndex	DmiInteger,
	horizontalResolution	DmiInteger,
	verticalResolution	DmiInteger,
	refreshRate	DmiInteger,
	verticalScanMode	DmiInteger,
	minimumMonitorRefreshRate	DmiInteger,
	maximumMonitorRefreshRate	DmiInteger
}

dmtfMonitorResolutionsTable OBJECT-TYPE
	SYNTAX		SEQUENCE OF SdmtfMonitorResolutions
	MAX-ACCESS	not-accessible
	STATUS		current
	DESCRIPTION	"This group defines all the resolutions supported by this
monitor"
	::= { dmtfMonitorMIF 2 }

dmtfMonitorResolutionsEntry OBJECT-TYPE
	SYNTAX		SdmtfMonitorResolutions
	MAX-ACCESS	not-accessible
	STATUS		current
	DESCRIPTION	"This group defines all the resolutions supported by this
monitor"
	INDEX		{ DmiCompId,DmiGroupId, monitorResolutionIndex }
	::= { dmtfMonitorResolutionsTable 1 }


dmtfMonitorResolutionsState OBJECT-TYPE
	SYNTAX		INTEGER {
		active(1),
		notInService(2),
		notReady(3),
		createAndGo(4),
		createAndWait(5),
		destroy(6)
	}
	MAX-ACCESS	read-write
	STATUS		current
	REFERENCE "'DMTF|Monitor Resolutions|002' 0"
	::= { dmtfMonitorResolutionsEntry 0 }

monitorResolutionIndex OBJECT-TYPE
	SYNTAX		DmiInteger
	MAX-ACCESS	read-only
	STATUS		current
	DESCRIPTION	"This is an index into the Monitor Resolution table."
	REFERENCE "'DMTF|Monitor Resolutions|002' 1"
	::= { dmtfMonitorResolutionsEntry 1 }

horizontalResolution OBJECT-TYPE
	SYNTAX		DmiInteger
	MAX-ACCESS	read-only
	STATUS		current
	DESCRIPTION	"Horizontal Resolution value in pixels"
	REFERENCE "'DMTF|Monitor Resolutions|002' 2"
	::= { dmtfMonitorResolutionsEntry 2 }

verticalResolution OBJECT-TYPE
	SYNTAX		DmiInteger
	MAX-ACCESS	read-only
	STATUS		current
	DESCRIPTION	"Vertical Resolution value in pixels"
	REFERENCE "'DMTF|Monitor Resolutions|002' 3"
	::= { dmtfMonitorResolutionsEntry 3 }

refreshRate OBJECT-TYPE
	SYNTAX		DmiInteger
	MAX-ACCESS	read-only
	STATUS		current
	DESCRIPTION	"Refresh Rate value for this resolution in Hz"
	REFERENCE "'DMTF|Monitor Resolutions|002' 4"
	::= { dmtfMonitorResolutionsEntry 4 }

verticalScanMode OBJECT-TYPE
	SYNTAX		INTEGER {
		other(1),
		unknown(2),
		unsupported(3),
		notInterlaced(4),
		interlaced(5)
	}
	MAX-ACCESS	read-only
	STATUS		current
	DESCRIPTION	"Vertical scan mode interlaced or not"
	REFERENCE "'DMTF|Monitor Resolutions|002' 5"
	::= { dmtfMonitorResolutionsEntry 5 }

minimumMonitorRefreshRate OBJECT-TYPE
	SYNTAX		DmiInteger
	MAX-ACCESS	read-only
	STATUS		current
	DESCRIPTION	"Minimum refresh rate value for this resolution for monitors
supporting a range of refresh rates."
	REFERENCE "'DMTF|Monitor Resolutions|002' 6"
	::= { dmtfMonitorResolutionsEntry 6 }

maximumMonitorRefreshRate OBJECT-TYPE
	SYNTAX		DmiInteger
	MAX-ACCESS	read-only
	STATUS		current
	DESCRIPTION	"Maximum refresh rate value for this resolution for monitors
supporting a range of refresh rates."
	REFERENCE "'DMTF|Monitor Resolutions|002' 7"
	::= { dmtfMonitorResolutionsEntry 7 }

END
