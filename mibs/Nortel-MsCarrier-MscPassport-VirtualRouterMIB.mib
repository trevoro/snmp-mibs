Nortel-MsCarrier-MscPassport-VirtualRouterMIB
DEFINITIONS ::= BEGIN



IMPORTS

      OBJECT-TYPE
   FROM RFC-1212

      mscPassportMIBs,
      mscComponents
   FROM Nortel-MsCarrier-MscPassport-UsefulDefinitionsMIB

      Counter32,
      RowPointer,
      DisplayString,
      StorageType,
      RowStatus,
      InterfaceIndex,
      Gauge32,
      Integer32,
      Unsigned32
   FROM Nortel-MsCarrier-MscPassport-StandardTextualConventionsMIB

      AsciiString,
      NonReplicated,
      HexString,
      Link,
      AsciiStringIndex,
      IntegerSequence
   FROM Nortel-MsCarrier-MscPassport-TextualConventionsMIB;




-- LAST-UPDATED   "9909010000Z"
-- ORGANIZATION   "Nortel Networks"
-- CONTACT-INFO   "
--         Nortel Carrier Data Network Management
--         
--         Postal:       P.O. Box 3511, Station C 
--                       Ottawa, Ontario 
--                       Canada  K1Y 4H7
--         
--         via the WEB:  http://www.nortelnetworks.com  
--                       select 'Contact Us' from the menu
--          
--         via phone:    1-800-4NORTEL"
-- DESCRIPTION
--    "The module describing the Nortel MsCarrier MscPassport
--     VirtualRouter Enterprise MIB."

virtualRouterMIB OBJECT IDENTIFIER ::= { mscPassportMIBs 26 }










-- Vr/<string>
-- The VirtualRouter component represents an instance of a Router on the 
-- platform. Vr provides a mechanism to segregate router traffic and 
-- maintenance activities based on a logical separation of ports into 
-- separate VirtualRouters.

mscVr OBJECT IDENTIFIER ::= { mscComponents 100 }



mscVrRowStatusTable OBJECT-TYPE
   SYNTAX     SEQUENCE OF MscVrRowStatusEntry
   ACCESS     not-accessible
   STATUS     mandatory
   DESCRIPTION
     "This entry controls the addition and deletion of 
      mscVr components."
::= { mscVr 1 }

mscVrRowStatusEntry OBJECT-TYPE
   SYNTAX     MscVrRowStatusEntry
   ACCESS     not-accessible
   STATUS     mandatory
   DESCRIPTION
     "A single entry in the table represents a single 
      mscVr component."
   INDEX {
      mscVrIndex }
::= { mscVrRowStatusTable 1 }

MscVrRowStatusEntry ::= SEQUENCE {
   mscVrRowStatus
      RowStatus,
   mscVrComponentName
      DisplayString,
   mscVrStorageType
      StorageType,
   mscVrIndex
      AsciiStringIndex }

mscVrRowStatus OBJECT-TYPE
   SYNTAX     RowStatus 
   ACCESS     read-write
   STATUS     mandatory
   DESCRIPTION
     "This variable is used as the basis for SNMP naming of
      mscVr components.
      These components can be added and deleted."
::= { mscVrRowStatusEntry 1 }

mscVrComponentName OBJECT-TYPE
   SYNTAX     DisplayString 
   ACCESS     read-only
   STATUS     mandatory
   DESCRIPTION
     "This variable provides the component's string name for
      use with the ASCII Console Interface"
::= { mscVrRowStatusEntry 2 }

mscVrStorageType OBJECT-TYPE
   SYNTAX     StorageType 
   ACCESS     read-only
   STATUS     mandatory
   DESCRIPTION
     "This variable represents the storage type value for the
      mscVr tables."
::= { mscVrRowStatusEntry 4 }

mscVrIndex OBJECT-TYPE
   SYNTAX     AsciiStringIndex (SIZE (1..8))
   ACCESS     not-accessible
   STATUS     mandatory
   DESCRIPTION
     "This variable represents the index for the mscVr tables."
::= { mscVrRowStatusEntry 10 }

mscVrAdminContorlTable OBJECT-TYPE
   SYNTAX     SEQUENCE OF MscVrAdminContorlEntry
   ACCESS     not-accessible
   STATUS     mandatory
   DESCRIPTION
     "This group includes the Administrative Control attribute. This 
      attribute defines the current administrative state of this component."
::= { mscVr 100 }

mscVrAdminContorlEntry OBJECT-TYPE
   SYNTAX     MscVrAdminContorlEntry
   ACCESS     not-accessible
   STATUS     mandatory
   DESCRIPTION
     "An entry in the mscVrAdminContorlTable."
   INDEX {
      mscVrIndex }
::= { mscVrAdminContorlTable 1 }

MscVrAdminContorlEntry ::= SEQUENCE {
   mscVrSnmpAdminStatus
      INTEGER,
   mscVrManagementAccess
      INTEGER,
   mscVrVirtualPrivateIntranetIdentifier
      INTEGER,
   mscVrVpnMode
      INTEGER }

mscVrSnmpAdminStatus OBJECT-TYPE
   SYNTAX     INTEGER  {
                 up(1),
                 down(2),
                 testing(3) }
   ACCESS     read-write
   STATUS     mandatory
   DESCRIPTION
     "This sets the desired state of this VirtualRouter. The up state   
      indicates the Vr is operational. The down state indicates the Vr is 
      not operational.  
      The down state is only valid when the managementAccess attribute 
      is disabled. Testing is an invalid state for the Vr."
   DEFVAL     { up }
::= { mscVrAdminContorlEntry 1 }

mscVrManagementAccess OBJECT-TYPE
   SYNTAX     INTEGER  {
                 disabled(0),
                 enabled(1) }
   ACCESS     read-write
   STATUS     mandatory
   DESCRIPTION
     "This attributes defines the routing capabilities of this Virtual Router
      and controls the TCP access into that Vr.  
      
      External access is only permitted through the Vr that has this     
      attribute enabled. 
      
      The attribute allows the following subcomponents to be
      provisioned: Ipx, Bridging, Sna, Sres, NetSentry, and Snmp.
      Exactly one Vr must have this attribute enabled.  
      
      The first provisioned Vr will have the attribute enabled by default.  
      Subsequent Vrs will have the attribute disabled."
::= { mscVrAdminContorlEntry 2 }

mscVrVirtualPrivateIntranetIdentifier OBJECT-TYPE
   SYNTAX     INTEGER (1..255)
   ACCESS     read-write
   STATUS     mandatory
   DESCRIPTION
     "Identifies the Virtual  Private Intranet (VPI) associated with this 
      Virtual Router. The vpiId must be unique for each VR on a    
      Passport and each interconnected VR must have the same vpiId."
::= { mscVrAdminContorlEntry 3 }

mscVrVpnMode OBJECT-TYPE
   SYNTAX     INTEGER  {
                 customer(0),
                 carrier(1) }
   ACCESS     read-write
   STATUS     mandatory
   DESCRIPTION
     "This attribute specifies if the virtual router behaves as a carrier 
      Virtual Router or a customer Virtual Router. 
      
      The value should be set to carrier only if this Virtual Router is part 
      of the backbone network of the Virtual Private Networks."
   DEFVAL     { customer }
::= { mscVrAdminContorlEntry 4 }

mscVrCidDataTable OBJECT-TYPE
   SYNTAX     SEQUENCE OF MscVrCidDataEntry
   ACCESS     not-accessible
   STATUS     mandatory
   DESCRIPTION
     "This group contains the attribute for a component's Customer 
      Identifier (CID). Refer to the attribute description for a detailed 
      explanation of CIDs."
::= { mscVr 101 }

mscVrCidDataEntry OBJECT-TYPE
   SYNTAX     MscVrCidDataEntry
   ACCESS     not-accessible
   STATUS     mandatory
   DESCRIPTION
     "An entry in the mscVrCidDataTable."
   INDEX {
      mscVrIndex }
::= { mscVrCidDataTable 1 }

MscVrCidDataEntry ::= SEQUENCE {
   mscVrCustomerIdentifier
      Unsigned32 }

mscVrCustomerIdentifier OBJECT-TYPE
   SYNTAX     Unsigned32 (0 | 1..8191)
   ACCESS     read-write
   STATUS     mandatory
   DESCRIPTION
     "This attribute holds the Customer Identifier (CID).
      
      Every component has a CID. If a component has a cid attribute, the 
      component's CID is the provisioned value of that attribute; 
      otherwise the component inherits the CID of its parent. The top-
      level component has a CID of 0.
      
      Every operator session also has a CID, which is the CID 
      provisioned for the operator's user ID. An operator will see only the 
      stream data for components having a matching CID. Also, the 
      operator will be allowed to issue commands for only those 
      components which have a matching CID.
      
      An operator CID of 0 is used to identify the Network Manager 
      (referred to as 'NetMan' in DPN). This CID matches the CID of 
      any component. Values 1 to 8191 inclusive (equivalent to 'basic 
      CIDs' in DPN) may be assigned to specific customers."
   DEFVAL     { 0 }
::= { mscVrCidDataEntry 1 }

mscVrOperStatusTable OBJECT-TYPE
   SYNTAX     SEQUENCE OF MscVrOperStatusEntry
   ACCESS     not-accessible
   STATUS     mandatory
   DESCRIPTION
     "This group includes the Operational Status attribute. This attribute 
      defines the current operational state of this component."
::= { mscVr 103 }

mscVrOperStatusEntry OBJECT-TYPE
   SYNTAX     MscVrOperStatusEntry
   ACCESS     not-accessible
   STATUS     mandatory
   DESCRIPTION
     "An entry in the mscVrOperStatusTable."
   INDEX {
      mscVrIndex }
::= { mscVrOperStatusTable 1 }

MscVrOperStatusEntry ::= SEQUENCE {
   mscVrSnmpOperStatus
      INTEGER }

mscVrSnmpOperStatus OBJECT-TYPE
   SYNTAX     INTEGER  {
                 up(1),
                 down(2),
                 testing(3) }
   ACCESS     read-only
   STATUS     mandatory
   DESCRIPTION
     "The current state of the interface. The up state indicates the 
      interface is operational and capable of forwarding packets. The 
      down state indicates the interface is not operational, thus unable to 
      forward packets. testing state indicates that no operational packets 
      can be passed."
   DEFVAL     { up }
::= { mscVrOperStatusEntry 1 }

mscVrStateTable OBJECT-TYPE
   SYNTAX     SEQUENCE OF MscVrStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { mscVr 104 }

mscVrStateEntry OBJECT-TYPE
   SYNTAX     MscVrStateEntry
   ACCESS     not-accessible
   STATUS     mandatory
   DESCRIPTION
     "An entry in the mscVrStateTable."
   INDEX {
      mscVrIndex }
::= { mscVrStateTable 1 }

MscVrStateEntry ::= SEQUENCE {
   mscVrAdminState
      INTEGER,
   mscVrOperationalState
      INTEGER,
   mscVrUsageState
      INTEGER }

mscVrAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { mscVrStateEntry 1 }

mscVrOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { mscVrStateEntry 2 }

mscVrUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { mscVrStateEntry 3 }

mscVrIfNumberOperTable OBJECT-TYPE
   SYNTAX     SEQUENCE OF MscVrIfNumberOperEntry
   ACCESS     not-accessible
   STATUS     mandatory
   DESCRIPTION
     "This group contains the ifNumber attribute."
::= { mscVr 105 }

mscVrIfNumberOperEntry OBJECT-TYPE
   SYNTAX     MscVrIfNumberOperEntry
   ACCESS     not-accessible
   STATUS     mandatory
   DESCRIPTION
     "An entry in the mscVrIfNumberOperTable."
   INDEX {
      mscVrIndex }
::= { mscVrIfNumberOperTable 1 }

MscVrIfNumberOperEntry ::= SEQUENCE {
   mscVrIfNumber
      Unsigned32 }

mscVrIfNumber OBJECT-TYPE
   SYNTAX     Unsigned32 (0..65535)
   ACCESS     read-only
   STATUS     mandatory
   DESCRIPTION
     "This attribute defines the number of IfEntries in the IfTable."
::= { mscVrIfNumberOperEntry 1 }


-- Vr/<string> Mm
-- The MemoryManagement component provides a mechanism which 
-- controls and monitors Dynamic Memory usage within a VirtualRouter. 
-- Upper layer protocols and other Vr subcomponents memory usage can 
-- be enforced using the provisioned attributes of this component.

mscVrMm OBJECT IDENTIFIER ::= { mscVr 2 }



mscVrMmRowStatusTable OBJECT-TYPE
   SYNTAX     SEQUENCE OF MscVrMmRowStatusEntry
   ACCESS     not-accessible
   STATUS     mandatory
   DESCRIPTION
     "This entry controls the addition and deletion of 
      mscVrMm components."
::= { mscVrMm 1 }

mscVrMmRowStatusEntry OBJECT-TYPE
   SYNTAX     MscVrMmRowStatusEntry
   ACCESS     not-accessible
   STATUS     mandatory
   DESCRIPTION
     "A single entry in the table represents a single 
      mscVrMm component."
   INDEX {
      mscVrIndex,
      mscVrMmIndex }
::= { mscVrMmRowStatusTable 1 }

MscVrMmRowStatusEntry ::= SEQUENCE {
   mscVrMmRowStatus
      RowStatus,
   mscVrMmComponentName
      DisplayString,
   mscVrMmStorageType
      StorageType,
   mscVrMmIndex
      NonReplicated }

mscVrMmRowStatus OBJECT-TYPE
   SYNTAX     RowStatus 
   ACCESS     read-only
   STATUS     mandatory
   DESCRIPTION
     "This variable is used as the basis for SNMP naming of
      mscVrMm components.
      These components cannot be added nor deleted."
::= { mscVrMmRowStatusEntry 1 }

mscVrMmComponentName OBJECT-TYPE
   SYNTAX     DisplayString 
   ACCESS     read-only
   STATUS     mandatory
   DESCRIPTION
     "This variable provides the component's string name for
      use with the ASCII Console Interface"
::= { mscVrMmRowStatusEntry 2 }

mscVrMmStorageType OBJECT-TYPE
   SYNTAX     StorageType 
   ACCESS     read-only
   STATUS     mandatory
   DESCRIPTION
     "This variable represents the storage type value for the
      mscVrMm tables."
::= { mscVrMmRowStatusEntry 4 }

mscVrMmIndex OBJECT-TYPE
   SYNTAX     NonReplicated 
   ACCESS     not-accessible
   STATUS     mandatory
   DESCRIPTION
     "This variable represents the index for the mscVrMm tables."
::= { mscVrMmRowStatusEntry 10 }

mscVrMmProvTable OBJECT-TYPE
   SYNTAX     SEQUENCE OF MscVrMmProvEntry
   ACCESS     not-accessible
   STATUS     mandatory
   DESCRIPTION
     "The group includes all provisioned attributes for the 
      MemoryManagement component."
::= { mscVrMm 10 }

mscVrMmProvEntry OBJECT-TYPE
   SYNTAX     MscVrMmProvEntry
   ACCESS     not-accessible
   STATUS     mandatory
   DESCRIPTION
     "An entry in the mscVrMmProvTable."
   INDEX {
      mscVrIndex,
      mscVrMmIndex }
::= { mscVrMmProvTable 1 }

MscVrMmProvEntry ::= SEQUENCE {
   mscVrMmVrMaxHeapSpace
      Unsigned32,
   mscVrMmIpMaxHeapSpace
      Unsigned32,
   mscVrMmIpxMaxHeapSpace
      Unsigned32,
   mscVrMmBridgingMaxHeapSpace
      Unsigned32,
   mscVrMmNetSentryMaxHeapSpace
      Unsigned32,
   mscVrMmSresMaxHeapSpace
      Unsigned32,
   mscVrMmSnaMaxHeapSpace
      Unsigned32 }

mscVrMmVrMaxHeapSpace OBJECT-TYPE
   SYNTAX     Unsigned32 (0..100)
   ACCESS     read-write
   STATUS     mandatory
   DESCRIPTION
     "The maximum percentage of the total system heap space that is 
      allowed for use by this Virtual Router. Memory allocation for this 
      VR which attempts to exceed this limit will fail causing a shut down 
      of the requesting process."
   DEFVAL     { 100 }
::= { mscVrMmProvEntry 1 }

mscVrMmIpMaxHeapSpace OBJECT-TYPE
   SYNTAX     Unsigned32 (0..100)
   ACCESS     read-write
   STATUS     mandatory
   DESCRIPTION
     "The maximum percentage of this VR's dynamic memory which can be 
      allocated to this VR's IP. An attempt to allocate memory in excess of 
      this limit forces IP to shut down."
   DEFVAL     { 100 }
::= { mscVrMmProvEntry 2 }

mscVrMmIpxMaxHeapSpace OBJECT-TYPE
   SYNTAX     Unsigned32 (0..100)
   ACCESS     read-write
   STATUS     mandatory
   DESCRIPTION
     "The maximum percentage of this VR's dynamic memory which can be 
      allocated to this VR's IPX. An attempt to allocate memory in excess of 
      this limit forces IPX to shut down."
   DEFVAL     { 100 }
::= { mscVrMmProvEntry 3 }

mscVrMmBridgingMaxHeapSpace OBJECT-TYPE
   SYNTAX     Unsigned32 (0..100)
   ACCESS     read-write
   STATUS     mandatory
   DESCRIPTION
     "The maximum percentage of this VR's dynamic memory which can be 
      allocated to this VR's Bridging. An attempt to allocate memory in 
      excess of this limit forces Bridging to shut down."
   DEFVAL     { 100 }
::= { mscVrMmProvEntry 6 }

mscVrMmNetSentryMaxHeapSpace OBJECT-TYPE
   SYNTAX     Unsigned32 (0..100)
   ACCESS     read-write
   STATUS     mandatory
   DESCRIPTION
     "The maximum percentage of this VR's dynamic memory which can be 
      allocated to this VR's NetSentry. An attempt to allocate memory in 
      excess of this limit forces NetSentry to shut down."
   DEFVAL     { 100 }
::= { mscVrMmProvEntry 7 }

mscVrMmSresMaxHeapSpace OBJECT-TYPE
   SYNTAX     Unsigned32 (0..100)
   ACCESS     read-write
   STATUS     mandatory
   DESCRIPTION
     "The maximum percentage of this VR's dynamic memory which can 
      be allocated to this VR's SourceRouteEndStation. An attempt to 
      allocate memory in excess of this limit forces 
      SourceRouteEndStation to shut down."
   DEFVAL     { 100 }
::= { mscVrMmProvEntry 8 }

mscVrMmSnaMaxHeapSpace OBJECT-TYPE
   SYNTAX     Unsigned32 (0..100)
   ACCESS     read-write
   STATUS     mandatory
   DESCRIPTION
     "The maximum percentage of this VR's dynamic memory which can 
      be allocated to this VR's SNA. An attempt to allocate memory in 
      excess of this limit forces SNA to shut down."
   DEFVAL     { 100 }
::= { mscVrMmProvEntry 9 }

mscVrMmOperTable OBJECT-TYPE
   SYNTAX     SEQUENCE OF MscVrMmOperEntry
   ACCESS     not-accessible
   STATUS     mandatory
   DESCRIPTION
     "The group includes all operational attributes for the 
      MemoryManagement component."
::= { mscVrMm 11 }

mscVrMmOperEntry OBJECT-TYPE
   SYNTAX     MscVrMmOperEntry
   ACCESS     not-accessible
   STATUS     mandatory
   DESCRIPTION
     "An entry in the mscVrMmOperTable."
   INDEX {
      mscVrIndex,
      mscVrMmIndex }
::= { mscVrMmOperTable 1 }

MscVrMmOperEntry ::= SEQUENCE {
   mscVrMmVrHeapSpaceBytesAllocated
      Unsigned32,
   mscVrMmVrHeapSpaceAllocated
      Unsigned32,
   mscVrMmIpHeapSpaceAllocated
      Unsigned32,
   mscVrMmIpxHeapSpaceAllocated
      Unsigned32,
   mscVrMmBridgingHeapSpaceAllocated
      Unsigned32,
   mscVrMmNetSentryHeapSpaceAllocated
      Unsigned32,
   mscVrMmSresHeapSpaceAllocated
      Unsigned32,
   mscVrMmSnaHeapSpaceAllocated
      Unsigned32 }

mscVrMmVrHeapSpaceBytesAllocated OBJECT-TYPE
   SYNTAX     Unsigned32 (0..4294967295)
   ACCESS     read-only
   STATUS     mandatory
   DESCRIPTION
     "The number of bytes of system dynamic memory which has been 
      allocated by this Virtual Router."
::= { mscVrMmOperEntry 1 }

mscVrMmVrHeapSpaceAllocated OBJECT-TYPE
   SYNTAX     Unsigned32 (0..100)
   ACCESS     read-only
   STATUS     mandatory
   DESCRIPTION
     "The percentage of system dynamic memory which is currently allocated 
      to this Virtual Router."
::= { mscVrMmOperEntry 2 }

mscVrMmIpHeapSpaceAllocated OBJECT-TYPE
   SYNTAX     Unsigned32 (0..100)
   ACCESS     read-only
   STATUS     mandatory
   DESCRIPTION
     "The percentage of this Virtual Router's dynamic memory which is 
      currently allocated to this Virtual Router's IP."
::= { mscVrMmOperEntry 3 }

mscVrMmIpxHeapSpaceAllocated OBJECT-TYPE
   SYNTAX     Unsigned32 (0..100)
   ACCESS     read-only
   STATUS     mandatory
   DESCRIPTION
     "The percentage of this Virtual Router's dynamic memory which is 
      currently allocated to this Virtual Router's IPX."
   DEFVAL     { 100 }
::= { mscVrMmOperEntry 4 }

mscVrMmBridgingHeapSpaceAllocated OBJECT-TYPE
   SYNTAX     Unsigned32 (0..100)
   ACCESS     read-only
   STATUS     mandatory
   DESCRIPTION
     "The percentage of this Virtual Router's dynamic memory which is 
      currently allocated to this Virtual Router's Bridging."
::= { mscVrMmOperEntry 7 }

mscVrMmNetSentryHeapSpaceAllocated OBJECT-TYPE
   SYNTAX     Unsigned32 (0..100)
   ACCESS     read-only
   STATUS     mandatory
   DESCRIPTION
     "The percentage of this Virtual Router's dynamic memory which is 
      currently allocated to this Virtual Router's NetSentry."
::= { mscVrMmOperEntry 8 }

mscVrMmSresHeapSpaceAllocated OBJECT-TYPE
   SYNTAX     Unsigned32 (0..100)
   ACCESS     read-only
   STATUS     mandatory
   DESCRIPTION
     "The percentage of this Virtual Router's dynamic memory which is 
      currently allocated to this Virtual Router's Source Route End Station."
::= { mscVrMmOperEntry 9 }

mscVrMmSnaHeapSpaceAllocated OBJECT-TYPE
   SYNTAX     Unsigned32 (0..100)
   ACCESS     read-only
   STATUS     mandatory
   DESCRIPTION
     "The percentage of this Virtual Router's dynamic memory which is 
      currently allocated to this Virtual Router's SNA."
::= { mscVrMmOperEntry 10 }


-- Vr/<string> Pp/<string>
-- This component represents a logical interface to the network. 
-- Protocol Ports are associated with physical or logical media via a 
-- linkage attribute. Protocol Ports allow for individual upper layer 
-- protocols to be enabled or disabled. 

mscVrPp OBJECT IDENTIFIER ::= { mscVr 3 }



mscVrPpRowStatusTable OBJECT-TYPE
   SYNTAX     SEQUENCE OF MscVrPpRowStatusEntry
   ACCESS     not-accessible
   STATUS     mandatory
   DESCRIPTION
     "This entry controls the addition and deletion of 
      mscVrPp components."
::= { mscVrPp 1 }

mscVrPpRowStatusEntry OBJECT-TYPE
   SYNTAX     MscVrPpRowStatusEntry
   ACCESS     not-accessible
   STATUS     mandatory
   DESCRIPTION
     "A single entry in the table represents a single 
      mscVrPp component."
   INDEX {
      mscVrIndex,
      mscVrPpIndex }
::= { mscVrPpRowStatusTable 1 }

MscVrPpRowStatusEntry ::= SEQUENCE {
   mscVrPpRowStatus
      RowStatus,
   mscVrPpComponentName
      DisplayString,
   mscVrPpStorageType
      StorageType,
   mscVrPpIndex
      AsciiStringIndex }

mscVrPpRowStatus OBJECT-TYPE
   SYNTAX     RowStatus 
   ACCESS     read-write
   STATUS     mandatory
   DESCRIPTION
     "This variable is used as the basis for SNMP naming of
      mscVrPp components.
      These components can be added and deleted."
::= { mscVrPpRowStatusEntry 1 }

mscVrPpComponentName OBJECT-TYPE
   SYNTAX     DisplayString 
   ACCESS     read-only
   STATUS     mandatory
   DESCRIPTION
     "This variable provides the component's string name for
      use with the ASCII Console Interface"
::= { mscVrPpRowStatusEntry 2 }

mscVrPpStorageType OBJECT-TYPE
   SYNTAX     StorageType 
   ACCESS     read-only
   STATUS     mandatory
   DESCRIPTION
     "This variable represents the storage type value for the
      mscVrPp tables."
::= { mscVrPpRowStatusEntry 4 }

mscVrPpIndex OBJECT-TYPE
   SYNTAX     AsciiStringIndex (SIZE (1..20))
   ACCESS     not-accessible
   STATUS     mandatory
   DESCRIPTION
     "This variable represents the index for the mscVrPp tables."
::= { mscVrPpRowStatusEntry 10 }

mscVrPpAdminControlTable OBJECT-TYPE
   SYNTAX     SEQUENCE OF MscVrPpAdminControlEntry
   ACCESS     not-accessible
   STATUS     mandatory
   DESCRIPTION
     "This group includes the Administrative Control attribute. This 
      attribute defines the current administrative state of this component."
::= { mscVrPp 100 }

mscVrPpAdminControlEntry OBJECT-TYPE
   SYNTAX     MscVrPpAdminControlEntry
   ACCESS     not-accessible
   STATUS     mandatory
   DESCRIPTION
     "An entry in the mscVrPpAdminControlTable."
   INDEX {
      mscVrIndex,
      mscVrPpIndex }
::= { mscVrPpAdminControlTable 1 }

MscVrPpAdminControlEntry ::= SEQUENCE {
   mscVrPpSnmpAdminStatus
      INTEGER }

mscVrPpSnmpAdminStatus OBJECT-TYPE
   SYNTAX     INTEGER  {
                 up(1),
                 down(2),
                 testing(3) }
   ACCESS     read-write
   STATUS     mandatory
   DESCRIPTION
     "The desired state of the interface. The up state indicates the 
      interface is operational and packet forwarding is allowed. The down 
      state indicates the interface is not operational and packet forwarding 
      is unavailable. The testing state indicates that no operational 
      packets can be passed."
   DEFVAL     { up }
::= { mscVrPpAdminControlEntry 1 }

mscVrPpProvTable OBJECT-TYPE
   SYNTAX     SEQUENCE OF MscVrPpProvEntry
   ACCESS     not-accessible
   STATUS     mandatory
   DESCRIPTION
     "This group includes provisioned attributes specific to the ProtocolPort 
      component."
::= { mscVrPp 101 }

mscVrPpProvEntry OBJECT-TYPE
   SYNTAX     MscVrPpProvEntry
   ACCESS     not-accessible
   STATUS     mandatory
   DESCRIPTION
     "An entry in the mscVrPpProvTable."
   INDEX {
      mscVrIndex,
      mscVrPpIndex }
::= { mscVrPpProvTable 1 }

MscVrPpProvEntry ::= SEQUENCE {
   mscVrPpLinkToMedia
      Link }

mscVrPpLinkToMedia OBJECT-TYPE
   SYNTAX     Link 
   ACCESS     read-write
   STATUS     mandatory
   DESCRIPTION
     "This attribute defines the Media Application which this Protocol Port is 
      using as an interface to the network."
::= { mscVrPpProvEntry 1 }

mscVrPpOperStatusTable OBJECT-TYPE
   SYNTAX     SEQUENCE OF MscVrPpOperStatusEntry
   ACCESS     not-accessible
   STATUS     mandatory
   DESCRIPTION
     "This group includes the Operational Status attribute. This attribute 
      defines the current operational state of this component."
::= { mscVrPp 102 }

mscVrPpOperStatusEntry OBJECT-TYPE
   SYNTAX     MscVrPpOperStatusEntry
   ACCESS     not-accessible
   STATUS     mandatory
   DESCRIPTION
     "An entry in the mscVrPpOperStatusTable."
   INDEX {
      mscVrIndex,
      mscVrPpIndex }
::= { mscVrPpOperStatusTable 1 }

MscVrPpOperStatusEntry ::= SEQUENCE {
   mscVrPpSnmpOperStatus
      INTEGER }

mscVrPpSnmpOperStatus OBJECT-TYPE
   SYNTAX     INTEGER  {
                 up(1),
                 down(2),
                 testing(3) }
   ACCESS     read-only
   STATUS     mandatory
   DESCRIPTION
     "The current state of the interface. The up state indicates the 
      interface is operational and capable of forwarding packets. The 
      down state indicates the interface is not operational, thus unable to 
      forward packets. testing state indicates that no operational packets 
      can be passed."
   DEFVAL     { up }
::= { mscVrPpOperStatusEntry 1 }

mscVrPpStateTable OBJECT-TYPE
   SYNTAX     SEQUENCE OF MscVrPpStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { mscVrPp 103 }

mscVrPpStateEntry OBJECT-TYPE
   SYNTAX     MscVrPpStateEntry
   ACCESS     not-accessible
   STATUS     mandatory
   DESCRIPTION
     "An entry in the mscVrPpStateTable."
   INDEX {
      mscVrIndex,
      mscVrPpIndex }
::= { mscVrPpStateTable 1 }

MscVrPpStateEntry ::= SEQUENCE {
   mscVrPpAdminState
      INTEGER,
   mscVrPpOperationalState
      INTEGER,
   mscVrPpUsageState
      INTEGER }

mscVrPpAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { mscVrPpStateEntry 1 }

mscVrPpOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { mscVrPpStateEntry 2 }

mscVrPpUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { mscVrPpStateEntry 3 }

mscVrPpOperTable OBJECT-TYPE
   SYNTAX     SEQUENCE OF MscVrPpOperEntry
   ACCESS     not-accessible
   STATUS     mandatory
   DESCRIPTION
     "This group includes operational attributes specific to the 
      ProtocolPort component."
::= { mscVrPp 104 }

mscVrPpOperEntry OBJECT-TYPE
   SYNTAX     MscVrPpOperEntry
   ACCESS     not-accessible
   STATUS     mandatory
   DESCRIPTION
     "An entry in the mscVrPpOperTable."
   INDEX {
      mscVrIndex,
      mscVrPpIndex }
::= { mscVrPpOperTable 1 }

MscVrPpOperEntry ::= SEQUENCE {
   mscVrPpIfIndex
      InterfaceIndex }

mscVrPpIfIndex OBJECT-TYPE
   SYNTAX     InterfaceIndex (1..65535)
   ACCESS     read-only
   STATUS     mandatory
   DESCRIPTION
     "This represents the SNMP ifIndex which is associated with this PP. 
      This ifIndex can be used to extract detailed information about the 
      PP from the ifTable."
::= { mscVrPpOperEntry 1 }

mscVrPpNbmaAddressTable OBJECT-TYPE
   SYNTAX     SEQUENCE OF MscVrPpNbmaAddressEntry
   ACCESS     not-accessible
   STATUS     mandatory
   DESCRIPTION
     "This group contains the operational attributes of the ProtocolPort 
      component specific to NHRP."
::= { mscVrPp 105 }

mscVrPpNbmaAddressEntry OBJECT-TYPE
   SYNTAX     MscVrPpNbmaAddressEntry
   ACCESS     not-accessible
   STATUS     mandatory
   DESCRIPTION
     "An entry in the mscVrPpNbmaAddressTable."
   INDEX {
      mscVrIndex,
      mscVrPpIndex }
::= { mscVrPpNbmaAddressTable 1 }

MscVrPpNbmaAddressEntry ::= SEQUENCE {
   mscVrPpAtmAddress
      HexString }

mscVrPpAtmAddress OBJECT-TYPE
   SYNTAX     HexString (SIZE (0..20))
   ACCESS     read-only
   STATUS     mandatory
   DESCRIPTION
     "This attribute indicates the ATM address which is associated with this 
      protocol port. NHRP uses this address to establish shortcut connections. 
      This attribute is not displayed if NHRP is not provisioned on this 
      protocol port."
::= { mscVrPpNbmaAddressEntry 1 }

-- 
-- *** THIS SUBTREE CURRENTLY NOT IMPLEMENTED ***
-- 

-- Vr/<string> IfTableEntry/n
-- Each instance of this component represents one row in the IfTable 
-- as defined in rfc1213. One entry will exist for each ProtocolPort 
-- defined under this VirtualRouter. If this is the management Vr, an 
-- entry also exists for each physical interface defined. 

mscVrIfTableEntry OBJECT IDENTIFIER ::= { mscVr 10 }



mscVrIfTableEntryRowStatusTable OBJECT-TYPE
   SYNTAX     SEQUENCE OF MscVrIfTableEntryRowStatusEntry
   ACCESS     not-accessible
   STATUS     mandatory
   DESCRIPTION
     "*** THIS TABLE CURRENTLY NOT IMPLEMENTED ***

      This entry controls the addition and deletion of 
      mscVrIfTableEntry components."
::= { mscVrIfTableEntry 1 }

mscVrIfTableEntryRowStatusEntry OBJECT-TYPE
   SYNTAX     MscVrIfTableEntryRowStatusEntry
   ACCESS     not-accessible
   STATUS     mandatory
   DESCRIPTION
     "A single entry in the table represents a single 
      mscVrIfTableEntry component."
   INDEX {
      mscVrIndex,
      mscVrIfTableEntryIndex }
::= { mscVrIfTableEntryRowStatusTable 1 }

MscVrIfTableEntryRowStatusEntry ::= SEQUENCE {
   mscVrIfTableEntryRowStatus
      RowStatus,
   mscVrIfTableEntryComponentName
      DisplayString,
   mscVrIfTableEntryStorageType
      StorageType,
   mscVrIfTableEntryIndex
      Integer32 }

mscVrIfTableEntryRowStatus OBJECT-TYPE
   SYNTAX     RowStatus 
   ACCESS     read-only
   STATUS     mandatory
   DESCRIPTION
     "This variable is used as the basis for SNMP naming of
      mscVrIfTableEntry components.
      These components cannot be added nor deleted."
::= { mscVrIfTableEntryRowStatusEntry 1 }

mscVrIfTableEntryComponentName OBJECT-TYPE
   SYNTAX     DisplayString 
   ACCESS     read-only
   STATUS     mandatory
   DESCRIPTION
     "This variable provides the component's string name for
      use with the ASCII Console Interface"
::= { mscVrIfTableEntryRowStatusEntry 2 }

mscVrIfTableEntryStorageType OBJECT-TYPE
   SYNTAX     StorageType 
   ACCESS     read-only
   STATUS     mandatory
   DESCRIPTION
     "This variable represents the storage type value for the
      mscVrIfTableEntry tables."
::= { mscVrIfTableEntryRowStatusEntry 4 }

mscVrIfTableEntryIndex OBJECT-TYPE
   SYNTAX     Integer32 (1..65535)
   ACCESS     not-accessible
   STATUS     mandatory
   DESCRIPTION
     "This variable represents the index for the mscVrIfTableEntry tables."
::= { mscVrIfTableEntryRowStatusEntry 10 }

mscVrIfTableEntryIftTable OBJECT-TYPE
   SYNTAX     SEQUENCE OF MscVrIfTableEntryIftEntry
   ACCESS     not-accessible
   STATUS     mandatory
   DESCRIPTION
     "*** THIS TABLE CURRENTLY NOT IMPLEMENTED ***

      This group represents the SNMP interface table entry."
::= { mscVrIfTableEntry 10 }

mscVrIfTableEntryIftEntry OBJECT-TYPE
   SYNTAX     MscVrIfTableEntryIftEntry
   ACCESS     not-accessible
   STATUS     mandatory
   DESCRIPTION
     "An entry in the mscVrIfTableEntryIftTable."
   INDEX {
      mscVrIndex,
      mscVrIfTableEntryIndex }
::= { mscVrIfTableEntryIftTable 1 }

MscVrIfTableEntryIftEntry ::= SEQUENCE {
   mscVrIfTableEntryIfAdminStatus
      INTEGER,
   mscVrIfTableEntryIfOperStatus
      INTEGER,
   mscVrIfTableEntryIfLastChange
      Unsigned32,
   mscVrIfTableEntryIfInOctets
      Counter32,
   mscVrIfTableEntryIfOutOctets
      Counter32,
   mscVrIfTableEntryIfInDiscards
      Counter32,
   mscVrIfTableEntryIfOutDiscards
      Counter32,
   mscVrIfTableEntryIfInErrors
      Counter32,
   mscVrIfTableEntryIfOutErrors
      Counter32,
   mscVrIfTableEntryIfInUcastPkts
      Counter32,
   mscVrIfTableEntryIfOutUcastPkts
      Counter32,
   mscVrIfTableEntryIfInNuCastPkts
      Counter32,
   mscVrIfTableEntryIfOutNuCastPkts
      Counter32,
   mscVrIfTableEntryIfInUnknownProtos
      Counter32,
   mscVrIfTableEntryIfOutQlength
      Gauge32,
   mscVrIfTableEntryIfDescription
      AsciiString,
   mscVrIfTableEntryIfType
      INTEGER,
   mscVrIfTableEntryIfMtu
      Unsigned32,
   mscVrIfTableEntryIfSpeed
      Unsigned32,
   mscVrIfTableEntryIfPhysicalAddress
      AsciiString,
   mscVrIfTableEntryIfSpecific
      IntegerSequence }

mscVrIfTableEntryIfAdminStatus OBJECT-TYPE
   SYNTAX     INTEGER  {
                 up(1),
                 down(2),
                 testing(3) }
   ACCESS     read-only
   STATUS     mandatory
   DESCRIPTION
     "The down state indicates the interface is not operational. The testing 
      state indicates that no operational packets can be passed."
   DEFVAL     { up }
::= { mscVrIfTableEntryIftEntry 2 }

mscVrIfTableEntryIfOperStatus OBJECT-TYPE
   SYNTAX     INTEGER  {
                 up(1),
                 down(2),
                 testing(3) }
   ACCESS     read-only
   STATUS     mandatory
   DESCRIPTION
     "This attribute provides the current operational status of the 
      interface. The testing state indicates that no operational packets can 
      be passed."
   DEFVAL     { down }
::= { mscVrIfTableEntryIftEntry 3 }

mscVrIfTableEntryIfLastChange OBJECT-TYPE
   SYNTAX     Unsigned32 (0..4294967295)
   ACCESS     read-only
   STATUS     mandatory
   DESCRIPTION
     "The value of sysUpTime at the time the interface entered its current 
      operational state. If the current state was entered prior to the last re- 
      initialization of the local network management subsystem, then this 
      object contains a zero value."
::= { mscVrIfTableEntryIftEntry 4 }

mscVrIfTableEntryIfInOctets OBJECT-TYPE
   SYNTAX     Counter32 
   ACCESS     read-only
   STATUS     mandatory
   DESCRIPTION
     "The total number of octets received on the interface, including 
      framing characters."
::= { mscVrIfTableEntryIftEntry 5 }

mscVrIfTableEntryIfOutOctets OBJECT-TYPE
   SYNTAX     Counter32 
   ACCESS     read-only
   STATUS     mandatory
   DESCRIPTION
     "The total number of octets transmitted out the interface, including 
      framing characters"
::= { mscVrIfTableEntryIftEntry 6 }

mscVrIfTableEntryIfInDiscards OBJECT-TYPE
   SYNTAX     Counter32 
   ACCESS     read-only
   STATUS     mandatory
   DESCRIPTION
     "The number of inbound packets which were chosen to be discarded 
      even though no errors had been detected to prevent their being 
      deliverable to a higher layer protocol. One possible reason for 
      discarding such a packet could be to free up buffer space."
::= { mscVrIfTableEntryIftEntry 7 }

mscVrIfTableEntryIfOutDiscards OBJECT-TYPE
   SYNTAX     Counter32 
   ACCESS     read-only
   STATUS     mandatory
   DESCRIPTION
     "The number of outbound packets which were chosen to be 
      discarded even though no errors had been detected to prevent their 
      being transmitted. One possible reason for discarding such a packet 
      could be to free up buffer space."
::= { mscVrIfTableEntryIftEntry 8 }

mscVrIfTableEntryIfInErrors OBJECT-TYPE
   SYNTAX     Counter32 
   ACCESS     read-only
   STATUS     mandatory
   DESCRIPTION
     "The number of inbound packet that contained errors preventing 
      them from being deliverable to a higher layer protocol."
::= { mscVrIfTableEntryIftEntry 9 }

mscVrIfTableEntryIfOutErrors OBJECT-TYPE
   SYNTAX     Counter32 
   ACCESS     read-only
   STATUS     mandatory
   DESCRIPTION
     "The number of outbound packets that could not be transmitted because 
      of errors."
::= { mscVrIfTableEntryIftEntry 10 }

mscVrIfTableEntryIfInUcastPkts OBJECT-TYPE
   SYNTAX     Counter32 
   ACCESS     read-only
   STATUS     mandatory
   DESCRIPTION
     "The number of subnetwork-unicast packets delivered to a higher-layer 
      protocol."
::= { mscVrIfTableEntryIftEntry 11 }

mscVrIfTableEntryIfOutUcastPkts OBJECT-TYPE
   SYNTAX     Counter32 
   ACCESS     read-only
   STATUS     mandatory
   DESCRIPTION
     "The total number of packets that higher level protocols requested be 
      transmitted to a subnetwork-unicast address, including those that 
      were discarded or not sent."
::= { mscVrIfTableEntryIftEntry 12 }

mscVrIfTableEntryIfInNuCastPkts OBJECT-TYPE
   SYNTAX     Counter32 
   ACCESS     read-only
   STATUS     mandatory
   DESCRIPTION
     "The number of non-unicast (i.e., subnetwork- broadcast or 
      subnetwork-multicast) packets delivered to a higher-layer protocol."
::= { mscVrIfTableEntryIftEntry 13 }

mscVrIfTableEntryIfOutNuCastPkts OBJECT-TYPE
   SYNTAX     Counter32 
   ACCESS     read-only
   STATUS     mandatory
   DESCRIPTION
     "The total number of packets that higher level protocols request be 
      transmitted to a non-unicast address, including those that were 
      discarded or not sent."
::= { mscVrIfTableEntryIftEntry 14 }

mscVrIfTableEntryIfInUnknownProtos OBJECT-TYPE
   SYNTAX     Counter32 
   ACCESS     read-only
   STATUS     mandatory
   DESCRIPTION
     "The number of packets received via the interface which were 
      discarded because of an unknown or unsupported protocol."
::= { mscVrIfTableEntryIftEntry 15 }

mscVrIfTableEntryIfOutQlength OBJECT-TYPE
   SYNTAX     Gauge32 (0..4294967295)
   ACCESS     read-only
   STATUS     mandatory
   DESCRIPTION
     "The length of the output packet queue (in packets)"
::= { mscVrIfTableEntryIftEntry 16 }

mscVrIfTableEntryIfDescription OBJECT-TYPE
   SYNTAX     AsciiString (SIZE (0..255))
   ACCESS     read-only
   STATUS     mandatory
   DESCRIPTION
     "A textual string containing information about the interface. This 
      string includes the name of the manufacturer, the product name and 
      the version of the hardware interface."
::= { mscVrIfTableEntryIftEntry 17 }

mscVrIfTableEntryIfType OBJECT-TYPE
   SYNTAX     INTEGER  {
                 other(1),
                 ddnX25(4),
                 rfc877x25(5),
                 ethernetCsmacd(6),
                 ethernet8023(7),
                 tokenBus8024(8),
                 tokenring8025(9),
                 man802(10),
                 starLan(11),
                 hyperChannel(14),
                 fddi(15),
                 lapb(16),
                 sdlc(17),
                 ds1(18),
                 e1(19),
                 basicIsdn(20),
                 primaryIsdn(21),
                 propPointToPointSerial(22),
                 ppp(23),
                 ds3(30),
                 smds(31),
                 frameRelay(32),
                 frameRelayService(44),
                 v35(45),
                 hssi(46),
                 aflane8023(59),
                 aflane8025(60),
                 v11(64),
                 atmMpeVcEncap(1039),
                 atmMpeLlcEncap(1040),
                 ilsForwarder(1041),
                 ipTunnel(1042),
                 virtualMedia(1043) }
   ACCESS     read-only
   STATUS     mandatory
   DESCRIPTION
     "The type of interface, distinguished according to the physical/link 
      protocol(s) immediately below the network layer in the protocol 
      stack"
::= { mscVrIfTableEntryIftEntry 18 }

mscVrIfTableEntryIfMtu OBJECT-TYPE
   SYNTAX     Unsigned32 (0..4294967295)
   ACCESS     read-only
   STATUS     mandatory
   DESCRIPTION
     "The size of the largest datagram which can be sent/received on the 
      interface, specified in octets. For interfaces that are used for 
      transmitting network datagrams, this is the size of the largest 
      network datagram that can be sent on the interface."
::= { mscVrIfTableEntryIftEntry 19 }

mscVrIfTableEntryIfSpeed OBJECT-TYPE
   SYNTAX     Unsigned32 (0..4294967295)
   ACCESS     read-only
   STATUS     mandatory
   DESCRIPTION
     "An estimate of the interface's current bandwidth in bits per second. 
      For interfaces which do not vary in bandwidth or for those where no 
      accurate estimation can be made, this object should contain the 
      nominal bandwidth."
::= { mscVrIfTableEntryIftEntry 20 }

mscVrIfTableEntryIfPhysicalAddress OBJECT-TYPE
   SYNTAX     AsciiString (SIZE (0..17))
   ACCESS     read-only
   STATUS     mandatory
   DESCRIPTION
     "The interface's address at the protocol layer immediately `below' the 
      network layer in the protocol stack.  For interfaces which do not 
      have such an address (e.g., a serial line), this object should be an 
      octet string of zero length."
::= { mscVrIfTableEntryIftEntry 21 }

mscVrIfTableEntryIfSpecific OBJECT-TYPE
   SYNTAX     IntegerSequence 
   ACCESS     read-only
   STATUS     mandatory
   DESCRIPTION
     "A reference to MIB definitions specific to the particular media 
      being used to realize the interface. For example, if the interface is 
      realized by an ethernet, then the value of this object refers to a 
      document defining objects specific to ethernet.  If this information is 
      not present, its value should be set to the OBJECT IDENTIFIER 
      0.0, which is a syntactically valid object identifier, and any 
      conformant implementation of ASN.1 and BER must be able to 
      generate and recognize this value."
::= { mscVrIfTableEntryIftEntry 22 }

mscVrIfTableEntryAdditionalInfoTable OBJECT-TYPE
   SYNTAX     SEQUENCE OF MscVrIfTableEntryAdditionalInfoEntry
   ACCESS     not-accessible
   STATUS     mandatory
   DESCRIPTION
     "*** THIS TABLE CURRENTLY NOT IMPLEMENTED ***

      This group contains additional information associated with this 
      ifEntry."
::= { mscVrIfTableEntry 11 }

mscVrIfTableEntryAdditionalInfoEntry OBJECT-TYPE
   SYNTAX     MscVrIfTableEntryAdditionalInfoEntry
   ACCESS     not-accessible
   STATUS     mandatory
   DESCRIPTION
     "An entry in the mscVrIfTableEntryAdditionalInfoTable."
   INDEX {
      mscVrIndex,
      mscVrIfTableEntryIndex }
::= { mscVrIfTableEntryAdditionalInfoTable 1 }

MscVrIfTableEntryAdditionalInfoEntry ::= SEQUENCE {
   mscVrIfTableEntryStdComponentName
      RowPointer }

mscVrIfTableEntryStdComponentName OBJECT-TYPE
   SYNTAX     RowPointer 
   ACCESS     read-only
   STATUS     mandatory
   DESCRIPTION
     "This attribute provides a component name associated with this 
      ifEntry. This component is the source of the data stored in this 
      entry. More data may be determined about this entry by looking at 
      the component associated with this component name."
::= { mscVrIfTableEntryAdditionalInfoEntry 1 }


-- Vr/<string> QosP/< n>
-- For egress traffic of certain media types, this component provides a 
-- mapping from a Class of Service (CoS) index (the instance value of 
-- this component) to specific Quality of Service (QoS) attributes. It is 
-- also used to provide the reverse mapping from QoS to CoS for 
-- classifying ingress traffic of certain media types. QosP/0 
-- corresponding to CoS index of zero (0), is defined at all times.
-- 
-- When a packet is received on a VNS protocol port, the 
-- QualityOfServiceProfile determines the initial CoS of the incoming 
-- packet. If the vnsEmissionPriority and vnsDiscardPriority of the 
-- ingress packet match one of the provisioned profiles, the packet is 
-- given the corresponding CoS; otherwise, the packet is given CoS 
-- zero (0). When the packet is received on a protocol port other than 
-- VNS, the initial CoS of the packet is determined by other means 
-- (see the assignedQoS attribute of the IpPort component). In any 
-- case, the initial CoS assigned to the packet may be overridden when 
-- a cosPolicyGroup is associated with the protocol port (see the 
-- cosPolicyAssignment attribute of the Ip and IpPort components).
-- 
-- When the packet is to be transmitted from a VNS protocol port, the 
-- CoS of the packet and the associated QualityOfServiceProfile 
-- determine the vnsEmissionPriority and vnsDiscardPriority of the 
-- outgoing packet. When the packet is to be transmitted on an FrDte 
-- or a PPP protocol port, the CoS of the packet and the associated 
-- QualityOfServiceProfile determine the wanEmissionPriority of the 
-- outgoing packet. For FrDte this applies only if the ipCos attribute 
-- on all staticDlci subcomponents under the frDte component are 
-- provisioned to be the same value.

mscVrQosP OBJECT IDENTIFIER ::= { mscVr 15 }



mscVrQosPRowStatusTable OBJECT-TYPE
   SYNTAX     SEQUENCE OF MscVrQosPRowStatusEntry
   ACCESS     not-accessible
   STATUS     mandatory
   DESCRIPTION
     "This entry controls the addition and deletion of 
      mscVrQosP components."
::= { mscVrQosP 1 }

mscVrQosPRowStatusEntry OBJECT-TYPE
   SYNTAX     MscVrQosPRowStatusEntry
   ACCESS     not-accessible
   STATUS     mandatory
   DESCRIPTION
     "A single entry in the table represents a single 
      mscVrQosP component."
   INDEX {
      mscVrIndex,
      mscVrQosPIndex }
::= { mscVrQosPRowStatusTable 1 }

MscVrQosPRowStatusEntry ::= SEQUENCE {
   mscVrQosPRowStatus
      RowStatus,
   mscVrQosPComponentName
      DisplayString,
   mscVrQosPStorageType
      StorageType,
   mscVrQosPIndex
      Integer32 }

mscVrQosPRowStatus OBJECT-TYPE
   SYNTAX     RowStatus 
   ACCESS     read-write
   STATUS     mandatory
   DESCRIPTION
     "This variable is used as the basis for SNMP naming of
      mscVrQosP components.
      These components can be added and deleted."
::= { mscVrQosPRowStatusEntry 1 }

mscVrQosPComponentName OBJECT-TYPE
   SYNTAX     DisplayString 
   ACCESS     read-only
   STATUS     mandatory
   DESCRIPTION
     "This variable provides the component's string name for
      use with the ASCII Console Interface"
::= { mscVrQosPRowStatusEntry 2 }

mscVrQosPStorageType OBJECT-TYPE
   SYNTAX     StorageType 
   ACCESS     read-only
   STATUS     mandatory
   DESCRIPTION
     "This variable represents the storage type value for the
      mscVrQosP tables."
::= { mscVrQosPRowStatusEntry 4 }

mscVrQosPIndex OBJECT-TYPE
   SYNTAX     Integer32 (0..3)
   ACCESS     not-accessible
   STATUS     mandatory
   DESCRIPTION
     "This variable represents the index for the mscVrQosP tables."
::= { mscVrQosPRowStatusEntry 10 }

mscVrQosPProvTable OBJECT-TYPE
   SYNTAX     SEQUENCE OF MscVrQosPProvEntry
   ACCESS     not-accessible
   STATUS     mandatory
   DESCRIPTION
     "This group includes all attributes that can be provisioned to define an 
      InwQualityofServiceProfile instance."
::= { mscVrQosP 10 }

mscVrQosPProvEntry OBJECT-TYPE
   SYNTAX     MscVrQosPProvEntry
   ACCESS     not-accessible
   STATUS     mandatory
   DESCRIPTION
     "An entry in the mscVrQosPProvTable."
   INDEX {
      mscVrIndex,
      mscVrQosPIndex }
::= { mscVrQosPProvTable 1 }

MscVrQosPProvEntry ::= SEQUENCE {
   mscVrQosPVnsDiscardPriority
      Unsigned32,
   mscVrQosPVnsEmissionPriority
      Unsigned32,
   mscVrQosPWanEmissionPriority
      Unsigned32 }

mscVrQosPVnsDiscardPriority OBJECT-TYPE
   SYNTAX     Unsigned32 (1..3)
   ACCESS     read-write
   STATUS     mandatory
   DESCRIPTION
     "This attribute specifies the throughput importance of the packets when 
      forwarded over VNS connections. In times of congestion the discard 
      priority of a packet is used to determine whether the packet should be 
      discarded to reduce the heavy traffic load. Packets with lower discard 
      priority (numerically higher vdp) are more likely to be discarded than 
      packets with higher discard priority (numerically lower vdp). Discard 
      priority one (vdp 1) should be used for the most important traffic, 
      whereas discard priority three (vdp 3) should be used for the least 
      important traffic."
   DEFVAL     { 2 }
::= { mscVrQosPProvEntry 1 }

mscVrQosPVnsEmissionPriority OBJECT-TYPE
   SYNTAX     Unsigned32 (1..2)
   ACCESS     read-write
   STATUS     mandatory
   DESCRIPTION
     "This attribute specifies the delay importance of the packets when 
      forwarded over VNS connections. Packets with higher emission 
      priority (vep 1) are transmitted before packets with lower emission 
      priority (vep 2). Delay sensitive packets should be sent with 
      emission priority one (vep 1)."
   DEFVAL     { 2 }
::= { mscVrQosPProvEntry 2 }

mscVrQosPWanEmissionPriority OBJECT-TYPE
   SYNTAX     Unsigned32 (1..2)
   ACCESS     read-write
   STATUS     mandatory
   DESCRIPTION
     "This attribute specifies the delay importance of the packets when 
      forwarded over WAN connections. Packets with higher emission 
      priority (wep 1) are transmitted before packets with lower emission 
      priority (wep 2). Delay sensitive packets should be sent with 
      emission priority one (wep 1)."
   DEFVAL     { 2 }
::= { mscVrQosPProvEntry 3 }




-- 
-- Version and Compliance statements
-- 



-- Object-Group Statement:
-- A list of all current accessible leaf objects.

-- OBJECTS { mscVrIfTableEntryIfType,
--           mscVrOperationalState,
--           mscVrIfTableEntryIfSpeed,
--           mscVrMmComponentName,
--           mscVrIfTableEntryIfInUnknownProtos,
--           mscVrIfTableEntryIfPhysicalAddress,
--           mscVrMmVrHeapSpaceAllocated,
--           mscVrPpUsageState,
--           mscVrMmIpxMaxHeapSpace,
--           mscVrIfTableEntryStorageType,
--           mscVrMmSnaHeapSpaceAllocated,
--           mscVrPpComponentName,
--           mscVrMmIpMaxHeapSpace,
--           mscVrPpAtmAddress,
--           mscVrIfTableEntryIfOutErrors,
--           mscVrIfTableEntryIfOutUcastPkts,
--           mscVrIfTableEntryIfOutDiscards,
--           mscVrIfTableEntryIfInOctets,
--           mscVrIfTableEntryIfInUcastPkts,
--           mscVrPpOperationalState,
--           mscVrIfTableEntryIfMtu,
--           mscVrMmBridgingHeapSpaceAllocated,
--           mscVrSnmpOperStatus,
--           mscVrQosPVnsEmissionPriority,
--           mscVrMmSnaMaxHeapSpace,
--           mscVrPpLinkToMedia,
--           mscVrQosPVnsDiscardPriority,
--           mscVrIfTableEntryIfDescription,
--           mscVrIfTableEntryIfAdminStatus,
--           mscVrMmNetSentryHeapSpaceAllocated,
--           mscVrIfTableEntryIfSpecific,
--           mscVrPpRowStatus,
--           mscVrIfTableEntryIfLastChange,
--           mscVrIfNumber,
--           mscVrVirtualPrivateIntranetIdentifier,
--           mscVrMmBridgingMaxHeapSpace,
--           mscVrMmVrHeapSpaceBytesAllocated,
--           mscVrQosPStorageType,
--           mscVrIfTableEntryIfOperStatus,
--           mscVrPpSnmpOperStatus,
--           mscVrIfTableEntryComponentName,
--           mscVrPpIfIndex,
--           mscVrIfTableEntryIfInErrors,
--           mscVrMmStorageType,
--           mscVrMmNetSentryMaxHeapSpace,
--           mscVrIfTableEntryIfOutNuCastPkts,
--           mscVrAdminState,
--           mscVrMmSresHeapSpaceAllocated,
--           mscVrVpnMode,
--           mscVrIfTableEntryStdComponentName,
--           mscVrQosPWanEmissionPriority,
--           mscVrPpStorageType,
--           mscVrRowStatus,
--           mscVrIfTableEntryRowStatus,
--           mscVrSnmpAdminStatus,
--           mscVrIfTableEntryIfOutQlength,
--           mscVrCustomerIdentifier,
--           mscVrQosPRowStatus,
--           mscVrIfTableEntryIfInNuCastPkts,
--           mscVrStorageType,
--           mscVrMmVrMaxHeapSpace,
--           mscVrIfTableEntryIfOutOctets,
--           mscVrMmSresMaxHeapSpace,
--           mscVrMmRowStatus,
--           mscVrUsageState,
--           mscVrPpAdminState,
--           mscVrComponentName,
--           mscVrMmIpxHeapSpaceAllocated,
--           mscVrManagementAccess,
--           mscVrQosPComponentName,
--           mscVrIfTableEntryIfInDiscards,
--           mscVrMmIpHeapSpaceAllocated,
--           mscVrPpSnmpAdminStatus }
-- STATUS  mandatory
-- DESCRIPTION
--   "A list of all current accessible leaf objects."

virtualRouterGroup OBJECT IDENTIFIER ::= { virtualRouterMIB 1 }
virtualRouterGroupCA OBJECT IDENTIFIER ::= { virtualRouterGroup 1 }
virtualRouterGroupCA02 OBJECT IDENTIFIER ::= { virtualRouterGroupCA 3 }
virtualRouterGroupCA02A OBJECT IDENTIFIER ::= { virtualRouterGroupCA02 2 }



-- Agent-Capabilities Statement:

-- PRODUCT-RELEASE "MscPassport Release 1.2 VirtualRouter."
-- STATUS          mandatory
-- DESCRIPTION     "Carrier Passport VirtualRouter MIB: MIB Version CA02A,
--                  Software Version CA02S9C."
-- SUPPORTS        Nortel-MsCarrier-MscPassport-VirtualRouterMIB
--    INCLUDES     { virtualRouterGroupCA02A }

virtualRouterCapabilities OBJECT IDENTIFIER ::= { virtualRouterMIB 3 }
virtualRouterCapabilitiesCA OBJECT IDENTIFIER ::= { virtualRouterCapabilities 1 }
virtualRouterCapabilitiesCA02 OBJECT IDENTIFIER ::= { virtualRouterCapabilitiesCA 3 }
virtualRouterCapabilitiesCA02A OBJECT IDENTIFIER ::= { virtualRouterCapabilitiesCA02 2 }





END
