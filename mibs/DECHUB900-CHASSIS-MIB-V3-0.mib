DECHUB900-CHASSIS-MIB-V3-0 DEFINITIONS ::= BEGIN

--
--  Definitions of Managed Objects for Digital Equipment Corporation's
--         MultiSwitch 900 and MultiSwitch 600 "Chassis MIB"
--         =================================================
--  
--  
--
--  
--                 Name:    chass3-0.txt
--                 Version: 3.0
--                 Date:    April, 1997
--                 Company: Digital Equipment Corporation
--                 Mail:    hub900-support@lkg.dec.com
--
--
--  
--  
--  
--  This Digital Equipment  Corporation  SNMP  Management  Information  Base
--  Specification  embodies Digital Equipment Corporation's confidential and
--  proprietary  intellectual  property.   Digital   Equipment   Corporation
--  retains  all  title  and  ownership  in the Specification, including any
--  revisions.
--  
--  It is Digital Equipment Corporation's intent to encourage the widespread
--  use  of  this Specification in connection with the management of Digital
--  Equipment Corporation products.
--  
--  Digital Equipment  Corporation  grants  vendors,  end-users,  and  other
--  interested  parties a non-exclusive license to use this Specification in
--  connection  with  the  management  of  Digital   Equipment   Corporation
--  products.
--  
--  Digital Equipment Corporation reserves the right to make changes in this
--  specification  and  other information contained in this document without
--  prior notice.
--  
--  Digital Equipment Corporation makes no  warranty,  either  expressed  or
--  implied,  as  to  the  use,  operation, condition, or performance of the
--  Specification.  In no  event  shall  Digital  Equipment  Corporation  be
--  liable  for  any incidental, indirect, special, or consequential damages
--  whatsoever (including but not limited to loss of profits) arising out of
--  or related to this document or the information contained in it.
--
--
--
--
--
--
--  1  Status Of This Memo
--
--
--  This MIB module provides definitions for Digital Equipment Corporation's
--  MultiSwitch 900 and MultiSwitch 600 "Chassis MIB".  This MIB is
--  implemented by the DEChub900's Hub Manager, and the MultiSwitch 600's
--  Stack Director.
--
--  Digital posts product MIBs on web sites at:
--
--            http://www.networks.digital.com/
--            http://www.networks.europe.digital.com/
--            http://www.networks.digital.com.au/
--
--  This particular MIB is kept in:
--
--            http://www.networks.digital.com/dr/hubs/mibs
--
--
--
--  Inquiries about the contents and use of this MIB may be sent to 
--  hub900-support@lkg.dec.com.
--
--
--  2  Relationship to Other MIBs
--
--
--  The  objects  defined  in  this   MIB   are   located   under   the
--  private.enterprises subtree as shown below:
--
--                    iso(1).org(3).dod(6).internet(1)
--                                 |
--                              private(4)
--                                 |
--                              enterprises(1)
--                                 |
--                              dec(36)
--                                 |
--                              ema(2)
--                                 |
--                              decMIBextension(18)
--                                 |
--                              decHub900(11)
--                                 |
--                     .___________.___________.___________// ...etc...
--                     |                       |
--                mgmtAgent(1)              common(2)
--                     |                       |    
--                mgmtAgentVersion1(1)      ...ect...
--                     |
--                     |
--               .____________.
--               | chassis(1) |
--               |____________|
--
--
--
--
--
--  3  Abstract
--  
--  The SNMP uses the UDP/IP stack to transport  SNMP  Messages.   The  SNMP
--  Agent  is  addressed  via  its  IP address.  The SNMP Message contains a
--  field called the community string  which  allows  different  "views"  of
--  management  information.   Hence  an  IP  address/SNMP  community string
--  combination specifies a set of management  information.   Commonly,  two
--  communities  are  supported  by an agent:  one for read-only access, and
--  the  other  for  read-write  access.   Additionally,  there  is  a  trap
--  community,  and  a  list  of  IP addresses of where the agent is to send
--  traps.
--  
--  Standard  MIBs  exist  to  provide  management  objects  for   specified
--  functions.  There are, for example, bridge, fddi, repeater, and ethernet
--  MIBs.  The Structure of Management Information  (SMI)  employed  by  the
--  SNMP  has  no  concept of instancing MIBs.  Multiple devices of the same
--  type are therefore not addressable.   For  example,  an  agent  may  not
--  contain  two  bridge  MIBs  since  there is no mechanism to individually
--  instance (address) more than one MIB of the same  type  using  the  same
--  agent.   Hubs  need  to  overcome this limitation since they may contain
--  multiple bridges, repeaters, fddi-concentrators, terminal servers, etc.
--  
--  Hubs overcome this limitation by  implementing  a  "chassis  MIB".   The
--  chassis  MIB contains objects which relate the devices in the hub to the
--  "entities" used  to  manage  the  device.   
--
--
--
--  4  References
--
--
--  [1]  RFC 1213.  McCloghrie, K., and M. Rose, "Management Information Base 
--       for Network Management of TCP/IP-based Internets".  March, 1991.
--
--  [2]  RFC 1155.  Rose, M., and K. McCloghrie, "Structure and Identification 
--       of Management Information for TCP/IP-based Internets".  May, 1990.
--
--  [3]  DEChub 900 MultiSwitch Owner's Manual.  Digital Equipment 
--       Corp.  Order number:  EK-DH2MS-OM.<version>.
--
--
--
--
--  5  Object Synopsis
--
--
--
--
--  Object Name                             Object ID
--  =================================       ====================
--
--   p = 1.3.6.1.4.1.36.2.18.decHub900(11).mgmtAgent(1).
--              mgmtAgentVersion1(1).chassis(1)
--
--  chassis                                  p
--    chasSlot                               p.1
--      chasNumSlots                         p.1.1.0
--      chasNumSlotsOccupied                 p.1.2.0
--      chasMaxExtendedSlots                 p.1.3.0
--      chasExtendedSlotsOccupied            p.1.4.0
--      chasPopulationChanges                p.1.5.0
--      chasSlotTable                        p.1.6
--        chasSlotEntry                      p.1.6.1
--          chasSlotIndex                    p.1.6.1.1.n
--          chasSlotModuleType               p.1.6.1.2.n
--          chasSlotLastChange               p.1.6.1.3.n
--          chasSlotModuleDescr              p.1.6.1.4.n
--          chasSlotModuleVersion            p.1.6.1.5.n
--          chasSlotModuleSerialNumber       p.1.6.1.6.n
--          chasSlotModuleSize               p.1.6.1.7.n
--          chasSlotModuleOperStatus         p.1.6.1.8.n
--          chasSlotModuleAdminStatus        p.1.6.1.9.n
--          chasSlotModuleNonFatalError      p.1.6.1.10.n
--      chasSlotResetAll                     p.1.7.0
--    chasEntity                             p.2
--      chasEntityChanges                    p.2.1.0
--      chasEntityTable                      p.2.2
--        chasEntityEntry                    p.2.2.1
--          chasEntityIndex                  p.2.2.1.1.n
--          chasEntityFunction               p.2.2.1.2.n	(Dep.)
--          chasEntityObjectID               p.2.2.1.3.n	(Dep.)
--          chasEntityDescr                  p.2.2.1.4.n	(Dep.)
--          chasEntityVersion                p.2.2.1.5.n	(Dep.)
--          chasEntityAdminStatus            p.2.2.1.6.n	(Dep.)
--          chasEntityOperStatus             p.2.2.1.7.n	(Dep.)
--          chasEntityTimeStamp              p.2.2.1.8.n	(Dep.)
--          chasEntityParty                  p.2.2.1.9.n	(Dep.)
--          chasEntityCommunity              p.2.2.1.10.n
--          chasEntityIpAddress              p.2.2.1.11.n
--          chasEntityComAccessRights        p.2.2.1.12.n
--          chasEntityAccessMethod           p.2.2.1.13.n
--          chasEntitySlotNumber             p.2.2.1.14.n
--          chasEntitySrcIpAddress           p.2.2.1.15.n
--          chasEntitySrcSubnetMask          p.2.2.1.16.n
--          chasEntityAccessCharacteristics  p.2.2.1.17.n
--      chasEntityAccessLoadTable            p.2.3
--        chasEntityAccessLoadEntry          p.2.3.1
--          chasEntityAccessLoadSlot         p.2.3.1.1.n
--          chasEntityAccessLoadMethod       p.2.3.1.2.n
--      chasEntityChangeTable                p.2.4
--        chasEntityChangeEntry              p.2.4.1
--          chasEntityChangeSlot             p.2.4.1.1.n
--          chasEntityChangeCounter          p.2.4.1.2.n
--    chasBackplane                          p.3
--      chasBackplaneTable                   p.3.1
--        chasBackplaneEntry                 p.3.1.1
--          chasBackplaneIndex               p.3.1.1.1.n
--          chasBackplaneDescr               p.3.1.1.2.n
--          chasBackplaneRev                 p.3.1.1.3.n
--          chasBackplaneNumSlots            p.3.1.1.4.n
--    chasSegment                            p.4
--      chasSegmentTable                     p.4.1
--        chasSegmentEntry                   p.4.1.1
--          chasSegmentIndex                 p.4.1.1.1.n
--          chasSegmentName                  p.4.1.1.2.n
--          chasSegmentType                  p.4.1.1.3.n
--          chasSegmentSubtypeSelect         p.4.1.1.4.n
--          chasSegmentEntryStatus           p.4.1.1.5.n
--      chasSegSubtypeTable                  p.4.2
--        chasSegSubtypeEntry                p.4.2.1
--          chasSegSubtypeIndex              p.4.2.1.8.n
--          chasSegSubtypeFlavor             p.4.2.1.9.n
--          chasSegSubtypeSpeed              p.4.2.1.10.n
--          chasSegSubtypeEntryStatus        p.4.2.1.11.n
--      chasSegDefVNbusState                 p.4.3.0
--    chasConfig                             p.5
--      chasChassisSerialNumber              p.5.1.0
--      chasConnChanges                      p.5.2.0
--      chasConnTable                        p.5.3
--        chasConnEntry                      p.5.3.1
--          chasConnIndex                    p.5.3.1.1.n
--          chasConnSegment                  p.5.3.1.2.n
--          chasConnPort                     p.5.3.1.3.n
--          chasConnNextPortIndex            p.5.3.1.4.n
--          chasConnEntryStatus              p.5.3.1.5.n
--    chasPort                               p.6
--      chasPortLastChange                   p.6.1.0
--      chasPortTable                        p.6.2
--        chasPortEntry                      p.6.2.1
--          chasPortIndex                    p.6.2.1.1.n
--          chasPortSlot                     p.6.2.1.2.n
--          chasPortName                     p.6.2.1.3.n
--          chasPortType                     p.6.2.1.4.n
--          chasPortSubtypeSelect            p.6.2.1.5.n
--          chasPortOperStatus               p.6.2.1.6.n
--      chasPortDescrTable                   p.6.3
--        chasPortDescrEntry                 p.6.3.1
--          chasPortDescrIndex               p.6.3.1.1.n
--          chasPortDescr                    p.6.3.1.2.n
--      chasPortSubtypeTable                 p.6.4
--        chasPortSubtypeEntry               p.6.4.1
--          chasPortSubtypeIndex             p.6.4.1.1.n
--          chasPortSubtypePortIndex         p.6.4.1.2.n
--          chasPortSubtypeFlavor            p.6.4.1.3.n
--          chasPortSubtypeSpeed             p.6.4.1.4.n
--    chasPowerConfig                        p.7
--      chasPowerConfigMaxSupplies           p.7.1.0
--      chasPowerConfigNumSupplies           p.7.2.0
--      chasPowerConfigChanges               p.7.3.0
--      chasPowerConfigRedundancyState       p.7.4.0
--      chasPowerConfigTable                 p.7.5
--        chasPowerConfigEntry               p.7.5.1
--          chasPowerConfigIndex             p.7.5.1.1.n
--          chasPowerConfigDescr             p.7.5.1.2.n
--          chasPowerConfigAdminStatus       p.7.5.1.3.n
--          chasPowerConfigOperStatus        p.7.5.1.4.n
--          chasPowerConfigHealthText        p.7.5.1.5.n
--          chasPowerConfigWarnings          p.7.5.1.6.n
--          chasPowerConfigFailures          p.7.5.1.7.n
--    chasPowerSource                        p.8
--      chasPowerSourceTotalPowerAvailable   p.8.1.0
--      chasPowerSourceTotalCurrentAvailable p.8.2.0
--      chasPowerSourceTable                 p.8.3
--        chasPowerSourceEntry               p.8.3.1
--          chasPowerSourceSupplyIndex       p.8.3.1.1.n
--          chasPowerSourceIndex             p.8.3.1.2.n
--          chasPowerSourceNominalVoltage    p.8.3.1.3.n
--          chasPowerSourcePower             p.8.3.1.4.n
--    chasPowerSink                          p.9
--      chasPowerSinkTable                   p.9.1
--        chasPowerSinkEntry                 p.9.1.1
--          chasPowerSinkSlotIndex           p.9.1.1.1.n
--          chasPowerSinkIndex               p.9.1.1.2.n
--          chasPowerSinkVoltage             p.9.1.1.3.n
--          chasPowerSinkWattage             p.9.1.1.4.n
--          chasPowerSinkOperStatus          p.9.1.1.5.n
--    chasEnviron                            p.10
--      chasEnvironChanges                   p.10.1.0
--      chasEnvironTable                     p.10.2
--        chasEnvironEntry                   p.10.2.1
--          chasEnvironSlotIndex             p.10.2.1.1.n
--          chasEnvironSensorIndex           p.10.2.1.2.n
--          chasEnvironSensor                p.10.2.1.3.n
--          chasEnvironAdminStatus           p.10.2.1.4.n
--          chasEnvironOperStatus            p.10.2.1.5.n
--          chasEnvironWarnings              p.10.2.1.6.n
--          chasEnvironFailures              p.10.2.1.7.n
--    chasLoad                               p.11
--      chasLoadTable                        p.11.1
--        chasLoadEntry                      p.11.1.1
--          chasLoadSlotIndex                p.11.1.1.1.n
--          chasLoadAdminStatus              p.11.1.1.2.n
--          chasLoadOperStatus               p.11.1.1.3.n
--          chasLoadFileName                 p.11.1.1.4.n
--          chasLoadIpHostAddr               p.11.1.1.5.n
--          chasLoadDevSpecific              p.11.1.1.6.n
--          chasLoadEntryStatus              p.11.1.1.7.n
--    chasKnownTypes                         p.12
--    chasLigo                               p.13
--	chasLigoNumEntries                   p.13.1.0
--	chasLigoTable                        p.13.2
--	  chasLigoEntry                      p.13.2.1
--        chasLigoIndex                      p.13.2.1.1.n
--        chasLigoSlot                       p.13.2.1.2.n
--        chasLigoType                       p.13.2.1.3.n
--        chasLigoSubtypeSelect              p.13.2.1.4.n
--	chasLigoSubtypeNumEntries            p.13.3.0
--	chasLigoSubtypeTable                 p.13.4
--        chasLigoSubtypeEntry               p.13.4.1
--        chasLigoSubtypeIndex               p.13.4.1.1.n
--        chasLigoSubtypeLigoIndex           p.13.4.1.2.n
--        chasLigoSubtypePortMask            p.13.4.1.3.n
--        chasLigoSubtypeLabelIndexMask      p.13.4.1.4.n
--        chasLigoSubtypeFlavor              p.13.4.1.5.n
--        chasLigoSubtypePortMaskV2          p.13.4.1.6.n
--        chasLigoSubtypeLabelIndexMaskV2    p.13.4.1.7.n
--      chasLigoLabelNumEntries              p.13.5.0
--      chasLigoLabelTable                   p.13.6
--        chasLigoLabelEntry                 p.13.6.1
--        chasLigoLabelIndex                 p.13.6.1.1.n
--        chasLigoLabelString                p.13.6.1.2.n
--    chasPatching                           p.14
--      chasRingPatching                     p.14.1.0
--      chasRingMemberTable                  p.14.2
--        chasRingMemberEntry                p.14.2.1
--        chasRingMemberSlot                 p.14.2.1.1.n
--        chasRingMemberSegment              p.14.2.1.2.n
--        chasRingMemberStatus               p.14.2.1.3.n
--        chasRingMemberSegmentMask          p.14.2.1.4.n
--
--

--
--                                Polling
--                                =======
--
--  This section briefly describes objects which may be polled by
--  a Network Management Station (NMS) to determine changes within
--  this MIB.
--
--  An NMS may poll:
--
--     o  chasEntityChanges - A counter which is incremented whenever 
--          entity table entries are added or deleted, and when one of 
--          the following fields of an existing chasEntityTable is modified:
--
--                  o  chasEntityCommunity,
--                  o  chasEntityIpAddress, or
--                  o  chasEntityAccessMethod
--
--          Entity changes occur when the IP address or one of the community 
--          strings of a device is changed.  This counter is also incremented:
--
--                  o  when modules are inserted,
--                  o  when modules are removed, and
--                  o  when chasEntityCommunity, chasEntityIpAddress, or
--                     chasEntityAccessMethod of an existing entry
--                     changes.
--
--     o  chasConnChanges - A counter which is incremented whenever
--          a backplane connection changes.  Backplane connections change:
--          
--            - when modules are inserted,
--            - when modules are removed, and
--            - due to management changes of the backplane configuration.
--
--     o  chasPopulationChanges - A counter which is incremented
--          whenever a module or extended module is inserted or
--          removed from the hub.
--
--     o  chasEnvironChanges - A counter which is incremented whenever
--          the chasEnvironOperStatus value of an existing entry in
--          the chasEnvironTable changes.
--
--     o  chasPowerConfigChanges - A counter which is incremented
--          whenever the operational status of a power supply changes.
--
--     o  chasPortLastChange - A TimeTicks which is changed each time
--          the value of chasPortOperStatus changes.
--
--  A single PDU contains all of these objects may sent to the agent
--  to determine if anything in the chassis has changed.
--  

--
--                           Textual Conventions
--                           ===================
--
--  Table Row Creation Using EntryStatus
--
--  There is no  standard  way  to  create  a  table  row  using  SNMP.
--  Instead, each implementation defines MIB objects which describe the
--  particular actions needed to create a row in each table.  The  lack
--  of  standard  row  creation  and  deletion semantics is a burden to
--  users.
--
--  Recently, the EntryStatus object has become a popular way to create
--  table   rows.    EntryStatus  is  defined  in  the  Remote  Network
--  Monitoring MIB (RFC1271) and appears in the SNMP  Version  2  draft
--  documents.   
--
--  This MIB imports the EntryStatus macro from RFC1271, where is is
--  defined as follows:
--
--              EntryStatus ::= INTEGER
--                         { valid(1),
--                           createRequest(2),
--                           underCreation(3),
--                           invalid(4)
--                         }
--
--               The status of a table entry.
--              
--               Setting this object to the value invalid(4) has the
--               effect of invalidating the corresponding entry.
--               That is, it effectively disassociates the mapping
--               identified with said entry.
--               It is an implementation-specific matter as to whether
--               the agent removes an invalidated entry from the table.
--               Accordingly, management stations must be prepared to
--               receive tabular information from agents that corresponds
--               to entries currently not in use.  Proper
--               interpretation of such entries requires examination
--               of the relevant EntryStatus object.
--              
--               An existing instance of this object cannot be set to
--               createRequest(2).  This object may only be set to
--               createRequest(2) when this instance is created.  When
--               this object is created, the agent may wish to create
--               supplemental object instances to complete a conceptual
--               row in this table.  Immediately after completing the
--               create operation, the agent must set this object to
--               underCreation(3).
--              
--               Entries shall exist in the underCreation(3) state until
--               the management station is finished configuring the
--               entry and sets this object to valid(1) or aborts,
--               setting this object to invalid(4).  If the agent
--               determines that an entry has been in the
--               underCreation(3) state for an abnormally long time,
--               it may decide that the management station has
--               crashed.  If the agent makes this decision,
--               it may set this object to invalid(4) to reclaim the
--               entry.  A prudent agent will understand that the
--               management station may need to wait for human input
--               and will allow for that possibility in its
--               determination of this abnormally long period.
--

-- ===========================================================================
-- =====================  S t a r t   o f   M I B   ==========================
-- ===========================================================================

IMPORTS
    Counter, Gauge, TimeTicks, IpAddress, enterprises
        FROM RFC1155-SMI
    OBJECT-TYPE
        FROM RFC-1212
    DisplayString
        FROM RFC1213-MIB;

--  Path to the chassis MIB.

dec                 OBJECT IDENTIFIER ::= { enterprises 36 }
ema                 OBJECT IDENTIFIER ::= { dec 2 }
decMIBextension     OBJECT IDENTIFIER ::= { ema 18 }
decHub900           OBJECT IDENTIFIER ::= { decMIBextension 11 }
mgmtAgent           OBJECT IDENTIFIER ::= { decHub900 1 }
mgmtAgentVersion1   OBJECT IDENTIFIER ::= { mgmtAgent 1 }

--  The DEC chassis MIB.

chassis             OBJECT IDENTIFIER ::= { mgmtAgentVersion1 1 }

-- Groups within the chassis MIB

chasSlot            OBJECT IDENTIFIER ::= { chassis 1 }
chasEntity          OBJECT IDENTIFIER ::= { chassis 2 }
chasBackplane       OBJECT IDENTIFIER ::= { chassis 3 }
chasSegment         OBJECT IDENTIFIER ::= { chassis 4 }
chasConfig          OBJECT IDENTIFIER ::= { chassis 5 }
chasPort            OBJECT IDENTIFIER ::= { chassis 6 }
chasPowerConfig     OBJECT IDENTIFIER ::= { chassis 7 }
chasPowerSource     OBJECT IDENTIFIER ::= { chassis 8 }
chasPowerSink       OBJECT IDENTIFIER ::= { chassis 9 }
chasEnviron         OBJECT IDENTIFIER ::= { chassis 10 }
chasLoad            OBJECT IDENTIFIER ::= { chassis 11 }
--chasKnownTypes      OBJECT IDENTIFIER ::= { chassis 12 }
chasLigo            OBJECT IDENTIFIER ::= { chassis 13 }
chasPatching 	    OBJECT IDENTIFIER ::= { chassis 14 }

-- ===========================================================================
-- ==================   T h e  S l o t  G r o u p   ==========================
-- ===========================================================================
--
--  The purpose of this group is to provide information about the
--  modules which populate the chassis.
--
--  The DEChub900 supports 'slots' and 'extended slots'.  As shown below,
--  some modules may be inserted directly into the chassis while others
--  may be attached to the directly attached modules.  Still others may
--  be attached to these modules.  Modules which are not directly attached
--  to the chassis are termed 'extended slots'.
-- 
--
--  .___________________________________________________________.________.
--  |                                                           |        |
--  |                  Chassis - Slot 9                         |   p1   |
--  |                                                           |        |
--  |___________________________________________________________.________.
--  |     1      2      3      4      5      6      7      8    |        |
--  |___________________________________________________________|   p2   |
--  |     |                    |             |                  |        |
--  |  ._____.              ._____.       ._____.               .________.
--  |  |  o  |              |  o  |       |  o__|_____.         |        |
--  |  |  o__|__.           |  o  |       |  o  |     |         |   p3   |
--  |  |  o  |  |           |  o  |       |  o__|__.  |         |        |
--  |  |_____|  |           |_____|       |_____|  |  |         .________.
--  |           |                                  |  |         |        |
--  |           |                                  |  |         |   p4   |
--  |           |                                  |  |         |        |
--  .___________________________________________________________.________.
--              |                                 /    \
--           ._____.                             /      \
--    ESN    |  o__|___.                     ._____. ._____.
--    102    |  o  |   |                     |  o  | |  o  |
--           |  o  |   |                     |  o  | |  o  |
--           |_____|   |                     |  o  | |  o  |
--                     |                     |_____| |_____|
--                  ._____.                    ESN     ESN
--           ESN    |  o  |                    603     601
--           10201  |  o  |
--                  |  o  |
--                  |_____|
--
--  Slots are numbered using 'slot numbers' while extended slots are 
--  numbered using 'extended slot numbers', or ESNs.  ESNs are numbered
--  by ss-pp-pp-pp-pp where ss is the slot number of the directly 
--  attached module and pp are the ports which comprise the path of
--  the ESN. 
--
--  In the example above, slots 1, 4, and 6 are occupied.  ESN 10201 is
--  so named because the path is consists of slot 1 connected to port 2,
--  which in turn is connected to port 1 of ENS 102.
--
--  Integral components, like the Management Agent Module, are numbered
--  as chasNumSlots + 1.
--
--  When a module is inserted into the chassis a chasSlotTable entry is
--  created.  After the chasSlotTable entry is created, other chassis
--  MIB table entries may be created for the module.  For example, after
--  a chasSlotTable entry for the module in slot 3 is created a
--  chasEnvironTable entry may be created for the newly inserted module.
--
--  When a module is removed from the chassis the chasSlotTable entry
--  for that module in deleted and then all other MIB table entries
--  pertaining to the module are deleted.  For example, after a
--  chasSlotTable entry for the module in slot 3 is deleted chasEnvironTable 
--  entries for the module are deleted.
--
--  When the chasSlotModuleOperStatus for a module indicates a status other
--  than 'up(1)' other MIB table entries maintain their old values.
--  For example, if the chasSlotModuleOperStatus for a module in slot 3
--  becomes 'disabled(2)' then the values in the modules chasEnvironTable
--  cease to be updated.  'fresh' information about a module is only 
--  guaranteed when the module's chasSlotModuleOperStatus is 'up(1)'.
--

chasNumSlots  OBJECT-TYPE
    SYNTAX  INTEGER (1..65535)
    ACCESS  read-only
    STATUS  mandatory
    DESCRIPTION
        "The number of slots directly connected to this chassis. 
         For example, a chassis implementation with 8 slots 
         returns 8 when this object is requested."
    ::= { chasSlot 1 }

chasNumSlotsOccupied  OBJECT-TYPE
    SYNTAX  INTEGER (0..65535)
    ACCESS  read-only
    STATUS  mandatory
    DESCRIPTION
        "The number of directly connected slots which are
         presently occupied."
    ::= { chasSlot 2 }

chasMaxExtendedSlots  OBJECT-TYPE
    SYNTAX  INTEGER (1..65535)
    ACCESS  read-only
    STATUS  mandatory
    DESCRIPTION
        "The maximum number of extended slot numbers supported
         in this chassis mib."
    ::= { chasSlot 3 }

chasExtendedSlotsOccupied OBJECT-TYPE
    SYNTAX  INTEGER (0..65535)
    ACCESS  read-only
    STATUS  mandatory
    DESCRIPTION
        "The total number of extended slots presently attached."
    ::= { chasSlot 4 }

chasPopulationChanges OBJECT-TYPE
    SYNTAX  Counter
    ACCESS  read-only
    STATUS  mandatory
    DESCRIPTION
        "The total number of modules and extended modules 
         which have been inserted and removed from the chassis.
         This counter is incremented:

             - when a module is inserted, and
             - when a module is removed.

         The goal of this object is to provide a single object 
         which can be polled by an NMS to determine if there 
         have been changes in the chassis population."
    ::= { chasSlot 5 }

--
--  The Slot Table
--
--  This group describes the physical modules residing within the chassis,
--  and any 'extended slot' supported by the chassis. 
--
--  Table Row Creation and Deletion
--  ===============================
--  
--  Entries in the chasSlotTable are created when modules are inserted
--  into the chassis.  Entries are deleted from this table when modules
--  are removed from the chassis.   Table rows can not be created or
--  deleted with SNMP operations.  chasSlotModuleAdminStatus may be used 
--  to disable a module.
--
--
--  chasSlotTable Example
--  =====================
--
--  This example refers the the chassis pictured above which is populated
--  with modules in slots 1, 4, and 6, and contains extended slots 102,
--  601, 603, and 10201.  Moreover, an integral component denoted as
--  slot 9 is shown.  (Integral components are numbered starting at
--  chasNumSlots + 1.)
--
--  .________________._____________________________________________________.
--  | chasSlotNumber |  Other parts of the chasSlotTable                   |
--  |________________|_____________________________________________________|
--  |       1        | Information about the module in slot 1.             |
--  |       4        | Information about the module in slot 4.             |
--  |       6        | Information about the module in slot 6.             |
--  |       9        | Information about an integral component.            |
--  |      102       | Info about mod attached to port 2 of mod in slot 1. |
--  |      601       | Info about mod attached to port 1 of mod in slot 6. |
--  |      603       | Info about mod attached to port 3 of mod in slot 6. |
--  |     10201      | Info about mod attached to port 1 of ESN 102.       |
--  |________________|_____________________________________________________|
--
--

chasSlotTable  OBJECT-TYPE
    SYNTAX  SEQUENCE OF ChasSlotEntry
    ACCESS  not-accessible
    STATUS  mandatory
    DESCRIPTION
        "A table that contains information about the slots
         in the chassis."
    ::= { chasSlot 6 }

chasSlotEntry OBJECT-TYPE
    SYNTAX  ChasSlotEntry
    ACCESS  not-accessible
    STATUS  mandatory
    DESCRIPTION
        "A list of information for each slot in the chassis.  
         Table rows may not be created or deleted with SNMP 
         operations."
    INDEX  { chasSlotIndex }
    ::= { chasSlotTable 1 }

ChasSlotEntry ::=
    SEQUENCE {
        chasSlotIndex
            INTEGER,
        chasSlotModuleType
            OBJECT IDENTIFIER,
        chasSlotLastChange
            TimeTicks,
        chasSlotModuleDescr
            DisplayString,
        chasSlotModuleVersion
            DisplayString,
        chasSlotModuleSerialNumber
            DisplayString,
        chasSlotModuleSize
            INTEGER,
        chasSlotModuleOperStatus
            INTEGER,
        chasSlotModuleAdminStatus
            INTEGER,
        chasSlotModuleNonFatalError
            INTEGER
    }

chasSlotIndex OBJECT-TYPE
    SYNTAX  INTEGER (1..899999999)
    ACCESS  read-only
    STATUS  mandatory
    DESCRIPTION
        "The number of the slot that the module occupies.

         Note that this index may exceed chasNumSlots if:

          - extended slots are present in the chassis, or
          - an integral component such as a management module
            is present in the chassis."
    ::= { chasSlotEntry 1 }

chasSlotModuleType OBJECT-TYPE
    SYNTAX  OBJECT IDENTIFIER
    ACCESS  read-only
    STATUS  mandatory
    DESCRIPTION
        "The sysObjectID of the module which occupies the slot.

         Besides sysObjectIDs, the value of this object may contain
         chasSlotUnknown or chasSlotBlocked.

         chasSlotUnknown (1.3.6.1.4.1.36.2.18.11.1.1.12.1.2)
         is used to describe a slot which contains a module
         which is for some reason 'unknown'.

         chasSlotBlocked (1.3.6.1.4.1.36.2.18.11.1.1.12.1.3)
         is used to describe a slot which is not usable because 
         a double, triple, etc. width module prevents its use."
    ::= { chasSlotEntry 2 }

chasSlotLastChange OBJECT-TYPE
    SYNTAX  TimeTicks
    ACCESS  read-only
    STATUS  mandatory
    DESCRIPTION
        "The value of MIB-II's sysUpTime (in the agent
         supporting this chassis MIB) at which a module was
         last inserted into this slot."
    ::= { chasSlotEntry 3 }

chasSlotModuleDescr  OBJECT-TYPE
    SYNTAX  DisplayString (SIZE (0..255))
    ACCESS  read-only
    STATUS  mandatory
    DESCRIPTION
        "A textual description of the module inserted into
         the slot.  If no description is available, this value 
         is a zero length string.  No description may be available
         if the module reports a chasSlotModuleAdminStaus of 
         fatal-error."
    ::= { chasSlotEntry 4 }

chasSlotModuleVersion  OBJECT-TYPE
    SYNTAX  DisplayString (SIZE (0..32))
    ACCESS  read-only
    STATUS  mandatory
    DESCRIPTION
        "A textual description of the version/revision level for 
         this module's hardware and firmware.  If not available, 
         this value is a zero-length string."
    ::= { chasSlotEntry 5 }

chasSlotModuleSerialNumber  OBJECT-TYPE
    SYNTAX  DisplayString (SIZE (0..32))
    ACCESS  read-only
    STATUS  mandatory
    DESCRIPTION
        "The serial number of the module present in the
         slot.  If no serial number is available for a module, 
         this value is a zero length string."
    ::= { chasSlotEntry 6 }

chasSlotModuleSize OBJECT-TYPE
    SYNTAX  INTEGER {
                min(1),
                max(2),
                system(3)
                }
    ACCESS  read-only
    STATUS  mandatory
    DESCRIPTION 
        "Indicates the size of the module.  min(1) modules
         are decHub90 compatible modules.  max(2) modules are
         full sized DEChub900 modules.  The value system(3) 
         is used to denote a module which is neither a min(1)
         or max(2) module;  for example, the integral management
         module is a system(3) module."
    ::= { chasSlotEntry 7 }

chasSlotModuleOperStatus OBJECT-TYPE
    SYNTAX  INTEGER {
                up(1),
                disabled(2),
                insufficient-power(3),
                fatal-error(4),
                non-fatal-error(5)
                }
    ACCESS  read-only
    STATUS  mandatory
    DESCRIPTION 
        "Indicates the operational state of the module.

         up(1) indicates that the module is performing as expected.

         disabled(2) indicates that the module has been disabled.

         insufficient-power(3) indicates that the chassis lacks the
         power needed by the module.

         fatal-error(4) indicates that the module encountered an 
         error which prevents its operation.  

         non-fatal-error(5) indicates that the module encountered
         an error which may inhibit its operation, but does not
         prevent its operating in a diminished capacity."
    ::= { chasSlotEntry 8 }

chasSlotModuleAdminStatus OBJECT-TYPE
    SYNTAX  INTEGER {
                unknown(1),  -- none of the following
                enabled(2),
                disabled(3),
                reset(4),
                restore-to-defaults(5)
                }
    ACCESS  read-write
    STATUS  mandatory
    DESCRIPTION
        "Provides the administratively desired state of
         the given module.

         A disabled module is activated by writing a value of
         enable(2).

         A slot may be de-activated by writing a value
         of disable(3).  A disabled slot is available for
         subsequent activation.

         Writing a value of reset(4) specifies that the model
         initiate a reset sequence.

         Writing a value of restore-to-defaults(5) specifies that
         the module restore all of its non-volatile parameters
         to their factory default state and reset the module.

         Agent support of the writing of any of the values
         of this object is implementation-specific.  For
         example, this object might be read only for
         slots that disabling would compromise the
         integrity of the chassis."
    ::= { chasSlotEntry 9 }

chasSlotModuleNonFatalError OBJECT-TYPE
    SYNTAX  INTEGER (0..4294967295)
    ACCESS  read-only
    STATUS  mandatory
    DESCRIPTION 
        "A device specific non-fatal error status indication."
    ::= { chasSlotEntry 10 }

--
--  Reset modules.
--

chasSlotResetAll OBJECT-TYPE
    SYNTAX  INTEGER {
                unknown(1),                -- Value when read.
                resetAllModules(2),
                resetAllModulesAndMgr(3),
                resetAllModulesToDefaults(4),
                resetAllModulesAndMgrToDefaults(5)
                }
    ACCESS  read-write
    STATUS  mandatory
    DESCRIPTION
        "This object is used to reset, restore, and test all active 
         modules in the chassis.

         Modules which are managed by the DECagent90 may only be reset
         using the DECagent90's MIB.  This object may be used to reset,
         restore, and test all DEChub900 modules and some DEChub90
         modules which reside in the DEChub900 chassis.

         When read, the value 'unknown(1) is returned.

         Setting this object to 'resetAllModules(2)' has the same 
         affect as setting the chasSlotModuleAdminStatus of each
         entry in the chasSlotTable, except the entry for the Hub
         manager itself, to 'reset(4)'.

         Setting this object to 'resetAllModulesAndMgr(3)' has the 
         same affect as setting the chasSlotModuleAdminStatus of each
         entry in the chasSlotTable to 'reset(4)'.  Since the Hub
         Manager is reset, no SNMP response is sent when this object
         is set to resetAllModulesAndMgr(3).

         Setting this object to 'resetAllModulesToDefaults(2)' has 
         the same affect as setting the chasSlotModuleAdminStatus of 
         each entry in the chasSlotTable, except the entry for the Hub
         manager itself, to 'restore-to-defaults(5)'.

         Setting this object to 'resetAllModulesAndMgrToDefaults(3)' 
         has the same affect as setting the chasSlotModuleAdminStatus 
         of each entry in the chasSlotTable to 'restore-to-defaults(5)'.  
         Since the Hub Manager is reset, no SNMP response is sent when 
         this object is set to resetAllModulesAndMgr(3)."
    ::= { chasSlot 7 }

--
--  ===========================================================================
--  ===================  T h e  E n t i t y  G r o u p   ======================
--  ===========================================================================
--
--  The purpose of this group is to provide information about the manageable
--  aspects (entities) of the modules populating the chassis.  Each entry
--  corresponds to a chasSlotIndex on, perhaps, a many-to-one basis.
--  (There may be more than one Entity per Slot.)
--

chasEntityChanges OBJECT-TYPE
    SYNTAX  Counter
    ACCESS  read-only
    STATUS  mandatory
    DESCRIPTION
        "A counter which is incremented whenever entity table entries
         are added or deleted, and when one of the following fields of 
         an existing chasEntityTable is modified:

                  o  chasEntityCommunity,
                  o  chasEntityIpAddress, or
                  o  chasEntityAccessMethod

          Entity changes occur when the IP address or one of the community 
          strings of a device is changed.  This counter is also incremented:

                  o  when modules are inserted,
                  o  when modules are removed, and
                  o  when chasEntityCommunity, chasEntityIpAddress, or
                     chasEntityAccessMethod of an existing entry
                     changes.

         (This does not count in chasEntityOperStatus of an existing
         entry.)"
    ::= { chasEntity 1 }

--
--  Entity Table
--  ============
--
--  The Entity Table provides information about how to manage components
--  within the chassis.  chasEntitySlotNumber contains an index which
--  links Entity Table entries to the Slot Table entries.
--
--  Table Row Creation and Deletion
--  ===============================
--  
--  Entries in the chasEntityTable are created when modules are inserted 
--  into the chassis, and when an inserted module is assigned an IP address 
--  and community string.  Conversely, entries are deleted from this table 
--  when modules are removed from the chassis, and when an inserted module's
--  IP address is deleted.   Table rows can not be created or deleted with 
--  SNMP operations.  
--
--  chasEntityTable Example
--  =======================
--
--  Consider the hub population shown below:
--
--  .___________________________________________________________.________.
--  |                                                           |        |
--  |                  Chassis - Slot 9                         |   p1   |
--  |                                                           |        |
--  |___________________________________________________________.________.
--  |     1      2      3      4      5      6      7      8    |        |
--  |___________________________________________________________|   p2   |
--  |     |                    |             |                  |        |
--  |  ._____.              ._____.       ._____.               .________.
--  |  |  o  |              |  o  |       |  o  |               |        |
--  |  |  o  |              |  o  |       |  o  |               |   p3   |
--  |  |  o  |              |  o  |       |  o  |               |        |
--  |  |_____|              |_____|       |_____|               .________.
--  |                                                           |        |
--  |                                                           |   p4   |
--  |                                                           |        |
--  .___________________________________________________________.________.
--
--
--  Select fields of the chasEntity table for this population might contain
--  the following:
--
--  Slot/ Community IP Address Access Source IP      Subnet      Access Method
--  Index                      Char.  Address        Mask           
--  ===== ========= ========== ====== =========      ======      =============
--   1.1  NULL       0.0.0.0       8   0.0.0.0      0.0.0.0  2,7,1,2,3,4,5,6,7
--                                                                           
--   4.1  anyone     2.2.2.2      49   2.2.0.0    FF.FF.0.0    NULL (0 length)
--   4.2  net_admin  2.2.2.2      50   2.2.2.5  FF.FF.FF.FF    NULL (0 length)
--   4.3  net_admin  2.2.2.2      50   2.2.2.6  FF.FF.FF.FF    NULL (0 length)
--   4.4  NULL       0.0.0.0      40   0.0.0.0      0.0.0.0   3,6,4,4,4,4,0,23
--                                                                           
--   6.1  public     3.3.3.3      33   0.0.0.0      0.0.0.0    NULL (0 length)
--   6.2  private    3.3.3.3      34   0.0.0.0      0.0.0.0    NULL (0 length)
--   6.3  traps      3.3.3.3      36   0.0.0.0      0.0.0.0    NULL (0 length)
--   6.4  public-6   1.1.1.1      21   0.0.0.0      0.0.0.0    NULL (0 length)
--   6.5  secret-6   1.1.1.1      18   0.0.0.0      0.0.0.0    NULL (0 length)
--                                                                           
--   9.1  public     1.1.1.1      21   0.0.0.0      0.0.0.0    NULL (0 length)
--   9.2  secret     1.1.1.1      18   0.0.0.0      0.0.0.0    NULL (0 length)
--  
--  
--  Slot 1 / Entity 1.1
--  ===================
--  The  device  in  slot  1  (entity 1.1)  is   not  manageable  via  SNMP.
--  chasEntityCommunity  and chasEntityIpAddress indicate this by  returning
--  NULL values.  chasEntityAccessMethod indicates that a management station
--  has   the  value  "2,7,1,2,3,4,5,6,7".  (Refer  to  the  description  of
--  chasEntityAccessLoadTable  for further details.)
--
--  The Access Characteristics column value has encoded the access rights as
--  other(3).  NOTE:  If the community name for  the  different  communities 
--  (i.e. readOnly(0), readWrite(1) etc.) is the same then the access rights
--  can  be  encoded into the same value. (Refer to the description  of  the 
--  chasEntityAccessCharacteristics obj. for access rights encoding  rules.)
--  
--  Slot 4 / Entities 4.1 thru 4.4
--  ==============================
--  The  device  in slot 4 (entities 4.1 thru 4.3) is  manageable  via  SNMP
--  using the communities indicated, and the IP address 2.2.2.2.  The device
--  supports host IP address authentication, therefore the Source IP Address
--  and  optionally  the  Subnet Mask are  populated.  Read-only  access  is 
--  granted  via the "anyone" community name, to those host machines on  the
--  2.2.0.0  subnet.   Read-write  access  is granted  via  the  "net_admin" 
--  community  name,  if the source address (of the SNMP PDU)  is  equal  to 
--  2.2.2.5  or 2.2.2.6. (Refer to the description of chasEntitySrcIpAddress 
--  for  details  on  host IP address authentication.)  Also,  Access  Char.
--  defines IP address 2.2.2.2 as a port(3) network interface. (Refer to the
--  description  of the chasEntityAccessCharacteristics object for  encoding
--  rules.)
--
--  The  device in slot 4 is also manageable via telnet (entity  4.4)  using
--  the IP address 4.4.4.4 and the TCP port number 23, which are encoded  in 
--  the  Access Method column. The Access Characteristics column defines the
--  access  rights as an other(3) and the network interface as ibm(2), which
--  using  the respective encoding schemes results in a value of 40.  (Refer
--  to the description of telnet(3) in the chasEntityAccessMethod object and
--  the descriptions  of  access  rights  and  network  interfaces  in   the 
--  chasEntityAccessCharacteristics object.)
-- 
--  Slot 6 / Entities 6.1 thru 6.5
--  ==============================
--  The device in slot 6(entities 6.1 thru 6.5) is manageable via SNMP using
--  the  communities  indicated,  and  the  IP address 3.3.3.3.  Communities
--  "public", "private", and "traps" are used for read-only, read-write, and
--  trap  access, respectively. Additionally, the device is manageable using
--  the Hub Manager's IP address (1.1.1.1).  The community "public-6" allows
--  read-only, and trap access.  The community "secret-6" allows read-write
--- access.
--  
--  The link associated with the device's own  IP  address  and  communities
--  (e.g.   3.3.3.3/public)  usually  provides  higher bandwidth.  Alternate
--  links  using  the  Hub  Manager  (e.g.   1.1.1.1/public-6)  provide   an
--  alternate path to the device's management agent.
--  
--  MIB objects which govern the creation of the  alternate  path  community
--  strings   are   defined   the  DEChub900  Management  Module  MIB.   The
--  communities "public-6" and "secret-6" are used in this example.   (Refer
--  to the hubAuthCreate group.)
--  
--  Slot 9 / Entities 9.1 thru 9.2
--  ==============================
--  Slots numbered from chasNumSlots + 1 (where chasNumSlots is  8  in  this
--  example)  are  used for integral components.  The DEChub900's Management
--  Module is shown as slot 9 in this example.
--  
--  The  device  in slot 9  (entities 9.1 thru 9.2)  is manageable via  SNMP
--  using  the IP address 1.1.1.1.  The community "public" allows read-only,
--  and trap access rights.  The community "secret" allows read-write access
--  rights.
--  
--  

chasEntityTable OBJECT-TYPE
    SYNTAX  SEQUENCE OF ChasEntityEntry
    ACCESS  not-accessible
    STATUS  mandatory
    DESCRIPTION
        "A table containing information about the 'logical' 
         networking devices (entity) in this chassis."
    ::= { chasEntity 2 }

chasEntityEntry OBJECT-TYPE
    SYNTAX  ChasEntityEntry
    ACCESS  not-accessible
    STATUS  mandatory
    DESCRIPTION
        "Information concerning an entity in the chassis.  Table 
         rows may not be created or deleted with SNMP operations."
    INDEX  { chasEntitySlotNumber,
             chasEntityIndex }
    ::= { chasEntityTable 1 }

ChasEntityEntry ::=
    SEQUENCE {
        chasEntityIndex
            INTEGER,
        chasEntityFunction              -- ** Deprecated!
            INTEGER,
        chasEntityObjectID              -- ** Deprecated!
            OBJECT IDENTIFIER,
        chasEntityDescr                 -- ** Deprecated!
            DisplayString,
        chasEntityVersion               -- ** Deprecated!
            DisplayString,
        chasEntityAdminStatus           -- ** Deprecated!
            INTEGER,
        chasEntityOperStatus            -- ** Deprecated!
            INTEGER,
        chasEntityTimeStamp             -- ** Deprecated!
            TimeTicks,
        chasEntityParty                 -- ** Deprecated!
            OBJECT IDENTIFIER,
        chasEntityCommunity
            OCTET STRING,
        chasEntityIpAddress
            IpAddress,
        chasEntityComAccessRights
            INTEGER,
        chasEntityAccessMethod
            OCTET STRING,
        chasEntitySlotNumber
            INTEGER,
        chasEntitySrcIpAddress
            IpAddress,
        chasEntitySrcSubnetMask
            IpAddress,
        chasEntityAccessCharacteristics
            INTEGER
    }

chasEntityIndex OBJECT-TYPE
    SYNTAX  INTEGER (1..65535)
    ACCESS  read-only
    STATUS  mandatory
    DESCRIPTION
        "A unique index for the table entry."
    ::= { chasEntityEntry 1 }

chasEntityFunction OBJECT-TYPE
    SYNTAX  INTEGER (1..32768)
    ACCESS  read-only
    STATUS  deprecated                  -- ** Deprecated!
    DESCRIPTION
        "The generic function of the entity.

         The value is a sum.  Starting from zero, for each
         type of generic function that the entity performs,
         2 raised to a power is added to the sum.  The
         powers are according to the following table:

                 Function  Power
                 --------  ------
                 repeater    0     -- e.g. Ethernet repeater,
                                   -- e.g. FDDI concentrator
                   bridge    1
                   router    2
           terminalServer    3
                    agent    4     -- entity that defines chassis MIB
                 services    5     -- e.g. MIB Walk tools manager etc
                      mau    6
                    power    7
           networkMonitor    8     -- e.g. RMON device
                    other   15     -- e.g. None of the above

           For example, an entity performing both bridging and
           routing functions would have a value of 6 (2^1 +
           2^2).

         ***************************************************************
         This object has been deprecated.  Devices no longer have to
         support it.  It's OID may not be reused.  For devices which
         already support it, it may *not* be used for any purpose other
         than its original indended purpose described above.
         ***************************************************************
        "
    ::= { chasEntityEntry 2 }

chasEntityObjectID  OBJECT-TYPE
    SYNTAX  OBJECT IDENTIFIER
    ACCESS  read-only
    STATUS  deprecated                  -- ** Deprecated!
    DESCRIPTION
        "The value of this object is analogous to the MIB-II 
         sysObjectID object.  As stated in MIB-II, `It provides 
         an easy and unambiguous means for determining what kind 
         of box is being managed.'

         ***************************************************************
         This object has been deprecated.  Devices no longer have to
         support it.  It's OID may not be reused.  For devices which
         already support it, it may *not* be used for any purpose other
         than its original indended purpose described above.
         ***************************************************************
        "
    ::= { chasEntityEntry 3 }

chasEntityDescr  OBJECT-TYPE
    SYNTAX  DisplayString (SIZE (0..255))
    ACCESS  read-only
    STATUS  deprecated                  -- ** Deprecated!
    DESCRIPTION
        "A textual description of the entity.

         ***************************************************************
         This object has been deprecated.  Devices no longer have to
         support it.  It's OID may not be reused.  For devices which
         already support it, it may *not* be used for any purpose other
         than its original indended purpose described above.
         ***************************************************************
        "
    ::= { chasEntityEntry 4 }

chasEntityVersion  OBJECT-TYPE
    SYNTAX  DisplayString (SIZE (0..32))
    ACCESS  read-only
    STATUS  deprecated                  -- ** Deprecated!
    DESCRIPTION
        "A textual description of the version/revision level for 
         this entity's hardware, ROM, and software.

         ***************************************************************
         This object has been deprecated.  Devices no longer have to
         support it.  It's OID may not be reused.  For devices which
         already support it, it may *not* be used for any purpose other
         than its original indended purpose described above.
         ***************************************************************
        "
    ::= { chasEntityEntry 5 }

chasEntityAdminStatus OBJECT-TYPE
    SYNTAX  INTEGER {
                unknown(1),             --  none of the following
                enable(2),
                disable(3),
                reset(4),
                programload(5),
                test(6)
                }
    ACCESS  read-write
    STATUS  deprecated                  -- ** Deprecated!
    DESCRIPTION
        "This object provides the administratively desired state of
         the given entity.

         An entity is activated by writing a value of enable(2).

         An entity may be de-activated by writing a value of disable(3).  
         In a disabled state, a entity exists within the chassis, but 
         is benign.  A disabled entity is available for subsequent 
         activation.  (The table entry remains, but the entity for which
         it refers is disabled.  The entity will perform no SNMP, except 
         the operation to this object.)

         Writing a value of reset(4) specifies an entity initiate a 
         reset sequence.

         Writing a value of programload(5) specifies an entity initiate 
         a program load sequence.

         Writing a value of test(6) specifies an entity initiate a 
         testing sequence.

         Agent support of the writing of any of the values of this object 
         is implementation-specific.  For example, this object might 
         be read-only for entities that disabling would compromise the
         integrity of the chassis.  Or, devices which do not support
         downline load may reject sets to programLoad(5).

         ***************************************************************
         This object has been deprecated.  Devices no longer have to
         support it.  It's OID may not be reused.  For devices which
         already support it, it may *not* be used for any purpose other
         than its original indended purpose described above.
         ***************************************************************
        "
    ::= { chasEntityEntry 6 }

chasEntityOperStatus OBJECT-TYPE
    SYNTAX  INTEGER {
                other(1),               --  none of the following
                invalid(2),
                testing(3),
                operational(4),
                resetInProgress(5),
                warning(6),
                nonFatalError(7),
                fatalError(8),
                loading(10)
                }
    ACCESS  read-only
    STATUS  deprecated                  -- ** Deprecated!
    DESCRIPTION
        "This object provides operational status of the entity.

         other - A value of other(1) implies some undetermined 
         state, possibly as a result of setting chasEntityAdminStatus 
         to a value of disable(3).  

         invalid - A value of invalid(2) indicates that the entity 
         exists but the chassis manager has no direct control of the 
         entity.  

         testing - A value of testing(3) is in a diagnostic state.  

         operational - A value of operational(4) implies that the 
         entity is running with no errors or warnings.

         resetInProgress - State resetInProgress(5) implies equivalent 
         of setting chasEntityAdminStatus to reset(4). 

         warning, nonFatalError, and fatalError - The states warning(6), 
         nonFatalError(7), fatalError(8) reflect conditions detected during
         operation.  The entity is functioning is a diminished capacity
         when warning or nonFatalError are indicated.  When fatalError is
         indicated the device may or may not be functional.  

         loading - State loading(10) is a result of asserting 
         programload(5) in chasEntityAdminStatus.

         ***************************************************************
         This object has been deprecated.  Devices no longer have to
         support it.  It's OID may not be reused.  For devices which
         already support it, it may *not* be used for any purpose other
         than its original indended purpose described above.
         ***************************************************************
        "
    ::= { chasEntityEntry 7 }

chasEntityTimeStamp  OBJECT-TYPE
    SYNTAX  TimeTicks
    ACCESS  read-only
    STATUS  deprecated                  -- ** Deprecated!
    DESCRIPTION
        "The value of MIB-II's sysUpTime (in the agent supporting this 
         MIB) at which this entity was last (re-)initialized.

         ***************************************************************
         This object has been deprecated.  Devices no longer have to
         support it.  It's OID may not be reused.  For devices which
         already support it, it may *not* be used for any purpose other
         than its original indended purpose described above.
         ***************************************************************
        "
    ::= { chasEntityEntry 8 }

chasEntityParty  OBJECT-TYPE
    SYNTAX  OBJECT IDENTIFIER
    ACCESS  read-only
    STATUS  deprecated                  -- ** Deprecated!
    DESCRIPTION
        "The SNMP Version 2 Party which provides access to the detailed 
         management information for this entity.  

         An entity which is not managed through SNMP Version 2 returns
         a zero-length object-identifier.

         An entity which is not managed through SNMP returns 
         chasEntityNoParty.

         ***************************************************************
         This object has been deprecated.  Devices no longer have to
         support it.  It's OID may not be reused.  For devices which
         already support it, it may *not* be used for any purpose other
         than its original indended purpose described above.
         ***************************************************************
        "
    ::= { chasEntityEntry 9 }

chasEntityCommunity  OBJECT-TYPE
    SYNTAX  OCTET STRING (SIZE (0..31))
    ACCESS  read-only
    STATUS  mandatory
    DESCRIPTION
        "The SNMP Community which when paired with chasEntityIpAddress
         provides access to the detailed management information for 
         this entity.

         For a entity which is not managed through access to a SNMP 
         Community, the value of this object is the zero-length string."
    ::= { chasEntityEntry 10 }

chasEntityIpAddress  OBJECT-TYPE
    SYNTAX  IpAddress
    ACCESS  read-only
    STATUS  mandatory
    DESCRIPTION
        "The IP address which when paired with chasEntityCommunity
         provides access to the detailed management information for 
         this entity.  When access is via proxy, this object contains 
         the IP address of the proxy agent.

         For a entity which is not managed through access through a
         community name, internet address pair the value of this object 
         is 0.0.0.0."
    ::= { chasEntityEntry 11 }

chasEntityComAccessRights OBJECT-TYPE
    SYNTAX  INTEGER {
                readOnly(1),
                readWrite(2),
                traps(3),
                other(4)
                }
    ACCESS  read-only
    STATUS  mandatory
    DESCRIPTION
        "The access rights associated with the community name, 
         internet address pair. 

         Note:  Just because a user directs a message to the community
                name, internet address pair does not imply that the
                user is authorized on that pair.  Additional security
                mechanisms may be employed such that only messages from
                particular internet addresses are authorized.

	        THIS OBJECT IS ONLY HERE FOR BACKWARDS COMPATIBILITY
	        WITH OLDER VERSION OF HUBWATCH THAT DO NOT SUPPORT
	        chasEntityAccessCharacteristics.  THIS OBJECT SHOULD BE
	        DEPRECATED WHEN ALL VERSIONS OF HUBWATCH, THAT ARE IN
	        THE FIELD, ARE SUPPORTING THE NEW INTERFACE."
    ::= { chasEntityEntry 12 }

chasEntityAccessMethod OBJECT-TYPE
    SYNTAX  OCTET STRING (SIZE (0..32))
    ACCESS  read-only
    STATUS  mandatory
    DESCRIPTION
        "This object contains methods of access for a given module.
         If the entity is accessed by SNMP the value of this object
         is a zero length string, or a host IP address used for 
         'security' purposes.  If access to the entity is by a means 
         other than SNMP, this object contains the protocol and address
         used to access the Entity.  This object is an opaque type.  It 
         contains a Type-Length-Value encoding where:

            octet 1  Type     The type of protocol address specified in 
                              the value portion of this encoding.  The 
                              type has the form:

                                    dh90Module(1),
                                    mgmtSet(2),
                                    telnet(3)

            octet 2  Length   The length of the value.  This length may 
                              contain a value from 1 to 30.

            octet 3..Length   The value, which may be up to 30 octets.

         The dh90Module(1) type indicates that the entity is a DEChub90
         module.  The eight octet value portion contains a 2 octet 
         DEChub90 module type, followed by a 6 octet hardware address.

         The mgmtSet(2) type indicates that the value of this object
         was derived from the chasEntityAccessLoadTable.  The value
         portion is 'opaque'.  It will take on any value which was
         set in the corresponding entry of the chasEntityAccessLoadTable.

         The telnet(3) type indicates that the module is accessible via
         telnet.  The six octet value portion contains a 4 octet
         IP address, and a 2 octet TCP port number.
        "
    ::= { chasEntityEntry 13 }

chasEntitySlotNumber OBJECT-TYPE
    SYNTAX  INTEGER (1..1024)
    ACCESS  read-only
    STATUS  mandatory
    DESCRIPTION
        "The slot number used to communicate with this agent.
         For entities which occupy more than one slot this value
         is the lowest slot number that this entity occupies."
    ::= { chasEntityEntry 14 }

chasEntitySrcIpAddress  OBJECT-TYPE
    SYNTAX  IpAddress
    ACCESS  read-only
    STATUS  mandatory
    DESCRIPTION
        "This object is used to provide HOST IP ADDRESS AUTHENTICATION.

         Host IP address authentication can be performed two different
         ways, depending on whether there is a subnet mask provided
         in chasEntitySrcSubnetMask.

         If chasEntitySrcSubnetMask is not defined,
         then the host IP address (source IP address in the SNMP command PDU) 
         must be equal to this object.

         If chasEntitySrcSubnetMask is defined,
         then the host IP address (source IP address in the SNMP command PDU)
         is ANDed with the chasEntitySrcSubnetMask, and the value must 
         be equal to this object.

         If the values are equal, 
         then that SNMP command is authorized the community access rights 
         for the associated chasEntityCommunity, chasEntityIpAddress pair.

         NOTE 1: This is assuming that the community profile has been 
         authorized.

         NOTE 2: Multiple source IP addresses can be defined for the
         same community name, internet address pair.  See example 
         at the begining of the chasEntityTable. 

         For an entity which is not supporting host IP address 
         authentication scheme, the value of this object is 0.0.0.0."
    ::= { chasEntityEntry 15 }

chasEntitySrcSubnetMask  OBJECT-TYPE
    SYNTAX  IpAddress
    ACCESS  read-only
    STATUS  mandatory
    DESCRIPTION
        "This object is used in conjunction with the chasEntitySrcIpAddress
         to provide HOST IP ADDRESS AUTHENTICATION.  Refer to
         chasEntitySrcIpAddress for a description

         For an entity that does not support the subnet mask, this 
         value is 0.0.0.0."
    ::= { chasEntityEntry 16 }

chasEntityAccessCharacteristics OBJECT-TYPE
    SYNTAX  INTEGER (1..32768)
    ACCESS  read-only
    STATUS  mandatory
    DESCRIPTION
        "This object is used to provide access characteristics
	 pertaining to other objects in the given entity row.
	 The characteristics are divided into categories.
	 Each category uses a set of predefined bits to 
	 encode data.

	 The following categories are currently supported:

	    Category		        Bits
            --------                    ----
	    Community Access Rights     1..4
	    Network Interface           5..6
	    UNUSED                      7..15

	 The categories are orthogonal to each other, so it
	 is not necessary to perform 'inter-category' bounds
	 checking.

	 The object value is a concatentation of encodings
	 from each category, and can be considered a sum.
	 The actual encoding mechanism is defined on a per
	 category basis.

	 Categories
         ==========

	 Community Access Rights
	 -----------------------
	 Community access rights are associated with the community
	 name, internet address pair.  More than one access right
	 can be defined for a given community name, internet
	 address pair.

         The encoding works as follows:  Starting from zero, for 
	 each access right supported, 2 raised to a power is
         added to the sum.  The powers are according to the
         following table:

                    Type         Power
                    ----         -----
                    readOnly       0
                    readWrite      1
                    trap           2
                    other          3

	 For example, a community name, internet address pair
	 with readOnly and readWrite access rights, would have
	 a value of 3 (2^0 + 2^1).

	 An access right of other(3) defines the entity row as
	 non-SNMP manageable.  Management information is provided 
	 in the chasEntityAccessMethod and the Network Interface
	 (defined below).

         Note:  Just because a user directs a message to the community
                name, internet address pair does not imply that the
                user is authorized on that pair.  Additional security
                mechanisms may be employed such that only messages from
                particular internet addresses are authorized.

	 Network Interface
	 -----------------
	 The network interface is associated with the internet
	 address and defines the route for management traffic.
	 A network interface can be one of the following:

		none(0),
	 	obm(1),
	        ibm(2), and
		port(3).

	 The value is placed in the 2-bits reserved for network
	 interfaces.

	 Note:  ibm(2) and port(3) are both in-band management.  The
	 	difference is ibm(2) is a module wide ip address, and
	 	port(3) is associated with a particular port/interface."
    ::= { chasEntityEntry 17 }

--  
--  chasEntityAccessLoad Table.  
--
--  This table allows Network Management Stations to load the Entity table's 
--  chasEntityAccessMethod object.
--
--  The chassis Hub Manager discovers the population of entities within
--  the hub and maintains information in the Chassis Entity Table.
--  There is a class of modules which can not be "identified" by the Hub
--  Manager.  The chasEntityAccessLoadTable allows for manual configuration 
--  of these entities.
--
--  For example, a user may enter the following into chasEntityAccessLoadTable:
--
--      Slot    AccessMethod
--      ====    ============================================
--       4     0x03,0x07,0x40,0x08,0x00,0x2b,0x12,0x34,0x56
--
--  If, upon initialization, a module is inserted into slot 4, and the 
--  module can not be identified by the Hub Manager, then the chasEntity-
--  AccessMethod for slot 4's entities are updated with chasEntityAccess-
--  LoadMethod.
--
--  In this example, if the module in slot 4 cannot be identified by the 
--  Hub Manager, then a partial chasEntityTable row for the slot will be 
--  created using the information in the chasEntityAccessLoad row for slot 4.
--  The partial row will contain values for only: 
--
--      chasEntityIndex,
--      chasEntitySlot, and 
--      chasEntityAccessMethod; 
--
--  all other objects in the row will be zeroed or null values.
--
--  Sets to the chasEntityAccessLoad table take effect immediately.  However, 
--  if an identified module resides in the specified slot the set will be 
--  rejected.
--
--  Entries in this table are non-volatile.  However, if a module residing 
--  in a slot for which there is an entry in the chasEntityAccessLoadTable 
--  is identified the entry will automatically be deleted from the 
--  chasEntityAccessLoadTable.  This prevents the case where an old entry 
--  in this table causes a failed module to be identified incorrectly 
--  following a management module reset.
--
--  Table Row Creation Semantics
--  ============================
--  Entries in the chasEntityAccessLoadTable are created under the
--  following conditions:
--
--    o  When chasEntityAccessLoadSlot is set.  In this case, the 
--       corresponding chasEntityAccessLoadMethod containing a NULL string 
--       is created.  Users may then set chasEntityAccessLoadMethod.
--    o  When chasEntityAccessLoadMethod is set.  In this case, the 
--       corresponding chasEntityAccessLoadSlot is created based on the 
--       instance provided.
--    o  When both chasEntityAccessLoadSlot and chasEntityAccessLoadMethod
--       are set.
--
--  Table Row Deletion Semantics
--  ============================
--  Entries in the chasEntityAccessLoadTable are deleted when 
--  chasEntityAccessLoadSlot is set to zero.
--
--  -

chasEntityAccessLoadTable OBJECT-TYPE
    SYNTAX  SEQUENCE OF ChasEntityAccessLoadEntry
    ACCESS  not-accessible
    STATUS  mandatory
    DESCRIPTION
        "A table that contain manually entered entity access
         information."
    ::= { chasEntity 3 }

chasEntityAccessLoadEntry OBJECT-TYPE
    SYNTAX  ChasEntityAccessLoadEntry
    ACCESS  not-accessible
    STATUS  mandatory
    DESCRIPTION
        "A list of information about how to access entities."
    INDEX { chasEntityAccessLoadSlot }
    ::= { chasEntityAccessLoadTable 1 }

ChasEntityAccessLoadEntry ::=
    SEQUENCE {
        chasEntityAccessLoadSlot
            INTEGER,
        chasEntityAccessLoadMethod
            OCTET STRING
    }

chasEntityAccessLoadSlot OBJECT-TYPE
    SYNTAX  INTEGER (1..1024)
    ACCESS  read-only
    STATUS  mandatory
    DESCRIPTION
        "The number of the slot in which the chasEntityAccessLoadMethod
         information applies."
    ::= { chasEntityAccessLoadEntry 1 }

chasEntityAccessLoadMethod OBJECT-TYPE
    SYNTAX  OCTET STRING (SIZE(0..16))
    ACCESS  read-write
    STATUS  mandatory
    DESCRIPTION
        "A value which is loaded into chasEntityAccessMethod if
         the slot is occupied by a module for which no better 
         information about how to access the entity exists."
    ::= { chasEntityAccessLoadEntry 2 }

--
--  Entity Change Table
--  ===================
--
--  The Entity Change Table provides a change counter for each
--  occupied slot in the chassis.  Since the Entity Table is
--  unbounded, it has the potential to be a large table.  The
--  Entity Change Table allows an NMS to only read the Entity Table 
--  rows of the modules that have changed.  chasEntityChangeSlot is 
--  an index which links the chasEntityChangeTable entries to the 
--  chasEntityTable.
--
--  Relation to chasEntityChanges
--  =============================
--
--  The chasEntityChanges counter is a global counter that is 
--  incremented on any change in the entire entity table (i.e. 
--  not slot specific).  
--  
--  The chasEntityChanges is most useful in providing a flag to
--  determine if an NMS should read the chasEntityChangeTable,
--  such as in polling.  
--  
--  Change Counter Resets
--  =====================
--
--  The Change Counters are all set to some pseudo-random number, that 
--  is seeded by a product of the MAM Reset counters, upon startup of 
--  the MAM.  Change Counters are reset *only* upon resets of the MAM.
--
--  Setting the Change Counters to some pseudo-random number reduces
--  the chance that Hubwatch and the MAM have different version's of 
--  the Entity Table.  There is a greater chance that a simple reset
--  to zero, between subsequent polls by Hubwatch, would produce the
--  same Change Counter value, even if the table was modified.
--
--  (NOTE: An alternative solution would be to save all the counters
--   in non-volatile storage.)
--  

chasEntityChangeTable OBJECT-TYPE
    SYNTAX  SEQUENCE OF ChasEntityChangeEntry
    ACCESS  not-accessible
    STATUS  mandatory
    DESCRIPTION
        "A table that contains change counters for each module
         in the chassis."
    ::= { chasEntity 4 }

chasEntityChangeEntry OBJECT-TYPE
    SYNTAX  ChasEntityChangeEntry
    ACCESS  not-accessible
    STATUS  mandatory
    DESCRIPTION
        "Information concerning module change counters."
    INDEX { chasEntityChangeSlot }
    ::= { chasEntityChangeTable 1 }

ChasEntityChangeEntry ::=
    SEQUENCE {
        chasEntityChangeSlot
            INTEGER,
        chasEntityChangeCounter
            Counter
    }

chasEntityChangeSlot OBJECT-TYPE
    SYNTAX  INTEGER (1..1024)
    ACCESS  read-only
    STATUS  mandatory
    DESCRIPTION
        "The slot number in which the chasEntityChangeCounter
         applies."
    ::= { chasEntityChangeEntry 1 }

chasEntityChangeCounter OBJECT-TYPE
    SYNTAX  Counter
    ACCESS  read-only
    STATUS  mandatory
    DESCRIPTION
        "A counter which is incremented whenever entity table entries,
         for a particular slot, are added, deleted, or changed.  Adds
         and deletes occur when:

                  o  IP addresses are added,
                  o  IP addresses are deleted,
                  o  modules are inserted, and
                  o  modules are removed.

         Entity changes occur when one of the following fields of an
         existing chasEntityTable is modified:

                  o  chasEntityCommunity,
                  o  chasEntityIpAddress, or
                  o  chasEntityAccessMethod.

         (This does not count in chasEntityOperStatus of an existing
         entry.)

         NOTE: The chasEntityChanges counter is incremented when ever
         an instance of the chasEntityChangeCounter is incremented."
    ::= { chasEntityChangeEntry 2 }

-- ===========================================================================
-- ================  T h e  B a c k p l a n e  G r o u p  ====================
-- ===========================================================================
--
--  The purpose of this group is to describe the backplanes supported
--  within the chassis.
--
--
--  Table Row Creation and Deletion
--  ================================
--  
--  Entries in the chasBackplaneTable are created upon initialization of
--  the SNMP agent.  Table rows can not be created or deleted with SNMP 
--  operations.  
--
--
--  chasBackplaneTable Example
--  ==========================
--  
--  The example below shows the contents of a typical DEChub900 
--  chasBackplaneTable:
-- 
--   Index    Description                         Rev           Num Slots
--   =====    ================================    ===========   =========
--     1      DEChub 900 Backplane                Version 1.0      8
--     2      DEChub 900 Multiswitch Backplane    Version 1.0      8
--

chasBackplaneTable OBJECT-TYPE
    SYNTAX  SEQUENCE OF ChasBackplaneEntry
    ACCESS  not-accessible
    STATUS  mandatory
    DESCRIPTION
        "A table that contains information about the backplane(s) 
         present in the chassis."
    ::= { chasBackplane 1 }

chasBackplaneEntry OBJECT-TYPE
    SYNTAX  ChasBackplaneEntry
    ACCESS  not-accessible
    STATUS  mandatory
    DESCRIPTION
        "A list of information of the backplane(s) in the chassis."
    INDEX  { chasBackplaneIndex }
    ::= {  chasBackplaneTable 1 }

ChasBackplaneEntry ::=
    SEQUENCE  {
        chasBackplaneIndex
            INTEGER,
        chasBackplaneDescr
            DisplayString,
        chasBackplaneRev
            DisplayString,
        chasBackplaneNumSlots
            INTEGER
        }

chasBackplaneIndex OBJECT-TYPE
    SYNTAX  INTEGER (1..255)
    ACCESS  read-only
    STATUS  mandatory
    DESCRIPTION
        "A unique index for the table entry."
    ::= { chasBackplaneEntry 1 }

chasBackplaneDescr OBJECT-TYPE
    SYNTAX  DisplayString (SIZE (0..255))
    ACCESS  read-only
    STATUS  mandatory
    DESCRIPTION
        "A textual description of the backplane."
    ::= { chasBackplaneEntry 2 }

chasBackplaneRev OBJECT-TYPE
    SYNTAX  DisplayString (SIZE (0..32))
    ACCESS  read-only
    STATUS  mandatory
    DESCRIPTION
        "A textual description of the revision level of the backplane."
     ::= { chasBackplaneEntry 3 }

chasBackplaneNumSlots OBJECT-TYPE
    SYNTAX  INTEGER (0..1024)
    ACCESS  read-only
    STATUS  mandatory
    DESCRIPTION
        "The number of slots this backplane supports."
    ::= { chasBackplaneEntry 4 }

-- ===========================================================================
-- =================  T h e  S e g m e n t  G r o u p   ======================
-- ===========================================================================
--
-- The purpose of this group is to describe the communication segments
-- within the chassis.  
--
-- The Segment Table

chasSegmentTable  OBJECT-TYPE
    SYNTAX  SEQUENCE OF ChasSegmentEntry
    ACCESS  not-accessible
    STATUS  mandatory
    DESCRIPTION
        "A table that contains information about the network segments
         contained within the chassis, and used to interconnect the 
         chassis' logical networking devices."
    ::= { chasSegment 1 }

ChasSegmentEntry ::=
    SEQUENCE {
        chasSegmentIndex
            INTEGER,
        chasSegmentName
            DisplayString,
        chasSegmentType
            INTEGER,
        chasSegmentSubtypeSelect
            INTEGER,
        chasSegmentEntryStatus
            INTEGER
        }

chasSegmentEntry OBJECT-TYPE
    SYNTAX  ChasSegmentEntry
    ACCESS  not-accessible
    STATUS  mandatory
    DESCRIPTION
        "A list of information for a particular segment in the chassis."
    INDEX  { chasSegmentIndex }
    ::= { chasSegmentTable 1 }

chasSegmentIndex OBJECT-TYPE
    SYNTAX  INTEGER (1..65535)
    ACCESS  read-only
    STATUS  mandatory
    DESCRIPTION
        "A unique index for the network segment for which this entry 
         contains information."
    ::= { chasSegmentEntry 1 }

chasSegmentName  OBJECT-TYPE
    SYNTAX  DisplayString (SIZE (0..32))
    ACCESS  read-write
    STATUS  mandatory
    DESCRIPTION
        "An administratively assigned segment name."
    ::= { chasSegmentEntry 2 }

chasSegmentType  OBJECT-TYPE
    SYNTAX  INTEGER {
                fddi(1),
                ethernet(2),
                tr(3),
                atm(4),
                async(5),
                pebus(6)
                }
    ACCESS  read-write
    STATUS  mandatory
    DESCRIPTION
        "A segment's media type."
    ::= { chasSegmentEntry 3 }

chasSegmentSubtypeSelect OBJECT-TYPE
    SYNTAX  INTEGER (0..65535)
    ACCESS  read-write
    STATUS  mandatory
    DESCRIPTION
        "The index of specific media type a segment is selected to 
         serve, from the chasSegSubtypeTable."
    ::= { chasSegmentEntry 4 }

chasSegmentEntryStatus  OBJECT-TYPE
    SYNTAX  INTEGER {
                valid(1),
                createRequest(2),
                underCreation(3),
                invalid(4)
                }
    ACCESS  read-write
    STATUS  mandatory
    DESCRIPTION
        "Status of a segment table entry."
    ::= { chasSegmentEntry 5 }

-- The Segment Subtype Table

chasSegSubtypeTable  OBJECT-TYPE
    SYNTAX  SEQUENCE OF ChasSegSubtypeEntry
    ACCESS  not-accessible
    STATUS  mandatory
    DESCRIPTION
        "A table that contains information about the subtype of a 
         network segment, contains additional information about the 
         segment.  The speed of a token ring may be specified, for 
         example."
    ::= { chasSegment 2 }

chasSegSubtypeEntry OBJECT-TYPE
    SYNTAX  ChasSegSubtypeEntry
    ACCESS  not-accessible
    STATUS  mandatory
    DESCRIPTION
        "A list of information of subtypes for segment in the chassis."
    INDEX  { chasSegSubtypeIndex }
    ::= { chasSegSubtypeTable 1 }

ChasSegSubtypeEntry ::=
    SEQUENCE {
        chasSegSubtypeIndex
            INTEGER,
        chasSegSubtypeFlavor
            INTEGER,
        chasSegSubtypeSpeed
            INTEGER,
        chasSegSubtypeEntryStatus
            INTEGER
        }

chasSegSubtypeIndex OBJECT-TYPE
    SYNTAX  INTEGER (1..65535)
    ACCESS  read-only
    STATUS  mandatory
    DESCRIPTION
        "A unique index for the table entry."
    ::= { chasSegSubtypeEntry 1 }

chasSegSubtypeFlavor OBJECT-TYPE
    SYNTAX  INTEGER {
                default(1),       -- Used when only one flavor exists
                thinwire(2),
                imb(3),
                imb2(4)
                }
    ACCESS read-write
    STATUS  mandatory
    DESCRIPTION
        "The specific media type a segment is selected to serve."
    ::= { chasSegSubtypeEntry 2 }

chasSegSubtypeSpeed OBJECT-TYPE
    SYNTAX  INTEGER (0..4294967295)
    ACCESS  read-write
    STATUS  mandatory
    DESCRIPTION
        "The speed of the segment expressed in thousands of bits 
         per second."
    ::= { chasSegSubtypeEntry 3 }

chasSegSubtypeEntryStatus OBJECT-TYPE
    SYNTAX  INTEGER {
                valid(1),
                createRequest(2),
                underCreation(3),
                invalid(4)
                }
    ACCESS  read-write
    STATUS  mandatory
    DESCRIPTION
        "Status of a segment table entry."
    ::= { chasSegSubtypeEntry 4 }

chasSegDefVNbusState  OBJECT-TYPE
    SYNTAX  INTEGER  {
		enabled(1),
		disabled(2)
		}
    ACCESS  read-write
    STATUS  mandatory
    DESCRIPTION 
	"The default VNbus state. While enabled(1), a VNbus segment will be
	 created automatically when a line card containing a VNbus port
	 awakens, and the port will be connected to the segment. The segment
	 will be removed when the last line card containing a VNbus port is
	 removed. No automatic segment/connection creation/removal takes
	 place while this is disabled(2). Enabling the default VNbus causes
	 any unconnected VNbus ports that have not been explicitly disconnected
	 to be connected to the VNbus segment (which will be created 
	 automatically if necessary). Disabling it has no effect on existing
	 VNbus port connections."
    ::= { chasSegment 3 }

-- ===========================================================================
-- ==================  T h e  C o n f i g  G r o u p    ======================
-- ===========================================================================
--
-- The purpose of this group is to both provide information about the
-- chassis type and configuration, and to allow communication channels
-- within the chassis to be configured.  Objects within this group
-- might be used to connect module ports to a communication segment within
-- the chassis.

chasChassisSerialNumber   OBJECT-TYPE
    SYNTAX  DisplayString (SIZE (0..31))
    ACCESS  read-write
    STATUS  mandatory
    DESCRIPTION
        "The serial number of the chassis. If no serial
         number is available, then the value of this object
         should be the zero length string."
    ::= { chasConfig 1 }

chasConnChanges  OBJECT-TYPE
    SYNTAX  Counter
    ACCESS  read-only
    STATUS  mandatory
    DESCRIPTION
        "The number of physical changes that have occurred
         in the chassis backplane configuration since the agent 
         was warm/cold started.  Specifically, this object is 
         incremented:

             1)  whenever chasConnEntryStatus for any object 
                 becomes 'valid',
             2)  whenever chasConnEntryStatus transitions
                 from 'valid' to any other state, and
             3)  whenever the chasConnSegment or chasConnPort
                 of a 'valid' chasConnEntry is modified."

    ::= { chasConfig 2 }

-- Connection table.

chasConnTable  OBJECT-TYPE
    SYNTAX  SEQUENCE OF ChasConnEntry
    ACCESS  not-accessible
    STATUS  mandatory
    DESCRIPTION
        "A list of Tx port to backplane connections.
         At cold boot, MAM initializes the table for a populated
         hub based on default configuration.  MAM has the
         ownership of this table.

         The creation of an entry in this table by NMS causes
         Management Agent to set the interface status of a 
         corresponding icomBpConnTable port to 'connected'."
    ::= { chasConfig 3 }

chasConnEntry  OBJECT-TYPE
    SYNTAX  ChasConnEntry
    ACCESS  not-accessible
    STATUS  mandatory
    DESCRIPTION
        "Backplane connection definition."
    INDEX   { chasConnIndex }
    ::= { chasConnTable 1 }

ChasConnEntry ::=
    SEQUENCE  {
        chasConnIndex
            INTEGER,
        chasConnSegment
            INTEGER,
        chasConnPort
            INTEGER,
        chasConnNextPortIndex
            INTEGER,
        chasConnEntryStatus
            INTEGER
        }

chasConnIndex  OBJECT-TYPE
    SYNTAX  INTEGER (1..65535)
    ACCESS  read-only
    STATUS  mandatory
    DESCRIPTION
        "Index into the table."
    ::= { chasConnEntry 1 }

chasConnSegment  OBJECT-TYPE
    SYNTAX  INTEGER (1..65535)
    ACCESS  read-write
    STATUS  mandatory
    DESCRIPTION
        "An index value of the chasSegmentTable."
    ::= { chasConnEntry 2 }

chasConnPort  OBJECT-TYPE
    SYNTAX  INTEGER (1..65535)
    ACCESS  read-write
    STATUS  mandatory
    DESCRIPTION
        "An index value of the chasPortTable."
    ::= { chasConnEntry 3 }

chasConnNextPortIndex  OBJECT-TYPE
    SYNTAX  INTEGER (1..65535)
    ACCESS  read-write
    STATUS  mandatory
    DESCRIPTION
        "A downstream neighbor's backplane port index in the
         chasPortTable.  It is only used by ring segments.
         This object has the value 65535 when not using a 
         ring segment, or no downstream neighbor exists."
    ::= { chasConnEntry 4 }

chasConnEntryStatus  OBJECT-TYPE
    SYNTAX  INTEGER {
                valid(1),
                createRequest(2),
                underCreation(3),
                invalid(4)
                }
    ACCESS  read-write
    STATUS  mandatory
    DESCRIPTION
        "Status of a connection table entry."
    ::= { chasConnEntry 5 }

-- ===========================================================================
-- ====================  T h e  P o r t  G r o u p    ========================
-- ===========================================================================
--
-- The purpose of this group is to provide information about communication
-- ports of modules within the chassis with can be connected to communication
-- segments within the chassis.  The chassis connection table is used to
-- connect ports described in this group. 

chasPortLastChange OBJECT-TYPE
    SYNTAX  TimeTicks
    ACCESS  read-only
    STATUS  mandatory
    DESCRIPTION
        "The value of MIB-II's sysUpTime (in the agent
         supporting this chassis MIB) at which a port had
         its chasPortOperStatus change."
    ::= { chasPort 1 }

chasPortTable OBJECT-TYPE
    SYNTAX  SEQUENCE OF ChasPortEntry
    ACCESS  not-accessible
    STATUS  mandatory
    DESCRIPTION
        "A list of backplane ports on installed line cards.
         MAM initializes the table based on what is learned from
         the icomBpIfTables and has the ownership of this
         table."
    ::= { chasPort 2 }

chasPortEntry  OBJECT-TYPE
    SYNTAX  ChasPortEntry
    ACCESS  not-accessible
    STATUS  mandatory
    DESCRIPTION
        "Line card backplane port definition."
    INDEX   { chasPortIndex }
    ::= { chasPortTable 1 }

ChasPortEntry ::=
    SEQUENCE  {
        chasPortIndex
            INTEGER,
        chasPortSlot
            INTEGER,
        chasPortName
            DisplayString,
        chasPortType
            INTEGER,
        chasPortSubtypeSelect
            INTEGER,
        chasPortOperStatus
            INTEGER
        }

chasPortIndex OBJECT-TYPE
    SYNTAX  INTEGER (1..65535)
    ACCESS  read-only
    STATUS  mandatory
    DESCRIPTION
        "Index into the table."
    ::= { chasPortEntry 1 }

chasPortSlot OBJECT-TYPE
    SYNTAX  INTEGER (1..1024)
    ACCESS  read-only
    STATUS  mandatory
    DESCRIPTION
        "Slot ID of a line card.  If a line card has more than
         one backplane port, same slot ID may appear multiple
         times in this table."
    ::= { chasPortEntry 2 }

chasPortName OBJECT-TYPE
    SYNTAX  DisplayString (SIZE (0..32))
    ACCESS  read-write
    STATUS  mandatory
    DESCRIPTION
        "An administratively assigned path name.  A Default value
         will be assigned by the management agent module. 
         Users may overwrite the default value.  

         This object in non-volatile.

         The default value is based on the values of chasPortType
         and chasPortSubtypeSelect.  Recommended defaults are:

         Default           chasPortType    chasPortSubtypeSelect
         ================= =============== =====================
         Ethernet          ethernet        0 (Nothing selected)
         Ethernet          ethernet        default
         Thinwire Ethernet ethernet        thinwire
         Repeater Bus      ethernet        imb
         FDDI              fddi            0 (Nothing selected)
         FDDI              fddi            default
         FDDI-A            fddi            fddiA
         FDDI-B            fddi            fddiB
         FDDI-M            fddi            fddiM
         FDDI-S            fddi            fddiS
         Token Ring        tr              0 (Nothing selected)
         Token Ring        tr              default 
         ATM               atm             0 (Nothing selected)
         ATM               atm             default
         Asynchronous      asynch          0 (Nothing selected)
         Asynchronous      asynch          default"

    ::= { chasPortEntry 3 }

chasPortType OBJECT-TYPE
    SYNTAX  INTEGER {
                fddi(1),
                ethernet(2),
                tr(3),
                atm(4),
                async(5),
                pebus(6)
                }
    ACCESS  read-only
    STATUS  mandatory
    DESCRIPTION
        "A port's media type.

         Ethernet type consists of IMB and ThinWire subtypes.
         TrMatrix and TrDH90 are not managed by the matrix
         manager for BL2 (reserved types)."
    ::= { chasPortEntry 4}

chasPortSubtypeSelect  OBJECT-TYPE
    SYNTAX  INTEGER (0..65535)
    ACCESS  read-write
    STATUS  mandatory
    DESCRIPTION
        "The index in chasPortSubtypeTable that has been
         selected for this port.  The 0 value for this index
	 is only legal as a place holder for an unconfigured
	 port."
    ::= { chasPortEntry 5 }

chasPortOperStatus  OBJECT-TYPE
    SYNTAX  INTEGER {
                broken(1),
                unconfigured(2),
                configured(3),
                testing(4),
                connected(5)
                }
    ACCESS  read-only
    STATUS  mandatory
    DESCRIPTION
        "Status of a port."
    ::= { chasPortEntry 6 }

--
--   The Port Descriptor Table
--
--        .________.____________________________.
--        |   Id   |   Descr                    |
--        |________|____________________________|
--
--  Example:
--
--    This example shows a chasPortDescrTable for a terminal
--    server that can load using one backplane ethernet interface
--    and provide terminal services on another once it is loaded.
--
--        .________.____________________________.
--        |   Id   |   Descr                    |
--        |________|____________________________|
--        |    1   |  "Terminal Service Port"   |
--        |________|____________________________|
--        |    2   |  "Downline Load Port"      |
--        |________|____________________________|
--

chasPortDescrTable OBJECT-TYPE
    SYNTAX  SEQUENCE OF ChasPortDescrEntry
    ACCESS  not-accessible
    STATUS  mandatory
    DESCRIPTION
        "A list of backplane port description for installed line cards.
         MAM initializes the table based on what is learned from
         the icomBpIfTables and has the ownership of this
         table."
    ::= { chasPort 3 }

chasPortDescrEntry  OBJECT-TYPE
    SYNTAX  ChasPortDescrEntry
    ACCESS  not-accessible
    STATUS  mandatory
    DESCRIPTION
        "Line card backplane port descriptive text."
    INDEX   { chasPortDescrIndex }
    ::= { chasPortDescrTable 1 }

ChasPortDescrEntry ::=
    SEQUENCE  {
        chasPortDescrIndex
            INTEGER,
        chasPortDescr
            DisplayString
        }

chasPortDescrIndex OBJECT-TYPE
    SYNTAX  INTEGER (1..65535)
    ACCESS  read-only
    STATUS  mandatory
    DESCRIPTION
        "Index in the Port Table of the port described by this entry"
    ::= { chasPortDescrEntry 1 }

chasPortDescr OBJECT-TYPE
    SYNTAX  DisplayString (SIZE (0..32))
    ACCESS  read-only
    STATUS  mandatory
    DESCRIPTION
        "Text that describes the function of the port.  This text is
         read from the line card."
    ::= { chasPortDescrEntry 2 }

--   The Port Subtype Table

chasPortSubtypeTable  OBJECT-TYPE
    SYNTAX  SEQUENCE OF ChasPortSubtypeEntry
    ACCESS  not-accessible
    STATUS  mandatory
    DESCRIPTION
        "A table that contains information about the
         subtype of a port, contains additional
         information about the port. The speed of a token
         ring port may be specified, for example."
    ::= { chasPort 4 }

chasPortSubtypeEntry OBJECT-TYPE
    SYNTAX  ChasPortSubtypeEntry
    ACCESS  not-accessible
    STATUS  mandatory
    DESCRIPTION
        "A list of information of subtypes for port in
         the port table."
    INDEX  { chasPortSubtypeIndex }
    ::= { chasPortSubtypeTable 1 }

ChasPortSubtypeEntry ::=
    SEQUENCE {
        chasPortSubtypeIndex
            INTEGER,
        chasPortSubtypePortIndex
            INTEGER,
        chasPortSubtypeFlavor
            INTEGER,
        chasPortSubtypeSpeed
            INTEGER
        }

chasPortSubtypeIndex OBJECT-TYPE
    SYNTAX  INTEGER (1..65535)
    ACCESS read-only
    STATUS  mandatory
    DESCRIPTION
        "Index into the table."
    ::= { chasPortSubtypeEntry 1 }

chasPortSubtypePortIndex OBJECT-TYPE
    SYNTAX  INTEGER (1..65535)
    ACCESS  read-only
    STATUS  mandatory
    DESCRIPTION
        "The index of a port in the chasPortTable that can support
         the specified chasPortSubtypeFlavor and chasPortSubtypeSpeed.
         A value of '-1' occurs in the first table row indicating a
         port which will not be reconnected on a hub power cycle."
    ::= { chasPortSubtypeEntry 2 }

chasPortSubtypeFlavor OBJECT-TYPE
    SYNTAX  INTEGER {
                default(1),       -- Used when only one flavor exists
                thinwireEndStation(2),
                thinwireRepeater(3),
                imbEndStation(4),
                imbRepeater(5),
                fddiA(6),
                fddiB(7),
                fddiM(8),
                fddiS(9),
                thinwireFlexRepeater(10),
                imbFlexRepeater(11),
                imb2EndStation(12),
                atmMaster(13),
                atmSlave(14),
                imb2Repeater(15),
                imb2FlexRepeater(16)
                }
    ACCESS read-only
    STATUS  mandatory
    DESCRIPTION
        "The specific media type a port is selected to support.
         A value of zero (0), though not allowed as an enumerated value,
         occurs in conjunction with the occurrance of a
         chasPortSubtypePortIndex of '-1' (see above)."
    ::= { chasPortSubtypeEntry 3 }

chasPortSubtypeSpeed OBJECT-TYPE
    SYNTAX  INTEGER (0..4294967295)
    ACCESS read-only
    STATUS  mandatory
    DESCRIPTION
        "The speed of the port expressed in hundreds of bits per 
         second."
    ::= { chasPortSubtypeEntry 4 }

-- ===========================================================================
-- ========  T h e  P o w e r  C o n f i g u r a t i o n   G r o u p  ========
-- ===========================================================================
--
-- The purpose of this group is to provide information about the power
-- supplies within the chassis.  
--

chasPowerConfigMaxSupplies OBJECT-TYPE
    SYNTAX  INTEGER (1..65535)
    ACCESS  read-only
    STATUS  mandatory
    DESCRIPTION
        "The maximum number of power supplies which may be installed
         within this chassis."
    ::= { chasPowerConfig 1 }

chasPowerConfigNumSupplies OBJECT-TYPE
    SYNTAX  INTEGER (1..65535)
    ACCESS  read-only
    STATUS  mandatory
    DESCRIPTION
        "The current number of power supplies which are installed
         within this chassis."
    ::= { chasPowerConfig 2 }

chasPowerConfigChanges OBJECT-TYPE
    SYNTAX  Counter
    ACCESS  read-only
    STATUS  mandatory
    DESCRIPTION
        "A count of the total number of times a chasPowerConfigOperStatus
         value in the chasPowerConfigTable has changed.  This does
         not include changes that occur when entries are created
         and deleted due to module insertion and deletion.

         This counter may not equal the sum of the chasPowerConfig-
         Warnings and chasPowerConfigFailures counters because
         modules which have undergone environmental changes could
         have been removed from the chassis.

         The purpose of this object is to provide a single 
         object which can be polled by an NMS to determine if 
         anything in the chasPowerConfigTable has changed."
    ::= { chasPowerConfig 3 }

chasPowerConfigRedundancyState OBJECT-TYPE
    SYNTAX  INTEGER {
                redundantPowerAvailable(1),
                redundantPowerNotAvailable(2)
                }
    ACCESS  read-only
    STATUS  mandatory
    DESCRIPTION
        "This indicates whether the present configuration can
         continue to operate if any one of the power supplies
         fail or is removed.

         In certain configurations, the hub may need one, two or three
         power supply modules.  The addition of an extra power supply
         module will allow for the failure of any one of the power
         supply modules.  A power system such as this which allows for 
         the failure of any one of the power supplies is referred to as 
         a 'redundant power system'.  Some redundant power systems
         provide standby power supplies which engages only when a 
         primary supply fails.  Unlike this type of system, the DEChub900 
         power system employs load sharing.  Each power supply provides
         a portion of the power necessary to power the system.  When
         redundant power is available in the system, the failure of
         one supply causes the load of the remaining supplies to 
         increase sufficiently to make up for the failed supply."
    ::= { chasPowerConfig 4 }

--
--  The Power Supply Configuration Table
--
--  This power supply table contains information about the power supplies
--  installed within the chassis.  The example below shows a chassis
--  containing slots for four power supplies in which power supplies are 
--  installed in power slots 1 and 3.  
--  
--  .______________________._______________________________________________.
--  | chasPowerConfigIndex |  Other parts of the chasPowerCOnfigTable      |
--  |______________________|_______________________________________________|
--  |          1           | Information about the supply in power slot 1. |
--  |          3           | Information about the supply in power slot 3. |
--  |______________________|_______________________________________________|
--

chasPowerConfigTable OBJECT-TYPE
    SYNTAX  SEQUENCE OF ChasPowerConfigEntry
    ACCESS  not-accessible
    STATUS  mandatory
    DESCRIPTION
        "A list of power supply entries, one for each
         power supply in the chassis."
    ::= { chasPowerConfig 5 }

chasPowerConfigEntry OBJECT-TYPE
    SYNTAX  ChasPowerConfigEntry
    ACCESS  not-accessible
    STATUS  mandatory
    DESCRIPTION
        "Values for a power supply."
    INDEX { chasPowerConfigIndex }
    ::= { chasPowerConfigTable 1 }

ChasPowerConfigEntry ::=
    SEQUENCE {
        chasPowerConfigIndex
            INTEGER,
        chasPowerConfigDescr
            DisplayString,
        chasPowerConfigAdminStatus
            INTEGER,
        chasPowerConfigOperStatus
            INTEGER,
        chasPowerConfigHealthText
            DisplayString,
        chasPowerConfigWarnings
            Counter,
        chasPowerConfigFailures
            Counter
        }

chasPowerConfigIndex OBJECT-TYPE
    SYNTAX  INTEGER (1..65535)
    ACCESS  read-only
    STATUS  mandatory
    DESCRIPTION
        "An index value that uniquely identifies a power
         supply."
    ::= { chasPowerConfigEntry 1 }

chasPowerConfigDescr OBJECT-TYPE
    SYNTAX  DisplayString (SIZE (0..255))
    ACCESS  read-only
    STATUS  mandatory
    DESCRIPTION
        "A textual description of the power supply,
         including the vendor's name and version."
    ::= { chasPowerConfigEntry 2 }

chasPowerConfigAdminStatus OBJECT-TYPE
    SYNTAX  INTEGER {
                unknown(1),
                enable(2),
                disable(3) 
                }
    ACCESS  read-write
    STATUS  mandatory
    DESCRIPTION
        "Desired status of the power supply."
    ::= { chasPowerConfigEntry 3 }

chasPowerConfigOperStatus OBJECT-TYPE
    SYNTAX  INTEGER {
                unknown(1),
                empty(2),
                disabled(3),
                bad(4),
                warning(5),
                standby(6),
                engaged(7),
                redundant(8) 
                }
    ACCESS  read-only
    STATUS  mandatory
    DESCRIPTION
        "Actual status of the power supply:

            o  unknown(1) - status not known.
            o  empty(2) - no power supply installed in slot
            o  disabled(3) - unable to supply power due to
                   chasPowerConfigAdminStatus
            o  bad(4) - unable to supply power due to failure
            o  warning(5) - supplying power but an output or
                   sensor is bad or warning
            o  standby(6) - believed usable but not supplying
                    power
            o  engaged(7) - supplying power
            o  redundant(8) - supplying power but not needed

         It is an implementation specific matter whether
         the agent keeps entries with status unknown(1) or
         empty(2) in the table."
    ::= { chasPowerConfigEntry 4 }

chasPowerConfigHealthText OBJECT-TYPE
    SYNTAX  DisplayString (SIZE (0..255))
    ACCESS  read-only
    STATUS  mandatory
    DESCRIPTION
        "A textual description of the power supply's
         operational status. Agents may use this string to
         provide detailed information on current failures,
         including how they were detected, and/or
         instructions for problem resolution. The contents
         are agent-specific."
    ::= { chasPowerConfigEntry 5 }

chasPowerConfigWarnings OBJECT-TYPE
    SYNTAX  Counter
    ACCESS  read-only
    STATUS  mandatory
    DESCRIPTION
        "The number of times chasPowerConfigOperStatus has
         gone to warning(5)."
    ::= { chasPowerConfigEntry 6 }

chasPowerConfigFailures OBJECT-TYPE
    SYNTAX  Counter
    ACCESS  read-only
    STATUS  mandatory
    DESCRIPTION
        "The number of times chasPowerConfigOperStatus has
         become bad(4)."
    ::= { chasPowerConfigEntry 7 }

-- ===========================================================================
-- ==============  T h e  P o w e r  S o u r c e   G r o u p  ================
-- ===========================================================================
--
-- The purpose of this group is to provide information about the power
-- sources available from power supplies within the chassis.

chasPowerSourceTotalPowerAvailable OBJECT-TYPE
    SYNTAX  INTEGER (0..2147483647)
    ACCESS  read-only
    STATUS  mandatory
    DESCRIPTION
        "The total amount of power available within the chassis.
         This value is expressed in milli-watts.  This value will
         not go below zero if there are unpowered modules in the
         chassis.

         This value is based on the maximum rating of the power
         supply.  Therefore, this value will not equal the sum
         of the chasPowerSourceTable's chasPowerSourcePower objects.
         The chasPowerSourcePower object specifies power available
         at a specific voltage."
    ::= { chasPowerSource 1 }

chasPowerSourceTotalCurrentAvailable OBJECT-TYPE
    SYNTAX  INTEGER (0..2147483647)
    ACCESS  read-only
    STATUS  mandatory
    DESCRIPTION
        "The total amount of current available within the chassis.
         This value is expressed in milli-amperes.  This value will
         not go below zero if there are unpowered modules in the
         chassis."
    ::= { chasPowerSource 2 }

--
--  The Power Source Table
--
--  The power supply source table contain information about power
--  sources available from power supplies within the chassis.
--
--  The example below shows a chassis capable of having four power
--  supplies.  Two power supplies are installed:  in slots 1 and 3.
--  The power supplies is slots 1 and 3 are each capable of sourcing
--  130A@+5V and 90A@+15V.  
--  
--  ._____________._______________._____________._____________.
--  | SupplyIndex |  SourceIndex  |  NomVoltage |    Power    |
--  |_____________|_______________|_____________|_____________|
--  |     1       |       1       |     5000    |    130000   |
--  |     1       |       2       |    15000    |     90000   |
--  |     3       |       1       |     5000    |    130000   |
--  |     3       |       2       |    15000    |     90000   |
--  |_____________|_______________|_____________|_____________|
--

chasPowerSourceTable OBJECT-TYPE
    SYNTAX  SEQUENCE OF ChasPowerSourceEntry
    ACCESS  not-accessible
    STATUS  mandatory
    DESCRIPTION
        "A list of power supply source capabilities."
    ::= { chasPowerSource 3 }

chasPowerSourceEntry OBJECT-TYPE
    SYNTAX  ChasPowerSourceEntry
    ACCESS  not-accessible
    STATUS  mandatory
    DESCRIPTION
        "Values for a power supply output."
    INDEX {  chasPowerSourceSupplyIndex,
             chasPowerSourceIndex }
    ::= { chasPowerSourceTable 1 }

ChasPowerSourceEntry ::=
    SEQUENCE {
        chasPowerSourceSupplyIndex
            INTEGER,
        chasPowerSourceIndex
            INTEGER,
        chasPowerSourceNominalVoltage
            INTEGER,
        chasPowerSourcePower
            INTEGER
        }

chasPowerSourceSupplyIndex OBJECT-TYPE
    SYNTAX  INTEGER (1..65535)
    ACCESS  read-only
    STATUS  mandatory
    DESCRIPTION
        "An index value that identifies the power supply.
         This value corresponds to chasPowerConfigIndex."
    ::= { chasPowerSourceEntry 1 }

chasPowerSourceIndex OBJECT-TYPE
    SYNTAX  INTEGER (1..65535)
    ACCESS  read-only
    STATUS  mandatory
    DESCRIPTION
        "An index value that uniquely identifies an output
         for the power supply.  A value of zero indicates that
         no power supply is installed."
    ::= { chasPowerSourceEntry 2 }

chasPowerSourceNominalVoltage OBJECT-TYPE
    SYNTAX  INTEGER (0..2147483647)
    ACCESS  read-only
    STATUS  mandatory
    DESCRIPTION
        "The nominal voltage available thru this supply.
         The value of this object is expressed in milli-volts."
    ::= { chasPowerSourceEntry 3 }

chasPowerSourcePower OBJECT-TYPE
    SYNTAX  INTEGER (0..2147483647)
    ACCESS  read-only
    STATUS  mandatory
    DESCRIPTION
        "The total power available at the nominal voltage of
         this supply.  The value of this object is expressed
         is milli-watts."
    ::= { chasPowerSourceEntry 4 }

-- ===========================================================================
-- ================  T h e  P o w e r  S i n k   G r o u p  ==================
-- ===========================================================================
--
--  The purpose of this group is to provide information about the power
--  consumption of the modules within the chassis. 

--
--  Power Sink Table 
--
--  The example power sink table population is based on the previous
--  example slot table.  In this chassis, modules are installed in
--  slots 1, 4, and 6.  In addition, extended slots 102, 601, 603,
--  and 10201 are installed.  An integral component to this eight slot
--  chassis is represented by a slot number of 9.
--
--  As shown, the module in slot 1 consumes 20W@+5V and 8.25W@+15V.
--  The module in slot 4 consumes 7W@+5V.  The module in slot 6 could
--  consume 45W@+5V and 22.5W@+15V but is currently not consuming any
--  power.  The integral component, represented as slot 9, consumes 
--  15W@+5V.  All extended slots (102, 601, 603, and 10201) are consuming
--  7W@+5V.  The remaining slots are empty.  
--
--  'notInUse' may denote slots which have failed or been turned of 
--  via management.  In the example below, the module in slot 6 is shown 
--  currently not consuming any power.
--  
--  .____________.__________.___________.__________.__________.
--  | SlotNumber |  Index   |  Voltage  | Wattage  |  Status  |
--  |____________|__________|___________|__________|__________|
--  |      1     |    1     |    5000   |   20000  |   inUse  |
--  |      1     |    2     |   15000   |    8250  |   inUse  | 
--  |      4     |    1     |    5000   |    7000  |   inUse  |
--  |      6     |    1     |    5000   |   45000  | notInUse |
--  |      6     |    2     |   15000   |   22500  | notInUse |
--  |      9     |    1     |    5000   |   15000  |   inUse  |
--  |    102     |    1     |    5000   |    7000  |   inUse  |
--  |    601     |    1     |    5000   |    7000  |   inUse  |
--  |    603     |    1     |    5000   |    7000  |   inUse  |
--  |  10201     |    1     |    5000   |    7000  |   inUse  |
--  |____________|__________|___________|__________|__________|
--  

chasPowerSinkTable  OBJECT-TYPE
    SYNTAX  SEQUENCE OF ChasPowerSinkEntry
    ACCESS  not-accessible
    STATUS  mandatory
    DESCRIPTION
        "A list of slot power requirements."
    ::= { chasPowerSink 1 }

chasPowerSinkEntry  OBJECT-TYPE
    SYNTAX  ChasPowerSinkEntry
    ACCESS  not-accessible
    STATUS  mandatory
    DESCRIPTION
        "A Slot's power requirement definition."
    INDEX   { chasPowerSinkSlotIndex,
              chasPowerSinkIndex }
    ::= { chasPowerSinkTable 1 }

ChasPowerSinkEntry ::=
    SEQUENCE  {
        chasPowerSinkSlotIndex
            INTEGER,
        chasPowerSinkIndex
            INTEGER,
        chasPowerSinkVoltage
            Gauge,
        chasPowerSinkWattage
            Gauge,
        chasPowerSinkOperStatus
            INTEGER
        }

chasPowerSinkSlotIndex  OBJECT-TYPE
    SYNTAX  INTEGER (1..65535)
    ACCESS  read-only
    STATUS  mandatory
    DESCRIPTION
        "An index into the table which corresponds to 
         chasSlotIndex."
    ::= { chasPowerSinkEntry 1 }

chasPowerSinkIndex OBJECT-TYPE
    SYNTAX  INTEGER (1..65535)
    ACCESS  read-only
    STATUS  mandatory
    DESCRIPTION
        "An index per chasPowerSinkVoltage."
    ::= { chasPowerSinkEntry 2 }

chasPowerSinkVoltage OBJECT-TYPE
    SYNTAX  Gauge
    ACCESS  read-only
    STATUS  mandatory
    DESCRIPTION
        "The voltage, in milli-volts used by the power sink."
    ::= { chasPowerSinkEntry 3 }

chasPowerSinkWattage OBJECT-TYPE
    SYNTAX  Gauge
    ACCESS  read-only
    STATUS  mandatory
    DESCRIPTION
        "The amount of power, in milli-watts, needed by the
         power sink."
    ::= { chasPowerSinkEntry 4 }

chasPowerSinkOperStatus OBJECT-TYPE
    SYNTAX  INTEGER {
                unknown(1),
                inUse(2),
                notInUse(3)  
                }
    ACCESS  read-only
    STATUS  mandatory
    DESCRIPTION
        "Indicates if the slot is drawing power.  It is
         an implementation specific matter whether the
         agent keeps entries with status unknown(1) in
         the table."
    ::= { chasPowerSinkEntry 5 }

--
-- ===========================================================================
-- ==============  T h e  E n v i r o n m e n t a l  G r o u p  ==============
-- ===========================================================================
--
--  The purpose of this group is to provide status and control of any
--  environmental sensors within the chassis or modules located within
--  the chassis.
--
--  The chasEnvironTable is indexed by chasEnvironSlotIndex which
--  corresponds to chasSlotNum, and by chasEnvironSensorIndex.
--  These indices allow a many-to-one relationship between sensors
--  and modules.  (They allow more than one sensor per module.)
--
--  As in the chasSlotTable, integral components are represented by
--  a chasEnvironSlotIndex beginning at chasNumSlots + 1.  (For example,
--  within an 8 slot chassis chasEnvironSlotIndex of 9 represents any 
--  sensors integral to the chassis.

--
--
--  Environmental Sensor Table 
--
--  The example environmental sensor table population is based on the 
--  previous example slot table.  In this chassis, modules are installed in
--  slots 1, 4, and 6.  In addition, extended slots 102, 601, 603,
--  and 10201 are installed.  An integral component to this eight slot
--  chassis is represented by a slot number of 9.
--
--  As shown, the module in slot 1 has two sensors, a temperature sensor
--  and a fan sensor.  Slots 2, 3, 5, 7, and 8 are empty.  The table below
--  shown the default values for these empty slots.  Slot 4 contain only
--  a fan sensor, while slot 6 contains both a fan and temperature sensor.
--  The extended slot numbered modules, 102, 601, 603, and 10201 contain
--  no sensors.
--
--  The example shows slot 6's sensor as disabled.  Sensors may be 
--  disabled by management.
--
--  An integral temperature sensor is represented by slot 9.
--
--  .___________._____________._________._____________._____________.___//___.
--  | SlotIndex | SensorIndex | Sensor  | OperStatus  | AdminStatus | Cntrs  |
--  |___________|_____________|_________|_____________|_____________|___//___|
--  |      1    |      1      | temp(2) |   good(4)   | enable(2)   |        |
--  |      1    |      2      | fan(3)  |   good(4)   | enable(2)   |        |
--  |      4    |      1      | fan(3)  |   good(4)   | enable(2)   |        |
--  |      6    |      1      | temp(2) | disabled(5) | disable(3)  |        |
--  |      6    |      2      | fan(3)  |   good(4)   | enable(2)   |        |
--  |      9    |      1      | temp(2) |   good(4)   | enable(2)   |        |
--  |___________|_____________|_________|_____________|_____________|___//___|
--

chasEnvironChanges OBJECT-TYPE
   SYNTAX  Counter
    ACCESS  read-only
    STATUS  mandatory
    DESCRIPTION
        "A count of the total number of changes to existing entries
         in the chasEnvironOperStatus have occurred.  This does not
         include changes that occur when entries are created
         and deleted due to module insertion and deletion.

         This counter may not equal the sum of the chasEnviron-
         Warnings and chasEnvironFailures counters because modules
         which have undergone environmental changes could have
         been removed from the chassis.

         The purpose of this object is to provide a single object
         which can be polled by an NMS to determine if anything
         in the chasEnvironTable has changed."
    ::= { chasEnviron 1 }

chasEnvironTable OBJECT-TYPE
    SYNTAX  SEQUENCE OF ChasEnvironEntry
    ACCESS  not-accessible
    STATUS  mandatory
    DESCRIPTION
        "A list of environmental entries, one for each environmental 
         sensor in the chassis."
    ::= { chasEnviron 2 }

chasEnvironEntry OBJECT-TYPE
    SYNTAX  ChasEnvironEntry
    ACCESS  not-accessible
    STATUS  mandatory
    DESCRIPTION
        "Values for an environmental sensor."
    INDEX { chasEnvironSlotIndex,
            chasEnvironSensorIndex }
    ::= { chasEnvironTable 1 }

ChasEnvironEntry ::=
    SEQUENCE {
        chasEnvironSlotIndex
            INTEGER,
        chasEnvironSensorIndex
            INTEGER,
        chasEnvironSensor
            INTEGER,                           
        chasEnvironOperStatus
            INTEGER,
        chasEnvironAdminStatus
            INTEGER,
        chasEnvironWarnings
            Counter,
        chasEnvironFailures
            Counter
        }

chasEnvironSlotIndex OBJECT-TYPE
    SYNTAX INTEGER (1..65535)
    ACCESS read-only
    STATUS mandatory
    DESCRIPTION
       "An index value that uniquely identifies the slot
        in which the sensor is sensing stuff."
    ::= { chasEnvironEntry 1 }

chasEnvironSensorIndex OBJECT-TYPE
    SYNTAX INTEGER (1..65535)
    ACCESS read-only
    STATUS mandatory
    DESCRIPTION
        "An index value that uniquely identifies one of
         possibly many sensors within a slot."
    ::= { chasEnvironEntry 2 }

chasEnvironSensor OBJECT-TYPE
    SYNTAX  INTEGER {
                other(1),
                temperature(2),
                fan(3),
                humidity(4),
                dc-power(5)
                }     
    ACCESS  read-only
    STATUS  mandatory
    DESCRIPTION
        "The type of the sensor."
    ::= { chasEnvironEntry 3 }

chasEnvironAdminStatus OBJECT-TYPE
    SYNTAX  INTEGER {
                unknown(1),             --  none of the following
                enable(2),
                disable(3)
                }
    ACCESS  read-write
    STATUS  mandatory
    DESCRIPTION
        "The desired state of the sensor.  When sensors are
         'disabled' their chasEnvironWarnings and chasEnvironFailures
         counters do not change.  Moreover, chasEnvironChanges will
         not change as a result of a 'disabled' sensor."
    ::= { chasEnvironEntry 4 }

chasEnvironOperStatus OBJECT-TYPE
    SYNTAX  INTEGER {
                unknown(1),
                bad(2),
                warning(3),
                good(4),
                disabled(5)
                }
    ACCESS  read-only
    STATUS  mandatory
    DESCRIPTION
        "Actual status indicated by the sensor.  It is an 
         implementation specific matter whether the agent keeps 
         entries with status unknown(1) in the table.  If 
         unknown(1), counters are meaningless.  If 'disabled',
         counters freeze."
    ::= { chasEnvironEntry 5 }

chasEnvironWarnings OBJECT-TYPE
    SYNTAX  Counter
    ACCESS  read-only
    STATUS  mandatory
    DESCRIPTION
        "The number of times chasEnvironStatus has gone
         to warning(3)."
    ::= { chasEnvironEntry 6 }

chasEnvironFailures OBJECT-TYPE
    SYNTAX  Counter
    ACCESS  read-only
    STATUS  mandatory
    DESCRIPTION
        "The number of times chasEnvironStatus has gone
         to bad(2)."
    ::= { chasEnvironEntry 7 }

--   
-- ===========================================================================
-- =======================  T h e  L o a d  G r o u p  =======================
-- ===========================================================================
--
--  The purpose of this group is to allow modules within the chassis
--  to be loaded with new firmware.  Only modules which contain hardware
--  capable of such upgrades support this group.
--
--  As in the chasSlotTable, integral components are represented by
--  a chasLoadIndex beginning at chasNumSlots + 1.  (For example, within 
--  an 8 slot chassis containing an integral component capable if being
--  loaded, like an integral management module, chasLoadIndex of 9 
--  is used to load this component.)
--
--  Example 1.
--  ==========
--  The example below shows a load table after a successful load of the
--  module in slot 4.
--
--  .______.___________.___________.__________.___________._________._________.
--  | Slot | AdminStat | OperStat  | FileName | IpAddress | DevSpec | EStatus |
--  |______|___________|___________|__________|___________|_________|_________|
--  |   4  |  other(1) |success(2) |  'foo'   |16.21.16.40|    ?    | valid   |
--  |______|___________|___________|__________|___________|_________|_________|
--

chasLoadTable  OBJECT-TYPE
    SYNTAX  SEQUENCE OF ChasLoadEntry
    ACCESS  not-accessible
    STATUS  mandatory
    DESCRIPTION
        "A list of boot/load information for the slots."
    ::= { chasLoad 1 }

chasLoadEntry  OBJECT-TYPE
    SYNTAX  ChasLoadEntry
    ACCESS  not-accessible
    STATUS  mandatory
    DESCRIPTION
            "Slot boot/load information."
    INDEX   { chasLoadSlotIndex}
    ::= { chasLoadTable 1 }

ChasLoadEntry ::= 
    SEQUENCE {
        chasLoadSlotIndex
            INTEGER,
        chasLoadAdminStatus
            INTEGER,
        chasLoadOperStatus
            INTEGER,
        chasLoadFileName
            DisplayString,
        chasLoadIpHostAddr
            IpAddress,
        chasLoadDevSpecific
            INTEGER,
        chasLoadEntryStatus
            INTEGER
        }

chasLoadSlotIndex OBJECT-TYPE
    SYNTAX  INTEGER (1..1024)
    ACCESS  read-only
    STATUS  mandatory
    DESCRIPTION
        "Slot ID of the owner of the boot information."
    ::= { chasLoadEntry 1 }

chasLoadAdminStatus OBJECT-TYPE
    SYNTAX  INTEGER {
                other(1),
                start-read(2),
                start-write(3),
                cancel(4)
                }
    ACCESS  read-write
    STATUS  mandatory
    DESCRIPTION
        "This object is used to control the program load process of
         a device.  When read, the value other(1) is returned.

         When set to start-read(2) the device initiates a TFTP read
         operation to read a new program image.  When set to
         start-write(3) the device is placed in such a state as to
         accept a new program image via a TFTP write operation.

         Once initiated, the status of the load attempt is 
         reflected in chasLoadOperStatus.

         A device shall always reset upon completion of a 
         successful load attempt.  It may reset upon unsuccessful 
         completion of the load attempt.

         When set to cancel(4) the device will attempt to cancel an
         ongoing load."
     ::= { chasLoadEntry 2 }

chasLoadOperStatus OBJECT-TYPE
    SYNTAX  INTEGER {
                none(1),
                success(2),
                failure(3)
                }
    ACCESS  read-only
    STATUS  mandatory
    DESCRIPTION
        "The final state of the last load attempt. none(1) 
         indicates that no load has been attempted, ever."
    ::= { chasLoadEntry 3 }

chasLoadFileName OBJECT-TYPE
    SYNTAX  DisplayString (SIZE(0..64))
    ACCESS  read-write
    STATUS  mandatory
    DESCRIPTION
        "The name of the file in which to load.  When the device is
         reading, this is the name of the file to be read.  When 
         the device is being written, this is the only name of the
         file in which writes will be accepted - provided the 
         device can check the file name.  If the device can not 
         check the file name then this object is ignored.  It is 
         the duty of the NMS triggering the device to load this 
         object.

         This object is non-volatile for a mam Load.  
         The initial value of this object is a zero-lengthed 
         string.

         In the case of multi-file loads (aka segmented loads) this
         object contains the name of the first file in which to
         load.  It is an application specific issue as to how to 
         get subsequent load files."
    ::= { chasLoadEntry 4 }

chasLoadIpHostAddr OBJECT-TYPE
    SYNTAX  IpAddress
    ACCESS  read-write
    STATUS  mandatory
    DESCRIPTION
        "The IP address of the host from which to load.  When the
         device is reading, this is the IP address of the host in
         which the read will be directed.  When the device is being
         written, this is the IP address of the only host in which
         writes will be accepted.

         This object is non-volatile for slotId corresponding to the
         management agent module.

         The initial value of this object is 0.0.0.0.  Sets of this
         object to 0.0.0.0 and 255.255.255.255 are rejected with a
         badValue error."
    ::= { chasLoadEntry 5 }

chasLoadDevSpecific OBJECT-TYPE
    SYNTAX  INTEGER (0..4294967295)
    ACCESS  read-only
    STATUS  mandatory
    DESCRIPTION
        "A device specific parameter which may be used to indicate
         detailed error information about the last attempted load.
         A value of zero indicates that no load has been attempted,
         or that there is nothing interesting to report of the last
         load."
    ::= { chasLoadEntry 6 }

chasLoadEntryStatus OBJECT-TYPE
    SYNTAX  INTEGER {
                valid(1),
                createRequest(2),
                underCreation(3),
                invalid(4)
                }
    ACCESS  read-write
    STATUS  mandatory
    DESCRIPTION
        "Used to create and delete rows in the load table."
    ::= { chasLoadEntry 7 }

-- ===========================================================================
-- ===============  T h e  K n o w n  T y p e   G r o u p  ===================
-- ===========================================================================
--
--  This group contain OBJECT IDENTIFIER values which may be used by
--  as values to objects within this MIB.
--
--  It is expected that the IETF will define standard 'well known types'.
--  When they do, the values of the OBJECT IDENTIFIERs will be rooted
--  in the MIB-II branch of the MIB tree.  Until such types are defined, 
--  'well known types' are rooted within DEC's private OBJECT IDENTIFIER
--  space.

-- Slot module types
-- =================
--
-- chasSlotEmpty     = 1.3.6.1.4.1.36.2.18.11.1.1.12.1.1
--                     This value is used to represent an empty slot.
--
-- chasSlotUnknown   = 1.3.6.1.4.1.36.2.18.11.1.1.12.1.2
--                     This value is used to represent a module
--                     which the chassis management agent is incapable
--                     of identifying.  (The value might be used if
--                     a broken module is installed in the chassis.
--                     It might also indicate that the software on
--                     either the management agent or module is out
--                     of rev)
--
-- chasSlotBlocked   = 1.3.6.1.4.1.36.2.18.11.1.1.12.1.3
--                     This value is used to indicate that a slot is
--                     blocked because a double (or triple?) width
--                     module is installed in slot(s) to the left
--                     of this slot.
-- 
--       chasKnownTypes     OBJECT IDENTIFIER ::= { chassis 12 }
--       chasKnownModules   OBJECT IDENTIFIER ::= { chasKnownTypes 1 }
--       chasSlotEmpty      OBJECT IDENTIFIER ::= { chasKnownModules 1 }
--       chasSlotUnknown    OBJECT IDENTIFIER ::= { chasKnownModules 2 }
--       chasSlotBlocked    OBJECT IDENTIFIER ::= { chasKnownModules 3 }

--   
-- ===========================================================================
-- =======================  T h e  L i g o  G r o u p  =======================
-- ===========================================================================
--
--

chasLigoNumEntries OBJECT-TYPE
    SYNTAX  INTEGER (0..65535)
    ACCESS  read-only
    STATUS  mandatory
    DESCRIPTION
        "The number of entries in the Ligo table."
    ::= { chasLigo 1 }

--
--  The ligo table.
--

chasLigoTable OBJECT-TYPE
    SYNTAX  SEQUENCE OF ChasLigoEntry
    ACCESS  not-accessible
    STATUS  mandatory
    DESCRIPTION
        "A list of LIGOs (building blocks)."
    ::= { chasLigo 2 }

chasLigoEntry OBJECT-TYPE
    SYNTAX  ChasLigoEntry
    ACCESS  not-accessible
    STATUS  mandatory
    DESCRIPTION
        "A LIGO entry containing objects which describe the building block."
    INDEX   { chasLigoIndex }
    ::= { chasLigoTable 1 }

ChasLigoEntry ::=
    SEQUENCE {
        chasLigoIndex          INTEGER,
        chasLigoSlot           INTEGER,
        chasLigoType           INTEGER,
        chasLigoSubtypeSelect  INTEGER
        }

chasLigoIndex OBJECT-TYPE
    SYNTAX  INTEGER (1..65535)
    ACCESS  read-only
    STATUS  mandatory
    DESCRIPTION
        "A unique value for each LIGO.  The value of
         this object ranges between 1 and n where n is the
         total number of building blocks supported by
         the device."
    ::= { chasLigoEntry 1 }

chasLigoSlot OBJECT-TYPE
    SYNTAX  INTEGER (0..4294967295)
    ACCESS  read-only
    STATUS  mandatory
    DESCRIPTION
        "Slot number associated with this building block."
    ::= { chasLigoEntry 2 }

chasLigoType OBJECT-TYPE
    SYNTAX  INTEGER  {
		other(1),
                fddi(2),
		ethernet(3),
                atm(4)
                }
    ACCESS  read-only
    STATUS  mandatory
    DESCRIPTION
        "A building block's type."
    ::= { chasLigoEntry 3 }

chasLigoSubtypeSelect OBJECT-TYPE
    SYNTAX  INTEGER (0..65535)
    ACCESS  read-write
    STATUS  mandatory
    DESCRIPTION
        "The chasLigoSubtypeIndex into the chasLigoSubtypeTable
         which describes the specific LIGO type a building block
         is selected to support.  The value of this object must be
         a valid index in the chasLigoTable.  A value of 0 
         indicates that no subtype has been selected."
    ::= { chasLigoEntry 4 }

--
--  LIGO subtypes.
--

chasLigoSubtypeNumEntries OBJECT-TYPE
    SYNTAX  INTEGER (0..65535)
    ACCESS  read-only
    STATUS  mandatory
    DESCRIPTION
        "The number of entries in the chasLigoSubtypeTable."
    ::= { chasLigo 3 }

chasLigoSubtypeTable OBJECT-TYPE
    SYNTAX  SEQUENCE OF ChasLigoSubtypeEntry
    ACCESS  not-accessible
    STATUS  mandatory
    DESCRIPTION
        "A list of LIGO (building blocks) subtypes."
    ::= { chasLigo 4 }

chasLigoSubtypeEntry OBJECT-TYPE
    SYNTAX  ChasLigoSubtypeEntry
    ACCESS  not-accessible
    STATUS  mandatory
    DESCRIPTION
        "An entry containing objects which describe the building block's
         specific type."
    INDEX   { chasLigoSubtypeIndex }
    ::= { chasLigoSubtypeTable 1 }

ChasLigoSubtypeEntry ::=
    SEQUENCE {
        chasLigoSubtypeIndex            INTEGER,
        chasLigoSubtypeLigoIndex        INTEGER,
        chasLigoSubtypePortMask         OCTET STRING,
	chasLigoSubtypeLabelIndexMask   OCTET STRING,
	chasLigoSubtypeFlavor           INTEGER,
        chasLigoSubtypePortMaskV2       OCTET STRING,
	chasLigoSubtypeLabelIndexMaskV2 OCTET STRING
        }

chasLigoSubtypeIndex OBJECT-TYPE
    SYNTAX  INTEGER (1..65535)
    ACCESS  read-only
    STATUS  mandatory
    DESCRIPTION
        "A unique value for each LIGO subtype."
    ::= { chasLigoSubtypeEntry 1 }

chasLigoSubtypeLigoIndex OBJECT-TYPE
    SYNTAX  INTEGER (1..65535)
    ACCESS  read-only
    STATUS  mandatory
    DESCRIPTION
        "The value of the LigoIndex in the chasLigoTable that can use
	 this subtype."
    ::= { chasLigoSubtypeEntry 2 }

chasLigoSubtypePortMask OBJECT-TYPE
    SYNTAX OCTET STRING ( SIZE (8))
    ACCESS  read-only
    STATUS  mandatory
    DESCRIPTION
        "This object specifies the ports that are used by this
         LigoSubtype.  It is a bit map of port indexes from the 
         chasPortTable with bit 0 corresponding to port index 1.

         Bits set to 1 indicate the ports which are used by the
	 LigoSubtype."
    ::= { chasLigoSubtypeEntry 3 }

chasLigoSubtypeLabelIndexMask OBJECT-TYPE
   SYNTAX  OCTET STRING ( SIZE (8))
   ACCESS  read-only
   STATUS  mandatory
   DESCRIPTION
       "This object specifies the labels that are used by this
        LigoSubtype.  It is a bit map of if indexes from the
        chasLigoLabelTable with bit 0 corresponding to if index 1.

        Bits set to 1 indicate the labels which are used by the
        LigoSubtype."
   ::= { chasLigoSubtypeEntry 4 }

chasLigoSubtypeFlavor OBJECT-TYPE
    SYNTAX  INTEGER  {
		fddiRoot-Primary(1),       -- A & B on front, M on backplane
                fddiRoot-Secondary(2),
		fddiNonroot(3),            -- M & S on front
		fddiTrunk-A-Primary(4),    -- A on backplane, B on front
		fddiTrunk-A-Secondary(5),
		fddiTrunk-B-Primary(6),    -- B on backplane, A on front
	        fddiTrunk-B-Secondary(7),
		fddiTrunk-AB-Primary(8),   -- A & B on backplane
		fddiTrunk-AB-Secondary(9),
		fddiStump-Primary(10),     -- A & B on front
		fddiStump-Secondary(11),
                ethernet-front(12),
                ethernet-back(13),
                fddiNonroot-M(14),	   -- S on front, M on backplane
                fddiNonroot-S(15),	   -- M on front, S on backplane
                fddiNonroot-SM(16),        -- M & S on backplane
                atm-front(17),
                atm-back(18)
                }
    ACCESS  read-only
    STATUS  mandatory
    DESCRIPTION
        "A building block's type."
    ::= { chasLigoSubtypeEntry 5 }

chasLigoSubtypePortMaskV2 OBJECT-TYPE
    SYNTAX OCTET STRING ( SIZE (16))
    ACCESS  read-only
    STATUS  mandatory
    DESCRIPTION
        "This object specifies the ports that are used by this
         LigoSubtype.  It is a bit map of port indexes from the 
         chasPortTable with bit 0 corresponding to port index 1.
         This object supports twice as many ports in the hub
         as chasLigoSubtypePortMask.

         Bits set to 1 indicate the ports which are used by the
	 LigoSubtype."
    ::= { chasLigoSubtypeEntry 6 }

chasLigoSubtypeLabelIndexMaskV2 OBJECT-TYPE
   SYNTAX  OCTET STRING ( SIZE (16))
   ACCESS  read-only
   STATUS  mandatory
   DESCRIPTION
       "This object specifies the labels that are used by this
        LigoSubtype.  It is a bit map of if indexes from the
        chasLigoLabelTable with bit 0 corresponding to if index 1.
        This object supports twice as many ligos in the hub
        as chasLigoSubtypeLabelIndexMask.

        Bits set to 1 indicate the labels which are used by the
        LigoSubtype."
   ::= { chasLigoSubtypeEntry 7 }

--
--  LIGO labels.
--

chasLigoLabelNumEntries OBJECT-TYPE
    SYNTAX  INTEGER (0..65535)
    ACCESS  read-only
    STATUS  mandatory
    DESCRIPTION
        "The number of entries in the chasLigo label table."
    ::= { chasLigo 5 }

chasLigoLabelTable OBJECT-TYPE
    SYNTAX  SEQUENCE OF ChasLigoLabelEntry
    ACCESS  not-accessible
    STATUS  mandatory
    DESCRIPTION
        "A list of Labels (for ports)."
    ::= { chasLigo 6 }

chasLigoLabelEntry OBJECT-TYPE
    SYNTAX  ChasLigoLabelEntry
    ACCESS  not-accessible
    STATUS  mandatory
    DESCRIPTION
        "An entry containing objects which describe the label of the
         port affected by the LIGO this module supports."
    INDEX   { chasLigoLabelIndex }
    ::= { chasLigoLabelTable 1 }

ChasLigoLabelEntry ::=
    SEQUENCE {
        chasLigoLabelIndex          INTEGER,
        chasLigoLabelString         DisplayString
        }

chasLigoLabelIndex OBJECT-TYPE
    SYNTAX  INTEGER (1..65535)
    ACCESS  read-only
    STATUS  mandatory
    DESCRIPTION
        "A unique value for each Label.  The value of
         this object ranges between 1 and n where n is the
         total number of Labels supported by the device."
    ::= { chasLigoLabelEntry 1 }

chasLigoLabelString OBJECT-TYPE
    SYNTAX  DisplayString (SIZE (0..32))
    ACCESS  read-only
    STATUS  mandatory
    DESCRIPTION
        "A textual description of the port number associated
         with a LIGO.  If the device is bridge then bridge port number
         should be used for the ethernet and fddi. If the device is a
         wire concentrator then concentrator port numbers should be used."
    ::= { chasLigoLabelEntry 2 }

--   
-- ===========================================================================
-- ==================  T h e  P a t c h i n g  G r o u p  ====================
-- ===========================================================================
--
--  The purpose of this group is to provide information about and control 
--  the Backplane Auto Healing capabilities of the Management Agent Module. 
-- 
--

chasRingPatching  OBJECT-TYPE
    SYNTAX  INTEGER  {
		enabled(1),
		disabled(2)
		}
    ACCESS  read-write
    STATUS  mandatory
    DESCRIPTION 
	"Provides the means to enable and disable Backplane Auto Healing. 
	 When enabled, the Management Agent Module updates the 
         chasRingMemberTable with the current backplane configuration, 
	 and takes action to repair FDDI rings and performs whatever steps
	 are necessary for all other backplane technologies when a module 
	 is out of service.

	 When disabled, all entries of the chasRingMember table are 
	 deleted and the Management Agent Module will not perform any
	 Backplane Auto Healing."
    ::= { chasPatching 1 }

chasRingMemberTable  OBJECT-TYPE
    SYNTAX  SEQUENCE OF ChasRingMemberEntry
    ACCESS  not-accessible
    STATUS  mandatory
    DESCRIPTION
	"A list of slots and their status."
    ::= { chasPatching 2}

chasRingMemberEntry  OBJECT-TYPE
    SYNTAX  ChasRingMemberEntry
    ACCESS  not-accessible
    STATUS  mandatory
    DESCRIPTION
	"An entry containing the objects which describe the slots and
	 their patching status."
    INDEX   { chasRingMemberSlot }
    ::= { chasRingMemberTable 1 }

ChasRingMemberEntry  ::=
    SEQUENCE {
	chasRingMemberSlot	INTEGER,
	chasRingMemberSegment   INTEGER,
	chasRingMemberStatus	INTEGER,
	chasRingMemberSegmentMask OCTET STRING
	}

chasRingMemberSlot OBJECT-TYPE
    SYNTAX  INTEGER (1..1024)
    ACCESS  read-only
    STATUS  mandatory
    DESCRIPTION
	"The backplane slot ID for this entry. Only slots that are 
	 currently eligible for patching will appear in the table."
    ::= { chasRingMemberEntry 1 }

chasRingMemberSegment OBJECT-TYPE
    SYNTAX  INTEGER (1..65535)
    ACCESS  read-only
    STATUS  mandatory
    DESCRIPTION
        "The FDDI network segment for which this entry contains information, 
         from chasSegmentIndex. This object is superceded by the 
	 chasRingMemberSegmentMask, but is left here for backwards 
	 compatibility."
    ::= { chasRingMemberEntry 2 }

chasRingMemberStatus OBJECT-TYPE
    SYNTAX  INTEGER {
		in(1),
		out(2)
		}
    ACCESS  read-only
    STATUS  mandatory
    DESCRIPTION
	"The current patch status of the slot. in(1) means that the linecard
	 is an active part of the hub. out(2) means the linecard has been 
         patched around if necessary, and is not currently attached to 
	 its backplane LAN(s)."
    ::= { chasRingMemberEntry 3 }

chasRingMemberSegmentMask OBJECT-TYPE
    SYNTAX OCTET STRING ( SIZE (4))
    ACCESS  read-only
    STATUS  mandatory
    DESCRIPTION
        "This object specifies the segments that are used by this
         slot module.  It is a bit map of segment indexes from the 
         chasSegmentTable with bit 0 corresponding to segment index 1.

         Bits set to 1 indicate the segments which are used by the
	 slot module."
    ::= { chasRingMemberEntry 4 }

-- ===========================================================================
-- =======================  E n d   o f   M I B   ============================
-- ===========================================================================

END
