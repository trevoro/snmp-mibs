Nortel-Magellan-Passport-ModAtmQosMIB
DEFINITIONS ::= BEGIN



IMPORTS

      OBJECT-TYPE
   FROM RFC-1212

      passportMIBs
   FROM Nortel-Magellan-Passport-UsefulDefinitionsMIB

      DisplayString,
      StorageType,
      RowStatus,
      Integer32,
      Unsigned32
   FROM Nortel-Magellan-Passport-StandardTextualConventionsMIB

      NonReplicated
   FROM Nortel-Magellan-Passport-TextualConventionsMIB

      modFrsIndex,
      modFrs
   FROM Nortel-Magellan-Passport-ModCommonMIB

      modIndex
   FROM Nortel-Magellan-Passport-ShelfMIB;




-- LAST-UPDATED   "9902010000Z"
-- ORGANIZATION   "Nortel"
-- CONTACT-INFO   "
--         Nortel Magellan Network Management
--         
--         Postal: P.O. Box 5080, Station F 
--                 Ottawa, Ontario 
--                 Canada  K2C 3T1
--         
--         Email:  nm_plm@nt.com"
-- DESCRIPTION
--    "The module describing the Nortel Magellan Passport
--     ModAtmQos Enterprise MIB."

modAtmQosMIB OBJECT IDENTIFIER ::= { passportMIBs 75 }










-- Mod Frs AtmNetworking
-- AtmNetworking is used to define a number of general characteristics 
-- for all Frame Relay to ATM interworking on module. All the 
-- modules in the network should have identical AtmNetworking 
-- attributes. If these attributes are not consistent across the network, 
-- then the service may be degraded. 

modFrsAtmNet OBJECT IDENTIFIER ::= { modFrs 2 }



modFrsAtmNetRowStatusTable OBJECT-TYPE
   SYNTAX     SEQUENCE OF ModFrsAtmNetRowStatusEntry
   ACCESS     not-accessible
   STATUS     mandatory
   DESCRIPTION
     "This entry controls the addition and deletion of 
      modFrsAtmNet components."
::= { modFrsAtmNet 1 }

modFrsAtmNetRowStatusEntry OBJECT-TYPE
   SYNTAX     ModFrsAtmNetRowStatusEntry
   ACCESS     not-accessible
   STATUS     mandatory
   DESCRIPTION
     "A single entry in the table represents a single 
      modFrsAtmNet component."
   INDEX {
      modIndex,
      modFrsIndex,
      modFrsAtmNetIndex }
::= { modFrsAtmNetRowStatusTable 1 }

ModFrsAtmNetRowStatusEntry ::= SEQUENCE {
   modFrsAtmNetRowStatus
      RowStatus,
   modFrsAtmNetComponentName
      DisplayString,
   modFrsAtmNetStorageType
      StorageType,
   modFrsAtmNetIndex
      NonReplicated }

modFrsAtmNetRowStatus OBJECT-TYPE
   SYNTAX     RowStatus 
   ACCESS     read-only
   STATUS     mandatory
   DESCRIPTION
     "This variable is used as the basis for SNMP naming of
      modFrsAtmNet components.
      These components cannot be added nor deleted."
::= { modFrsAtmNetRowStatusEntry 1 }

modFrsAtmNetComponentName OBJECT-TYPE
   SYNTAX     DisplayString 
   ACCESS     read-only
   STATUS     mandatory
   DESCRIPTION
     "This variable provides the component's string name for
      use with the ASCII Console Interface"
::= { modFrsAtmNetRowStatusEntry 2 }

modFrsAtmNetStorageType OBJECT-TYPE
   SYNTAX     StorageType 
   ACCESS     read-only
   STATUS     mandatory
   DESCRIPTION
     "This variable represents the storage type value for the
      modFrsAtmNet tables."
::= { modFrsAtmNetRowStatusEntry 4 }

modFrsAtmNetIndex OBJECT-TYPE
   SYNTAX     NonReplicated 
   ACCESS     not-accessible
   STATUS     mandatory
   DESCRIPTION
     "This variable represents the index for the modFrsAtmNet tables."
::= { modFrsAtmNetRowStatusEntry 10 }

modFrsAtmNetProvTable OBJECT-TYPE
   SYNTAX     SEQUENCE OF ModFrsAtmNetProvEntry
   ACCESS     not-accessible
   STATUS     mandatory
   DESCRIPTION
     "This group contains information related to the Frame Relay to ATM 
      interworking."
::= { modFrsAtmNet 10 }

modFrsAtmNetProvEntry OBJECT-TYPE
   SYNTAX     ModFrsAtmNetProvEntry
   ACCESS     not-accessible
   STATUS     mandatory
   DESCRIPTION
     "An entry in the modFrsAtmNetProvTable."
   INDEX {
      modIndex,
      modFrsIndex,
      modFrsAtmNetIndex }
::= { modFrsAtmNetProvTable 1 }

ModFrsAtmNetProvEntry ::= SEQUENCE {
   modFrsAtmNetRetryTimerPeriod
      Unsigned32 }

modFrsAtmNetRetryTimerPeriod OBJECT-TYPE
   SYNTAX     Unsigned32 (30..300)
   ACCESS     read-write
   STATUS     mandatory
   DESCRIPTION
     "This attribute specifies the module wide retry timer interval for 
      failed SPVC calls using Frame Relay to ATM Networking. Changes 
      to this attribute will take effect on subsequent call setups."
   DEFVAL     { 60 }
::= { modFrsAtmNetProvEntry 1 }


-- Mod Frs AtmNet TransferPriorityMapping/n
-- This component specifies call setup parameters for Frame Relay to 
-- ATM interworking using transfer priority n. The changed 
-- parameters will take effect on new calls.
-- 
-- Some attributes can be overidden on per interface basis by FrAtm 
-- Ca Tpm component.

modFrsAtmNetTpm OBJECT IDENTIFIER ::= { modFrsAtmNet 2 }



modFrsAtmNetTpmRowStatusTable OBJECT-TYPE
   SYNTAX     SEQUENCE OF ModFrsAtmNetTpmRowStatusEntry
   ACCESS     not-accessible
   STATUS     mandatory
   DESCRIPTION
     "This entry controls the addition and deletion of 
      modFrsAtmNetTpm components."
::= { modFrsAtmNetTpm 1 }

modFrsAtmNetTpmRowStatusEntry OBJECT-TYPE
   SYNTAX     ModFrsAtmNetTpmRowStatusEntry
   ACCESS     not-accessible
   STATUS     mandatory
   DESCRIPTION
     "A single entry in the table represents a single 
      modFrsAtmNetTpm component."
   INDEX {
      modIndex,
      modFrsIndex,
      modFrsAtmNetIndex,
      modFrsAtmNetTpmIndex }
::= { modFrsAtmNetTpmRowStatusTable 1 }

ModFrsAtmNetTpmRowStatusEntry ::= SEQUENCE {
   modFrsAtmNetTpmRowStatus
      RowStatus,
   modFrsAtmNetTpmComponentName
      DisplayString,
   modFrsAtmNetTpmStorageType
      StorageType,
   modFrsAtmNetTpmIndex
      Integer32 }

modFrsAtmNetTpmRowStatus OBJECT-TYPE
   SYNTAX     RowStatus 
   ACCESS     read-write
   STATUS     mandatory
   DESCRIPTION
     "This variable is used as the basis for SNMP naming of
      modFrsAtmNetTpm components.
      These components can be added."
::= { modFrsAtmNetTpmRowStatusEntry 1 }

modFrsAtmNetTpmComponentName OBJECT-TYPE
   SYNTAX     DisplayString 
   ACCESS     read-only
   STATUS     mandatory
   DESCRIPTION
     "This variable provides the component's string name for
      use with the ASCII Console Interface"
::= { modFrsAtmNetTpmRowStatusEntry 2 }

modFrsAtmNetTpmStorageType OBJECT-TYPE
   SYNTAX     StorageType 
   ACCESS     read-only
   STATUS     mandatory
   DESCRIPTION
     "This variable represents the storage type value for the
      modFrsAtmNetTpm tables."
::= { modFrsAtmNetTpmRowStatusEntry 4 }

modFrsAtmNetTpmIndex OBJECT-TYPE
   SYNTAX     Integer32 (0..15)
   ACCESS     not-accessible
   STATUS     mandatory
   DESCRIPTION
     "This variable represents the index for the modFrsAtmNetTpm tables."
::= { modFrsAtmNetTpmRowStatusEntry 10 }

modFrsAtmNetTpmProvTable OBJECT-TYPE
   SYNTAX     SEQUENCE OF ModFrsAtmNetTpmProvEntry
   ACCESS     not-accessible
   STATUS     mandatory
   DESCRIPTION
     "This group specifies the mapping from Frame Relay parameters to 
      ATM parameters for a Frame Relay using the defined transfer 
      priority."
::= { modFrsAtmNetTpm 2 }

modFrsAtmNetTpmProvEntry OBJECT-TYPE
   SYNTAX     ModFrsAtmNetTpmProvEntry
   ACCESS     not-accessible
   STATUS     mandatory
   DESCRIPTION
     "An entry in the modFrsAtmNetTpmProvTable."
   INDEX {
      modIndex,
      modFrsIndex,
      modFrsAtmNetIndex,
      modFrsAtmNetTpmIndex }
::= { modFrsAtmNetTpmProvTable 1 }

ModFrsAtmNetTpmProvEntry ::= SEQUENCE {
   modFrsAtmNetTpmEmissionPriority
      Unsigned32,
   modFrsAtmNetTpmAtmServiceCategory
      INTEGER,
   modFrsAtmNetTpmAvgFrameSize
      Unsigned32,
   modFrsAtmNetTpmTrafficParmConversionPolicy
      INTEGER,
   modFrsAtmNetTpmAssignedBandwidthPool
      INTEGER }

modFrsAtmNetTpmEmissionPriority OBJECT-TYPE
   SYNTAX     Unsigned32 (0..3)
   ACCESS     read-write
   STATUS     mandatory
   DESCRIPTION
     "This attribute specifies the egress emission priority at the FR to 
      ATM interface. A value of 3 specifies the highest priority, whereas a 
      value of 0 specifies the lowest priority."
   DEFVAL     { 0 }
::= { modFrsAtmNetTpmProvEntry 1 }

modFrsAtmNetTpmAtmServiceCategory OBJECT-TYPE
   SYNTAX     INTEGER  {
                 ubr(0),
                 cbr(1),
                 rtVbr(2),
                 nrtVbr(3) }
   ACCESS     read-write
   STATUS     mandatory
   DESCRIPTION
     "This attribute specifies the ATM class of service value to be used on 
      a transport connection."
   DEFVAL     { nrtVbr }
::= { modFrsAtmNetTpmProvEntry 2 }

modFrsAtmNetTpmAvgFrameSize OBJECT-TYPE
   SYNTAX     Unsigned32 (1..8187)
   ACCESS     read-write
   STATUS     mandatory
   DESCRIPTION
     "This attribute specifies the average frame size that is used in the 
      traffic parameter conversion policy calculations for this transfer 
      priority to determine the overhead factor for FR to ATM 
      interworking. The overhead factor affects the granularity of the 
      bandwidth requirements. The values should be identical across the 
      network. Otherwise, there may result in bandwidth conversion 
      inconsistencies."
   DEFVAL     { 128 }
::= { modFrsAtmNetTpmProvEntry 3 }

modFrsAtmNetTpmTrafficParmConversionPolicy OBJECT-TYPE
   SYNTAX     INTEGER  {
                 n3(3),
                 n4(4),
                 n5(5),
                 n6(6) }
   ACCESS     read-write
   STATUS     mandatory
   DESCRIPTION
     "This attribute specifies the traffic parameter conversion policy to use 
      for this transfer priority to specify the equivalent bandwidth rate at 
      the FrAtm interface. 
      
      Policy 3 characterizes the traffic in the following way:
      - ATM traffic descriptor type 6 is selected
      - PCR0+1 is based on the AR
      - SCR0+1 is based on the CIR and EIR
      - MBS0+1 is based on Bc,Be,CIR,EIR and AR
      - Takes into account that the instananeous rate of the frame relay 
      stream can burst above CIR and up tp the AR.
      
      Policy 4 characterizes the traffic in the following way:
      - ATM traffic descriptor type 7 or 8 is selected. Type 7 is chosen 
      when non-conforming cells are to be discarded and type 8 when 
      non-conforming cells are tagged by UPC traffic policer.
      - PCR0+1 is based on the AR
      - SCR0 is based on the CIR
      - MBS0 is based on Bc,CIR and AR
      - There is no direct characterization of EIR. The allowed EIR can be 
      derived using the difference between the AR and CIR.
      
      Policy 5 characterizes the traffic in the following way:
      - ATM traffic descriptor type 7 or 8 is selected . Type 7 is chosen 
      when non-conforming cells are to be discarded and type 8 when 
      non-conforming cells are tagged by UPC traffic policer
      - PCR0+1 is based on CIR and EIR
      - SCR0 is based on the CIR
      - MBS0 is based on the Bc,CIR and AR
      - The maximum PCR is no longer based on AR but based on the 
      CIR and EIR.
      
      Policy 6 characterizes the traffic in the following way:
      - ATM traffic descriptor type 3 is selected
      - PCR0+1 is based only on CIR."
   DEFVAL     { n6 }
::= { modFrsAtmNetTpmProvEntry 4 }

modFrsAtmNetTpmAssignedBandwidthPool OBJECT-TYPE
   SYNTAX     INTEGER  {
                 n0(0),
                 n1(1),
                 n2(2),
                 n3(3),
                 n4(4),
                 n5(5),
                 n6(6),
                 n7(7),
                 n8(8),
                 n9(9),
                 n10(10),
                 n11(11),
                 n12(12),
                 n13(13),
                 n14(14),
                 n15(15) }
   ACCESS     read-write
   STATUS     mandatory
   DESCRIPTION
     "This attribute specifies the bandwidth pool which is used to support 
      this transfer priority. The bandwidth pool is defined in the frAtm Ca 
      component."
   DEFVAL     { n0 }
::= { modFrsAtmNetTpmProvEntry 5 }




-- 
-- Version and Compliance statements
-- 



-- Object-Group Statement:
-- A list of all current accessible leaf objects.

-- OBJECTS { modFrsAtmNetTpmEmissionPriority,
--           modFrsAtmNetTpmTrafficParmConversionPolicy,
--           modFrsAtmNetTpmComponentName,
--           modFrsAtmNetComponentName,
--           modFrsAtmNetTpmStorageType,
--           modFrsAtmNetTpmRowStatus,
--           modFrsAtmNetStorageType,
--           modFrsAtmNetRowStatus,
--           modFrsAtmNetTpmAvgFrameSize,
--           modFrsAtmNetRetryTimerPeriod,
--           modFrsAtmNetTpmAssignedBandwidthPool,
--           modFrsAtmNetTpmAtmServiceCategory }
-- STATUS  mandatory
-- DESCRIPTION
--   "A list of all current accessible leaf objects."

modAtmQosGroup OBJECT IDENTIFIER ::= { modAtmQosMIB 1 }
modAtmQosGroupBE OBJECT IDENTIFIER ::= { modAtmQosGroup 5 }
modAtmQosGroupBE01 OBJECT IDENTIFIER ::= { modAtmQosGroupBE 2 }
modAtmQosGroupBE01A OBJECT IDENTIFIER ::= { modAtmQosGroupBE01 2 }



-- Agent-Capabilities Statement:

-- PRODUCT-RELEASE "Passport Release 7.0 ModAtmQos."
-- STATUS          mandatory
-- DESCRIPTION     "ModAtmQos MIB: MIB Version BE01A,
--                  Software Version BG00S4C."
-- SUPPORTS        Nortel-Magellan-Passport-ModAtmQosMIB
--    INCLUDES     { modAtmQosGroupBE01A }

modAtmQosCapabilities OBJECT IDENTIFIER ::= { modAtmQosMIB 3 }
modAtmQosCapabilitiesBE OBJECT IDENTIFIER ::= { modAtmQosCapabilities 5 }
modAtmQosCapabilitiesBE01 OBJECT IDENTIFIER ::= { modAtmQosCapabilitiesBE 2 }
modAtmQosCapabilitiesBE01A OBJECT IDENTIFIER ::= { modAtmQosCapabilitiesBE01 2 }





END
