-- *****************************************************************
-- CISCO-POWER-ETHERNET-EXT-CAPABILITY.my:
-- Cisco CISCO-POWER-ETHERNET-EXT-MIB AGENT-CAPABILITIES
--   
-- June 2004, Seth Wang
--   
-- Copyright (c) 2004,2006-2007 by Cisco Systems, Inc.
--  
--   
-- All rights reserved.
-- ***************************************************************

CISCO-POWER-ETHERNET-EXT-CAPABILITY DEFINITIONS ::= BEGIN

IMPORTS
    MODULE-IDENTITY,
    Unsigned32
        FROM SNMPv2-SMI
    AGENT-CAPABILITIES
        FROM SNMPv2-CONF
    ciscoAgentCapability
        FROM CISCO-SMI;


ciscoPowerEthernetExtCapability MODULE-IDENTITY
    LAST-UPDATED    "200612200000Z"
    ORGANIZATION    "Cisco Systems, Inc."
    CONTACT-INFO
            "Cisco Systems
            Customer Service

            Postal: 170 West Tasman Drive
            San Jose, CA  95134
            USA

            Tel: +1 800 553-NETS

            E-mail: cs-lan-switch-snmp@cisco.com"
    DESCRIPTION
        "The capabilities description of
        CISCO-POWER-ETHERNET-EXT-MIB."
    REVISION        "200612200000Z"
    DESCRIPTION
        "Added capability statement cPowerEthExtCapCatOSV08R0601."
    REVISION        "200610190000Z"
    DESCRIPTION
        "Added capability statement
        cPowerEthExtCapC3kV122SR035."
    REVISION        "200406150000Z"
    DESCRIPTION
        "Added capability statement
        cPowerEthExtCapCatOSV08R0501."
    REVISION        "200406070000Z"
    DESCRIPTION
        "Initial version of this MIB module."
          ::= { ciscoAgentCapability 406 }



cPowerEthExtCapCatOSV08R0401 AGENT-CAPABILITIES
    PRODUCT-RELEASE "Cisco CatOS 8.4(1)."
    STATUS          current
    DESCRIPTION     "CISCO-POWER-ETHERNET-EXT-MIB capabilities."

    SUPPORTS        CISCO-POWER-ETHERNET-EXT-MIB
    INCLUDES        {
                        cpeExtPsePortGroup,
                        cpeExtPsePortGlobalConfigGroup
                    }
    VARIATION       cpeExtPsePortPwrMax
    SYNTAX          Unsigned32 (4000..15400 )
    DESCRIPTION     "Only a limited set of values is supported."

    VARIATION       cpeExtDefaultAllocation
    SYNTAX          Unsigned32 (4000..15400 )
    DESCRIPTION     "Only a limited set of values is supported."

    VARIATION       cpeExtPsePortEnable
    SYNTAX          INTEGER  {
                        auto(1),
                        static(2)
                    }
    DESCRIPTION
        "The enumerated values supported are all those
        defined at the time this clause was written."

    ::= { ciscoPowerEthernetExtCapability 1 }

cPowerEthExtCapCatOSV08R0501 AGENT-CAPABILITIES
    PRODUCT-RELEASE "Cisco CatOS 8.5(1)."
    STATUS          current
    DESCRIPTION     "CISCO-POWER-ETHERNET-EXT-MIB capabilities."

    SUPPORTS        CISCO-POWER-ETHERNET-EXT-MIB
    INCLUDES        {
                        cpeExtPsePortGroup,
                        cpeExtPsePortGlobalConfigGroup,
                        cpeExtPsePortPwrMonitorGroup,
                        cpeExtMainPseGroup
                    }
    VARIATION       cpeExtPsePortPwrMax
    SYNTAX          Unsigned32 (4000..15400 )
    DESCRIPTION     "Only a limited set of values is supported."

    VARIATION       cpeExtDefaultAllocation
    SYNTAX          Unsigned32 (4000..15400 )
    DESCRIPTION     "Only a limited set of values is supported."

    VARIATION       cpeExtPsePortEnable
    SYNTAX          INTEGER  {
                        auto(1),
                        static(2),
                        limit(3)
                    }
    DESCRIPTION
        "The enumerated values supported are all those
        defined at the time this clause was written."

    ::= { ciscoPowerEthernetExtCapability 2 }

cPowerEthExtCapC3kV122SR035 AGENT-CAPABILITIES
    PRODUCT-RELEASE "CISCO IOS 12.2S(0.35) for Cat3k"
    STATUS          current
    DESCRIPTION     "CISCO-POWER-ETHERNET-EXT-MIB Capabilities"

    SUPPORTS        CISCO-POWER-ETHERNET-EXT-MIB
    INCLUDES        {
                        cpeExtPsePortGroup,
                        cpeExtMainPseGroup,
                        cpeExtPsePortGlobalConfigGroup,
                        cpeExtPsePortPwrMonitorGroup
                    }
    VARIATION       cpeExtDefaultAllocation
    ACCESS          not-implemented
    DESCRIPTION     "This object is not implemented."

    VARIATION       cpeExtPsePortEnable
    SYNTAX          INTEGER  {
                        auto(1),
                        static(2)
                    }
    DESCRIPTION     "Value Limit(3) is not supported."

    VARIATION       cpeExtPsePortAdditionalStatus
    SYNTAX          BITS {
                        deny(0)
                    }
    DESCRIPTION
        "value 'overdraw(1)' is not supported on 3750/3560."

    VARIATION       cpeExtPsePortPwrConsumption
    SYNTAX          Unsigned32
    DESCRIPTION     "Shows available power for 3750/3560"

    VARIATION       cpeExtPsePortMaxPwrDrawn
    SYNTAX          Unsigned32
    DESCRIPTION     "This object is not supported on 3750/3560"

    ::= { ciscoPowerEthernetExtCapability 3 }

cPowerEthExtCapCatOSV08R0601 AGENT-CAPABILITIES
    PRODUCT-RELEASE "Cisco CatOS 8.6(1)"
    STATUS          current
    DESCRIPTION
        "
        CISCO-POWER-ETHERNET-EXT-MIB capabilities.

        "

    SUPPORTS        CISCO-POWER-ETHERNET-EXT-MIB
    INCLUDES        {
                        cpeExtPsePortGroup,
                        cpeExtPsePortGlobalConfigGroup,
                        cpeExtPsePortPwrMonitorGroup,
                        cpeExtPortEntityIndexGroup,
                        cpeExtMainPseGroup2,
                        cpeExtPseGrpPwrGroup
                    }
    VARIATION       cpeExtPsePortPwrMax
    SYNTAX          Unsigned32 (4000..15400 )
    DESCRIPTION     "Only a limited set of values is supported."

    VARIATION       cpeExtDefaultAllocation
    SYNTAX          Unsigned32 (4000..15400 )
    DESCRIPTION     "Only a limited set of values is supported."

    VARIATION       cpeExtPsePortEnable
    SYNTAX          INTEGER  {
                        auto(1),
                        static(2),
                        limit(3)
                    }
    DESCRIPTION
        "The enumerated values supported are all those
        defined at the time this clause was written."

    ::= { ciscoPowerEthernetExtCapability 4 }

END
