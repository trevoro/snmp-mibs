Usr-bridge-MIB DEFINITIONS ::= BEGIN

          IMPORTS
               Counter, TimeTicks
                    FROM RFC1155-SMI
               OBJECT-TYPE
                    FROM RFC-1212
					DisplayString FROM RFC1213-MIB
               usrBridge, UsrUserName, UsrConfigStatus
                    FROM USR-DEFINITIONS-MIB;


          -- All representations of MAC addresses in this MIB Module
          -- use, as a textual convention (i.e. this convention does
          -- not affect their encoding), the data type:

          MacAddress ::= OCTET STRING (SIZE (6))    -- a 6 octet address
                                                    -- in the
                                                    -- "canonical"
                                                    -- order
          -- defined by IEEE 802.1a, i.e., as if it were transmitted
          -- least significant bit first, even though 802.5 (in
          -- contrast to other n802.x protocols) requires MAC
          -- addresses to be transmitted most significant bit first.
          --
          -- 16-bit addresses, if needed, are represented by setting
          -- their upper 4 octets to all 0's, i.e., AAFF would be
          -- represented as 00000000AAFF.


          -- Similarly, all representations of Bridge-Id in this MIB
          -- Module use, as a textual convention (i.e. this
          -- convention does not affect their encoding), the data
          -- type:

          BridgeId ::= OCTET STRING (SIZE (8))   -- the
                                                 -- Bridge-Identifier
                                                 -- as used in the
                                                 -- Spanning Tree
          -- Protocol to uniquely identify a bridge.  Its first two
          -- octets (in network byte order) contain a priority
          -- value and its last 6 octets contain the MAC address
          -- used to refer to a bridge in a unique fashion
          -- (typically, the numerically smallest MAC address
          -- of all ports on the bridge).
          --
          -- Several objects in this MIB module represent values of
          -- timers used by the Spanning Tree Protocol.  In this
          -- MIB, these timers have values in units of hundreths of
          -- a second (i.e. 1/100 secs).
          -- These timers, when stored in a Spanning Tree Protocol's
          -- BPDU, are in units of 1/256 seconds.  Note, however,
          -- that 802.1D-1990 specifies a settable granularity of
          -- no more than 1 second for these timers.  To avoid
          -- ambiguity, a data type is defined here as a textual
          -- convention and all representation of these timers
          -- in this MIB module are defined using this data type.  An
          -- algorithm is also defined for converting between the
          -- different units, to ensure a timer's value is not
          -- distorted by multiple conversions.
          -- The data type is:

          Timeout ::= INTEGER -- a STP timer in units of 1/100 seconds

          -- To convert a Timeout value into a value in units of
          -- 1/256 seconds, the following algorithm should be used:
          --
          --      b  = floor( (n * 256) / 100)
          --
          -- where:
          --      floor   =  quotient [ignore remainder]
          --      n is the value in 1/100 second units
          --      b is the value in 1/256 second units
          --
          -- To convert the value from 1/256 second units back to
          -- 1/100 seconds, the following algorithm should be used:
          --
          --      n = ceiling( (b * 100) / 256)
          --
          -- where:
          --      ceiling =  quotient [if remainder is 0], or
          --                 quotient + 1 [if remainder is non-zero]
          --      n is the value in 1/100 second units
          --      b is the value in 1/256 second units
          --
          -- Note: it is important that the arithmetic operations are
          -- done in the order specified (i.e., multiply first, divide
          -- second).


          -- groups in the Bridge MIB

          usrBRBase       OBJECT IDENTIFIER ::= { usrBridge 1 }

          usrBRStp        OBJECT IDENTIFIER ::= { usrBridge 2 }

          usrBRTp         OBJECT IDENTIFIER ::= { usrBridge 3 }

          usrBRStaticMAC  OBJECT IDENTIFIER ::= { usrBridge 4 }


          -- the usrBRBase group

          -- Implementation of the usrBRBase group is mandatory for all
          -- bridges.

          usrBRBaseBridgeAddress OBJECT-TYPE
              SYNTAX  MacAddress
              ACCESS  read-only
              STATUS  mandatory
              DESCRIPTION
                      "The MAC address used by this bridge when it must
                      be referred to in a unique fashion.   It is
                      recommended that this be the numerically smallest
                      MAC address of all ports that belong to this
                      bridge.  However it is only required to be unique.
                      When concatenated with usrBRStpPriority a unique
                      BridgeIdentifier is formed which is used in the
                      Spanning Tree Protocol."
              REFERENCE
                      "IEEE 802.1D-1990: Sections 6.4.1.1.3 and 3.12.5"
              ::= { usrBRBase 1 }

          usrBRBaseNumPorts OBJECT-TYPE
              SYNTAX  INTEGER
              ACCESS  read-only
              STATUS  mandatory
              DESCRIPTION
                      "The number of ports controlled by this bridging
                      entity."
              REFERENCE
                      "IEEE 802.1D-1990: Section 6.4.1.1.3"
              ::= { usrBRBase 2 }

          usrBRBaseType OBJECT-TYPE
              SYNTAX  INTEGER {
                          unknown(1),
                          transparent-only(2),
                          sourceroute-only(3),
                          srt(4)
                      }
              ACCESS  read-only
              STATUS  mandatory
              DESCRIPTION
                      "Indicates what type of bridging this bridge can
                      perform.  If a bridge is actually performing a
                      certain type of bridging this will be indicated by
                      entries in the port table for the given type."
              ::= { usrBRBase 3 }

          usrBRBaseStaticMacsOnly OBJECT-TYPE
              SYNTAX  INTEGER {
                        enabled(1),
                        disabled(2)
                      }
              ACCESS   read-write
              STATUS   mandatory
              DESCRIPTION
                      "Indicates whether the bridge will forward
                      all (non-local) packets or just those to and
					  from the stations whose MAC addresses are
					  specified in the Access List (BRStaticTable)."
              DEFVAL { disabled }
              --CONFIGURABLE
              ::= { usrBRBase 4 }

          usrBRBaseAgingTime OBJECT-TYPE
              SYNTAX   INTEGER (10..1000000)
              ACCESS   read-write
              STATUS   mandatory
              DESCRIPTION
                      "The timeout period in seconds for aging out
                      dynamically learned forwarding information.
                      802.1D-1990 recommends a default of 300 seconds."
              REFERENCE
                      "IEEE 802.1D-1990: Section 6.7.1.1.3"
              --CONFIGURABLE
              ::= { usrBRBase 5 }

          usrBRBaseLearnedEntryDiscards OBJECT-TYPE
              SYNTAX  Counter
              ACCESS  read-only
              STATUS  mandatory
              DESCRIPTION
                      "The total number of Forwarding Database entries,
                      which have been or would have been learnt, but
                      have been discarded due to a lack of space to
                      store them in the Forwarding Database.  If this
                      counter is increasing, it indicates that the
                      Forwarding Database is regularly becoming full (a
                      condition which has unpleasant performance effects
                      on the subnetwork).  If this counter has a
                      significant value but is not presently increasing,
                      it indicates that the problem has been occurring
                      but is not persistent."
              REFERENCE
                      "IEEE 802.1D-1990: Section 6.7.1.1.3"
              ::= { usrBRBase 6 }

          usrBRBaseCfgFileName OBJECT-TYPE
              SYNTAX   DisplayString
              ACCESS   read-write
              STATUS   mandatory
              DESCRIPTION
                      "The name of a ConfigFile to read/write
                      permanent database records. If the value of this
                      object is an empty string, then the Bridge process
                      uses the default name `@file://BridgeFile.cfg'."
              ::= { usrBRBase 7 }

          usrBRBaseCFMSaveStatus OBJECT-TYPE
              SYNTAX  UsrConfigStatus
              ACCESS  read-write
              STATUS  mandatory
              DESCRIPTION
                      "Setting the value of this object to `save'
                      causes the values of the Bridge Base Group
                      entries to be written out to the current Bridge
                      config file. While the new config file is being
                      written, the Bridge process will set the value
                      of this flag set to `saving''. Any attempts to set
                      the value while it is  not `normal' (i.e. the file
                      is currently being written to the config file)
                      while result in a badValue error being returned.
                      Setting the value to `normal' will result in no
                      action."
              ::= { usrBRBase 8 }


          usrBRBaseWanToWanForwarding OBJECT-TYPE
              SYNTAX  INTEGER {
                        enabled(1),
                        disabled(2)
                      }
              ACCESS   read-write
              STATUS   mandatory
              DESCRIPTION
                      "Indicates whether the bridge will forward
                      packets received on a wide area port
					  to other wide area ports."
              DEFVAL { disabled }
              --CONFIGURABLE
              ::= { usrBRBase 9 }

          -- The Generic Bridge Port Table (Port equals Network )

          usrBRBasePortTable OBJECT-TYPE
              SYNTAX  SEQUENCE OF UsrBRBasePortEntry
              ACCESS  not-accessible
              STATUS  mandatory
              DESCRIPTION
                      "A table that contains generic information about
                      every port that is associated with this bridge.
                      Transparent, source-route, and srt ports are
                      included."
              ::= { usrBRBase 10 }

          usrBRBasePortEntry OBJECT-TYPE
              SYNTAX  UsrBRBasePortEntry
              ACCESS  not-accessible
              STATUS  mandatory
              DESCRIPTION
                      "A list of information for each port of the
                      bridge."
              REFERENCE
                      "IEEE 802.1D-1990: Section 6.4.2, 6.6.1"
              INDEX  { usrBRBasePortId }
              ::= { usrBRBasePortTable 1 }


          UsrBRBasePortEntry ::=
              SEQUENCE {
                  usrBRBasePortId
                      INTEGER,
                  usrBRBaseIfName
                      DisplayString,
                  usrBRBasePortIfIndex
                      INTEGER,
                  usrBRBasePortInFrames
                      Counter,
                  usrBRBasePortOutFrames
                      Counter,
                  usrBRBasePortInDiscards
                      Counter
              }

          usrBRBasePortId OBJECT-TYPE
              SYNTAX  INTEGER
              ACCESS  not-accessible
              STATUS  mandatory
              DESCRIPTION
                      "The value of the instance of the ifIndex object,
                      defined in MIB-II, for the interface corresponding
                      to this port."
              ::= { usrBRBasePortEntry 1 }

          usrBRBaseIfName OBJECT-TYPE
              SYNTAX  DisplayString
              ACCESS  read-only
              STATUS  mandatory
              DESCRIPTION
                      "The interface name of the port for which this entry
                      contains bridge management information."
              ::= { usrBRBasePortEntry 2 }

          usrBRBasePortIfIndex OBJECT-TYPE
              SYNTAX  INTEGER
              ACCESS  read-only
              STATUS  mandatory
              DESCRIPTION
                      "The value of the instance of the ifIndex object,
                      defined in MIB-II, for the interface corresponding
                      to this port."
              ::= { usrBRBasePortEntry 3 }

          usrBRBasePortInFrames OBJECT-TYPE
              SYNTAX  Counter
              ACCESS  read-only
              STATUS  mandatory
              DESCRIPTION
                      "The number of frames that have been received by
                      this port from its segment. Note that a frame
                      received on the interface corresponding to this
                      port is only counted by this object if and only if
                      it is for a protocol being processed by the local
                      bridging function, including bridge management
                      frames."
              REFERENCE
                      "IEEE 802.1D-1990: Section 6.6.1.1.3"
              ::= { usrBRBasePortEntry 4 }

          usrBRBasePortOutFrames OBJECT-TYPE
              SYNTAX  Counter
              ACCESS  read-only
              STATUS  mandatory
              DESCRIPTION
                      "The number of frames that have been transmitted
                      by this port to its segment.  Note that a frame
                      transmitted on the interface corresponding to this
                      port is only counted by this object if and only if
                      it is for a protocol being processed by the local
                      bridging function, including bridge management
                      frames."
              REFERENCE
                      "IEEE 802.1D-1990: Section 6.6.1.1.3"
              ::= { usrBRBasePortEntry 5 }

          usrBRBasePortInDiscards OBJECT-TYPE
              SYNTAX   Counter
              ACCESS   read-only
              STATUS   mandatory
              DESCRIPTION
                      "Count of valid frames received which were
                      discarded (i.e., filtered) by the Forwarding
                      Process."
              REFERENCE
                      "IEEE 802.1D-1990: Section 6.6.1.1.3"
              ::= { usrBRBasePortEntry 6 }


          usrBRBaseBridgeFirewallMode  OBJECT-TYPE
              SYNTAX  INTEGER {
                        discard(0),
                        unicast(1),
						all(2)
                      }
              ACCESS   read-write
              STATUS   mandatory
              DESCRIPTION
                      "The Firewall mode determines how the bridge forwards 
					  packets when the Platform is enabled as a Bridge/Router. 
					  If set to 0, all enabled routed protocols are not 
					  forwarded over bridge ports.  If set to 1, only unicasts 
					  not destined to the BRouter's are forwarded, and if set
					  to 2, pkts defined in (1) and Broadcasts are forwarded."
              DEFVAL { discard }
              --CONFIGURABLE
              ::= { usrBRBase 11 }


          -- the usrBRStp group

          -- Implementation of the usrBRStp group is optional.  It is
          -- implemented by those bridges that support the Spanning Tree
          -- Protocol.


          usrBRStpMode   OBJECT-TYPE
              SYNTAX  INTEGER {
                        enabled(1),
                        disabled(2)
                      }
              ACCESS  read-write
              STATUS  mandatory
              DESCRIPTION
                      "Indicates whether the Spanning Tree Protocol is
                      enabled for this unit."
              DEFVAL { disabled }
              --CONFIGURABLE
              ::= { usrBRStp 1 }

          usrBRStpProtocolSpecification OBJECT-TYPE
              SYNTAX  INTEGER {
                          unknown(1),
                          decLb100(2),
                          ieee8021d(3)
                      }
              ACCESS  read-only
              STATUS  mandatory
              DESCRIPTION
                      "An indication of what version of the Spanning
                      Tree Protocol is being run.  The value
                      'decLb100(2)' indicates the DEC LANbridge 100
                      Spanning Tree protocol.  IEEE 802.1d
                      implementations will return 'ieee8021d(3)'.  If
                      future versions of the IEEE Spanning Tree Protocol
                      are released that are incompatible with the
                      current version a new value will be defined."
              ::= { usrBRStp 2 }

          usrBRStpPriority OBJECT-TYPE
              SYNTAX  INTEGER (0..65535)
              ACCESS  read-write
              STATUS  mandatory
              DESCRIPTION
                      "The value of the write-able portion of the Bridge
                      ID, i.e., the first two octets of the (8 octet
                      long) Bridge ID.  The other (last) 6 octets of the
                      Bridge ID are given by the value of
                      usrBRBaseBridgeAddress."
              REFERENCE
                      "IEEE 802.1D-1990: Section 4.5.3.7"
              --CONFIGURABLE
              ::= { usrBRStp 3 }

          usrBRStpTimeSinceTopologyChange OBJECT-TYPE
              SYNTAX  TimeTicks
              ACCESS  read-only
              STATUS  mandatory
              DESCRIPTION
                      "The time (in hundredths of a second) since the
                      last time a topology change was detected by the
                      bridge entity."
              REFERENCE
                      "IEEE 802.1D-1990: Section 6.8.1.1.3"
              ::= { usrBRStp 4 }

          usrBRStpTopChanges OBJECT-TYPE
              SYNTAX  Counter
              ACCESS  read-only
              STATUS  mandatory
              DESCRIPTION
                      "The total number of topology changes detected by
                      this bridge since the management entity was last
                      reset or initialized."
              REFERENCE
                      "IEEE 802.1D-1990: Section 6.8.1.1.3"
              ::= { usrBRStp 5 }

          usrBRStpDesignatedRoot OBJECT-TYPE
              SYNTAX  BridgeId
              ACCESS  read-only
              STATUS  mandatory
              DESCRIPTION
                      "The bridge identifier of the root of the spanning
                      tree as determined by the Spanning Tree Protocol
                      as executed by this node.  This value is used as
                      the Root Identifier parameter in all Configuration
                      Bridge PDUs originated by this node."
              REFERENCE
                      "IEEE 802.1D-1990: Section 4.5.3.1"
              ::= { usrBRStp 6 }

          usrBRStpRootCost OBJECT-TYPE
              SYNTAX  INTEGER
              ACCESS  read-only
              STATUS  mandatory
              DESCRIPTION
                      "The cost of the path to the root as seen from
                      this bridge."
              REFERENCE
                      "IEEE 802.1D-1990: Section 4.5.3.2"
              ::= { usrBRStp 7 }

          usrBRStpRootPort OBJECT-TYPE
              SYNTAX  INTEGER
              ACCESS  read-only
              STATUS  mandatory
              DESCRIPTION
                      "The port number of the port which offers the
                      lowest cost path from this bridge to the root
                      bridge."
              REFERENCE
                      "IEEE 802.1D-1990: Section 4.5.3.3"
              ::= { usrBRStp 8 }

          usrBRStpMaxAge OBJECT-TYPE
              SYNTAX  Timeout
              ACCESS  read-only
              STATUS  mandatory
              DESCRIPTION
                      "The maximum age of Spanning Tree Protocol
                      information learned from the network on any port
                      before it is discarded, in units of hundredths of
                      a second.  This is the actual value that this
                      bridge is currently using."
              REFERENCE
                      "IEEE 802.1D-1990: Section 4.5.3.4"
              ::= { usrBRStp 9 }

          usrBRStpHelloTime OBJECT-TYPE
              SYNTAX  Timeout
              ACCESS  read-only
              STATUS  mandatory
              DESCRIPTION
                      "The amount of time between the transmission of
                      Configuration bridge PDUs by this node on any port
                      when it is the root of the spanning tree or trying
                      to become so, in units of hundredths of a second.
                      This is the actual value that this bridge is
                      currently using."
              REFERENCE
                      "IEEE 802.1D-1990: Section 4.5.3.5"
              ::= { usrBRStp 10 }

          usrBRStpHoldTime OBJECT-TYPE
              SYNTAX  INTEGER
              ACCESS  read-only
              STATUS  mandatory
              DESCRIPTION
                      "This time value determines the interval length
                      during which no more than two Configuration bridge
                      PDUs shall be transmitted by this node, in units
                      of hundredths of a second."
              REFERENCE
                      "IEEE 802.1D-1990: Section 4.5.3.14"
              ::= { usrBRStp 11 }

          usrBRStpForwardDelay OBJECT-TYPE
              SYNTAX  Timeout
              ACCESS  read-only
              STATUS  mandatory
              DESCRIPTION
                      "This time value, measured in units of hundredths
                      of a second, controls how fast a port changes its
                      spanning state when moving towards the Forwarding
                      state.  The value determines how long the port
                      stays in each of the Listening and Learning
                      states, which precede the Forwarding state.  This
                      value is also used, when a topology change has
                      been detected and is underway, to age all dynamic
                      entries in the Forwarding Database.  [Note that
                      this value is the one that this bridge is
                      currently using, in contrast to
                      usrBRStpBridgeForwardDelay which is the value that
                      this bridge and all others would start using
                      if/when this bridge were to become the root.]"
              REFERENCE
                      "IEEE 802.1D-1990: Section 4.5.3.6"
              ::= { usrBRStp 12 }

          usrBRStpBridgeMaxAge OBJECT-TYPE
              SYNTAX  Timeout (600..4000)
              ACCESS  read-write
              STATUS  mandatory
              DESCRIPTION
                      "The value that all bridges use for MaxAge when
                      this bridge is acting as the root.  Note that
                      802.1D-1990 specifies that the range for this
                      parameter is related to the value of
                      usrBRStpBridgeHelloTime. The granularity of this
                      timer is specified by 802.1D-1990 to be 1 second.
                      An agent may return a badValue error if a set is
                      attempted to a value which is not a whole number
                      of seconds."
              REFERENCE
                      "IEEE 802.1D-1990: Section 4.5.3.8"
              --CONFIGURABLE
              ::= { usrBRStp 13 }

          usrBRStpBridgeHelloTime OBJECT-TYPE
              SYNTAX  Timeout (1..10)
              ACCESS  read-write
              STATUS  mandatory
              DESCRIPTION
                      "The value that all bridges use for HelloTime when
                      this bridge is acting as the root.  The
                      granularity of this timer is specified by 802.1D-
                      1990 to be 1 second.  An agent may return a
                      badValue error if a set is attempted to a value
                      which is not a whole number of seconds."
              REFERENCE
                      "IEEE 802.1D-1990: Section 4.5.3.9"
              --CONFIGURABLE
              ::= { usrBRStp 14 }

          usrBRStpBridgeForwardDelay OBJECT-TYPE
              SYNTAX  Timeout (4..30)
              ACCESS  read-write
              STATUS  mandatory
              DESCRIPTION
                      "The value that all bridges use for ForwardDelay
                      when this bridge is acting as the root.  Note that
                      802.1D-1990 specifies that the range for this
                      parameter is related to the value of
                      usrBRStpBridgeMaxAge.  The granularity of this
                      timer is specified by 802.1D-1990 to be 1 second.
                      An agent may return a badValue error if a set is
                      attempted to a value which is not a whole number
                      of seconds."
              REFERENCE
                      "IEEE 802.1D-1990: Section 4.5.3.10"
              --CONFIGURABLE
              ::= { usrBRStp 15 }


          -- The Spanning Tree Port Table

          usrBRStpPortTable OBJECT-TYPE
              SYNTAX  SEQUENCE OF UsrBRStpPortEntry
              ACCESS  not-accessible
              STATUS  mandatory
              DESCRIPTION
                      "A table that contains port-specific information
                      for the Spanning Tree Protocol."
              ::= { usrBRStp 16 }

          usrBRStpPortEntry OBJECT-TYPE
              SYNTAX  UsrBRStpPortEntry
              ACCESS  not-accessible
              STATUS  mandatory
              DESCRIPTION
                      "A list of information maintained by every port
                      about the Spanning Tree Protocol state for that
                      port."
              INDEX   { usrBRStpPortId }
              ::= { usrBRStpPortTable 1 }

          UsrBRStpPortEntry ::=
              SEQUENCE {
                  usrBRStpPortId
                      INTEGER,
                  usrBRStpPort
                      INTEGER,
                  usrBRStpPortPriority
                      INTEGER,
                  usrBRStpPortState
                      INTEGER,
                  usrBRStpPortEnable
                      INTEGER,
                  usrBRStpPortPathCost
                      INTEGER,
                  usrBRStpPortDesignatedRoot
                      BridgeId,
                  usrBRStpPortDesignatedCost
                      INTEGER,
                  usrBRStpPortDesignatedBridge
                      BridgeId,
                  usrBRStpPortDesignatedPort
                      OCTET STRING,
                  usrBRStpPortForwardTransitions
                      Counter
              }

          usrBRStpPortId OBJECT-TYPE
              SYNTAX  INTEGER
              ACCESS  not-accessible
              STATUS  mandatory
              DESCRIPTION
                      "The value of the instance of the ifIndex object,
                      defined in MIB-II, for the interface corresponding
                      to this port."
              ::= { usrBRStpPortEntry 1 }

          usrBRStpPort OBJECT-TYPE
              SYNTAX  INTEGER (1..65535)
              ACCESS  read-only
              STATUS  mandatory
              DESCRIPTION
                      "The port number of the port for which this entry
                      contains Spanning Tree Protocol management
                      information."
              REFERENCE
                      "IEEE 802.1D-1990: Section 6.8.2.1.2"
              ::= { usrBRStpPortEntry 2 }

          usrBRStpPortPriority OBJECT-TYPE
              SYNTAX  INTEGER (0..255)
              ACCESS  read-only
              STATUS  mandatory
              DESCRIPTION
                      "The value of the priority field which is
                      contained in the first (in network byte order)
                      octet of the (2 octet long) Port ID.  The other
                      octet of the Port ID is given by the value of
                      usrBRStpPort."
              REFERENCE
                      "IEEE 802.1D-1990: Section 4.5.5.1"
              ::= { usrBRStpPortEntry 3 }

          usrBRStpPortState OBJECT-TYPE
              SYNTAX  INTEGER {
                          disabled(1),
                          on-demand-idle(2),
                          on-demand-initing(3),
                          blocking(4),
                          listening(5),
                          learning(6),
                          forwarding(7),
                          broken(8)
                      }
              ACCESS  read-only
              STATUS  mandatory
              DESCRIPTION
                      "The port's current state as defined by
                      application of the Spanning Tree Protocol.  This
                      state controls what action a port takes on
                      reception of a frame.  For ports which are
                      disabled (see usrBRStpPortEnable), this object
                      will have a value of disabled(1)."
              REFERENCE
                      "IEEE 802.1D-1990: Section 4.5.5.2"
              ::= { usrBRStpPortEntry 4 }

          usrBRStpPortEnable OBJECT-TYPE
              SYNTAX  INTEGER {
                          enabled(1),
                          disabled(2)
                      }
              ACCESS  read-only
              STATUS  mandatory
              DESCRIPTION
                      "The enabled/disabled status of the port."
              REFERENCE
                      "IEEE 802.1D-1990: Section 4.5.5.2"
              ::= { usrBRStpPortEntry 5 }

          usrBRStpPortPathCost OBJECT-TYPE
              SYNTAX  INTEGER (1..65535)
              ACCESS  read-only
              STATUS  mandatory
              DESCRIPTION
                      "The contribution of this port to the path cost of
                      paths towards the spanning tree root which include
                      this port.  802.1D-1990 recommends that the
                      default value of this parameter be in inverse
                      proportion to the speed of the attached LAN."
              REFERENCE
                      "IEEE 802.1D-1990: Section 4.5.5.3"
              ::= { usrBRStpPortEntry 6 }

          usrBRStpPortDesignatedRoot OBJECT-TYPE
              SYNTAX  BridgeId
              ACCESS  read-only
              STATUS  mandatory
              DESCRIPTION
                      "The unique Bridge Identifier of the Bridge
                      recorded as the Root in the Configuration BPDUs
                      transmitted by the Designated Bridge for the
                      segment to which the port is attached."
              REFERENCE
                      "IEEE 802.1D-1990: Section 4.5.5.4"
              ::= { usrBRStpPortEntry 7 }

          usrBRStpPortDesignatedCost OBJECT-TYPE
              SYNTAX  INTEGER
              ACCESS  read-only
              STATUS  mandatory
              DESCRIPTION
                      "The path cost of the Designated Port of the
                      segment connected to this port.  This value is
                      compared to the Root Path Cost field in received
                      bridge PDUs."
              REFERENCE
                      "IEEE 802.1D-1990: Section 4.5.5.5"
              ::= { usrBRStpPortEntry 8 }

          usrBRStpPortDesignatedBridge OBJECT-TYPE
              SYNTAX  BridgeId
              ACCESS  read-only
              STATUS  mandatory
              DESCRIPTION
                      "The Bridge Identifier of the bridge which this
                      port considers to be the Designated Bridge for
                      this port's segment."
              REFERENCE
                      "IEEE 802.1D-1990: Section 4.5.5.6"
              ::= { usrBRStpPortEntry 9 }

          usrBRStpPortDesignatedPort OBJECT-TYPE
              SYNTAX  OCTET STRING
              ACCESS  read-only
              STATUS  mandatory
              DESCRIPTION
                      "The Port Identifier of the port on the Designated
                      Bridge for this port's segment."
              REFERENCE
                      "IEEE 802.1D-1990: Section 4.5.5.7"
              ::= { usrBRStpPortEntry 10 }

          usrBRStpPortForwardTransitions OBJECT-TYPE
              SYNTAX  Counter
              ACCESS  read-only
              STATUS  mandatory
              DESCRIPTION
                      "The number of times this port has transitioned
                      from the Learning state to the Forwarding state."
              ::= { usrBRStpPortEntry 11 }


          --  The Forwarding Database for Transparent Bridges

          usrBRTpFdbTable OBJECT-TYPE
              SYNTAX  SEQUENCE OF UsrBRTpFdbEntry
              ACCESS  not-accessible
              STATUS  mandatory
              DESCRIPTION
                      "This table that contains information about unicast
                      entries for which the bridge has forwarding and/or
                      filtering information.  This information is used
                      by the transparent bridging function in
                      determining how to propagate a received frame."
              ::= { usrBRTp 1 }

          usrBRTpFdbEntry OBJECT-TYPE
              SYNTAX  UsrBRTpFdbEntry
              ACCESS  not-accessible
              STATUS  mandatory
              DESCRIPTION
                      "Information about a specific unicast MAC address
                      for which the bridge has some forwarding and/or
                      filtering information."
              INDEX   { usrBRTpFdbAddress }
              ::= { usrBRTpFdbTable 1 }

          UsrBRTpFdbEntry ::=
              SEQUENCE {
                  usrBRTpFdbAddress
                      MacAddress,
                  usrBRTpFdbPort
                      INTEGER,
                  usrBRTpFdbStatus
                      INTEGER,
                  usrBRTpFdbRxPkts
                      Counter,
                  usrBRTpFdbRxOctets
                      Counter,
                  usrBRTpFdbRxFiltPkts
                      Counter,
                  usrBRTpFdbRxFwdPkts
                      Counter,
                  usrBRTpFdbTxPkts
                      Counter,
                  usrBRTpFdbTxOctets
                      Counter
              }

          usrBRTpFdbAddress OBJECT-TYPE
              SYNTAX  MacAddress
              ACCESS  not-accessible
              STATUS  mandatory
              DESCRIPTION
                      "A unicast MAC address for which the bridge has
                      forwarding and/or filtering information."
              REFERENCE
                      "IEEE 802.1D-1990: Section 3.9.1, 3.9.2"
              ::= { usrBRTpFdbEntry 1 }

          usrBRTpFdbPort OBJECT-TYPE
              SYNTAX  INTEGER
              ACCESS  read-only
              STATUS  mandatory
              DESCRIPTION
                      "Either the value '0', or the port number of the
                      port on which a frame having a source address
                      equal to the value of the corresponding instance
                      of usrBRTpFdbAddress has been seen.  A value of
                      '0' indicates that the port number has not been
                      learned but that the bridge does have some
                      forwarding/filtering information about this
                      address (e.g. in the usrBRStaticTable).
                      Implementors are encouraged to assign the port
                      value to this object whenever it is learned even
                      for addresses for which the corresponding value of
                      usrBRTpFdbStatus is not learned(3)."
              ::= { usrBRTpFdbEntry 2 }

          usrBRTpFdbStatus OBJECT-TYPE
              SYNTAX  INTEGER {
                          other(1),
                          invalid(2),
                          learned(3),
                          self(4),
                          mgmt(5)
                      }
              ACCESS  read-only
              STATUS  mandatory
              DESCRIPTION
                      "The status of this entry.  The meanings of the
                      values are:

                        other(1)   : none of the following.  This would
                                     include the case where some other
                                     MIB object (not the corresponding
                                     instance of usrBRTpFdbPort, nor an
                                     entry in the usrBRStaticTable) is
                                     being used to determine if and how
                                     frames addressed to the value of
                                     the corresponding instance of
                                     usrBRTpFdbAddress are being
                                     forwarded.

                        invalid(2) : this entry is not longer valid
                                     (e.g., it was learned but has since
                                     aged-out), but has not yet been
                                     flushed from the table.

                        learned(3) : the value of the corresponding
                                     instance of usrBRTpFdbPort was
                                     learned, and is being used.

                        self(4)    : the value of the corresponding
                                     instance of usrBRTpFdbAddress
                                     represents one of the bridge's
                                     addresses.  The corresponding
                                     instance of usrBRTpFdbPort
                                     indicates which of the bridge's
                                     ports has this address.

                        mgmt(5)    : the value of the corresponding
                                     instance of usrBRTpFdbAddress is
                                     also the value of an existing
                                     instance of usrBRStaticAddress."
              ::= { usrBRTpFdbEntry 3 }

          usrBRTpFdbRxPkts OBJECT-TYPE
              SYNTAX  Counter
              ACCESS  read-only
              STATUS  mandatory
              DESCRIPTION
                      "Number of packets received from this MAC station."
              ::= { usrBRTpFdbEntry 4 }

          usrBRTpFdbRxOctets OBJECT-TYPE
              SYNTAX  Counter
              ACCESS  read-only
              STATUS  mandatory
              DESCRIPTION
                      "Number of bytes received from this MAC station."
              ::= { usrBRTpFdbEntry 5 }

          usrBRTpFdbRxFiltPkts OBJECT-TYPE
              SYNTAX  Counter
              ACCESS  read-only
              STATUS  mandatory
              DESCRIPTION
                      "Number of packets received from this MAC station
                      that were filtered (not forwarded)."
              ::= { usrBRTpFdbEntry 6 }

          usrBRTpFdbRxFwdPkts OBJECT-TYPE
              SYNTAX  Counter
              ACCESS  read-only
              STATUS  mandatory
              DESCRIPTION
                      "Number of packets received from this MAC station
                      that were forwarded."
              ::= { usrBRTpFdbEntry 7 }

          usrBRTpFdbTxPkts OBJECT-TYPE
              SYNTAX  Counter
              ACCESS  read-only
              STATUS  mandatory
              DESCRIPTION
                      "Number of packets forwarded to this MAC station."
              ::= { usrBRTpFdbEntry 8 }

          usrBRTpFdbTxOctets OBJECT-TYPE
              SYNTAX  Counter
              ACCESS  read-only
              STATUS  mandatory
              DESCRIPTION
                      "Number of bytes forwarded to this MAC station."
              ::= { usrBRTpFdbEntry 9 }


          --  The Static MAC Address Table


          usrBRStaticMACTable OBJECT-TYPE
              SYNTAX  SEQUENCE OF UsrBRStaticMACEntry
              ACCESS  not-accessible
              STATUS  mandatory
              DESCRIPTION
                      "This table contains MAC addresses of stations
					   whose traffic is allowed to pass from one bridge
					   port to another.  Note that this table is used
					   to filter traffic only when BRBaseStaticMacsOnly 
					   is set to Enabled." 
					   
              ::= { usrBRStaticMAC 1 }

          usrBRStaticMACEntry OBJECT-TYPE
              SYNTAX  UsrBRStaticMACEntry
              ACCESS  not-accessible
              STATUS  mandatory
              DESCRIPTION
                      "A MAC Address that identifies a station whose
                      traffic is allowed to pass from one bridge port
					  to another."		
              INDEX   { usrBRStaticMACAddress }
              ::= { usrBRStaticMACTable 1 }

          UsrBRStaticMACEntry ::=
              SEQUENCE {
                  usrBRStaticMACAddress
                      MacAddress,
                  usrBRStaticMACUser
                      UsrUserName,
                  usrBRStaticStatus
                      INTEGER
              }

          usrBRStaticMACAddress OBJECT-TYPE
              SYNTAX  MacAddress
              ACCESS  not-accessible
              STATUS  mandatory
              DESCRIPTION
                      "The MAC Address of the station allowed access
					   through the bridge."
              --CONFIGURABLE
              ::= { usrBRStaticMACEntry 1 }

          usrBRStaticMACUser OBJECT-TYPE
              SYNTAX  UsrUserName
              ACCESS  read-write
              STATUS  mandatory
              DESCRIPTION
                      "Name of the user to be associated with the
                      specified MAC Address."
              --CONFIGURABLE
              ::= { usrBRStaticMACEntry 2 }

          usrBRStaticStatus OBJECT-TYPE
              SYNTAX  INTEGER {
                          normal(1),
                          delete(2)
                      }
              ACCESS  read-write
              STATUS  mandatory
              DESCRIPTION
                      "Setting this variable to delete removes the entry."
              DEFVAL { normal }
              ::= { usrBRStaticMACEntry 3 }

          END
