BAS-CLUSTER-MIB DEFINITIONS ::= BEGIN

IMPORTS
	MODULE-IDENTITY, OBJECT-TYPE, 
	Counter32						FROM SNMPv2-SMI
	RowStatus						FROM SNMPv2-TC
	basCluster, BasChassisId, 
	BasSlotId, BasInterfaceId, 
	BasLogicalPortId				FROM BAS-MIB;

basClusterMib MODULE-IDENTITY
	LAST-UPDATED "9911181828Z"
	ORGANIZATION "Broadband Access Systems"
	CONTACT-INFO
		" Tech Support
		  Broadband Access Systems
		  8 Technology Drive
		  Westborough, MA  01581
		  U.S.A.
		  
		  508-336-8833
		  support@basystems.com"
	DESCRIPTION
		"This MIB module defines the configuration MIB objects
		 for a Broadband Access System Cluster."
	::= { basCluster 1 }


basClusterConfig	OBJECT IDENTIFIER ::= { basClusterMib 1 }


--
-- ----------------------------------------------------------------------
--
-- Bas Cluster Chassis Table
--
-- ----------------------------------------------------------------------
--
basClChTable OBJECT-TYPE
	SYNTAX		SEQUENCE OF BasClChEntry
	MAX-ACCESS	not-accessible
	STATUS		current
	DESCRIPTION
		"Info about the list of Chassis known to a slot."
	::= { basClusterConfig 1 }

basClChEntry OBJECT-TYPE
	SYNTAX      BasClChEntry
	MAX-ACCESS  not-accessible
	STATUS      current
	DESCRIPTION
		"Info about a chassis."
	INDEX		{ basClChLocalChassis,
				  basClChLocalSlot,
				  basClChLocalIf,
				  basClChLocalLPort,
				  basClChRemoteChassis
				}
	::= { basClChTable 1 }

BasClChEntry ::= SEQUENCE {
		basClChLocalChassis	BasChassisId,
		basClChLocalSlot	BasSlotId,
		basClChLocalIf		BasInterfaceId,
		basClChLocalLPort	BasLogicalPortId,
		basClChRemoteChassis	BasChassisId,
		basClChLocalNextSlot	INTEGER,
		basClChLocalNextIf	BasInterfaceId,
		basClChLocalNextLPort	BasLogicalPortId,
		basClChTargetStatus	INTEGER,
                basClChArpFlags		BITS
	    }

basClChLocalChassis OBJECT-TYPE
	SYNTAX		BasChassisId
	MAX-ACCESS	not-accessible
	STATUS		current
	DESCRIPTION
		"The BAS Chassis ID of the local slot."
	::= { basClChEntry 1 }

basClChLocalSlot OBJECT-TYPE
	SYNTAX		BasSlotId
	MAX-ACCESS	not-accessible
	STATUS		current
	DESCRIPTION
		"The BAS Slot ID of the local slot."
	::= { basClChEntry 2 }

basClChLocalIf OBJECT-TYPE
	SYNTAX		BasInterfaceId
	MAX-ACCESS	not-accessible
	STATUS		current
	DESCRIPTION
		"The BAS interface ID of the local slot."
	::= { basClChEntry 3 }

basClChLocalLPort OBJECT-TYPE
	SYNTAX		BasLogicalPortId
	MAX-ACCESS	not-accessible
	STATUS		current
	DESCRIPTION
		"The BAS logical port ID of the local slot."
	::= { basClChEntry 4 }

basClChRemoteChassis OBJECT-TYPE
	SYNTAX		BasChassisId
	MAX-ACCESS	not-accessible
	STATUS		current
	DESCRIPTION
		"The BAS Chassis ID of the remote chassis."
	::= { basClChEntry 5 }

basClChLocalNextSlot OBJECT-TYPE
	SYNTAX		INTEGER(0..12)
	MAX-ACCESS	read-create
	STATUS		current
	DESCRIPTION
		"The BAS Slot ID of the next hop local slot."
	::= { basClChEntry 6 }

basClChLocalNextIf OBJECT-TYPE
	SYNTAX		BasInterfaceId
	MAX-ACCESS	read-create
	STATUS		current
	DESCRIPTION
		"The BAS interface ID of the next hop local slot."
	::= { basClChEntry 7 }

basClChLocalNextLPort OBJECT-TYPE
	SYNTAX		BasLogicalPortId
	MAX-ACCESS	read-create
	STATUS		current
	DESCRIPTION
		"The BAS logical port ID of the next hop local slot."
	::= { basClChEntry 8 }

basClChTargetStatus OBJECT-TYPE
	SYNTAX	 INTEGER {
		        enable (1),
			disable (2)
                     }			
	MAX-ACCESS	read-create
	STATUS		current
	DESCRIPTION
		"The status object used to determine if the entry 
		 is valid or not."
	::= { basClChEntry 9 }

basClChArpFlags OBJECT-TYPE
	SYNTAX      BITS {
					clear(0),
					waiting(1),
					doNotQueue(2),
					doNotTimeout(3),
					cmtsWaiting(4),
					cmtsOk(5)
				}
	MAX-ACCESS  read-create
	STATUS      current
	DESCRIPTION
		"ICL ARP flags."
	::= { basClChEntry 10 }

--
-- ----------------------------------------------------------------------
--
-- End
--
-- ----------------------------------------------------------------------
--

END
