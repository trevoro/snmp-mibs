-- Copyright 1994 General DataComm Inc., Inc. All Rights Reserved.
--
-- Reproduction of this document is authorized on condition that the
-- foregoing copyright notice is included. This General DataComm, GDC,
-- SNMP Management Information Base Specification embodies GDCs'
-- confidential and proprietary intellectual property. GDC retains all
-- title and ownership in the Specification, including any revisions.
--
-- It is GDCs intent to encourage the widespread use of this Specification
-- in connection with the management of GDC's products. GDC grants vendors,
-- end-users, and other interested parties a non-exclusive license to use
-- this Specification in connection with the management of GDC's products.
--
-- This Specification is supplied "AS IS," and GDC makes no warranty,
-- either expressed or implied, as to the use operation, condition, or
-- performance of the Specification.

-- Revision History
-- Version   Date	Name		Description 
-- 1.00A     14-Oct-94  E. Moreno-Leon  Initial Revision
-- 1.00B     28-Mar-95  E. Moreno-Leon  Revised hdsl730D2SystemMIBversion for undeclared 			--
-- 1.00C     01-Sep-95	C. Amorossi	Added Interface Comments
-- 1.00D     13-Mar-96	E. Moreno-Leon	Added Major and Minor BER Alarms

HDSL730D2-MIB DEFINITIONS ::= BEGIN

IMPORTS
	OBJECT-TYPE			FROM RFC-1212
	DisplayString			FROM RFC1213-MIB
	hdsl730D2                       FROM GDCHDSL-MIB;

hdsl730D2System            OBJECT IDENTIFIER ::= { hdsl730D2 1 }
hdsl730D2Version           OBJECT IDENTIFIER ::= { hdsl730D2System 1 }

-- This MIB module is a subset of the HDSL 730 series products
-- This products are the only one to support a DTE interface.

-- ***************************************************************************
-- The interfaces are defined as follows:
--	Unit	0
--	DTE	1
--	Loop1	2
--	Loop2   3
-- ***************************************************************************

gdc730D2SystemMIBversion OBJECT-TYPE
    	SYNTAX DisplayString (SIZE (5))
     	ACCESS read-only
     	STATUS mandatory
     	DESCRIPTION
     		"Identifies the version of the MIB. The format of the version
     		is x.yzT, where 'x' identifies the major revision number, 'y'
     		identifies the minor revision number, 'z' identifies the
     		typographical revision, and T identifies the test revision.
     		Acceptable values for the individual revision components are
     		as follows:
 
     		x: 1 - 9
     		y: 0 - 9
     		z: 0 - 9
     		T: A - Z
 
     		Upon formal release, no designation for the test revision will
     		be present."
     	::= { hdsl730D2Version 1 }
 
 
 
-- ********************************************************************
-- GDC Hdsl Alarm Object Identifier Definitions
-- ********************************************************************
hdsl730D2Alarms            OBJECT IDENTIFIER ::= { hdsl730D2 2 }

hdsl730D2NoResponseAlm		OBJECT IDENTIFIER ::= { hdsl730D2Alarms 1 }
hdsl730D2DiagRxErrAlm		OBJECT IDENTIFIER ::= { hdsl730D2Alarms 2 }
hdsl730D2PowerUpAlm		OBJECT IDENTIFIER ::= { hdsl730D2Alarms 3 }
hdsl730D2UnitFailure            OBJECT IDENTIFIER ::= { hdsl730D2Alarms 4 }
hdsl730D2ChecksumCorrupt        OBJECT IDENTIFIER ::= { hdsl730D2Alarms 5 }
hdsl730D2LossofSignal		OBJECT IDENTIFIER ::= { hdsl730D2Alarms 6 }
hdsl730D2UnavailableSec		OBJECT IDENTIFIER ::= { hdsl730D2Alarms 7 }
hdsl730D2ErrorSec		OBJECT IDENTIFIER ::= { hdsl730D2Alarms 8 }
hdsl730D2LossofSyncWord		OBJECT IDENTIFIER ::= { hdsl730D2Alarms 9 }
hdsl730D2MajorBER 		OBJECT IDENTIFIER ::= { hdsl730D2Alarms 10 }
hdsl730D2MinorBER 		OBJECT IDENTIFIER ::= { hdsl730D2Alarms 11 }

 
-- ALARM			Maskable	Valid Interfaces
--===============================================================
--hdslNoResponseAlm		No		Unit
--hdslDiagRxErrAlm              No              Unit
--hdslPowerUpAlm		No		Unit
--hdslUnitFailure               No              Unit
--hdslChecksumCorrupt           No              Unit
--hdslLossofSignal              Yes             L1, L2
--hdslUnavailableSec            Yes             L1, L2
--hdslErrorSec                  Yes             L1, L2
--hdslLossofSyncWord		Yes		L1, L2
--hdsl730D2MajorBER		Yes		L1, L2
--hdsl730D2MinorBER		Yes		L1, L2


END
