ACC-MULTILINK DEFINITIONS ::= BEGIN

    IMPORTS
	 OBJECT-TYPE, IpAddress, TimeTicks, Gauge, Counter FROM RFC1155-SMI
	 TRAP-TYPE FROM RFC-1215
          accTrapLogSeqNum FROM ACC-SYSTEM
	accBRG, DisplayString, RowStatus, IfIndex, SmdsAddress
            FROM ACC-MIB
--        ifOperStatus FROM RFC-1213;
        ifOperStatus FROM ACC-FAKE;
-- Multilink Group
      accMultilink      OBJECT IDENTIFIER ::= { accBRG 9 }
accMultilinkParameterTable OBJECT-TYPE
	SYNTAX SEQUENCE OF AccMultilinkParameterEntry
	ACCESS not-accessible
	STATUS mandatory
	DESCRIPTION
		" "
      ::= { accMultilink 1 }
accMultilinkParameterEntry OBJECT-TYPE
	SYNTAX AccMultilinkParameterEntry
	ACCESS not-accessible
	STATUS mandatory
	DESCRIPTION
		" "
	INDEX { accMultilinkParameterIndex }
      ::= { accMultilinkParameterTable 1 }
AccMultilinkParameterEntry ::= SEQUENCE {
	accMultilinkParameterIndex		INTEGER,
	accMultilinkParameterIfIndex		INTEGER,
	accMultilinkParameterMessageLevel	INTEGER,
	accMultilinkParameterPhysicalPort	DisplayString,
	accMultilinkParameterAdminState		INTEGER,
	accMultilinkParameterOperState		INTEGER,
        accMultilinkParameterEncapsulation      INTEGER,
        accMultilinkParameterContents	        INTEGER,
        accMultilinkParameterCongeToCall	INTEGER,
        accMultilinkParameterCongeToClear	INTEGER,
        accMultilinkParameterDampingFactor	INTEGER,
        accMultilinkParameterFragmentSize	INTEGER,
        accMultilinkParameterMppAdminState	INTEGER,
        accMultilinkParameterBWprotocol		INTEGER,
        accMultilinkParameterBWprotocolOpSt	INTEGER
	}
accMultilinkParameterIndex OBJECT-TYPE
	SYNTAX INTEGER
	ACCESS read-write
	STATUS mandatory
	DESCRIPTION
		"An integer that uniquely identifies this multilink
		group."
      ::= { accMultilinkParameterEntry 1 }
accMultilinkParameterIfIndex OBJECT-TYPE
	SYNTAX INTEGER
	ACCESS read-write
	STATUS mandatory
	DESCRIPTION
		"An integer that identifies the row of the
		systemwide interfaces table associated with this
		multilink group."
      ::= { accMultilinkParameterEntry 2 }
accMultilinkParameterMessageLevel OBJECT-TYPE
	SYNTAX INTEGER (1..7)
	ACCESS read-write
	STATUS mandatory
	DESCRIPTION
		"How verbose the multilink port will be
		when reporting state changes, errors, and
		warnings.  Level 1 is the least verbose, 
		level 7 the most.  The message levels
		are broken down as follows:
		1 - Error messages.
		2 - Unused + 1.
		3 - Warning messages + 2.
		4 - Unused + 3. 
		5 - Multilink activity + 4.
		6 - Unused + 5.
		7 - Multilink port state changes + 6."
	DEFVAL { 1 }
      ::= { accMultilinkParameterEntry 3 }
accMultilinkParameterPhysicalPort OBJECT-TYPE
	SYNTAX DisplayString
	ACCESS read-only
	STATUS mandatory
	DESCRIPTION
		"A text string listing all physical ports
		associated with this multilink port."
      ::= { accMultilinkParameterEntry 9 } -- was 4 but returned wrong value
accMultilinkParameterAdminState OBJECT-TYPE
	SYNTAX INTEGER {
		enabled(1),
		disabled(2)
	}
	ACCESS read-write
	STATUS mandatory
	DESCRIPTION
		"An integer that specifies the administrative enabling or
		disabling of this multilink group."
      ::= { accMultilinkParameterEntry 5 }
accMultilinkParameterOperState OBJECT-TYPE
	SYNTAX INTEGER {
		down(1),
		starting(2),
		seq-received-ok(3),
		seq-send-ok(4),
		up(5),
		disabled(6)
	}
	ACCESS read-only
	STATUS mandatory
	DESCRIPTION
		"An integer that specifies the operational state
		of this multilink group."
      ::= { accMultilinkParameterEntry 6 }
accMultilinkParameterEncapsulation OBJECT-TYPE
        SYNTAX INTEGER {
                acc(1),
                ietf-ppp(2),
                acc-new(3)
        }
        ACCESS read-write
        STATUS mandatory
        DESCRIPTION
                "If set to ietf-ppp, a multilink group of PPP links will
		follow the standard PPP multilink operations methods. 
		The value acc-new is reserved for future use.  The value
		acc is reserved for compatibility with past offerings."
        DEFVAL { ietf-ppp }
      ::= { accMultilinkParameterEntry 7 }
accMultilinkParameterContents OBJECT-TYPE
        SYNTAX INTEGER {
                valid (1),
                invalid (2)
        }
        ACCESS read-write
        STATUS mandatory
        DESCRIPTION
                "Set to valid when adding a row to the Multilink
                 parameter table. Set to invalid to delete a row."
      ::= { accMultilinkParameterEntry 8 }
accMultilinkParameterCongeToCall OBJECT-TYPE
        SYNTAX INTEGER (0..101)
        ACCESS read-write
        STATUS mandatory
        DESCRIPTION
                "Multilink Congestion to Call Threshold"
        DEFVAL { 90 }
      ::= { accMultilinkParameterEntry 10 }
accMultilinkParameterCongeToClear OBJECT-TYPE
        SYNTAX INTEGER (0..100)
        ACCESS read-write
        STATUS mandatory
        DESCRIPTION
                "Multilink Congestion to Call Threshold"
        DEFVAL { 50 }
      ::= { accMultilinkParameterEntry 11 }
accMultilinkParameterDampingFactor OBJECT-TYPE
        SYNTAX INTEGER (0..64)
        ACCESS read-write
        STATUS mandatory
        DESCRIPTION
                "Multilink Congestion Calculation Damping Factor"
        DEFVAL { 2 }
      ::= { accMultilinkParameterEntry 12 }
accMultilinkParameterFragmentSize OBJECT-TYPE
        SYNTAX INTEGER (0..4096)
        ACCESS read-write
        STATUS mandatory
        DESCRIPTION
                "Multilink Fragment Size"
        DEFVAL { 0 } -- disabled
      ::= { accMultilinkParameterEntry 13 }
accMultilinkParameterMppAdminState OBJECT-TYPE
        SYNTAX INTEGER {
                enabled(1),
                disabled(2)
        }
        ACCESS read-write
        STATUS deprecated
        DESCRIPTION
                "Multilink MLX Admin State
		 It's default enabled for standard mlink"
        DEFVAL { enabled }
      ::= { accMultilinkParameterEntry 14 }
accMultilinkParameterBWprotocol OBJECT-TYPE
        SYNTAX INTEGER (0..2)
        ACCESS read-write
        STATUS mandatory
        DESCRIPTION
                "Bandwidth management protocol
			DEFAULT(0),
                	MLX(1),
	                BACP/BAP(2),
        	"
        DEFVAL { 2 }
      ::= { accMultilinkParameterEntry 15 }
accMultilinkParameterBWprotocolOpSt OBJECT-TYPE
        SYNTAX INTEGER (0..1)
        ACCESS read-write
        STATUS mandatory
        DESCRIPTION
                "Bandwidth management protocol
		    down(0),
		    up(1),
       		" 
        DEFVAL { 0 }
      ::= { accMultilinkParameterEntry 16 }
	accMlTable	OBJECT-TYPE
			SYNTAX SEQUENCE OF AccMlEntry
			ACCESS not-accessible
			STATUS mandatory
			 DESCRIPTION
                  "  A table of Multilink (load-sharing) groups."
			 ::= { accMultilink 2 }
          accMlEntry    OBJECT-TYPE
                        SYNTAX AccMlEntry
                        ACCESS not-accessible
                        STATUS mandatory
                        DESCRIPTION
                          " Info on specific multilink group "
                        INDEX { ifIndex }
                        ::= { accMlTable 1 }
		AccMlEntry ::= SEQUENCE {
			accMlAdminStatus	INTEGER
			}
	    accMlAdminStatus	OBJECT-TYPE   
			SYNTAX	INTEGER {
				on(1),
				off(2),
				undefined(3)
				}
			ACCESS	read-write
			STATUS	mandatory
			DESCRIPTION
                 " Status of  load sharing capability.  In those systems
                   which support the accSlotProtocol object, the protocol
                   must be set to HDLC for both ports."
			::= { accMlEntry 7 }
accMultilinkStatTable OBJECT-TYPE
	SYNTAX SEQUENCE OF AccMultilinkStatEntry
	ACCESS not-accessible
	STATUS mandatory
	DESCRIPTION
		" "
      ::= { accMultilink 3 }
accMultilinkStatEntry OBJECT-TYPE
	SYNTAX AccMultilinkStatEntry
	ACCESS not-accessible
	STATUS mandatory
	DESCRIPTION
		" "
	INDEX { accMultilinkStatIndex }
      ::= { accMultilinkStatTable 1 }
AccMultilinkStatEntry ::= SEQUENCE {
	accMultilinkStatIndex		INTEGER,
        accMultilinkStatRcvInSeqs	Counter,
        accMultilinkStatRcvOutSeqs	Counter,
        accMultilinkStatRcvOutWindows	Counter,
        accMultilinkStatRcvSeqBreaks	Counter,
        accMultilinkStatRcvPendings	Gauge,
	accMultilinkStatRcvRingColls	Counter,
	accMultilinkStatRcvWrongEncaps	Counter,
	accMultilinkStatSendEncapFails	Counter,
	accMultilinkStatRcvMessages	Counter,
	accMultilinkStatRcvUnSeqs	Counter,
	accMultilinkStatRcvSeqs		Counter,
	accMultilinkStatSendMessages	Counter,
	accMultilinkStatSendUnSeqs	Counter,
	accMultilinkStatSendSeqs	Counter,
	accMultilinkStatRcvSeqNum	INTEGER,
	accMultilinkStatSendSeqNum	INTEGER,
	accMultilinkStatSendCongSeqNum	INTEGER,
	accMultilinkStatRcvSeqWraps	Counter,
	accMultilinkStatSendSeqWraps	Counter,
	accMultilinkStatTotalLinks	Gauge,
	accMultilinkStatActiveLinks	Gauge,
	accMultilinkStatTotalBandwidth	Gauge,
	accMultilinkStatUsedBandwidth	Gauge,
	accMultilinkStatCallThreshold	Gauge,
	accMultilinkStatClearThreshold	Gauge
	}
accMultilinkStatIndex OBJECT-TYPE
	SYNTAX INTEGER
	ACCESS read-only
	STATUS mandatory
	DESCRIPTION
		"An integer that uniquely identifies this
		multilink group."
      ::= { accMultilinkStatEntry 1 }
accMultilinkStatRcvInSeqs OBJECT-TYPE
	SYNTAX Counter
	ACCESS read-only
	STATUS mandatory
	DESCRIPTION
		"The number of messages received over all 
		physical ports associated with this multilink 
		group whose multilink sequence number matched
		what the receiver expected."
      ::= { accMultilinkStatEntry 2 }
accMultilinkStatRcvOutSeqs OBJECT-TYPE
	SYNTAX Counter
	ACCESS read-only
	STATUS mandatory
	DESCRIPTION
		"The number of messages received over all 
		physical ports associated with this multilink 
		group whose multilink sequence number did not
		match what the receiver expected."
      ::= { accMultilinkStatEntry 3 }
accMultilinkStatRcvOutWindows OBJECT-TYPE
	SYNTAX Counter
	ACCESS read-only
	STATUS mandatory
	DESCRIPTION
		"The number of messages received over all 
		physical ports associated with this multilink 
		group whose multilink sequence number did not
		fall within the receiver's window of acceptable 
		sequence numbers."
      ::= { accMultilinkStatEntry 4 }
accMultilinkStatRcvSeqBreaks OBJECT-TYPE
	SYNTAX Counter
	ACCESS read-only
	STATUS mandatory
	DESCRIPTION
		"The number of times the receiver has declared
		that a break in sequence numbers has occurred."
      ::= { accMultilinkStatEntry 5 }
accMultilinkStatRcvWrongEncaps OBJECT-TYPE
	SYNTAX Counter
	ACCESS read-only
	STATUS mandatory
	DESCRIPTION
		"The number of messages received over all 
		physical ports associated with this multilink 
		group that did not bear the expected multilink
		header."
      ::= { accMultilinkStatEntry 6 }
accMultilinkStatRcvPendings OBJECT-TYPE
	SYNTAX Gauge
	ACCESS read-only
	STATUS mandatory
	DESCRIPTION
		"The number of messages received over all 
		physical ports associated with this multilink 
		group that are currently being held pending the
		arrival of a message with an earlier sequence
		number."
      ::= { accMultilinkStatEntry 7 }
accMultilinkStatRcvRingColls OBJECT-TYPE
	SYNTAX Counter
	ACCESS read-only
	STATUS mandatory
	DESCRIPTION
		"The number of messages received over all 
		physical ports associated with this multilink 
		group that would have occupied the same storage
		as another message being held pending the
		arrival of a message with an earlier sequence
		number."
      ::= { accMultilinkStatEntry 8 }
accMultilinkStatSendEncapFails OBJECT-TYPE
	SYNTAX Counter
	ACCESS read-only
	STATUS mandatory
	DESCRIPTION
		"The number of times the multilink group was
		unable to encapsulate an outgoing message."
      ::= { accMultilinkStatEntry 9 }
accMultilinkStatRcvMessages OBJECT-TYPE
        SYNTAX Counter
        ACCESS read-only
        STATUS mandatory
        DESCRIPTION
                "Number of messages received over the bundle. "
      ::= { accMultilinkStatEntry 10 }
accMultilinkStatRcvUnSeqs OBJECT-TYPE
        SYNTAX Counter
        ACCESS read-only
        STATUS mandatory
        DESCRIPTION
                "Number of unsequenced messages received."
      ::= { accMultilinkStatEntry 11 }
accMultilinkStatRcvSeqs OBJECT-TYPE
        SYNTAX Counter
        ACCESS read-only
        STATUS mandatory
        DESCRIPTION
                "Number of sequenced messages received."
      ::= { accMultilinkStatEntry 12 }
accMultilinkStatSendMessages OBJECT-TYPE
        SYNTAX Counter
        ACCESS read-only
        STATUS mandatory
        DESCRIPTION
                "Number of messages sent over the bundle."
      ::= { accMultilinkStatEntry 13 }
accMultilinkStatSendUnSeqs OBJECT-TYPE
        SYNTAX Counter
        ACCESS read-only
        STATUS mandatory
        DESCRIPTION
                "Number of unsequenced messages sent."
      ::= { accMultilinkStatEntry 14 }
accMultilinkStatSendSeqs OBJECT-TYPE
        SYNTAX Counter
        ACCESS read-only
        STATUS mandatory
        DESCRIPTION
                "Number of sequenced messages sent."
      ::= { accMultilinkStatEntry 15 }
accMultilinkStatRcvSeqNum OBJECT-TYPE
        SYNTAX INTEGER
        ACCESS read-only
        STATUS mandatory
        DESCRIPTION
                "Sequence number of last message received."
      ::= { accMultilinkStatEntry 16 }
accMultilinkStatSendSeqNum OBJECT-TYPE
        SYNTAX INTEGER
        ACCESS read-only
        STATUS mandatory
        DESCRIPTION
                "Sequence number of last message sent."
      ::= { accMultilinkStatEntry 17 }
accMultilinkStatSendCongSeqNum OBJECT-TYPE
        SYNTAX INTEGER
        ACCESS read-only
        STATUS mandatory
        DESCRIPTION
                "Sequence number of last message queued because of
                 congestion on the send side."
      ::= { accMultilinkStatEntry 18 }
accMultilinkStatRcvSeqWraps OBJECT-TYPE
        SYNTAX Counter
        ACCESS read-only
        STATUS mandatory
        DESCRIPTION
                "Number of times the receive sequence number has wrapped."
      ::= { accMultilinkStatEntry 19 }
accMultilinkStatSendSeqWraps OBJECT-TYPE
        SYNTAX Counter
        ACCESS read-only
        STATUS mandatory
        DESCRIPTION
                "Number of times the send sequence number has wrapped."
      ::= { accMultilinkStatEntry 20 }
accMultilinkStatTotalLinks OBJECT-TYPE
        SYNTAX Gauge
        ACCESS read-only
        STATUS mandatory
        DESCRIPTION
                "Total Number of Substrates Configured for a Bundle"
      ::= { accMultilinkStatEntry 21 }
accMultilinkStatActiveLinks OBJECT-TYPE
        SYNTAX Gauge
        ACCESS read-only
        STATUS mandatory
        DESCRIPTION
                "Total Number of Active Substrates in a Bundle"
      ::= { accMultilinkStatEntry 22 }
accMultilinkStatTotalBandwidth OBJECT-TYPE
        SYNTAX Gauge
        ACCESS read-only
        STATUS mandatory
        DESCRIPTION
                "Total Bandwidth of the Active Substrates"
      ::= { accMultilinkStatEntry 23 }
accMultilinkStatUsedBandwidth OBJECT-TYPE
        SYNTAX Gauge
        ACCESS read-only
        STATUS mandatory
        DESCRIPTION
                "Total Bandwidth Used for Output Traffic"
      ::= { accMultilinkStatEntry 24 }
accMultilinkStatCallThreshold OBJECT-TYPE
        SYNTAX Gauge
        ACCESS read-only
        STATUS mandatory
        DESCRIPTION
                "Multilink Congestion to Call in Bit per Second"
      ::= { accMultilinkStatEntry 25 }
accMultilinkStatClearThreshold OBJECT-TYPE
        SYNTAX Gauge
        ACCESS read-only
        STATUS mandatory
        DESCRIPTION
                "Multilink Congestion to Clear in Bit per Second"
      ::= { accMultilinkStatEntry 26 }
accMultilinkStackTable OBJECT-TYPE
	SYNTAX SEQUENCE OF AccMultilinkStackEntry
	ACCESS not-accessible
	STATUS mandatory
	DESCRIPTION
		" "
      ::= { accMultilink 4 }
accMultilinkStackEntry OBJECT-TYPE
	SYNTAX AccMultilinkStackEntry
	ACCESS not-accessible
	STATUS mandatory
	DESCRIPTION
		" "
	INDEX { accMultilinkStackGroup, accMultilinkStackInterface }
      ::= { accMultilinkStackTable 1 }
AccMultilinkStackEntry ::= SEQUENCE {
	accMultilinkStackGroup		INTEGER,
	accMultilinkStackInterface	INTEGER
	}
accMultilinkStackGroup OBJECT-TYPE
	SYNTAX INTEGER
	ACCESS read-write
	STATUS mandatory
	DESCRIPTION
		"An integer identifying the row of the ifTable 
		 containing information about a multilink group."
      ::= { accMultilinkStackEntry 1 }
accMultilinkStackInterface OBJECT-TYPE
	SYNTAX INTEGER
	ACCESS read-write
	STATUS mandatory
	DESCRIPTION
		"An integer identifying the row of the systemwide
		interfaces table containing information about a
		physical port or dial port associated with a
		multilink group."
      ::= { accMultilinkStackEntry 2 }
          accMlPppProtocolTable   OBJECT-TYPE
               SYNTAX    SEQUENCE OF AccMlPppProtocolEntry
               ACCESS    not-accessible
               STATUS    mandatory
               DESCRIPTION
                         " This table gives the status of forwarders
		           over MLPPP."
               ::= { accMultilink 5 }
          accMlPppProtocolEntry   OBJECT-TYPE
               SYNTAX    AccMlPppProtocolEntry
               ACCESS    not-accessible
               STATUS    mandatory
               DESCRIPTION
                         " "
               INDEX     { accMlPppIndex }
               ::= { accMlPppProtocolTable 1 }
          AccMlPppProtocolEntry ::= SEQUENCE {
                accMlPppIndex
                    INTEGER,
                accMlPppProtocol
                    INTEGER,
                accMlPppAdminStatus
                    INTEGER,
                accMlPppOperStatus
                    INTEGER
          }
          accMlPppIndex   OBJECT-TYPE
               SYNTAX    INTEGER
               ACCESS    read-only
               STATUS    mandatory
               DESCRIPTION
                        " The multilink group index"
               ::= { accMlPppProtocolEntry 1 }
          accMlPppProtocol   OBJECT-TYPE
               SYNTAX    INTEGER 
               ACCESS    read-only
               STATUS    mandatory
               DESCRIPTION
                        "Protocol client to the multilink group "
               ::= { accMlPppProtocolEntry 2 }
          accMlPppAdminStatus   OBJECT-TYPE
               SYNTAX    INTEGER {
                         enabled(1),
                         disabled(2)
                    }
               ACCESS    read-only
               STATUS    mandatory
               DESCRIPTION
                        "The administrative state of the MLPPP protocol client"
               ::= { accMlPppProtocolEntry 3 }
          accMlPppOperStatus   OBJECT-TYPE
               SYNTAX    INTEGER
               ACCESS    read-only
               STATUS    mandatory
               DESCRIPTION
                        "The PPP operational state of the MLPPP clent "
               ::= { accMlPppProtocolEntry 4 }
accMultilinkParameterMaxLinkCount OBJECT-TYPE
        SYNTAX INTEGER (0..999)
        ACCESS read-write
        STATUS mandatory
        DESCRIPTION
                "Maximum Multilink Group Can Be Configured"
      ::= { accMultilink 6 }

mlStateChange TRAP-TYPE
	ENTERPRISE accMultilink
	VARIABLES  { accMultilinkParameterIndex, ifOperStatus ,
               accTrapLogSeqNum}
	DESCRIPTION
		"This trap indicates that the indicated 
		Multilink Group has changed state.  It has 
		either been created or invalidated, or 
		has toggled  between the active and 
		inactive states.
		This is a level 1 trap.
SEVERITY-DEFAULT: Warning 
EVENTTYPE-DEFAULT: 10 
ADDITIONAL-TEXT-VARIABLES: { accTrapLogSeqNum }
PCAUSE-DEFAULT: 7 "  
      ::= 1
mlInError TRAP-TYPE
	ENTERPRISE accMultilink
	VARIABLES  { accMultilinkParameterIndex ,
               accTrapLogSeqNum}
	DESCRIPTION
		"This trap indicates that the indicated 
		Multilink Group has received a inbound
		packet that contained one or more errors 
		preventing it from being deliverable
		to an upper-layer protocol.  An example
		of such an error would be if the
		multilink port received a packet not
		bearing a multilink header.
		This is a level 5 trap.
SEVERITY-DEFAULT: Warning 
EVENTTYPE-DEFAULT: 2 
ADDITIONAL-TEXT-VARIABLES: { accTrapLogSeqNum }
PCAUSE-DEFAULT: 5 "  
      ::= 2
mlOutError TRAP-TYPE
	ENTERPRISE accMultilink
	VARIABLES  { accMultilinkParameterIndex ,
               accTrapLogSeqNum}
	DESCRIPTION
		"This trap indicates that the indicated 
		Multilink Group has encountered one or 
		more errors preventing an outbound 
		packet from being deliverable to a
		lower-layer protocol.  An example of
		such an error would be if memory were
		not available in which to store the
		multilink header.
		This is a level 5 trap.
SEVERITY-DEFAULT: Warning 
EVENTTYPE-DEFAULT: 2 
ADDITIONAL-TEXT-VARIABLES: { accTrapLogSeqNum }
PCAUSE-DEFAULT: 5 "  
      ::= 3
mlDiscard TRAP-TYPE
	ENTERPRISE accMultilink
	VARIABLES  { accMultilinkParameterIndex ,
               accTrapLogSeqNum}
	DESCRIPTION
		"This trap indicates that the indicated 
		Multilink Group has discarded an incoming
		or outgoing packet.
		This is a level 7 trap.
SEVERITY-DEFAULT: Warning 
EVENTTYPE-DEFAULT: 2 
ADDITIONAL-TEXT-VARIABLES: { accTrapLogSeqNum }
PCAUSE-DEFAULT: 106 "  
      ::= 4
END
