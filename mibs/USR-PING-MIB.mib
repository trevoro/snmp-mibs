USR-PING-MIB DEFINITIONS ::= BEGIN
	IMPORTS
		OBJECT-TYPE, MODULE-IDENTITY, Integer32, Counter32, IpAddress
								FROM	SNMPv2-SMI
		TruthValue, DisplayString	
								FROM SNMPv2-TC
		common, UsrConfigStatus
								FROM USR-DEFINITIONS-MIB;
usrPing MODULE-IDENTITY
        LAST-UPDATED	"200102161500Z"
        ORGANIZATION	"CommWorks"
	   CONTACT-INFO	""
        DESCRIPTION
            "This MIB Module defines the Commworks enterprise specific
		   interface to the Ping for Services process."
        ::= { common 36 }
-- Begin managed object definitions here...
	usrPingVersion OBJECT-TYPE
	SYNTAX	     DisplayString
	MAX-ACCESS     read-only
	STATUS      	current
	DESCRIPTION
		"The current software version of the Ping Process."
	::= { usrPing 1}
	usrPingConfigFileName OBJECT-TYPE
	SYNTAX	     DisplayString
	MAX-ACCESS     read-only
	STATUS      	current
	DESCRIPTION		
		"The name of a ConfigFile to read/write  permanent database records.
		 If the value of this object is an empty string, then the
		 Ping process uses the default name `@file://PingProcess.cfg'. "
	::= { usrPing 2 }
	usrPingCFMStatusFlag  OBJECT-TYPE
	SYNTAX		UsrConfigStatus
	MAX-ACCESS     read-write
	STATUS      	current
	DESCRIPTION
		"Setting the value of this object to `save' causes the values
		 of the Ping Group to be written out to the current config
		 file, which is stored in the cfgPingFile object. While
		 the new ConfigFile is being written, the Ping process
		 will set the value of this flag set to `saving''. Any
		 attempts to set the value while it is  not `normal'
		 (i.e. the file is currently being written to the
		 ConfigFile) while result in a badValue error being
		 returned. Setting the value to `normal' will result in no
		 action."
	::= { usrPing 3 }
	usrPingBusyOutEnabled	OBJECT-TYPE
	SYNTAX		TruthValue
	MAX-ACCESS	read-write
	STATUS		current
	DESCRIPTION
		"The variable defines whether the Ping process will continuously
		 ping a list of systems and busy out the modems if those systems
		 do not respond in the specified period of time."
	DEFVAL	{ 1 }
	--CONFIGURABLE
	::= { usrPing 4 }
	usrPingBusyOutTable	OBJECT-TYPE
	SYNTAX		SEQUENCE OF UsrPingBusyOutEntry
	MAX-ACCESS	not-accessible
	STATUS		current
	DESCRIPTION
	      	"A list of systems to ping for connectivity."
	::= { usrPing 5 }
	usrPingBusyOutEntry OBJECT-TYPE
	SYNTAX		UsrPingBusyOutEntry
	MAX-ACCESS	not-accessible
	STATUS		current
	DESCRIPTION
			"An entry containing the server info."
	INDEX { usrPingSystem }
	::= { usrPingBusyOutTable 1 }
	UsrPingBusyOutEntry ::=
	SEQUENCE {
		usrPingSystem DisplayString,
		usrPingServerStatus				INTEGER,
		usrPingFrequency				Integer32,
		usrPingMissesAllowed			Integer32,
		usrPingTimeOut					Integer32,
		usrPingServerReachable			INTEGER,
		usrPingServerTimeSinceContacted	Integer32,
		usrPingServerNumberPingsSent		Counter32,
		usrPingServerPingsReceived		Counter32,
		usrPingServerNumberTimeouts		Counter32,
		usrPingServerNumberUnreachable	Counter32,
		usrPingServerAverageResponseTime	Integer32,
		usrPingServerAddress			IpAddress,
		usrPingServerAverageResponseTimeMS Integer32
		}
	usrPingSystem	OBJECT-TYPE
	SYNTAX		DisplayString (SIZE (0..132))
	MAX-ACCESS	not-accessible
	STATUS		current
	DESCRIPTION
		"The name or IP address of the system to ping..."
	--CONFIGURABLE
	::= { usrPingBusyOutEntry 1 }
	usrPingServerStatus	OBJECT-TYPE
	SYNTAX		INTEGER {
				enabled(1),
				disabled(2),
				delete(3)
				}
	MAX-ACCESS	read-write
	STATUS		current
	DESCRIPTION
		"Is this particular server pinged or not?"
	DEFVAL	{ enabled }
	--CONFIGURABLE
	::= { usrPingBusyOutEntry 2 }
	usrPingFrequency	OBJECT-TYPE
	SYNTAX		Integer32(1..200)
	UNITS		"seconds"
	MAX-ACCESS	read-write
	STATUS		current
	DESCRIPTION	
		"How many seconds between each ping request."
	DEFVAL	{ 30 }
	--CONFIGURABLE
	::= { usrPingBusyOutEntry 3 }
	usrPingMissesAllowed	OBJECT-TYPE
	SYNTAX		Integer32(1..1000)
	MAX-ACCESS	read-write
	STATUS		current
	DESCRIPTION	
		"The number of allowable misses before this system is declared
		 unreachable."
	DEFVAL	{ 1 }
	--CONFIGURABLE
	::= { usrPingBusyOutEntry 4 }
	usrPingTimeOut		OBJECT-TYPE
	SYNTAX		Integer32(1..6000)
	UNITS		"seconds"
	MAX-ACCESS	read-write
	STATUS		current
	DESCRIPTION
		"The number of seconds a ping request can be outstanding before
		 it is declared a miss (failure)."
	DEFVAL	{ 10 }
	--CONFIGURABLE
	::= { usrPingBusyOutEntry 5 }
	usrPingServerReachable	OBJECT-TYPE
	SYNTAX		INTEGER {
				reachable (1),
				unreachable (2),
				badNameOrAddress (3),
				unTried (4),
				dnsTimeout (5)
				}
	MAX-ACCESS	read-only
	STATUS		current
	DESCRIPTION
		"Do we consider this server connected?"
	::= { usrPingBusyOutEntry 6 }
	usrPingServerTimeSinceContacted	OBJECT-TYPE
	SYNTAX		Integer32
	UNITS		"seconds"
	MAX-ACCESS	read-only
	STATUS		current
	DESCRIPTION
		"The number of seconds since this server was contacted."
	::= { usrPingBusyOutEntry 7 }
	usrPingServerNumberPingsSent	OBJECT-TYPE
	SYNTAX		Counter32
	MAX-ACCESS	read-only
	STATUS		current
	DESCRIPTION
		"The number of ping requests sent to this server."
	::= { usrPingBusyOutEntry 8 }
	usrPingServerPingsReceived	OBJECT-TYPE
	SYNTAX		Counter32
	MAX-ACCESS	read-only
	STATUS		current
	DESCRIPTION
		"The number of ping responses received from this server."
	::= { usrPingBusyOutEntry 9 }
	usrPingServerNumberTimeouts	OBJECT-TYPE
	SYNTAX		Counter32
	MAX-ACCESS	read-only
	STATUS		current
	DESCRIPTION
		"The number of ping requests sent but not responded to in the specified time."
	::= { usrPingBusyOutEntry 10 }
	usrPingServerNumberUnreachable	OBJECT-TYPE
	SYNTAX		Counter32
	MAX-ACCESS	read-only
	STATUS		current
	DESCRIPTION
		"The number of ICMP responses received that indicate the system was unreachable."
	::= { usrPingBusyOutEntry 11 }
	usrPingServerAverageResponseTime	OBJECT-TYPE
	SYNTAX		Integer32
	UNITS		"seconds"
	MAX-ACCESS	read-only
	STATUS		current
	DESCRIPTION
		"The average response time, in seconds, between ping request and response
		 for this server."
	::= { usrPingBusyOutEntry 12 }
	usrPingServerAddress	OBJECT-TYPE
	SYNTAX		IpAddress
	MAX-ACCESS	read-only
	STATUS		current
	DESCRIPTION
		"The translated IP address of this entry"
	::= { usrPingBusyOutEntry 13 }
	usrPingServerAverageResponseTimeMS	OBJECT-TYPE
	SYNTAX		Integer32
	UNITS		"milliseconds"
	MAX-ACCESS	read-only
	STATUS		current
	DESCRIPTION
		"The average response time, in milliseconds, between ping request
		and response for this server."
	::= { usrPingBusyOutEntry 14 }
END  -- End of USR-PING-MIB DEFINITIONS
-- ************************************************************************
--
--      usr_remote_ping.mib - An enterprise specific Remote Ping MIB
--
-- Author:         Reuben Sivan
-- Created:        Feb-24-1997
--
