Nortel-Magellan-Passport-CallServerMIB
DEFINITIONS ::= BEGIN



IMPORTS

      OBJECT-TYPE
   FROM RFC-1212

      components,
      passportMIBs
   FROM Nortel-Magellan-Passport-UsefulDefinitionsMIB

      Counter32,
      DisplayString,
      StorageType,
      RowStatus,
      Unsigned32
   FROM Nortel-Magellan-Passport-StandardTextualConventionsMIB

      NonReplicated,
      WildcardedDigitString
   FROM Nortel-Magellan-Passport-TextualConventionsMIB;




-- LAST-UPDATED   "9603010000Z"
-- ORGANIZATION   "Nortel"
-- CONTACT-INFO   "
--         Nortel Magellan Network Management
--         
--         Postal: P.O. Box 5080, Station F 
--                 Ottawa, Ontario 
--                 Canada  K2C 3T1
--         
--         Email:  nm_plm@nt.com"
-- DESCRIPTION
--    "The module describing the Nortel Magellan Passport
--     CallServer Enterprise MIB."

callServerMIB OBJECT IDENTIFIER ::= { passportMIBs 41 }










-- CallRouter
-- This component performs the call routing function. It is a database 
-- containing prefix-DNAs. Unlike the DNAs under the 
-- NumberingPlanIndicator component which are only local DNAs, 
-- the DNAs under this component can refer to local DNAs and DNAs 
-- resident on other Passport modules. This component represents a 
-- database that is used to translate a DNA in a call setup packet into a 
-- ModuleId or a RoutingId so that the call setup packet can be routed 
-- to the correct Passport module within the subnet or to the correct 
-- Passport subnet. This call router can only be used for a Passport 
-- only network. This call router only provides service when there is 
-- no CSRM attached to the Passport subnet. If a CSRM is connected 
-- to the subnet, the CSRM will provide the call routing service.

cR OBJECT IDENTIFIER ::= { components 42 }



cRRowStatusTable OBJECT-TYPE
   SYNTAX     SEQUENCE OF CRRowStatusEntry
   ACCESS     not-accessible
   STATUS     mandatory
   DESCRIPTION
     "This entry controls the addition and deletion of 
      cR components."
::= { cR 1 }

cRRowStatusEntry OBJECT-TYPE
   SYNTAX     CRRowStatusEntry
   ACCESS     not-accessible
   STATUS     mandatory
   DESCRIPTION
     "A single entry in the table represents a single 
      cR component."
   INDEX {
      cRIndex }
::= { cRRowStatusTable 1 }

CRRowStatusEntry ::= SEQUENCE {
   cRRowStatus
      RowStatus,
   cRComponentName
      DisplayString,
   cRStorageType
      StorageType,
   cRIndex
      NonReplicated }

cRRowStatus OBJECT-TYPE
   SYNTAX     RowStatus 
   ACCESS     read-write
   STATUS     mandatory
   DESCRIPTION
     "This variable is used as the basis for SNMP naming of
      cR components.
      These components can be added and deleted."
::= { cRRowStatusEntry 1 }

cRComponentName OBJECT-TYPE
   SYNTAX     DisplayString 
   ACCESS     read-only
   STATUS     mandatory
   DESCRIPTION
     "This variable provides the component's string name for
      use with the ASCII Console Interface"
::= { cRRowStatusEntry 2 }

cRStorageType OBJECT-TYPE
   SYNTAX     StorageType 
   ACCESS     read-only
   STATUS     mandatory
   DESCRIPTION
     "This variable represents the storage type value for the
      cR tables."
::= { cRRowStatusEntry 4 }

cRIndex OBJECT-TYPE
   SYNTAX     NonReplicated 
   ACCESS     not-accessible
   STATUS     mandatory
   DESCRIPTION
     "This variable represents the index for the cR tables."
::= { cRRowStatusEntry 10 }


-- CallRouter NumberingPlanId/<x121,e164> 
-- This component collects all the prefix DNAs provisioned for a 
-- particular numbering plan indicator. There are two numbering plans 
-- allowed, E.164 and X.121.

cRNpi OBJECT IDENTIFIER ::= { cR 2 }



cRNpiRowStatusTable OBJECT-TYPE
   SYNTAX     SEQUENCE OF CRNpiRowStatusEntry
   ACCESS     not-accessible
   STATUS     mandatory
   DESCRIPTION
     "This entry controls the addition and deletion of 
      cRNpi components."
::= { cRNpi 1 }

cRNpiRowStatusEntry OBJECT-TYPE
   SYNTAX     CRNpiRowStatusEntry
   ACCESS     not-accessible
   STATUS     mandatory
   DESCRIPTION
     "A single entry in the table represents a single 
      cRNpi component."
   INDEX {
      cRIndex,
      cRNpiIndex }
::= { cRNpiRowStatusTable 1 }

CRNpiRowStatusEntry ::= SEQUENCE {
   cRNpiRowStatus
      RowStatus,
   cRNpiComponentName
      DisplayString,
   cRNpiStorageType
      StorageType,
   cRNpiIndex
      INTEGER }

cRNpiRowStatus OBJECT-TYPE
   SYNTAX     RowStatus 
   ACCESS     read-write
   STATUS     mandatory
   DESCRIPTION
     "This variable is used as the basis for SNMP naming of
      cRNpi components.
      These components can be added and deleted."
::= { cRNpiRowStatusEntry 1 }

cRNpiComponentName OBJECT-TYPE
   SYNTAX     DisplayString 
   ACCESS     read-only
   STATUS     mandatory
   DESCRIPTION
     "This variable provides the component's string name for
      use with the ASCII Console Interface"
::= { cRNpiRowStatusEntry 2 }

cRNpiStorageType OBJECT-TYPE
   SYNTAX     StorageType 
   ACCESS     read-only
   STATUS     mandatory
   DESCRIPTION
     "This variable represents the storage type value for the
      cRNpi tables."
::= { cRNpiRowStatusEntry 4 }

cRNpiIndex OBJECT-TYPE
   SYNTAX     INTEGER  {
                 x121(0),
                 e164(1) }
   ACCESS     not-accessible
   STATUS     mandatory
   DESCRIPTION
     "This variable represents the index for the cRNpi tables."
::= { cRNpiRowStatusEntry 10 }

cRNpiStatsTable OBJECT-TYPE
   SYNTAX     SEQUENCE OF CRNpiStatsEntry
   ACCESS     not-accessible
   STATUS     mandatory
   DESCRIPTION
     "This group of attributes contains the statistics kept for a particular 
      numbering plan indicator."
::= { cRNpi 10 }

cRNpiStatsEntry OBJECT-TYPE
   SYNTAX     CRNpiStatsEntry
   ACCESS     not-accessible
   STATUS     mandatory
   DESCRIPTION
     "An entry in the cRNpiStatsTable."
   INDEX {
      cRIndex,
      cRNpiIndex }
::= { cRNpiStatsTable 1 }

CRNpiStatsEntry ::= SEQUENCE {
   cRNpiTotalDnas
      Unsigned32,
   cRNpiCallsRouted
      Counter32,
   cRNpiCallsFailed
      Counter32 }

cRNpiTotalDnas OBJECT-TYPE
   SYNTAX     Unsigned32 (0..4294967295)
   ACCESS     read-only
   STATUS     mandatory
   DESCRIPTION
     "This attribute contains the total number of prefix-DNAs 
      provisioned."
   DEFVAL     { 0 }
::= { cRNpiStatsEntry 1 }

cRNpiCallsRouted OBJECT-TYPE
   SYNTAX     Counter32 
   ACCESS     read-only
   STATUS     mandatory
   DESCRIPTION
     "This attribute contains the total number of call setup packets routed. 
      When the counter reaches the maximum, it wraps back to zero."
::= { cRNpiStatsEntry 2 }

cRNpiCallsFailed OBJECT-TYPE
   SYNTAX     Counter32 
   ACCESS     read-only
   STATUS     mandatory
   DESCRIPTION
     "This attribute contains the total number of call setup packets that 
      failed to route. This could be caused by the MID or RID being 
      unreachable or by the DNA failing to translate to a MID or RID. 
      Check the prefix-DNA provisioning data and the DNAs associated 
      to the endpoints of the connection. When the counter reaches the 
      maximum, it wraps back to zero."
::= { cRNpiStatsEntry 3 }


-- Cr Npi/<x121,e164> Dna/<BCD(1..15, WILDCARDED)>
-- This subcomponent represents a prefix-DNA in the numbering plan. 
-- The instance value must be 1 to 15 digits each of value 0 through 9 
-- or wildcard.Wild digits may be used so that the digit position 
-- specified by the wild digit is ignored when making a routing 
-- decision. This will reduce the number of prefix-DNAs needed to 
-- properly route the calls. The wild digit is represented by "?". 
-- Wildcarding inconsistencies can not exist. If a prefix-DNA already 
-- exists in the database with a specific digit in position 3, new prefix-
-- DNAs may not be added with a wildcard in position 3. Similarly, if 
-- the prefix-DNA already exists with a wildcard in a particular 
-- position, a similar prefix-DNA cannot be added with a specific digit 
-- in the same position.

cRNpiDna OBJECT IDENTIFIER ::= { cRNpi 2 }



cRNpiDnaRowStatusTable OBJECT-TYPE
   SYNTAX     SEQUENCE OF CRNpiDnaRowStatusEntry
   ACCESS     not-accessible
   STATUS     mandatory
   DESCRIPTION
     "This entry controls the addition and deletion of 
      cRNpiDna components."
::= { cRNpiDna 1 }

cRNpiDnaRowStatusEntry OBJECT-TYPE
   SYNTAX     CRNpiDnaRowStatusEntry
   ACCESS     not-accessible
   STATUS     mandatory
   DESCRIPTION
     "A single entry in the table represents a single 
      cRNpiDna component."
   INDEX {
      cRIndex,
      cRNpiIndex,
      cRNpiDnaIndex }
::= { cRNpiDnaRowStatusTable 1 }

CRNpiDnaRowStatusEntry ::= SEQUENCE {
   cRNpiDnaRowStatus
      RowStatus,
   cRNpiDnaComponentName
      DisplayString,
   cRNpiDnaStorageType
      StorageType,
   cRNpiDnaIndex
      WildcardedDigitString }

cRNpiDnaRowStatus OBJECT-TYPE
   SYNTAX     RowStatus 
   ACCESS     read-write
   STATUS     mandatory
   DESCRIPTION
     "This variable is used as the basis for SNMP naming of
      cRNpiDna components.
      These components can be added and deleted."
::= { cRNpiDnaRowStatusEntry 1 }

cRNpiDnaComponentName OBJECT-TYPE
   SYNTAX     DisplayString 
   ACCESS     read-only
   STATUS     mandatory
   DESCRIPTION
     "This variable provides the component's string name for
      use with the ASCII Console Interface"
::= { cRNpiDnaRowStatusEntry 2 }

cRNpiDnaStorageType OBJECT-TYPE
   SYNTAX     StorageType 
   ACCESS     read-only
   STATUS     mandatory
   DESCRIPTION
     "This variable represents the storage type value for the
      cRNpiDna tables."
::= { cRNpiDnaRowStatusEntry 4 }

cRNpiDnaIndex OBJECT-TYPE
   SYNTAX     WildcardedDigitString (SIZE (1..15))
   ACCESS     not-accessible
   STATUS     mandatory
   DESCRIPTION
     "This variable represents the index for the cRNpiDna tables."
::= { cRNpiDnaRowStatusEntry 10 }

cRNpiDnaProvTable OBJECT-TYPE
   SYNTAX     SEQUENCE OF CRNpiDnaProvEntry
   ACCESS     not-accessible
   STATUS     mandatory
   DESCRIPTION
     "This group of attributes represents what the prefix-DNA maps to."
::= { cRNpiDna 10 }

cRNpiDnaProvEntry OBJECT-TYPE
   SYNTAX     CRNpiDnaProvEntry
   ACCESS     not-accessible
   STATUS     mandatory
   DESCRIPTION
     "An entry in the cRNpiDnaProvTable."
   INDEX {
      cRIndex,
      cRNpiIndex,
      cRNpiDnaIndex }
::= { cRNpiDnaProvTable 1 }

CRNpiDnaProvEntry ::= SEQUENCE {
   cRNpiDnaRoutingId
      Unsigned32,
   cRNpiDnaModuleId
      Unsigned32 }

cRNpiDnaRoutingId OBJECT-TYPE
   SYNTAX     Unsigned32 (0..126)
   ACCESS     read-write
   STATUS     mandatory
   DESCRIPTION
     "This attribute identifies the routingId that the prefix-DNA maps to. 
      If the value is set to zero, then the routingId is not used. Note that at 
      least one and only one of the attributes in this group must be set to a 
      non-zero value."
   DEFVAL     { 0 }
::= { cRNpiDnaProvEntry 1 }

cRNpiDnaModuleId OBJECT-TYPE
   SYNTAX     Unsigned32 (0..1909)
   ACCESS     read-write
   STATUS     mandatory
   DESCRIPTION
     "This attribute contains the module identifier value that the DNA 
      maps to. If the value is set to zero, then the moduleId is not used. 
      Note that at least one and only one of the attributes in this group 
      must be set to a non-zero value."
   DEFVAL     { 0 }
::= { cRNpiDnaProvEntry 2 }




-- 
-- Version and Compliance statements
-- 



-- Object-Group Statement:
-- A list of all current accessible leaf objects.

-- OBJECTS { cRNpiCallsFailed,
--           cRNpiCallsRouted,
--           cRNpiDnaComponentName,
--           cRNpiDnaStorageType,
--           cRNpiTotalDnas,
--           cRNpiDnaRowStatus,
--           cRNpiComponentName,
--           cRNpiDnaRoutingId,
--           cRComponentName,
--           cRNpiStorageType,
--           cRNpiRowStatus,
--           cRNpiDnaModuleId,
--           cRStorageType,
--           cRRowStatus }
-- STATUS  mandatory
-- DESCRIPTION
--   "A list of all current accessible leaf objects."

callServerGroup OBJECT IDENTIFIER ::= { callServerMIB 1 }
callServerGroupBC OBJECT IDENTIFIER ::= { callServerGroup 3 }
callServerGroupBC02 OBJECT IDENTIFIER ::= { callServerGroupBC 3 }
callServerGroupBC02A OBJECT IDENTIFIER ::= { callServerGroupBC02 2 }



-- Agent-Capabilities Statement:

-- PRODUCT-RELEASE "Passport Release 7.0 CallServer."
-- STATUS          mandatory
-- DESCRIPTION     "CallServer MIB: MIB Version BC02A,
--                  Software Version BG00S4C."
-- SUPPORTS        Nortel-Magellan-Passport-CallServerMIB
--    INCLUDES     { callServerGroupBC02A }

callServerCapabilities OBJECT IDENTIFIER ::= { callServerMIB 3 }
callServerCapabilitiesBC OBJECT IDENTIFIER ::= { callServerCapabilities 3 }
callServerCapabilitiesBC02 OBJECT IDENTIFIER ::= { callServerCapabilitiesBC 3 }
callServerCapabilitiesBC02A OBJECT IDENTIFIER ::= { callServerCapabilitiesBC02 2 }





END
