ACC-TSM DEFINITIONS ::= BEGIN

    IMPORTS
		OBJECT-TYPE, IpAddress, TimeTicks, Gauge, Counter FROM RFC1155-SMI
		TRAP-TYPE FROM RFC-1215
 accTrapLogSeqNum FROM ACC-SYSTEM
	accBRG, DisplayString, RowStatus, IfIndex, SmdsAddress
             FROM ACC-MIB;

-- TDM Switching Manager Group
accTsmGroup OBJECT IDENTIFIER ::= { accBRG 56 }
-- TSM Table --
	accTsmTable	OBJECT-TYPE
		SYNTAX SEQUENCE OF AccTsmTableEntry
		ACCESS not-accessible
		STATUS mandatory
		DESCRIPTION
			"Table containing operational parameters of the TDM Bus."
		::= { accTsmGroup 1 }
	accTsmTableEntry  OBJECT-TYPE
		SYNTAX AccTsmTableEntry
		ACCESS not-accessible
		STATUS mandatory
		DESCRIPTION
			"An entry in the TSM table."
		INDEX { INTEGER }
		::= { accTsmTable 1 }
	AccTsmTableEntry  ::= SEQUENCE {
		accTsmLdxIndex		INTEGER,
		accTsmMsgLevel 		INTEGER
	}
	accTsmLdxIndex OBJECT-TYPE
		SYNTAX INTEGER
		ACCESS read-only
		STATUS mandatory
		DESCRIPTION
			"The slot index of the current LDX  from 
		 	 which the switching matrix is displayed."
		::=  { accTsmTableEntry 1 }
	accTsmMsgLevel OBJECT-TYPE
		SYNTAX INTEGER
		ACCESS read-write
		STATUS mandatory
		DESCRIPTION
			"Message level for displaying TSM generated traps."
		::= { accTsmTableEntry 2 }
-- TSM Switch Table --
	accTsmSwitchTable	OBJECT-TYPE
		SYNTAX SEQUENCE OF AccTsmSwitchTableEntry
		ACCESS not-accessible
		STATUS mandatory
		DESCRIPTION
			"Table containing switched parameters of the TDM Bus."
		::= { accTsmGroup 2 }
	accTsmSwitchTableEntry  OBJECT-TYPE
		SYNTAX AccTsmSwitchTableEntry
		ACCESS not-accessible
		STATUS mandatory
		DESCRIPTION
			"An entry in the TSM switching table."
		INDEX { INTEGER }
		::= { accTsmSwitchTable 1 }
	AccTsmSwitchTableEntry  ::= SEQUENCE {
		accTsmSwitchingId	INTEGER,
		accTsmLocStream		OCTET STRING,
		accTsmLocTimeslot  	OCTET STRING,
		accTsmTdmStream 	OCTET STRING,
		accTsmTdmTimeslot	OCTET STRING,
		accTsmSrcCkt		INTEGER,
		accTsmDstCkt		INTEGER
	}
	accTsmSwitchingId OBJECT-TYPE
		SYNTAX INTEGER
		ACCESS read-write
		STATUS mandatory
		DESCRIPTION
			"TSM assigned switching ID of this specific 
			 switching."
		::= { accTsmSwitchTableEntry 1 }
	accTsmLocStream OBJECT-TYPE
		SYNTAX  OCTET STRING
		ACCESS read-only
		STATUS mandatory
		DESCRIPTION
			"Local stream allocated for this switching setup."
		::= { accTsmSwitchTableEntry 2 }
	accTsmLocTimeslot  OBJECT-TYPE
		SYNTAX  OCTET STRING
		ACCESS read-only
		STATUS mandatory
		DESCRIPTION
			"Local timeslot on the local stream allocated 
			 for this switching setup."
		::= { accTsmSwitchTableEntry 3 }
	accTsmTdmStream OBJECT-TYPE
		SYNTAX  OCTET STRING
		ACCESS read-only
		STATUS mandatory
		DESCRIPTION
			"TDM stream allocated for this switching setup."
		::= { accTsmSwitchTableEntry 4 }
	accTsmTdmTimeslot  OBJECT-TYPE
		SYNTAX  OCTET STRING
		ACCESS read-only
		STATUS mandatory
		DESCRIPTION
			"Remote timeslot on the remote stream allocated 
			 for this switching setup."
		::= { accTsmSwitchTableEntry 5 }
	accTsmSrcCkt OBJECT-TYPE
		SYNTAX  INTEGER
		ACCESS read-only
		STATUS mandatory
		DESCRIPTION
			"Source circuit."
		::= { accTsmSwitchTableEntry 6 }
	accTsmDstCkt  OBJECT-TYPE
		SYNTAX  INTEGER
		ACCESS read-only
		STATUS mandatory
		DESCRIPTION
			"Destination circuit."
		::= { accTsmSwitchTableEntry 7 }
-- Tsm Test Object --
	accTsmTest  OBJECT-TYPE
		SYNTAX  INTEGER
		ACCESS read-write
		STATUS mandatory
		DESCRIPTION
			"A Test objcet to setup test commands for 
			 internal use."
		::= { accTsmGroup 3 }
	-- SSU section of TSM MIB branch
	accSsuSrcTable	OBJECT-TYPE
	    SYNTAX	SEQUENCE OF AccSsuSrcEntry
	    ACCESS	not-accessible
	    STATUS	mandatory
	    DESCRIPTION
	      " Table of potential serial synchronization unit clock sources.
		An entry exists for all potential clock sources."
	    ::= { accTsmGroup 4 }
	accSsuSrcEntry	OBJECT-TYPE
	    SYNTAX	AccSsuSrcEntry
	    ACCESS      not-accessible
	    STATUS      mandatory
    	    DESCRIPTION
	      " Configuration and status objects for a particular SSU source."
	    INDEX { accSsuSrcType, accSsuSrcIfIndex }
	    ::= { accSsuSrcTable 1 }
	AccSsuSrcEntry	::= SEQUENCE {
	    accSsuSrcType		INTEGER,
	    accSsuSrcIfIndex		INTEGER,
	    accSsuSrcPriority		INTEGER,
	    accSsuSrcFrequency		INTEGER,
	    accSsuSrcRecovery		INTEGER,
	    accSsuSrcThreshold		INTEGER,
	    accSsuSrcState		INTEGER,
	    accSsuSrcFailures		Counter
	    }
	    accSsuSrcType		OBJECT-TYPE
		SYNTAX	INTEGER {
		    external(1),
		    derived(2),
		    internal(3)
		    }
		ACCESS	read-only
		STATUS	mandatory
		DESCRIPTION
		  "The type of this clock source."
		::= { accSsuSrcEntry 1 }
	    accSsuSrcIfIndex		OBJECT-TYPE
		SYNTAX	INTEGER
		ACCESS	read-only
		STATUS	mandatory
		DESCRIPTION
		  "The ifIndex of the clock source if its type is derived."
		::= { accSsuSrcEntry 2 }
	    accSsuSrcPriority		OBJECT-TYPE
		SYNTAX	INTEGER {
		    high(1),
		    medium(2),
		    low(3),
		    disabled(4)
		    }
		ACCESS	read-write
		STATUS	mandatory
		DESCRIPTION
		  "The relative priority of this clock source."
		::= { accSsuSrcEntry 3 }
	    accSsuSrcFrequency	OBJECT-TYPE
		SYNTAX	INTEGER 
		ACCESS	read-write
		STATUS	mandatory
		DESCRIPTION
		  "The frequency in Khz of the clock source.  This
		  is settable only for the external source."
		::= { accSsuSrcEntry 4 }
	    accSsuSrcRecovery	OBJECT-TYPE
		SYNTAX	INTEGER {
		    automatic(1),
		    manual(2)
		    }
		ACCESS	read-write
		STATUS	mandatory
		DESCRIPTION
		  "The recovery mechanism to use following source failure.
		  This is only settable for the derived sources."
		::= { accSsuSrcEntry 5 }
	    accSsuSrcThreshold	OBJECT-TYPE
		SYNTAX	INTEGER
		ACCESS	read-write
		STATUS	mandatory
		DESCRIPTION
		  "The numbers of failures permitted in an hour before a clock
		  source whose recovery mechanism is automatic is disabled."
		::= { accSsuSrcEntry 6 }
	    accSsuSrcState	OBJECT-TYPE
		SYNTAX	INTEGER {
		    current(1),
		    ready(2),
		    not-ready(3),
		    disabled-ready(4),
		    disabled-not-ready(5)
		    }
		ACCESS	read-only
		STATUS	mandatory
		DESCRIPTION
		  "The current state of this clock source."
		::= { accSsuSrcEntry 7 }
	    accSsuSrcFailures	OBJECT-TYPE
		SYNTAX	Counter
		ACCESS	read-only
		STATUS	mandatory
		DESCRIPTION
		  "The count of failures detected on this clock source."
		::= { accSsuSrcEntry 8 }
        accTsmDITable     OBJECT-TYPE
                SYNTAX SEQUENCE OF AccTsmDIEntry
                ACCESS not-accessible
                STATUS mandatory
                DESCRIPTION
                        "Table containing Drop Insert objects."
                ::= { accTsmGroup 5 }
        accTsmDIEntry  OBJECT-TYPE
                SYNTAX AccTsmDIEntry
                ACCESS not-accessible
                STATUS mandatory
                DESCRIPTION
                        "An entry in the TSM Drop Insert table."
                INDEX { INTEGER }
                ::= { accTsmDITable 1 }
        AccTsmDIEntry  ::= SEQUENCE {
	    accTsmDIId 			INTEGER,
	    accTsmDIFromDS0 		INTEGER,
	    accTsmDIFromDS1 		INTEGER,
	    accTsmDIToDS0 		INTEGER,
	    accTsmDIToDS1 		INTEGER,
	    accTsmDIRowStatus 		INTEGER
        }
	-- TSM Drop Insert section of TSM MIB branch
	    accTsmDIId	OBJECT-TYPE
		SYNTAX  INTEGER	
		ACCESS	read-only
		STATUS	mandatory
		DESCRIPTION
                    "Internal identifier for the switched circuit."
		::= { accTsmDIEntry 1 }
	    accTsmDIFromDS0	OBJECT-TYPE
		SYNTAX  INTEGER	
		ACCESS	read-only
		STATUS	mandatory
		DESCRIPTION
                    "Contains source timeslot."
		::= { accTsmDIEntry 2 }
	    accTsmDIFromDS1	OBJECT-TYPE
		SYNTAX  INTEGER	
		ACCESS	read-only
		STATUS	mandatory
		DESCRIPTION
                    "Contains source DS1."
		::= { accTsmDIEntry 3 }
	    accTsmDIToDS0	OBJECT-TYPE
		SYNTAX  INTEGER	
		ACCESS	read-only
		STATUS	mandatory
		DESCRIPTION
                    "Contains destination DS0."
		::= { accTsmDIEntry 4 }
	    accTsmDIToDS1	OBJECT-TYPE
		SYNTAX  INTEGER	
		ACCESS	read-only
		STATUS	mandatory
		DESCRIPTION
                    "Contains destination DS1."
		::= { accTsmDIEntry 5 }
	    accTsmDIRowStatus	OBJECT-TYPE
		SYNTAX	INTEGER {
		    add(1),
		    delete(2)
		    }
		ACCESS	read-only
		STATUS	mandatory
		DESCRIPTION
                    "Contains validity of switching entry."
		::= { accTsmDIEntry 6 }

END
