USR-FR-MIB DEFINITIONS ::= BEGIN
     IMPORTS
             OBJECT-TYPE, MODULE-IDENTITY,
             Integer32
                      FROM SNMPv2-SMI
             common, UsrConfigStatus, DisplayString
                     FROM USR-DEFINITIONS-MIB;
    usrFR MODULE-IDENTITY
         LAST-UPDATED "200205052000Z"
         ORGANIZATION "CommWorks Corporation, a 3Com Company"
         CONTACT-INFO "Customer Support"
         DESCRIPTION
                 "The commWorks enterprise defined MIB objects
                   for Frame Relay."
--       REVISION "200205052000Z"
--       DESCRIPTION "Convert to SNMPv2 and remove obsolete
--                    tables to usr_fr_obsolete.mib. These tables
--                    were obsoleted by the implementation of
--                    RFC2115-frDTE.mib."
         ::= { common 15 }
     --  Frame Relay DTE MIB
     --
     --      the range of ifIndex
     --
     Index ::= Integer32       -- 1..ifNumber
     --
     --      the range of a Data Link Connection Identifier
     --
     DLCI ::= Integer32        -- 0..DLCINumber
     --
     -- The Frame Relay Base Group.
     --
     usrfrBaseCfgFileName OBJECT-TYPE
         SYNTAX       DisplayString
         MAX-ACCESS   read-only
         STATUS       current
         DESCRIPTION
                 "The name of a ConfigFile to read/write
                 permanent database records. If the value of this
                 object is an empty string, then the FR process
                 uses the default name `@file://FrFile.cfg'."
         ::= { usrFR 1 }
     usrfrBaseCFMSaveStatus OBJECT-TYPE
         SYNTAX  UsrConfigStatus
         MAX-ACCESS  read-write
         STATUS      current
         DESCRIPTION
                 "Setting the value of this object to `save'
                 causes the values of the FR Base Group
                 entries to be written out to the current FR
                 config file. While the new config file is being
                 written, the FR process will set the value
                 of this flag set to `saving''. Any attempts to set
                 the value while it is  not `normal' (i.e. the file
                 is currently being written to the config file)
                 while result in a badValue error being returned.
                 Setting the value to `normal' will result in no
                 action."
         ::= { usrFR 2 }
--  The following OID's and leaf objects are obsoleted 
--  by rfc2115-frDTE.mib
     usrfrDlcmiTable OBJECT IDENTIFIER ::= { usrFR 3 }
     usrfrCircuitTable OBJECT IDENTIFIER ::= { usrFR 4 }
     usrfrErrTable OBJECT IDENTIFIER ::= { usrFR 5 }
     END -- End of USR-FR-MIB DEFINITIONS
