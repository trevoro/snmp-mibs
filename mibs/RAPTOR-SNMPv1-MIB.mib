RAPTOR-SNMPv1-MIB DEFINITIONS ::= BEGIN
 
IMPORTS
    enterprises, OBJECT-TYPE
        FROM RFC1155-SMI
    TRAP-TYPE
        FROM RFC-1215;
 
--
-- Assigned by IANA
--

raptorSystems      OBJECT IDENTIFIER ::= { enterprises 1294 }
 
--
-- Raptor Systems subtrees
--

raptorModules OBJECT IDENTIFIER ::= { raptorSystems 1 }
raptorObjects OBJECT IDENTIFIER ::= { raptorSystems 2 }
raptorTraps   OBJECT IDENTIFIER ::= { raptorSystems 3 }
 
--
-- Managed objects follow
--
-- Contents:
--     raptorNotifyMessage      Alert generated by Raptor Firewall
--

raptorNotifyMessage OBJECT-TYPE
    SYNTAX       OCTET STRING
    ACCESS       not-accessible
    STATUS       mandatory
    DESCRIPTION  "An alert message generated by a Raptor Firewall."
 
    ::= { raptorObjects 1 }
 

--
-- Traps follow
--
-- Contents:
--     raptorNotifyTrap         Trap containing a single raptorNotifyMessage
--

raptorNotifyTrap TRAP-TYPE
    ENTERPRISE   raptorSystems
    VARIABLES    { raptorNotifyMessage }
    DESCRIPTION  "An alert generated by a Raptor Firewall."

    ::= 1
 
END
