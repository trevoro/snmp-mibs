XEDIA-FRAME-RELAY-MIB DEFINITIONS ::= BEGIN

IMPORTS 
    MODULE-IDENTITY, OBJECT-TYPE, IpAddress
        FROM SNMPv2-SMI
    DisplayString
        FROM SNMPv2-TC
    MODULE-COMPLIANCE, OBJECT-GROUP
        FROM SNMPv2-CONF
    xediaMibs
        FROM XEDIA-REG
    frCircuitEntry
	FROM  RFC1315-MIB
    ;

xediaFrameRelayMIB MODULE-IDENTITY
    LAST-UPDATED "9808242155Z" -- August 24, 1998
    ORGANIZATION "Xedia Corp."
    CONTACT-INFO
        "support@xedia.com"
    DESCRIPTION
        "This module defines additional objects for management of Frame Relay
        in Xedia devices, above and beyond what is defined in the
        IETF's Frame Relay MIBs."
    ::= { xediaMibs 19 }

-- Top-level organization of the MIB

xfrObjects          OBJECT IDENTIFIER ::= { xediaFrameRelayMIB 1 }
xfrNotifications    OBJECT IDENTIFIER ::= { xediaFrameRelayMIB 2 }
xfrConformance      OBJECT IDENTIFIER ::= { xediaFrameRelayMIB 3 }

-- ****************************************************************
-- Object Definitions
-- ****************************************************************

--
-- Frame Relay ARP Table
--

xfrArpTable OBJECT-TYPE
    SYNTAX      SEQUENCE OF XfrArpEntry
    MAX-ACCESS  not-accessible
    STATUS      current
    DESCRIPTION
        "The IP Address Translation table used for mapping from IP
        addresses to physical addresses, in this case frame relay DLCIs.
        This table contains much of the same information that is in the
        ipNetToMediaTable."
    ::= { xfrObjects 1 }

xfrArpEntry OBJECT-TYPE
    SYNTAX      XfrArpEntry
    MAX-ACCESS  not-accessible
    STATUS      current
    DESCRIPTION
        "Each entry contains one IpAddress to `physical' address
        equivalence."
    INDEX       { xfrArpIfIndex,
                  xfrArpNetAddress }
    ::= { xfrArpTable 1 }

XfrArpEntry ::= SEQUENCE {
    xfrArpIfIndex      INTEGER,
    xfrArpNetAddress   IpAddress,
    xfrArpType         INTEGER,
    xfrArpDlci         INTEGER,
    xfrArpIfStack      DisplayString
}

xfrArpIfIndex OBJECT-TYPE
    SYNTAX  INTEGER (1..2147483647)
    MAX-ACCESS  read-create
    STATUS  current
    DESCRIPTION
            "The interface on which this entry's equivalence is
            effective.  The interface identified by a particular value
            of this index is the same interface as identified by the
            same value of RFC 1573's ifIndex."
    ::= { xfrArpEntry 1 }

xfrArpNetAddress OBJECT-TYPE
    SYNTAX  IpAddress
    MAX-ACCESS  read-create
    STATUS  current
    DESCRIPTION
            "The IpAddress corresponding to the frame relay DLCI."
    ::= { xfrArpEntry 2 }

xfrArpType OBJECT-TYPE
    SYNTAX  INTEGER {
                other(1),        -- none of the following
                invalid(2),      -- an invalidated mapping
                dynamic(3),
                static(4)
            }
    MAX-ACCESS  read-create
    STATUS  current
    DESCRIPTION
            "The type of mapping.
            Setting this object to the value invalid(2) has the effect
            of invalidating the corresponding entry in the
            xfrArpEntryTable.  That is, it effectively disassociates
            the interface identified with said entry from the mapping
            identified with said entry.  It is an implementation-
            specific matter as to whether the agent removes an
            invalidated entry from the table.  Accordingly, management
            stations must be prepared to receive tabular information
            from agents that corresponds to entries not currently in
            use.  Proper interpretation of such entries requires
            examination of the relevant xfrArpEntryType object."
    DEFVAL      { static }
    ::= { xfrArpEntry 3 }

xfrArpDlci OBJECT-TYPE
    SYNTAX      INTEGER (16..991)
    MAX-ACCESS  read-create
    STATUS      current
    DESCRIPTION
            "The DLCI attached to the IP address."
    DEFVAL      { 16 }
    ::= { xfrArpEntry 4 }

xfrArpIfStack OBJECT-TYPE
    SYNTAX      DisplayString
    MAX-ACCESS  read-only
    STATUS      current
    DESCRIPTION
            "A description of the interface stack containing this frame 
            relay interface, with the IP interface, the frame relay interface,
            and the device interface."
    ::= { xfrArpEntry 5 }


xFrCircuitTable OBJECT-TYPE
    SYNTAX      SEQUENCE OF XFrCircuitEntry
    MAX-ACCESS  not-accessible
    STATUS      current
    DESCRIPTION
    "A table containing additional information about specific Data
     Link Connection Identifiers and corresponding virtual circuits."
    ::= { xfrObjects 2 }
 
xFrCircuitEntry     OBJECT-TYPE
    SYNTAX      XFrCircuitEntry
    MAX-ACCESS  not-accessible
    STATUS      current
    DESCRIPTION
    "The additional information regarding a single  Data  Link
     Connection Identifier."
    AUGMENTS    { frCircuitEntry }
    ::= { xFrCircuitTable 1 }

XFrCircuitEntry ::=
    SEQUENCE {
      -- 
      -- DLCI status info
      --
      xfrCircuitType          INTEGER
    }

xfrCircuitType OBJECT-TYPE
    SYNTAX      INTEGER { dynamic(1), static(2) }
    MAX-ACCESS  read-only
    STATUS      current
    DESCRIPTION
        "The type of DLCI "
    ::= { xFrCircuitEntry 1 }

-- ****************************************************************
-- Conformance Information
-- ****************************************************************

xfrCompliances OBJECT IDENTIFIER ::= { xfrConformance 1 }
xfrGroups      OBJECT IDENTIFIER ::= { xfrConformance 2 }

--
-- Compliance Statements
--

xfrCompliance MODULE-COMPLIANCE
    STATUS      current
    DESCRIPTION
        "The compliance statement for all agents that support this
        MIB. A compliant agent implements all objects defined in this
        MIB."
    MODULE  -- this module
    MANDATORY-GROUPS {
        xfrAllGroup
    }
    ::= { xfrCompliances 1 }

--
-- Object Groups
--

xfrAllGroup OBJECT-GROUP
    OBJECTS {
        xfrArpIfIndex,
        xfrArpNetAddress,
        xfrArpDlci,
        xfrArpIfStack,
    	xfrArpType,
    	xfrCircuitType
    }
    STATUS      current
    DESCRIPTION
        "The set of all accessible objects in this MIB."
    ::= { xfrGroups 1 }

END
