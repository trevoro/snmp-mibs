IPX-INTERFACE-MANAGEMENT-PRIVATE-MIB DEFINITIONS ::= BEGIN

-- Referencing the parent branch.

IMPORTS
    MODULE-IDENTITY, OBJECT-TYPE, Integer32     FROM SNMPv2-SMI
    RowStatus, DisplayString                    FROM SNMPv2-TC
    NetNumber                                   FROM IPX-PRIVATE-MIB
    cjnMgmt                                     FROM Cajun-ROOT; 

cjnIpxIfMgmt MODULE-IDENTITY
    LAST-UPDATED "9904010000Z" -- Thursday, April 1, 1999"
    ORGANIZATION "Lucent's Concord Technology Center (CTC)"
    CONTACT-INFO
        "Marc Cochran -- mcochran@lucent.com"
    DESCRIPTION
            "Cajun Private IPX Interface Management MIB"
    ::= { cjnMgmt 2 }


-- IPX Interface Group
--
    cjnIpxIfGroup    OBJECT IDENTIFIER ::= { cjnIpxIfMgmt 1 }

    cjnIpxIfNextIndex OBJECT-TYPE
        SYNTAX      INTEGER   
        MAX-ACCESS  read-only
        STATUS      current
        DESCRIPTION
                "The next available IfIndex. This number should be used to 
                create new rows in the IpxIfTable."
        ::= { cjnIpxIfGroup 1 }

    cjnIpxIfNumber OBJECT-TYPE
        SYNTAX      INTEGER   
        MAX-ACCESS  read-only
        STATUS      current
        DESCRIPTION
                "The number of IPX interfaces."
        ::= { cjnIpxIfGroup 2 }

    cjnIpxIfTable OBJECT-TYPE
        SYNTAX      SEQUENCE OF CjnIpxIfEntry
        MAX-ACCESS  not-accessible
        STATUS      current
        DESCRIPTION
                "A list of Cajun IPX interface entries.  The number of 
                entries is given by the value of cjnIpxIfNumber."
        ::= { cjnIpxIfGroup 3 }
    
    cjnIpxIfEntry OBJECT-TYPE
        SYNTAX      CjnIpxIfEntry
        MAX-ACCESS  not-accessible
        STATUS      current
        DESCRIPTION
                "A Cajun IPX interface instance."
        INDEX       { cjnIpxIfIndex }
        ::= { cjnIpxIfTable 1 }

        CjnIpxIfEntry ::=
            SEQUENCE {
                cjnIpxIfIndex               Integer32,
                cjnIpxIfRowStatus           RowStatus,  
                cjnIpxIfNetNumber           NetNumber,
                cjnIpxIfEncapsType          INTEGER,
                cjnIpxIfVlanIfIndex         Integer32,
                cjnIpxIfName                DisplayString,
                cjnIpxIfTicks               Integer32,
                cjnIpxIfType20RbcastMode    INTEGER,
                cjnIpxIfAdminStatus         INTEGER,
                cjnIpxIfOperStatus          INTEGER
            }
    
    cjnIpxIfIndex OBJECT-TYPE
        SYNTAX      Integer32   
        MAX-ACCESS  read-only
        STATUS      current
        DESCRIPTION
                "The globally unique identifier for this interface.  This 
                number MUST correlate with the IfTable's IfIndex in MIB-II 
                or RFC2233."
        ::= { cjnIpxIfEntry 1 }

    cjnIpxIfRowStatus OBJECT-TYPE
        SYNTAX      RowStatus 
        MAX-ACCESS  read-create
        STATUS      current
        DESCRIPTION
                "The status of this row, by which new entries may be
                created, or old entries deleted from this table."
        ::= { cjnIpxIfEntry 2 }

    cjnIpxIfNetNumber OBJECT-TYPE
        SYNTAX      NetNumber
        MAX-ACCESS  read-create
        STATUS      current
        DESCRIPTION
                "The IPX network number associated with this IPX interface."
        ::= { cjnIpxIfEntry 3 }

    cjnIpxIfEncapsType OBJECT-TYPE
        SYNTAX      INTEGER {
                        ethernetV2(1), 
                        ethernet8022(2),
                        ethernetSNAP(3),
                        ethernet8023(4)
                    }
        MAX-ACCESS  read-create
        STATUS      current
        DESCRIPTION
                "The Ethernet encapsulation type used on this IPX interface."
        DEFVAL      { ethernetV2 }
        ::= { cjnIpxIfEntry 4 }

    cjnIpxIfVlanIfIndex OBJECT-TYPE
        SYNTAX      Integer32   
        MAX-ACCESS  read-create
        STATUS      current
        DESCRIPTION
                "The interface index of the VLAN for this interface.  This 
                number MUST correlate with the IfTable's IfIndex in MIB-II 
                or RFC2233."
        ::= { cjnIpxIfEntry 5 }
    
    cjnIpxIfName OBJECT-TYPE
        SYNTAX      DisplayString (SIZE(0..31))
        MAX-ACCESS  read-create
        STATUS      current
        DESCRIPTION
                "The protocol unique name associated with this interface.  
                This name is limited to 31 characters and may appear in 
                other protocol interface entries such as IP and Appletalk 
                but MAY NOT be duplicated within the cjnIpxIfTable.  
                In other words, other protocols can use this interface name 
                but IPX may only have this name associated with one 
                interface."
        ::= { cjnIpxIfEntry 6 }

    cjnIpxIfTicks OBJECT-TYPE
        SYNTAX      Integer32
        MAX-ACCESS  read-create
        STATUS      current
        DESCRIPTION
                "The period of time, in ticks, that it takes to transmit one 
                byte of data, excluding protocol headers, to a destination on 
                the other end of the circuit, if the circuit is free of 
                other traffic."
        DEFVAL      { 1 }
        ::= { cjnIpxIfEntry 7 }

    cjnIpxIfType20RbcastMode OBJECT-TYPE
        SYNTAX      INTEGER { disabled(1), inbound(2), outbound(3), both(4) }
        MAX-ACCESS  read-create
        STATUS      current
        DESCRIPTION
                "The handling of NetBIOS Type 20 packets on the interface.  
                If set to disabled(1), Type 20 packets are neither sent nor 
                received on the interface.  If set to inbound(2), Type 20 
                packets may be received but not sent.  If set to 
                outbound(3), Type 20 packets may be sent on the interface 
                but not received.  If set to both(4), Type 20 packets may 
                be sent and received."
        DEFVAL      { disabled }
        ::= { cjnIpxIfEntry 8 }

    cjnIpxIfAdminStatus OBJECT-TYPE
        SYNTAX      INTEGER { up(1), down(2), testing(3) }   
        MAX-ACCESS  read-create
        STATUS      current
        DESCRIPTION
                "The administrative state of this interface.  The testing(3)  
                state indicates that no operational packets can be 
                passed.  When a managed system initializes, all 
                interfaces start with ifAdminStatus in the down(2) 
                state.  As a result of either explicit management 
                action or per configuration information retained by 
                the managed system, ifAdminStatus is then changed to 
                either the up(1) or testing(3) states (or remains in 
                the down(2) state)."
        ::= { cjnIpxIfEntry 9 }

    cjnIpxIfOperStatus OBJECT-TYPE
        SYNTAX      INTEGER { up(1), down(2), testing(3), lowerLayerDown(4) }   
        MAX-ACCESS  read-only
        STATUS      current
        DESCRIPTION
                "The current operational state of this interface.  The 
                testing(3) state indicates that no operational packets can 
                be passed.  If cjnIpxIfAdminStatus is down(2) then
                cjnIpxIfOperStatus should be down(2).  If 
                cjnIpxIfAdminStatus is up(1) then cjnIpxIfOperStatus should 
                change to up(1) if the interface is ready to transmit and 
                receive network traffic; it should change to 
                lowerLayerDown(4) if the interface is waiting for external
                actions (such as a port on the VLAN associated with the
                interface becoming operational)."
        ::= { cjnIpxIfEntry 10 }

END
