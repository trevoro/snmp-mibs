SCHEDEXT-MIB

   --FORCE-INCLUDE <mib.h>
   --FORCE-INCLUDE <snmpdefs.h>
   --FORCE-INCLUDE <snmpstat.h>
   --FORCE-INCLUDE "mibproto.h"
 
   DEFINITIONS ::= BEGIN

	IMPORTS
		MODULE-IDENTITY, OBJECT-TYPE
			FROM SNMPv2-SMI
		RowStatus, DisplayString
			FROM SNMPv2-TC
		schedExt
			FROM APENT-MIB;


    schedExtMib MODULE-IDENTITY
	   LAST-UPDATED "9801282000Z" -- Wed January 28 20:00:00 EST 1998
	   ORGANIZATION "ArrowPoint Communications Inc."
	   CONTACT-INFO
	   "Postal:               ArrowPoint Communications Inc.
				                 50 Nagog Park
				                 Acton, Massachusetts 01720
	   Tel:                   +1 978-206-3000  option 1
	   E-Mail:                support@arrowpoint.com"
       DESCRIPTION
	"This MIB module describes the ArrowPoint enterprise
	 MIB support for CLI cmd scheduler records"
      ::= { schedExt 1}


apSchedRecTable OBJECT-TYPE
	SYNTAX      SEQUENCE OF ApSchedRecEntry
	MAX-ACCESS  not-accessible
	STATUS      current
	DESCRIPTION
		"A table of CLM cmd schedule records"
	::= {schedExt 2}

apSchedRecEntry OBJECT-TYPE
	SYNTAX      ApSchedRecEntry
	MAX-ACCESS  not-accessible
	STATUS      current
	DESCRIPTION
	       "ArrowPoint Cmd Schedule record"
	INDEX  { apSchedRecName}
	::= {apSchedRecTable 1}

ApSchedRecEntry ::=
	SEQUENCE 
	{
	apSchedRecName				DisplayString,
	apSchedRecMin				DisplayString,
	apSchedRecHour				DisplayString,
	apSchedRecDay				DisplayString,
	apSchedRecMonth				DisplayString,
	apSchedRecWDay				DisplayString,
	apSchedRecCmd				DisplayString,
	apSchedRecLogFile			DisplayString,
	apSchedRecId				INTEGER,
	apSchedRecStatus			RowStatus
	}

apSchedRecName OBJECT-TYPE
	SYNTAX      DisplayString(SIZE (1..16))
	MAX-ACCESS  read-create
	STATUS      current
	DESCRIPTION
	       "A name which uniquely identifies this schedule record"
	::= {apSchedRecEntry 1}

apSchedRecMin OBJECT-TYPE
	SYNTAX      DisplayString(SIZE (1..40))
	MAX-ACCESS  read-create
	STATUS      current
	DESCRIPTION
	       "The minute of the hour (0-59)"
	::= {apSchedRecEntry 2}

apSchedRecHour OBJECT-TYPE
	SYNTAX      DisplayString(SIZE (1..40))
	MAX-ACCESS  read-create
	STATUS      current
	DESCRIPTION
	       "The hour of the day (0-32)"
	::= {apSchedRecEntry 3}

apSchedRecDay OBJECT-TYPE
	SYNTAX      DisplayString(SIZE (1..40))
	MAX-ACCESS  read-create
	STATUS      current
	DESCRIPTION
	       "The day of the Month (1-31)"
	::= {apSchedRecEntry 4}

apSchedRecMonth OBJECT-TYPE
	SYNTAX      DisplayString(SIZE (1..40))
	MAX-ACCESS  read-create
	STATUS      current
	DESCRIPTION
	       "The month ot the year (1-12)"
	::= {apSchedRecEntry 5}

apSchedRecWDay OBJECT-TYPE
	SYNTAX      DisplayString(SIZE (1..40))
	MAX-ACCESS  read-create
	STATUS      current
	DESCRIPTION
	       "The day of the week (1-7) Sunday=1"
	::= {apSchedRecEntry 6}

apSchedRecCmd OBJECT-TYPE
	SYNTAX      DisplayString(SIZE (1..255))
	MAX-ACCESS  read-create
	STATUS      current
	DESCRIPTION
	       "command to be executed"
	::= {apSchedRecEntry 7}

apSchedRecLogFile OBJECT-TYPE
	SYNTAX      DisplayString(SIZE (1..32))
	MAX-ACCESS  read-create
	STATUS      current
	DESCRIPTION
	       "log file to capture output"
	::= {apSchedRecEntry 8}
	

apSchedRecId OBJECT-TYPE
	SYNTAX      INTEGER
	MAX-ACCESS  read-only
	STATUS      current
	DESCRIPTION
	       "A internal identifier for this record"
	::= {apSchedRecEntry 9}

apSchedRecStatus OBJECT-TYPE
	SYNTAX      RowStatus
	MAX-ACCESS  read-create
	STATUS      current
	DESCRIPTION
	       "This status object for this row"
	::= {apSchedRecEntry 10}



apSchedEnable OBJECT-TYPE
	SYNTAX      INTEGER {
                             disable(0),
                             enable(1)
                            }
	MAX-ACCESS  read-write
	STATUS      current
	DESCRIPTION
	       "Parameter to enable or disable cmd scheduling functionality."
	DEFVAL {disable}
	::= {schedExt 3}

apSchedLogEnable OBJECT-TYPE
	SYNTAX      INTEGER {
                             disable(0),
                             enable(1)
                            }
	MAX-ACCESS  read-write
	STATUS      current
	DESCRIPTION
	       "Parameter to enable or disable cmd scheduling disk logging"
	DEFVAL {disable}
	::= {schedExt 4}
END
