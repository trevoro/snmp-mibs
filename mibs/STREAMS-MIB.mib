STREAMS-MIB DEFINITIONS ::= BEGIN

IMPORTS
	MODULE-IDENTITY, OBJECT-TYPE, Counter32,
	Gauge32, Integer32                        FROM SNMPv2-SMI
    TEXTUAL-CONVENTION, DisplayString				FROM SNMPv2-TC
	 OBJECT-GROUP, MODULE-COMPLIANCE 				FROM SNMPv2-CONF
	 enterprises											FROM RFC1155-SMI;

aii         OBJECT IDENTIFIER ::= { enterprises 539 }
aiSLC2      OBJECT IDENTIFIER ::= { aii 16 }



streams MODULE-IDENTITY
       LAST-UPDATED "9506281200Z"
       ORGANIZATION "Copestone Research Ltd"
       CONTACT-INFO
                  "        Nick Felisiak

                   Postal: Copestone Research Ltd
						   8 Burnside,
						   Eddleston,
						   Peebles,
						   EH45 8QP,
						   Scotland
                           

                   Tel:    +44 1721 730 288
                   E-Mail: nick@copestone.com"
       DESCRIPTION
               "This MIB provides configuration and status information
               for a STREAMS subsystem."
       ::= { aiSLC2 4 }

streamsAdmnTable		OBJECT-TYPE
	SYNTAX				SEQUENCE OF StreamsAdmnEntry
    MAX-ACCESS			not-accessible
    STATUS				current
    DESCRIPTION
            "This table contains configuration information,
			 for a STREAMS Subsystem.  There is one entry		
		     for each such such subsystem in a managed system."

    ::= {streams  1 }

streamsAdmnEntry       OBJECT-TYPE
    SYNTAX			   StreamsAdmnEntry
    MAX-ACCESS			not-accessible	
    STATUS				current
    DESCRIPTION
            "A list of STREAMS configuration values"
    INDEX       { streamsAdmnSubsystemIndex }
    ::= { streamsAdmnTable 1 }

StreamsAdmnEntry ::= SEQUENCE {
		streamsAdmnSubsystemIndex		Integer32,
		streamsAdmnMaxStorage			Integer32,
		streamsAdmnNumQueues			Integer32,
		streamsAdmnNumStreams			Integer32,
		streamsAdmnNumBufcalls			Integer32,
		streamsAdmnNumTimeouts			Integer32,
		streamsAdmnNumMblks				Integer32,
		streamsAdmnNumExtended			Integer32,
		streamsAdmnLoSafetyMark			Integer32,
		streamsAdmnMidSafetyMark		Integer32,
		streamsAdmnNumBufs0				Integer32,
		streamsAdmnNumBufs1				Integer32,
		streamsAdmnNumBufs2				Integer32,
		streamsAdmnNumBufs3				Integer32,
		streamsAdmnNumBufs4				Integer32,
		streamsAdmnNumBufs5				Integer32,
		streamsAdmnNumBufs6				Integer32,
		streamsAdmnNumBufs7				Integer32,
		streamsAdmnNumBufs8				Integer32,
		streamsAdmnNumBufs9				Integer32,
		streamsAdmnSizeBufs0			Integer32,
		streamsAdmnSizeBufs1			Integer32,
		streamsAdmnSizeBufs2			Integer32,
		streamsAdmnSizeBufs3			Integer32,
		streamsAdmnSizeBufs4			Integer32,
		streamsAdmnSizeBufs5			Integer32,
		streamsAdmnSizeBufs6			Integer32,
		streamsAdmnSizeBufs7			Integer32,
		streamsAdmnSizeBufs8			Integer32,
		streamsAdmnSizeBufs9			Integer32
}


		
streamsAdmnSubsystemIndex				OBJECT-TYPE
	SYNTAX								Integer32
	MAX-ACCESS							read-write
	STATUS								current
	DESCRIPTION
		"T B S"
	::= {streamsAdmnEntry 1}


streamsAdmnMaxStorage					OBJECT-TYPE
	SYNTAX								Integer32
	MAX-ACCESS							read-write
	STATUS								current
	DESCRIPTION
		"T B S"
	::= {streamsAdmnEntry 2}


streamsAdmnNumQueues					OBJECT-TYPE
	SYNTAX								Integer32
	MAX-ACCESS							read-only
	STATUS								current
	DESCRIPTION
		"T B S"
	::= {streamsAdmnEntry 3}


streamsAdmnNumStreams					OBJECT-TYPE
	SYNTAX								Integer32
	MAX-ACCESS							read-write
	STATUS								current
	DESCRIPTION
		"T B S"
	::= {streamsAdmnEntry 4}


streamsAdmnNumBufcalls					OBJECT-TYPE
	SYNTAX								Integer32
	MAX-ACCESS							read-write
	STATUS								current
	DESCRIPTION
		"T B S"
	::= {streamsAdmnEntry 5}


streamsAdmnNumTimeouts					OBJECT-TYPE
	SYNTAX								Integer32
	MAX-ACCESS							read-write
	STATUS								current
	DESCRIPTION
		"T B S"
	::= {streamsAdmnEntry 6}


streamsAdmnNumMblks						OBJECT-TYPE
	SYNTAX								Integer32
	MAX-ACCESS							read-write
	STATUS								current
	DESCRIPTION
		"T B S"
	::= {streamsAdmnEntry 7}


streamsAdmnNumExtended					OBJECT-TYPE
	SYNTAX								Integer32
	MAX-ACCESS							read-write
	STATUS								current
	DESCRIPTION
		"T B S"
	::= {streamsAdmnEntry 8}


streamsAdmnLoSafetyMark					OBJECT-TYPE
	SYNTAX								Integer32
	MAX-ACCESS							read-write
	STATUS								current
	DESCRIPTION
		"T B S"
	::= {streamsAdmnEntry 9}


streamsAdmnMidSafetyMark				OBJECT-TYPE
	SYNTAX								Integer32
	MAX-ACCESS							read-write
	STATUS								current
	DESCRIPTION
		"T B S"
	::= {streamsAdmnEntry 10}


streamsAdmnNumBufs0						OBJECT-TYPE
	SYNTAX								Integer32
	MAX-ACCESS							read-write
	STATUS								current
	DESCRIPTION
		"T B S"
	::= {streamsAdmnEntry 11}

streamsAdmnNumBufs1						OBJECT-TYPE
	SYNTAX								Integer32
	MAX-ACCESS							read-write
	STATUS								current
	DESCRIPTION
		"T B S"
	::= {streamsAdmnEntry 12}

streamsAdmnNumBufs2						OBJECT-TYPE
	SYNTAX								Integer32
	MAX-ACCESS							read-write
	STATUS								current
	DESCRIPTION
		"T B S"
	::= {streamsAdmnEntry 13}

streamsAdmnNumBufs3						OBJECT-TYPE
	SYNTAX								Integer32
	MAX-ACCESS							read-write
	STATUS								current
	DESCRIPTION
		"T B S"
	::= {streamsAdmnEntry 14}

streamsAdmnNumBufs4						OBJECT-TYPE
	SYNTAX								Integer32
	MAX-ACCESS							read-write
	STATUS								current
	DESCRIPTION
		"T B S"
	::= {streamsAdmnEntry 15}

streamsAdmnNumBufs5						OBJECT-TYPE
	SYNTAX								Integer32
	MAX-ACCESS							read-write
	STATUS								current
	DESCRIPTION
		"T B S"
	::= {streamsAdmnEntry 16}

streamsAdmnNumBufs6						OBJECT-TYPE
	SYNTAX								Integer32
	MAX-ACCESS							read-write
	STATUS								current
	DESCRIPTION
		"T B S"
	::= {streamsAdmnEntry 17}

streamsAdmnNumBufs7						OBJECT-TYPE
	SYNTAX								Integer32
	MAX-ACCESS							read-write
	STATUS								current
	DESCRIPTION
		"T B S"
	::= {streamsAdmnEntry 18}

streamsAdmnNumBufs8						OBJECT-TYPE
	SYNTAX								Integer32
	MAX-ACCESS							read-write
	STATUS								current
	DESCRIPTION
		"T B S"
	::= {streamsAdmnEntry 19}

streamsAdmnNumBufs9						OBJECT-TYPE
	SYNTAX								Integer32
	MAX-ACCESS							read-write
	STATUS								current
	DESCRIPTION
		"T B S"
	::= {streamsAdmnEntry 20}



streamsAdmnSizeBufs0					OBJECT-TYPE
	SYNTAX								Integer32
	MAX-ACCESS							read-write
	STATUS								current
	DESCRIPTION
		"T B S"
	::= {streamsAdmnEntry 21}

streamsAdmnSizeBufs1					OBJECT-TYPE
	SYNTAX								Integer32
	MAX-ACCESS							read-write
	STATUS								current
	DESCRIPTION
		"T B S"
	::= {streamsAdmnEntry 22}

streamsAdmnSizeBufs2					OBJECT-TYPE
	SYNTAX								Integer32
	MAX-ACCESS							read-write
	STATUS								current
	DESCRIPTION
		"T B S"
	::= {streamsAdmnEntry 23}

streamsAdmnSizeBufs3					OBJECT-TYPE
	SYNTAX								Integer32
	MAX-ACCESS							read-write
	STATUS								current
	DESCRIPTION
		"T B S"
	::= {streamsAdmnEntry 24}

streamsAdmnSizeBufs4					OBJECT-TYPE
	SYNTAX								Integer32
	MAX-ACCESS							read-write
	STATUS								current
	DESCRIPTION
		"T B S"
	::= {streamsAdmnEntry 25}

streamsAdmnSizeBufs5					OBJECT-TYPE
	SYNTAX								Integer32
	MAX-ACCESS							read-write
	STATUS								current
	DESCRIPTION
		"T B S"
	::= {streamsAdmnEntry 26}

streamsAdmnSizeBufs6					OBJECT-TYPE
	SYNTAX								Integer32
	MAX-ACCESS							read-write
	STATUS								current
	DESCRIPTION
		"T B S"
	::= {streamsAdmnEntry 27}

streamsAdmnSizeBufs7					OBJECT-TYPE
	SYNTAX								Integer32
	MAX-ACCESS							read-write
	STATUS								current
	DESCRIPTION
		"T B S"
	::= {streamsAdmnEntry 28}

streamsAdmnSizeBufs8					OBJECT-TYPE
	SYNTAX								Integer32
	MAX-ACCESS							read-write
	STATUS								current
	DESCRIPTION
		"T B S"
	::= {streamsAdmnEntry 29}

streamsAdmnSizeBufs9					OBJECT-TYPE
	SYNTAX								Integer32
	MAX-ACCESS							read-write
	STATUS								current
	DESCRIPTION
		"T B S"
	::= {streamsAdmnEntry 30}




streamsStatsTable		OBJECT-TYPE
	SYNTAX				SEQUENCE OF StreamsStatsEntry
    MAX-ACCESS			not-accessible
    STATUS				current
    DESCRIPTION
            "This table contains run-time staus information,
			 for a STREAMS Subsystem.  There is one entry		
		     for each such such subsystem in a managed system."

    ::= {streams  2 }

streamsStatsEntry       OBJECT-TYPE
    SYNTAX				StreamsStatsEntry
    MAX-ACCESS			not-accessible	
    STATUS				current
    DESCRIPTION
            "A list of STREAMS Statistics"
    INDEX       { streamsStatsSubsystemIndex }
    ::= { streamsStatsTable 1 }

StreamsStatsEntry ::= SEQUENCE {
		streamsStatsSubsystemIndex		Integer32,
		streamsStatsAllocStorage		Integer32,
		streamsStatsQueuesConfig		Integer32,
		streamsStatsQueuesInUse			Integer32,
		streamsStatsQueuesUsed			Integer32,
		streamsStatsQueuesMaxUsed		Integer32,
		streamsStatsQueuesFails			Integer32,
		streamsStatsStreamsConfig		Integer32,
		streamsStatsStreamsInUse		Integer32,
		streamsStatsStreamsUsed			Integer32,
		streamsStatsStreamsMaxUsed		Integer32,
		streamsStatsStreamsFails		Integer32,
		streamsStatsBufcallsConfig		Integer32,
		streamsStatsBufcallsInUse		Integer32,
		streamsStatsBufcallsUsed		Integer32,
		streamsStatsBufcallsMaxUsed		Integer32,
		streamsStatsBufcallsFails		Integer32,
		streamsStatsTimeoutsConfig		Integer32,
		streamsStatsTimeoutsInUse		Integer32,
		streamsStatsTimeoutsUsed		Integer32,
		streamsStatsTimeoutsMaxUsed		Integer32,
		streamsStatsTimeoutsFails		Integer32,
		streamsStatsMblksConfig			Integer32,
		streamsStatsMblksInUse			Integer32,
		streamsStatsMblksUsed			Integer32,
		streamsStatsMblksMaxUsed		Integer32,
		streamsStatsMblksFails			Integer32,
		streamsStatsExtendedConfig		Integer32,
		streamsStatsExtendedInUse		Integer32,
		streamsStatsExtendedUsed		Integer32,
		streamsStatsExtendedMaxUsed		Integer32,
		streamsStatsExtendedFails		Integer32,
		streamsStatsBufs0Config			Integer32,
		streamsStatsBufs0InUse			Integer32,
		streamsStatsBufs0Used			Integer32,
		streamsStatsBufs0MaxUsed		Integer32,
		streamsStatsBufs0Fails			Integer32,
		streamsStatsBufs1Config			Integer32,
		streamsStatsBufs1InUse			Integer32,
		streamsStatsBufs1Used			Integer32,
		streamsStatsBufs1MaxUsed		Integer32,
		streamsStatsBufs1Fails			Integer32,
		streamsStatsBufs2Config			Integer32,
		streamsStatsBufs2InUse			Integer32,
		streamsStatsBufs2Used			Integer32,
		streamsStatsBufs2MaxUsed		Integer32,
		streamsStatsBufs2Fails			Integer32,
		streamsStatsBufs3Config			Integer32,
		streamsStatsBufs3InUse			Integer32,
		streamsStatsBufs3Used			Integer32,
		streamsStatsBufs3MaxUsed		Integer32,
		streamsStatsBufs3Fails			Integer32,
		streamsStatsBufs4Config			Integer32,
		streamsStatsBufs4InUse			Integer32,
		streamsStatsBufs4Used			Integer32,
		streamsStatsBufs4MaxUsed		Integer32,
		streamsStatsBufs4Fails			Integer32,
		streamsStatsBufs5Config			Integer32,
		streamsStatsBufs5InUse			Integer32,
		streamsStatsBufs5Used			Integer32,
		streamsStatsBufs5MaxUsed		Integer32,
		streamsStatsBufs5Fails			Integer32,
		streamsStatsBufs6Config			Integer32,
		streamsStatsBufs6InUse			Integer32,
		streamsStatsBufs6Used			Integer32,
		streamsStatsBufs6MaxUsed		Integer32,
		streamsStatsBufs6Fails			Integer32,
		streamsStatsBufs7Config			Integer32,
		streamsStatsBufs7InUse			Integer32,
		streamsStatsBufs7Used			Integer32,
		streamsStatsBufs7MaxUsed		Integer32,
		streamsStatsBufs7Fails			Integer32,
		streamsStatsBufs8Config			Integer32,
		streamsStatsBufs8InUse			Integer32,
		streamsStatsBufs8Used			Integer32,
		streamsStatsBufs8MaxUsed		Integer32,
		streamsStatsBufs8Fails			Integer32,
		streamsStatsBufs9Config			Integer32,
		streamsStatsBufs9InUse			Integer32,
		streamsStatsBufs9Used			Integer32,
		streamsStatsBufs9MaxUsed		Integer32,
		streamsStatsBufs9Fails			Integer32
}

streamsStatsSubsystemIndex		OBJECT-TYPE
	SYNTAX				Integer32
	MAX-ACCESS			read-only
	STATUS				current
	DESCRIPTION	
			"The particular STREAMS subsystem on the host for which
			 statistics are required."
	::= {streamsStatsEntry 1}

streamsStatsAllocStorage		OBJECT-TYPE
	SYNTAX				Integer32
	MAX-ACCESS			read-only
	STATUS				current
	DESCRIPTION	
			"The amount of storage allocated to the STREAMS system
		     for buffers, queues, etc"

	::= {streamsStatsEntry 2}

streamsStatsQueuesConfig		OBJECT-TYPE
	SYNTAX				Integer32
	MAX-ACCESS			read-only
	STATUS				current
	DESCRIPTION	
			"The number of queues configured in the running system.
		     If dynamically, created, the number currently in existence"

	::= {streamsStatsEntry 3}

streamsStatsQueuesInUse		OBJECT-TYPE
	SYNTAX				Integer32
	MAX-ACCESS			read-only
	STATUS				current
	DESCRIPTION	
			"The number of queues currently in use" 
	::= {streamsStatsEntry 4}

streamsStatsQueuesUsed		OBJECT-TYPE
	SYNTAX				Integer32
	MAX-ACCESS			read-only
	STATUS				current
	DESCRIPTION	
			"The number of queues used since the system was initialised"
	::= {streamsStatsEntry 5}

streamsStatsQueuesMaxUsed		OBJECT-TYPE
	SYNTAX				Integer32
	MAX-ACCESS			read-only
	STATUS				current
	DESCRIPTION	
			"The maximum number of queues concurrently in use at any
			 time since the system was initialised"
	::= {streamsStatsEntry 6}

streamsStatsQueuesFails		OBJECT-TYPE
	SYNTAX				Integer32
	MAX-ACCESS			read-only
	STATUS				current
	DESCRIPTION	
			"The number of times a queue allocation request has been denied"
	::= {streamsStatsEntry 7}

streamsStatsStreamsConfig		OBJECT-TYPE
	SYNTAX				Integer32
	MAX-ACCESS			read-only
	STATUS				current
	DESCRIPTION	
			"The number of streams configured in the running system.
		     If dynamically, created, the number currently in existence"
	::= {streamsStatsEntry 8}

streamsStatsStreamsInUse		OBJECT-TYPE
	SYNTAX				Integer32
	MAX-ACCESS			read-only
	STATUS				current
	DESCRIPTION
			"The number of streams currently in use" 
	::= {streamsStatsEntry 9}

streamsStatsStreamsUsed		OBJECT-TYPE
	SYNTAX				Integer32
	MAX-ACCESS			read-only
	STATUS				current
	DESCRIPTION	
			"The number of streams used since the system was initialised"
	::= {streamsStatsEntry 10}

streamsStatsStreamsMaxUsed		OBJECT-TYPE
	SYNTAX				Integer32
	MAX-ACCESS			read-only
	STATUS				current
	DESCRIPTION	
			"The maximum number of streams concurrently in use at any
			 time since the system was initialised"
	::= {streamsStatsEntry 11}

streamsStatsStreamsFails		OBJECT-TYPE
	SYNTAX				Integer32
	MAX-ACCESS			read-only
	STATUS				current
	DESCRIPTION	
			"The number of times a stream allocation request has been denied"
	::= {streamsStatsEntry 12}

streamsStatsBufcallsConfig		OBJECT-TYPE
	SYNTAX				Integer32
	MAX-ACCESS			read-only
	STATUS				current
	DESCRIPTION	
			" T B S"

	::= {streamsStatsEntry 13}

streamsStatsBufcallsInUse		OBJECT-TYPE
	SYNTAX				Integer32
	MAX-ACCESS			read-only
	STATUS				current
	DESCRIPTION	
			" T B S"

	::= {streamsStatsEntry 14}

streamsStatsBufcallsUsed		OBJECT-TYPE
	SYNTAX				Integer32
	MAX-ACCESS			read-only
	STATUS				current
	DESCRIPTION	
			" T B S"

	::= {streamsStatsEntry 15}

streamsStatsBufcallsMaxUsed		OBJECT-TYPE
	SYNTAX				Integer32
	MAX-ACCESS			read-only
	STATUS				current
	DESCRIPTION	
			" T B S"

	::= {streamsStatsEntry 16}

streamsStatsBufcallsFails		OBJECT-TYPE
	SYNTAX				Integer32
	MAX-ACCESS			read-only
	STATUS				current
	DESCRIPTION	
			" T B S"

	::= {streamsStatsEntry 17}

streamsStatsTimeoutsConfig		OBJECT-TYPE
	SYNTAX				Integer32
	MAX-ACCESS			read-only
	STATUS				current
	DESCRIPTION	
			" T B S"

	::= {streamsStatsEntry 18}

streamsStatsTimeoutsInUse		OBJECT-TYPE
	SYNTAX				Integer32
	MAX-ACCESS			read-only
	STATUS				current
	DESCRIPTION	
			" T B S"

	::= {streamsStatsEntry 19}

streamsStatsTimeoutsUsed		OBJECT-TYPE
	SYNTAX				Integer32
	MAX-ACCESS			read-only
	STATUS				current
	DESCRIPTION	
			" T B S"

	::= {streamsStatsEntry 20}

streamsStatsTimeoutsMaxUsed		OBJECT-TYPE
	SYNTAX				Integer32
	MAX-ACCESS			read-only
	STATUS				current
	DESCRIPTION	
			" T B S"

	::= {streamsStatsEntry 21}

streamsStatsTimeoutsFails		OBJECT-TYPE
	SYNTAX				Integer32
	MAX-ACCESS			read-only
	STATUS				current
	DESCRIPTION	
			" T B S"

	::= {streamsStatsEntry 22}

streamsStatsMblksConfig		OBJECT-TYPE
	SYNTAX				Integer32
	MAX-ACCESS			read-only
	STATUS				current
	DESCRIPTION	
			" T B S"

	::= {streamsStatsEntry 23}

streamsStatsMblksInUse		OBJECT-TYPE
	SYNTAX				Integer32
	MAX-ACCESS			read-only
	STATUS				current
	DESCRIPTION	
			" T B S"

	::= {streamsStatsEntry 24}

streamsStatsMblksUsed		OBJECT-TYPE
	SYNTAX				Integer32
	MAX-ACCESS			read-only
	STATUS				current
	DESCRIPTION	
			" T B S"

	::= {streamsStatsEntry 25}

streamsStatsMblksMaxUsed		OBJECT-TYPE
	SYNTAX				Integer32
	MAX-ACCESS			read-only
	STATUS				current
	DESCRIPTION	
			" T B S"

	::= {streamsStatsEntry 26}

streamsStatsMblksFails		OBJECT-TYPE
	SYNTAX				Integer32
	MAX-ACCESS			read-only
	STATUS				current
	DESCRIPTION	
			" T B S"

	::= {streamsStatsEntry 27}

streamsStatsExtendedConfig		OBJECT-TYPE
	SYNTAX				Integer32
	MAX-ACCESS			read-only
	STATUS				current
	DESCRIPTION	
			" T B S"

	::= {streamsStatsEntry 28}

streamsStatsExtendedInUse		OBJECT-TYPE
	SYNTAX				Integer32
	MAX-ACCESS			read-only
	STATUS				current
	DESCRIPTION	
			" T B S"

	::= {streamsStatsEntry 29}

streamsStatsExtendedUsed		OBJECT-TYPE
	SYNTAX				Integer32
	MAX-ACCESS			read-only
	STATUS				current
	DESCRIPTION	
			" T B S"

	::= {streamsStatsEntry 30}

streamsStatsExtendedMaxUsed		OBJECT-TYPE
	SYNTAX				Integer32
	MAX-ACCESS			read-only
	STATUS				current
	DESCRIPTION	
			" T B S"

	::= {streamsStatsEntry 31}

streamsStatsExtendedFails		OBJECT-TYPE
	SYNTAX				Integer32
	MAX-ACCESS			read-only
	STATUS				current
	DESCRIPTION	
			" T B S"

	::= {streamsStatsEntry 32}

streamsStatsBufs0Config		OBJECT-TYPE
	SYNTAX				Integer32
	MAX-ACCESS			read-only
	STATUS				current
	DESCRIPTION	
			" T B S"

	::= {streamsStatsEntry 33}

streamsStatsBufs0InUse		OBJECT-TYPE
	SYNTAX				Integer32
	MAX-ACCESS			read-only
	STATUS				current
	DESCRIPTION	
			" T B S"

	::= {streamsStatsEntry 34}

streamsStatsBufs0Used		OBJECT-TYPE
	SYNTAX				Integer32
	MAX-ACCESS			read-only
	STATUS				current
	DESCRIPTION	
			" T B S"

	::= {streamsStatsEntry 35}

streamsStatsBufs0MaxUsed		OBJECT-TYPE
	SYNTAX				Integer32
	MAX-ACCESS			read-only
	STATUS				current
	DESCRIPTION	
			" T B S"

	::= {streamsStatsEntry 36}

streamsStatsBufs0Fails		OBJECT-TYPE
	SYNTAX				Integer32
	MAX-ACCESS			read-only
	STATUS				current
	DESCRIPTION	
			" T B S"

	::= {streamsStatsEntry 37}

streamsStatsBufs1Config		OBJECT-TYPE
	SYNTAX				Integer32
	MAX-ACCESS			read-only
	STATUS				current
	DESCRIPTION	
			" T B S"

	::= {streamsStatsEntry 38}

streamsStatsBufs1InUse		OBJECT-TYPE
	SYNTAX				Integer32
	MAX-ACCESS			read-only
	STATUS				current
	DESCRIPTION	
			" T B S"

	::= {streamsStatsEntry 39}

streamsStatsBufs1Used		OBJECT-TYPE
	SYNTAX				Integer32
	MAX-ACCESS			read-only
	STATUS				current
	DESCRIPTION	
			" T B S"

	::= {streamsStatsEntry 40}

streamsStatsBufs1MaxUsed		OBJECT-TYPE
	SYNTAX				Integer32
	MAX-ACCESS			read-only
	STATUS				current
	DESCRIPTION	
			" T B S"

	::= {streamsStatsEntry 41}

streamsStatsBufs1Fails		OBJECT-TYPE
	SYNTAX				Integer32
	MAX-ACCESS			read-only
	STATUS				current
	DESCRIPTION	
			" T B S"

	::= {streamsStatsEntry 42}

streamsStatsBufs2Config		OBJECT-TYPE
	SYNTAX				Integer32
	MAX-ACCESS			read-only
	STATUS				current
	DESCRIPTION	
			" T B S"

	::= {streamsStatsEntry 43}

streamsStatsBufs2InUse		OBJECT-TYPE
	SYNTAX				Integer32
	MAX-ACCESS			read-only
	STATUS				current
	DESCRIPTION	
			" T B S"

	::= {streamsStatsEntry 44}

streamsStatsBufs2Used		OBJECT-TYPE
	SYNTAX				Integer32
	MAX-ACCESS			read-only
	STATUS				current
	DESCRIPTION	
			" T B S"

	::= {streamsStatsEntry 45}

streamsStatsBufs2MaxUsed		OBJECT-TYPE
	SYNTAX				Integer32
	MAX-ACCESS			read-only
	STATUS				current
	DESCRIPTION	
			" T B S"

	::= {streamsStatsEntry 46}

streamsStatsBufs2Fails		OBJECT-TYPE
	SYNTAX				Integer32
	MAX-ACCESS			read-only
	STATUS				current
	DESCRIPTION	
			" T B S"

	::= {streamsStatsEntry 47}

streamsStatsBufs3Config		OBJECT-TYPE
	SYNTAX				Integer32
	MAX-ACCESS			read-only
	STATUS				current
	DESCRIPTION	
			" T B S"

	::= {streamsStatsEntry 48}

streamsStatsBufs3InUse		OBJECT-TYPE
	SYNTAX				Integer32
	MAX-ACCESS			read-only
	STATUS				current
	DESCRIPTION	
			" T B S"

	::= {streamsStatsEntry 49}

streamsStatsBufs3Used		OBJECT-TYPE
	SYNTAX				Integer32
	MAX-ACCESS			read-only
	STATUS				current
	DESCRIPTION	
			" T B S"

	::= {streamsStatsEntry 50}

streamsStatsBufs3MaxUsed		OBJECT-TYPE
	SYNTAX				Integer32
	MAX-ACCESS			read-only
	STATUS				current
	DESCRIPTION	
			" T B S"

	::= {streamsStatsEntry 51}

streamsStatsBufs3Fails		OBJECT-TYPE
	SYNTAX				Integer32
	MAX-ACCESS			read-only
	STATUS				current
	DESCRIPTION	
			" T B S"

	::= {streamsStatsEntry 52}

streamsStatsBufs4Config		OBJECT-TYPE
	SYNTAX				Integer32
	MAX-ACCESS			read-only
	STATUS				current
	DESCRIPTION	
			" T B S"

	::= {streamsStatsEntry 53}

streamsStatsBufs4InUse		OBJECT-TYPE
	SYNTAX				Integer32
	MAX-ACCESS			read-only
	STATUS				current
	DESCRIPTION	
			" T B S"

	::= {streamsStatsEntry 54}

streamsStatsBufs4Used		OBJECT-TYPE
	SYNTAX				Integer32
	MAX-ACCESS			read-only
	STATUS				current
	DESCRIPTION	
			" T B S"

	::= {streamsStatsEntry 55}

streamsStatsBufs4MaxUsed		OBJECT-TYPE
	SYNTAX				Integer32
	MAX-ACCESS			read-only
	STATUS				current
	DESCRIPTION	
			" T B S"

	::= {streamsStatsEntry 56}

streamsStatsBufs4Fails		OBJECT-TYPE
	SYNTAX				Integer32
	MAX-ACCESS			read-only
	STATUS				current
	DESCRIPTION	
			" T B S"

	::= {streamsStatsEntry 57}

streamsStatsBufs5Config		OBJECT-TYPE
	SYNTAX				Integer32
	MAX-ACCESS			read-only
	STATUS				current
	DESCRIPTION	
			" T B S"

	::= {streamsStatsEntry 58}

streamsStatsBufs5InUse		OBJECT-TYPE
	SYNTAX				Integer32
	MAX-ACCESS			read-only
	STATUS				current
	DESCRIPTION	
			" T B S"

	::= {streamsStatsEntry 59}

streamsStatsBufs5Used		OBJECT-TYPE
	SYNTAX				Integer32
	MAX-ACCESS			read-only
	STATUS				current
	DESCRIPTION	
			" T B S"

	::= {streamsStatsEntry 60}

streamsStatsBufs5MaxUsed		OBJECT-TYPE
	SYNTAX				Integer32
	MAX-ACCESS			read-only
	STATUS				current
	DESCRIPTION	
			" T B S"

	::= {streamsStatsEntry 61}

streamsStatsBufs5Fails		OBJECT-TYPE
	SYNTAX				Integer32
	MAX-ACCESS			read-only
	STATUS				current
	DESCRIPTION	
			" T B S"

	::= {streamsStatsEntry 62}

streamsStatsBufs6Config		OBJECT-TYPE
	SYNTAX				Integer32
	MAX-ACCESS			read-only
	STATUS				current
	DESCRIPTION	
			" T B S"

	::= {streamsStatsEntry 63}

streamsStatsBufs6InUse		OBJECT-TYPE
	SYNTAX				Integer32
	MAX-ACCESS			read-only
	STATUS				current
	DESCRIPTION	
			" T B S"

	::= {streamsStatsEntry 64}

streamsStatsBufs6Used		OBJECT-TYPE
	SYNTAX				Integer32
	MAX-ACCESS			read-only
	STATUS				current
	DESCRIPTION	
			" T B S"

	::= {streamsStatsEntry 65}

streamsStatsBufs6MaxUsed		OBJECT-TYPE
	SYNTAX				Integer32
	MAX-ACCESS			read-only
	STATUS				current
	DESCRIPTION	
			" T B S"

	::= {streamsStatsEntry 66}

streamsStatsBufs6Fails		OBJECT-TYPE
	SYNTAX				Integer32
	MAX-ACCESS			read-only
	STATUS				current
	DESCRIPTION	
			" T B S"

	::= {streamsStatsEntry 67}

streamsStatsBufs7Config		OBJECT-TYPE
	SYNTAX				Integer32
	MAX-ACCESS			read-only
	STATUS				current
	DESCRIPTION	
			" T B S"

	::= {streamsStatsEntry 68}

streamsStatsBufs7InUse		OBJECT-TYPE
	SYNTAX				Integer32
	MAX-ACCESS			read-only
	STATUS				current
	DESCRIPTION	
			" T B S"

	::= {streamsStatsEntry 69}

streamsStatsBufs7Used		OBJECT-TYPE
	SYNTAX				Integer32
	MAX-ACCESS			read-only
	STATUS				current
	DESCRIPTION	
			" T B S"

	::= {streamsStatsEntry 70}

streamsStatsBufs7MaxUsed		OBJECT-TYPE
	SYNTAX				Integer32
	MAX-ACCESS			read-only
	STATUS				current
	DESCRIPTION	
			" T B S"

	::= {streamsStatsEntry 71}

streamsStatsBufs7Fails		OBJECT-TYPE
	SYNTAX				Integer32
	MAX-ACCESS			read-only
	STATUS				current
	DESCRIPTION	
			" T B S"

	::= {streamsStatsEntry 72}

streamsStatsBufs8Config		OBJECT-TYPE
	SYNTAX				Integer32
	MAX-ACCESS			read-only
	STATUS				current
	DESCRIPTION	
			" T B S"

	::= {streamsStatsEntry 73}

streamsStatsBufs8InUse		OBJECT-TYPE
	SYNTAX				Integer32
	MAX-ACCESS			read-only
	STATUS				current
	DESCRIPTION	
			" T B S"

	::= {streamsStatsEntry 74}

streamsStatsBufs8Used		OBJECT-TYPE
	SYNTAX				Integer32
	MAX-ACCESS			read-only
	STATUS				current
	DESCRIPTION	
			" T B S"

	::= {streamsStatsEntry 75}

streamsStatsBufs8MaxUsed		OBJECT-TYPE
	SYNTAX				Integer32
	MAX-ACCESS			read-only
	STATUS				current
	DESCRIPTION	
			" T B S"

	::= {streamsStatsEntry 76}

streamsStatsBufs8Fails		OBJECT-TYPE
	SYNTAX				Integer32
	MAX-ACCESS			read-only
	STATUS				current
	DESCRIPTION	
			" T B S"

	::= {streamsStatsEntry 77}

streamsStatsBufs9Config		OBJECT-TYPE
	SYNTAX				Integer32
	MAX-ACCESS			read-only
	STATUS				current
	DESCRIPTION	
			" T B S"

	::= {streamsStatsEntry 78}

streamsStatsBufs9InUse		OBJECT-TYPE
	SYNTAX				Integer32
	MAX-ACCESS			read-only
	STATUS				current
	DESCRIPTION	
			" T B S"

	::= {streamsStatsEntry 79}

streamsStatsBufs9Used		OBJECT-TYPE
	SYNTAX				Integer32
	MAX-ACCESS			read-only
	STATUS				current
	DESCRIPTION	
			" T B S"

	::= {streamsStatsEntry 80}

streamsStatsBufs9MaxUsed		OBJECT-TYPE
	SYNTAX				Integer32
	MAX-ACCESS			read-only
	STATUS				current
	DESCRIPTION	
			" T B S"

	::= {streamsStatsEntry 81}

streamsStatsBufs9Fails		OBJECT-TYPE
	SYNTAX				Integer32
	MAX-ACCESS			read-only
	STATUS				current
	DESCRIPTION	
			" T B S"

	::= {streamsStatsEntry 82}


END
