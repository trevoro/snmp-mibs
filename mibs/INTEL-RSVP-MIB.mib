INTEL-RSVP-MIB DEFINITIONS ::= BEGIN

-- Copyright (C) 1997 Intel Corporation. All rights reserved.
--
-- Proprietary RSVP MIB, 98-05-19
--
-- This MIB defines the management information for a system supporting RSVP.
--
-- Change History:
-- 98-05-19 Initial version

    IMPORTS
      mib2ext            FROM INTEL-GEN-MIB
      OBJECT-TYPE        FROM RFC-1212;


    rsvp                 OBJECT IDENTIFIER ::= { mib2ext 33 }

--********************** RSVP configuration *********************************

    conf                 OBJECT IDENTIFIER ::= { rsvp 1 }

--********************** RSVP link configuration ****************************

    confIfTable OBJECT-TYPE
    SYNTAX SEQUENCE OF ConfIfEntry
    ACCESS not-accessible
    STATUS mandatory
    DESCRIPTION "The table contains configuration information for each
                 RSVP link."
    ::= { conf 1 }

    confIfEntry OBJECT-TYPE
    SYNTAX ConfIfEntry
    ACCESS not-accessible
    STATUS mandatory
    DESCRIPTION "Configuration information for the RSVP link."
    INDEX { confIfIndex }
    ::= { confIfTable 1 }

    ConfIfEntry ::=
    SEQUENCE {
      confIfIndex
        INTEGER,
      confIfCreateObj
        OCTET STRING (SIZE (5)),
      confIfDeleteObj
        INTEGER,
      confIfUdpEncap
        INTEGER,
      confIfRsvpTotalBw
        INTEGER,
      confIfMaxBwPerFlow
        INTEGER
    }

    confIfIndex OBJECT-TYPE
    SYNTAX INTEGER
    ACCESS read-only
    STATUS mandatory
    DESCRIPTION "The ifIndex of the RSVP link."
    ::= { confIfEntry 1 }

    confIfCreateObj OBJECT-TYPE
    SYNTAX OCTET STRING (SIZE (5))
    ACCESS read-write
    STATUS mandatory
    DESCRIPTION "Create a non existing table entry. If the entry already exist,
                 genError is returned.
                 Binary format:
                 1 byte  : confIfUdpEncap
                 2 bytes : confIfRsvpTotalBw
                 2 bytes : confIfMaxBwPerFlow
                 "
    ::= { confIfEntry 2 }

    confIfDeleteObj OBJECT-TYPE
    SYNTAX INTEGER {
      delete (1)
    }
    ACCESS read-write
    STATUS mandatory
    DESCRIPTION "Delete an existing table entry"
    ::= { confIfEntry 3 }

    confIfUdpEncap OBJECT-TYPE
    SYNTAX INTEGER {
      disabled (1),
      enabled (2)
    }
    ACCESS read-write
    STATUS mandatory
    DESCRIPTION "Indicates whether RSVP messages are also sent using UDP
                 encapsulation on the link."
    ::= { confIfEntry 4 }

    confIfRsvpTotalBw OBJECT-TYPE
    SYNTAX INTEGER
    ACCESS read-write
    STATUS mandatory
    DESCRIPTION "The percentage of the link bandwidth which is allowed
                 for RSVP reservations on the link. The range 0-10000
                 is mapped to 0-100 %."
    ::= { confIfEntry 5 }

    confIfMaxBwPerFlow OBJECT-TYPE
    SYNTAX INTEGER
    ACCESS read-write
    STATUS mandatory
    DESCRIPTION "The percentage of the link bandwidth which is allowed
                 for an RSVP reservation on the link. The range 0-10000
                 is mapped to 0-100 %."
    ::= { confIfEntry 6 }

--********************** RSVP global configuration **************************

    confRsvpEnabled OBJECT-TYPE
    SYNTAX INTEGER {
      disabled (1),
      enabled (2)
    }
    ACCESS read-write
    STATUS mandatory
    DESCRIPTION "Indicates whether RSVP is enabled in this system."
    ::= { conf 2 }

    confRefreshTimer OBJECT-TYPE
    SYNTAX INTEGER
    ACCESS read-write
    STATUS mandatory
    DESCRIPTION "The time interval in seconds between RSVP messages."
    ::= { conf 3 }

    confCleanupFactor OBJECT-TYPE
    SYNTAX INTEGER
    ACCESS read-write
    STATUS mandatory
    DESCRIPTION "The number of refresh messages that can be lost before
                 RSVP state information times out."
    ::= { conf 4 }

    END
