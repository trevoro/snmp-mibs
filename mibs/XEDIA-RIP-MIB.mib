XEDIA-RIP-MIB DEFINITIONS ::= BEGIN

IMPORTS 
    MODULE-IDENTITY, OBJECT-TYPE
        FROM SNMPv2-SMI
    MODULE-COMPLIANCE, OBJECT-GROUP
        FROM SNMPv2-CONF
    rip2IfConfEntry
        FROM RIPv2-MIB
    xediaMibs
        FROM XEDIA-REG
    ;    

xediaRipMIB MODULE-IDENTITY
    LAST-UPDATED "9702182155Z" -- February 18, 1997
    ORGANIZATION "Xedia Corp."
    CONTACT-INFO
        "support@xedia.com"
    DESCRIPTION
        "This module defines additional objects for management of RIP
        in Xedia devices, above and beyond what is defined in the
        IETF's RIPv2-MIB."
    ::= { xediaMibs 5 }

-- Top-level organization of the MIB

xripObjects          OBJECT IDENTIFIER ::= { xediaRipMIB 1 }
xripConformance      OBJECT IDENTIFIER ::= { xediaRipMIB 2 }

--
-- A RIP on/off control
--

xripAdminStat OBJECT-TYPE
    SYNTAX      INTEGER {
                    enabled(1),
                    disabled(2)
                }
    MAX-ACCESS  read-write
    STATUS      current
    DESCRIPTION
        "The administrative status of RIP in the router. The value
        'enabled(1)' indicates that the RIP process is active on
        at least one interface; 'disabled(2)' indicates it is
        disable on all interfaces."
    DEFVAL      { enabled }
    ::= { xripObjects 1 }

--
-- A RIP Import metric on/off control
--

xripImportAdmin OBJECT-TYPE
    SYNTAX      INTEGER {
                    enabled(1),
                    disabled(2)
                }
    MAX-ACCESS  read-write
    STATUS      current
    DESCRIPTION
        "The control for enabling and disabling importing of metrics."
    DEFVAL      { enabled }
    ::= { xripObjects 2 }

--
-- A RIP Import Metric value
--

xripImportMetric OBJECT-TYPE
    SYNTAX      INTEGER  (0..15)
    MAX-ACCESS  read-write
    STATUS      current
    DESCRIPTION
        "The import metric value used."
    DEFVAL      { 6 }
    ::= { xripObjects 3 }

xripUpdateTimer OBJECT-TYPE
    SYNTAX      INTEGER  (10..360)
    MAX-ACCESS  read-write
    STATUS      current
    DESCRIPTION
        "The time between updates in seconds."
    DEFVAL      { 30 }
    ::= { xripObjects 4 }

xRip2XIfConfTable        OBJECT-TYPE
    SYNTAX      SEQUENCE OF XRip2XIfConfEntry
    MAX-ACCESS  not-accessible
    STATUS      current
    DESCRIPTION
            "A list of interface entries.  The number of entries
            is given by the value of ifNumber.  This table
            contains additional objects for the interface table."
    ::= { xripObjects 10 }
 
xRip2XIfConfEntry        OBJECT-TYPE
    SYNTAX      XRip2XIfConfEntry
    MAX-ACCESS  not-accessible
    STATUS      current
    DESCRIPTION
            "An entry containing additional management information
            applicable to a particular Rip2 interface."
    AUGMENTS    { rip2IfConfEntry }
    ::= { xRip2XIfConfTable 1 }

XRip2XIfConfEntry ::=
    SEQUENCE {
        xrip2IfConfSlowConvergenceTechnique INTEGER,
	xrip2IfConfTriggerEvents            INTEGER
    }

xrip2IfConfSlowConvergenceTechnique OBJECT-TYPE
    SYNTAX      INTEGER { none(1),
                          splitHorizon(2),
                          poisonReverse(3) }
    MAX-ACCESS  read-write
    STATUS      current
    DESCRIPTION
            "The method used to inform other routers about routes."
    DEFVAL      { poisonReverse }
    ::= { xRip2XIfConfEntry 1 }

xrip2IfConfTriggerEvents OBJECT-TYPE
    SYNTAX      INTEGER { enabled(1),
                          disabled(2) }
    MAX-ACCESS  read-write
    STATUS      current
    DESCRIPTION
            "The object used to control the sending of Rip triggered
	     events."
    DEFVAL      { enabled }
    ::= { xRip2XIfConfEntry 2 }


-- ****************************************************************
-- Conformance Information
-- ****************************************************************

xripCompliances OBJECT IDENTIFIER ::= { xripConformance 1 }
xripGroups      OBJECT IDENTIFIER ::= { xripConformance 2 }

--
-- Compliance Statements
--

xripCompliance MODULE-COMPLIANCE
    STATUS      current
    DESCRIPTION
        "The compliance statement for all agents that support this
        MIB. A compliant agent implements all objects defined in this
        MIB."
    MODULE  -- this module
    MANDATORY-GROUPS {
        xripAllGroup
    }
    ::= { xripCompliances 1 }

--
-- Object Groups
--

xripAllGroup OBJECT-GROUP
    OBJECTS {
        xripAdminStat,
        xripImportAdmin,
        xripImportMetric,
        xrip2IfConfSlowConvergenceTechnique,
	xrip2IfConfTriggerEvents
    }
    STATUS      current
    DESCRIPTION
        "The set of all accessible objects in this MIB."
    ::= { xripGroups 1 }

END
