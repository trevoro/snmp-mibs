SS7VIEW-MIB DEFINITIONS ::= BEGIN

          --  Nortel Networks's Dial Access Management System MIB 

          IMPORTS
                  enterprises 	FROM RFC1155-SMI
                  IpAddress 		FROM RFC1155-SMI
                  DisplayString 	FROM RFC1213-MIB 
                  OBJECT-TYPE 	FROM RFC-1212
                  TRAP-TYPE 		FROM RFC-1215;

		  --   dialaccess  - is for Nortel Network's dial access product line 
		  --   ss7view - is for the CVX-SS7-Gateway Network Management product

          nortel  					OBJECT IDENTIFIER ::= { enterprises 562 }
          dialaccess	 				OBJECT IDENTIFIER ::= { nortel 14 }
          ss7view		 				OBJECT IDENTIFIER ::= { dialaccess 1 }
          ss7viewTrapVars			OBJECT IDENTIFIER ::= { ss7view 1 }
          ss7viewTraps	 			OBJECT IDENTIFIER ::= { ss7view 2 }
          ss7viewWebUITrapVars	OBJECT IDENTIFIER ::= { ss7view 4 }
          ss7viewINCTrapVars		OBJECT IDENTIFIER ::= { ss7view 5 }
          ss7viewINCTraps			OBJECT IDENTIFIER ::= { ss7view 6 }

--     
-- Trap Variables  
--
     
    partitionName OBJECT-TYPE
        SYNTAX DisplayString  
        ACCESS not-accessible
        STATUS mandatory
        DESCRIPTION
            " Identifies disk partition name."
        ::={ss7viewTrapVars 1}

    diskCapacity OBJECT-TYPE
        SYNTAX DisplayString
        ACCESS not-accessible
        STATUS mandatory
        DESCRIPTION
            " Indicates (in Percentage) how full the disk is."
        ::={ss7viewTrapVars 2}
        
    diskThreshold OBJECT-TYPE
        SYNTAX DisplayString
        ACCESS not-accessible
        STATUS mandatory
        DESCRIPTION
            " Indicates the threshold of diskCapacity."
        ::={ss7viewTrapVars 3}

	 trapSource OBJECT-TYPE
			SYNTAX DisplayString
			ACCESS not-accessible
			STATUS mandatory
			DESCRIPTION
				" Indicates where the trap comes from."
			::={ss7viewTrapVars 4}

 
    pollSS7ViewHost OBJECT-TYPE
        SYNTAX DisplayString
        ACCESS not-accessible
        STATUS mandatory
        DESCRIPTION
            " The host name of the SS7View workstation"
        ::={ss7viewTrapVars 30}

    pollSS7ViewIP OBJECT-TYPE
        SYNTAX IpAddress 
        ACCESS not-accessible
        STATUS mandatory
        DESCRIPTION
            " The IP Address of the SS7View workstation"
        ::={ss7viewTrapVars 31}

    pollServerName OBJECT-TYPE
        SYNTAX DisplayString
        ACCESS not-accessible
        STATUS mandatory
        DESCRIPTION
            " The CSG Server system/local host/object name"
        ::={ss7viewTrapVars 32}

    pollServerCLLI OBJECT-TYPE
        SYNTAX DisplayString
        ACCESS not-accessible
        STATUS mandatory
        DESCRIPTION
            " The CSG Server CLLI name"
        ::={ss7viewTrapVars 33}

    pollServerIpAddress OBJECT-TYPE
        SYNTAX IpAddress
        ACCESS not-accessible
        STATUS mandatory
        DESCRIPTION
            " The CSG Server CLLI name"
        ::={ss7viewTrapVars 34}

    pollFailReason OBJECT-TYPE
        SYNTAX DisplayString
        ACCESS not-accessible
        STATUS mandatory
        DESCRIPTION
            " The first line (50 characters) of the reason for the poll failure"
        ::={ss7viewTrapVars 35}

    pollSeverity OBJECT-TYPE
        SYNTAX DisplayString
        ACCESS not-accessible
        STATUS mandatory
        DESCRIPTION
            " The severity of the failure which can be one of 
              Warning, Minor, Major, or Critical"
        ::={ss7viewTrapVars 36}


	stateChangeServerName OBJECT-TYPE
        SYNTAX DisplayString
        ACCESS not-accessible
        STATUS mandatory
        DESCRIPTION
            " The CSG Server system/local host/object name"
        ::={ss7viewTrapVars 50}

	stateChangeServerCLLI OBJECT-TYPE
        SYNTAX DisplayString
        ACCESS not-accessible
        STATUS mandatory
        DESCRIPTION
            " The CSG Server CLLI name"
        ::={ss7viewTrapVars 51}

	stateChangeServerOpState OBJECT-TYPE
        SYNTAX DisplayString  
        ACCESS not-accessible
        STATUS mandatory
        DESCRIPTION
           " Identifies the Operational State of INC."
        ::={ss7viewTrapVars 52}

	stateChangeServerStandbyState OBJECT-TYPE
        SYNTAX DisplayString  
        ACCESS not-accessible
        STATUS mandatory
        DESCRIPTION
           " Identifies the Standby state of INC."
        ::={ss7viewTrapVars 53}

	stateChangeServerAvailState OBJECT-TYPE
        SYNTAX DisplayString  
        ACCESS not-accessible
        STATUS mandatory
        DESCRIPTION
           " Identifies the Availability state of INC."
        ::={ss7viewTrapVars 54}

	logArchiveName OBJECT-TYPE
        SYNTAX DisplayString  
        ACCESS not-accessible
        STATUS mandatory
        DESCRIPTION
           " Identifies the created archive name for the log files."
        ::={ss7viewTrapVars 80}

----------------------
-- Trap definitions --
----------------------

	-- Traps will be four digits Digit 1 represents the severity of the trap
	-- 1 = normal 2 = warning 3 minor 4 = major 5 = critical

	-- Digits 2, 3 and 4 represent the unique id for trap within the ss7view.
	
	-- This definition is not applicable to private traps.


----------------------
-- Trap definitions --
----------------------

	ss7viewDiskFullRaise TRAP-TYPE
		ENTERPRISE ss7viewTraps
		VARIABLES  {
			partitionName,
			diskCapacity,
			diskThreshold
		}
		DESCRIPTION
			"The Trap generated when the disk capacity is greater than 
			threshold."
		::= 2002

	ss7viewDiskFullClear TRAP-TYPE
		ENTERPRISE ss7viewTraps
		VARIABLES  {
			partitionName,
			diskCapacity,
			diskThreshold	
		 }
		DESCRIPTION
			"The Trap generated when the disk is cleared until the 
			capacity is less than the threshold."
		::= 1002

	csgStatusPollClear TRAP-TYPE
	ENTERPRISE ss7viewTrapVars 
		 VARIABLES  {
			pollSS7ViewHost,
			pollSS7ViewIP,
			pollServerName,
			pollServerCLLI,
			pollServerIpAddress
		 }
	DESCRIPTION
	    "The SS7View status poll of the CSG succeeded. This is 
	     generated after a poll to a CSG which previously failed 
	     is now successful." 
	::= 1031

	csgStatusPollFailed TRAP-TYPE
	ENTERPRISE ss7viewTrapVars
		VARIABLES  {
			pollSS7ViewHost,
			pollSS7ViewIP,
			pollServerName,
			pollServerCLLI,
			pollServerIpAddress,
			pollFailReason,
			pollSeverity
		 }
	DESCRIPTION
	    "The SS7View status poll of the CSG failed.  There may be 
	     multiple failure reasons but only the first line of the reason 
		  (up to 50 characters) is shown. 
	     Check the WebNMS/logs/stderr.txt for the complete list of
		  failures." 
	::= 1033


	csgStateChangeWarning TRAP-TYPE
	ENTERPRISE ss7viewTrapVars
		VARIABLES  {
			stateChangeServerName,
			stateChangeServerCLLI,
			stateChangeServerOpState,	
			stateChangeServerStandbyState,
			stateChangeServerAvailState
		 }
	DESCRIPTION
	    "The CSG Server state triplet changed.  Based on the state values,
		  SS7View computes that this is a Warning alarm."
	::= 1052

	csgStateChangeMinor TRAP-TYPE
	ENTERPRISE ss7viewTrapVars
		VARIABLES  {
			stateChangeServerName,
			stateChangeServerCLLI,
			stateChangeServerOpState,	
			stateChangeServerStandbyState,
			stateChangeServerAvailState
		 }
	DESCRIPTION
	    "The CSG Server state triplet changed.  Based on the state values,
		  SS7View computes that this is a Minor alarm."
	::= 1053

	csgStateChangeMajor TRAP-TYPE
	ENTERPRISE ss7viewTrapVars
		VARIABLES  {
			stateChangeServerName,
			stateChangeServerCLLI,
			stateChangeServerOpState,	
			stateChangeServerStandbyState,
			stateChangeServerAvailState
		 }
	DESCRIPTION
	    "The CSG Server state triplet changed.  Based on the state values,
		  SS7View computes that this is a Major alarm."
	::= 1054

	csgStateChangeCritical TRAP-TYPE
	ENTERPRISE ss7viewTrapVars
		VARIABLES  {
			stateChangeServerName,
			stateChangeServerCLLI,
			stateChangeServerOpState,	
			stateChangeServerStandbyState,
			stateChangeServerAvailState
		 }
	DESCRIPTION
	    "The CSG Server state triplet changed.  Based on the state values,
		  SS7View computes that this is a Critical alarm."
	::= 1055

	csgStateChangeNormal TRAP-TYPE
	ENTERPRISE ss7viewTrapVars
		VARIABLES  {
			stateChangeServerName,
			stateChangeServerCLLI,
			stateChangeServerOpState,	
			stateChangeServerStandbyState,
			stateChangeServerAvailState
		 }
	DESCRIPTION
	    "The CSG Server state triplet changed.  Based on the state values,
		  SS7View computes that this is a Clear/Normal alarm."
	::= 1051

	ss7viewLogArchive TRAP-TYPE
	ENTERPRISE ss7viewTrapVars
		VARIABLES  {
			pollSS7ViewHost,
			pollSS7ViewIP,
			logArchiveName	
		 }
	DESCRIPTION
	    "An SS7View audit has found the WebNMS logs directory to be
		  excessively large, taken action by archiving the directory, and
        has removed all but the most current few lines of information."
	::= 1081

	webServerRestarted TRAP-TYPE
	ENTERPRISE ss7viewWebUITrapVars 
	DESCRIPTION
	    "The SS7View WebUI web server has started/restarted." 
	::= 4010

--
------  BELOW ARE DEFINITIONS FROM PREVIOUS RELEASES WHICH ARE  ------
------  NO LONGER USED.  THEY ARE KEPT HERE TO AVOID ACCIDENTAL ------
------  REUSE.                                                  ------

------  Private Trap Variables  -----
--
	  privateTrapVars OBJECT-TYPE
		SYNTAX OBJECT IDENTIFIER
		ACCESS not-accessible
		STATUS mandatory
		DESCRIPTION
		"The subordinates of this node which are internal trap variables
		 used within ss7view are not for browsing."
		::= { ss7view 3 }

	 privateTraps OBJECT-TYPE
		SYNTAX OBJECT IDENTIFIER
		ACCESS not-accessible
		STATUS mandatory
		DESCRIPTION
		"The subordinates of this node which are internal traps used
		 within ss7view are not for browsing."
		::= { ss7view 4 }
 
      AlarmRaiseType ::=
         INTEGER { clear(0), raise(1), state(2) }

      alarmRaise OBJECT-TYPE
         SYNTAX AlarmRaiseType
         ACCESS not-accessible
         STATUS mandatory
         DESCRIPTION
            "Indicates if the INC alarm is raised or not
		0 = clear
		1 = raise
		2 = state

	     *It is the internal variable used in ss7view."
         ::= {privateTrapVars 1}

      incSelectionName OBJECT-TYPE
         SYNTAX DisplayString  
         ACCESS not-accessible
         STATUS mandatory
         DESCRIPTION
            " Identifies INC selection name.
	   
	      *It is the internal variable used in ss7view."
         ::={privateTrapVars 2}
--
------  ss7view INC Trap Variables  -----
------  NOT USED AS OF SS7VIEW 3.0/CSG 3.0 ------
--

      incComplexAlarmVars OBJECT-TYPE
         SYNTAX OBJECT IDENTIFIER
         ACCESS not-accessible
         STATUS mandatory
         DESCRIPTION
            " The subordinates of this node which are INC complex trap 
              variables used within ss7view."
         ::= { ss7viewINCTrapVars 1 }

      incComplexName OBJECT-TYPE
         SYNTAX DisplayString  
         ACCESS not-accessible
         STATUS mandatory
         DESCRIPTION
            " Identifies INC complex name. (CLLI)"
         ::={incComplexAlarmVars 1}

      incComplexIpAddress OBJECT-TYPE
         SYNTAX IpAddress  
         ACCESS not-accessible
         STATUS mandatory
         DESCRIPTION
            " Identifies the IPs of INCs in complex."
         ::={incComplexAlarmVars 2}

      incComplexState OBJECT-TYPE
         SYNTAX DisplayString
         ACCESS not-accessible
         STATUS mandatory
         DESCRIPTION
            " Identifies the state of INC."
         ::={incComplexAlarmVars 3}

      incComplexOpState OBJECT-TYPE
         SYNTAX DisplayString  
         ACCESS not-accessible
         STATUS mandatory
         DESCRIPTION
            " Identifies the Operational State of INC."
         ::={incComplexAlarmVars 4}

      incComplexStandbyState OBJECT-TYPE
         SYNTAX DisplayString  
         ACCESS not-accessible
         STATUS mandatory
         DESCRIPTION
            " Identifies the Standby state of INC."
         ::={incComplexAlarmVars 5}

      incComplexAvailState OBJECT-TYPE
         SYNTAX DisplayString  
         ACCESS not-accessible
         STATUS mandatory
         DESCRIPTION
            " Identifies the Availability state of INC."
         ::={incComplexAlarmVars 6}

------- Trap definitions. 

	-- Traps will be four digits Digit 1 represents the severity of the trap
	-- 1 = normal 2 = warning 3 minor 4 = major 5 = critical

	-- Digits 2, 3 and 4 represent the unique id for trap within the ss7view.
	
	-- This definition is not applicable to private traps.


------ General ss7view Traps ---------------------------------

------ trap 1000 not used as of SS7View 3.0 ------
	ss7viewApplyConfigFile TRAP-TYPE
         ENTERPRISE ss7viewTraps
		VARIABLES  {
		       trapSource
                }
         DESCRIPTION
            "The Trap generated when dialaccess map is re-read."
         ::= 1000
      
------ trap 2002 not used as of SS7View 3.0 ------
	ss7viewRefreshReadOnlyMap TRAP-TYPE
         ENTERPRISE ss7viewTraps
         DESCRIPTION
            "The Trap generated when dialaccess map gets changed." 
         ::= 1001
-- Private Trap Definition

 	 -- The private trap will not be for browsing, so a weired number
	 -- is assigned to it, which does not carry severity info.

------	Private Traps

------ trap 58916871 not used as of SS7View 3.0 ------
	privateNotifyMap TRAP-TYPE
	 ENTERPRISE privateTraps
		VARIABLES  {
			incSelectionName,
			alarmRaise
		
		}
	 DESCRIPTION
	    "This trap will notify the dialaccessMap process of changes to an 
		INC alarm state.

	     * It is the internal trap used in ss7view, not for browsing."

	 ::= 58916871

------ trap 3000 not used as of SS7View 3.0 ------
	privateRestarted TRAP-TYPE
	 ENTERPRISE privateTraps
	 DESCRIPTION
	    "Process incsurvd has been re-started.
	     
	     * It is the internal trap used in ss7view, not for browsing."	

	::= 3000

------	ss7view INC Traps ------

------ traps 1005, 1004, 1003, 1002, 1001 not used as of SS7View 3.0 ------
	incCompStateCritical TRAP-TYPE
	ENTERPRISE ss7viewINCTraps
		 VARIABLES  {
			incComplexName,
			incComplexIpAddress,
			incComplexState,
			incComplexIpAddress,
			incComplexState
		 }
	DESCRIPTION
	    "If the alarm state of INC complex is changed into Critical,
	     this trap will be raised. The alarm state of INC complexe
	     is caculated by Operational State, Standby State, and
             Availability state of INCs in the complex."
	::= 1005

	incCompStateMajor TRAP-TYPE
	ENTERPRISE ss7viewINCTraps
		 VARIABLES  {
			incComplexName,
			incComplexIpAddress,
			incComplexState,
			incComplexIpAddress,
			incComplexState
		 }
	DESCRIPTION
	    "If the alarm state of INC complex is changed into Major,
	     this trap will be raised. The alarm state of INC complexe
	     is caculated by Operational State, Standby State, and
             Availability state of INCs in the complex."
	::= 1004

	incCompStateMinor TRAP-TYPE
	ENTERPRISE ss7viewINCTraps
		 VARIABLES  {
			incComplexName,
			incComplexIpAddress,
			incComplexState,
			incComplexIpAddress,
			incComplexState
		 }
	DESCRIPTION
	    "If the alarm state of INC complex is changed into Minor,
	     this trap will be raised. The alarm state of INC complexe
	     is caculated by Operational State, Standby State, and
             Availability state of INCs in the complex."
	::= 1003

	incCompStateWarning TRAP-TYPE
 	ENTERPRISE ss7viewINCTraps
		 VARIABLES  {
			incComplexName,
			incComplexIpAddress,
			incComplexState,
			incComplexIpAddress,
			incComplexState
		 }
	DESCRIPTION
	    "If the alarm state of INC complex is changed into Warning,
	     this trap will be raised. The alarm state of INC complexe
	     is caculated by Operational State, Standby State, and
             Availability state of INCs in the complex."
	::= 1002

	incCompStateNormal TRAP-TYPE
	ENTERPRISE ss7viewINCTraps
		 VARIABLES  {
			incComplexName,
			incComplexIpAddress,
			incComplexState,
			incComplexIpAddress,
			incComplexState
		 }
	DESCRIPTION
	    "If the alarm state of INC complex is changed into Normal,
	     this trap will be raised. The alarm state of INC complexe
	     is caculated by Operational State, Standby State, and
             Availability state of INCs in the complex."
	::= 1001


	telnetServerRestarted TRAP-TYPE
	ENTERPRISE ss7viewWebUITrapVars 
	DESCRIPTION
	    "The SS7View WebUI telnet server has started/restarted." 
	::= 4000

END
