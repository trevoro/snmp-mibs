-- extracted from draft-ietf-mip4-udptunnel-mib-00.txt
-- at Sat Jun 16 06:08:32 2007

MIP-UDPTUNNEL-MIB DEFINITIONS ::= BEGIN 
 
    IMPORTS 
        Counter32, Unsigned32, MODULE-IDENTITY,  
        OBJECT-TYPE 
                FROM SNMPv2-SMI                    -- [RFC2578] 
        TruthValue 
                FROM SNMPv2-TC                     -- [RFC2579] 
        MODULE-COMPLIANCE, OBJECT-GROUP 
                FROM SNMPv2-CONF                   -- [RFC2580] 
        mipMIB  
                FROM MIP-MIB;                      -- [2006bis] 
 
    mipUdpTunnelMIB    MODULE-IDENTITY 
        LAST-UPDATED    "200706120000Z" 
        ORGANIZATION    "IETF Mobility for IPv4 Group" 
        CONTACT-INFO     
                        "   Hans Sjostrand 
                            ipUnplugged 
                            hans@ipunplugged.com" 
        DESCRIPTION 
               "The MIB module for configuring and displaying Mobile 
                IP Traversal of Network Address Translation (NAT)  
                Devices information. 
  
                Copyright (C) IETF Trust (2007). This version 
                of this MIB module is part of RFC yyyy;  see the RFC 
                itself for full legal notices." 
        REVISION      "200706120000Z" 
        DESCRIPTION 
            "First version." 
        ::= { mipMIB 4 } 
 
    mipUdpTunnelMIBObjects   OBJECT IDENTIFIER ::= { mipUdpTunnelMIB 1 } 
 
    mnUdpTunnel       OBJECT IDENTIFIER ::= { mipUdpTunnelMIBObjects 1 } 
    haUdpTunnel       OBJECT IDENTIFIER ::= { mipUdpTunnelMIBObjects 2 } 
    faUdpTunnel       OBJECT IDENTIFIER ::= { mipUdpTunnelMIBObjects 3 } 
 
 
    -- ================================================================= 
    -- mnUdpTunnel Group 
 
    mnUdpTunnelEnable OBJECT-TYPE 
         SYNTAX      TruthValue 
         MAX-ACCESS  read-write 
         STATUS      current 
         DESCRIPTION 
                 "This parameter enables and disables the RFC 3519 UDP 
                  tunneling function in the MN completely." 
         DEFVAL      { true }   
         ::= { mnUdpTunnel 1 } 
 
    mnUdpTunnelForce OBJECT-TYPE 
         SYNTAX      TruthValue 
         MAX-ACCESS  read-write 
         STATUS      current 
         DESCRIPTION 
                 "This parameter enables (or disables) the MN to set 
                 the F (force) flag. It indicates that the mobile 
                 node wants to use traversal regardless of the 
                 outcome of NAT detection performed by the home agent." 
        REFERENCE  
                "RFC3519, MIP Traversal of NAT Devices, Section 3.1.1" 
        DEFVAL      { false }   
         ::= { mnUdpTunnel 2 } 
 
    mnUdpTunnelKeepaliveInterval OBJECT-TYPE 
        SYNTAX      Unsigned32 
        UNITS       "seconds" 
        MAX-ACCESS  read-write 
        STATUS      current 
        DESCRIPTION 
                "Defines the default NAT keepalive interval that the 
                 mobile node will use in the case that the HA does 
                 not impose another value by setting the Keepalive 
                 Interval in the UDP Tunnel Reply Extension." 
        REFERENCE 
                "RFC3519, MIP Traversal of NAT Devices, Section 4.9" 
        DEFVAL      { 110 }   
        ::= { mnUdpTunnel 3 } 
 
         
    -- ================================================================= 
    -- haUdpTunnel Group 
 
    haUdpTunnelEnable OBJECT-TYPE 
         SYNTAX      TruthValue 
         MAX-ACCESS  read-write 
         STATUS      current 
         DESCRIPTION 
                 "This parameter enables and disables the RFC 3519 UDP 
                  tunneling function in the HA completely." 
         DEFVAL      { true }   
         ::= { haUdpTunnel 1 } 
 
    haUdpTunnelKeepaliveInterval OBJECT-TYPE 
        SYNTAX      Unsigned32 
        UNITS       "seconds" 
        MAX-ACCESS  read-write 
        STATUS      current 
        DESCRIPTION 
                "This parameter sets the keepalive interval override. 
                 Normally, the MN uses the keepalive time that was  
                 configured using UDP tunneling and sending 
                 keepalive messages. The HA can override this  
                 configured keepalive time by setting a new 
                 interval value for this parameter to a value other  
                 than zero." 
        REFERENCE  
                "RFC3519, MIP Traversal of NAT Devices, Section 3.2" 
        DEFVAL      { 0 }   
        ::= { haUdpTunnel 2 } 
 
    haUdpTunnelForce OBJECT-TYPE 
        SYNTAX      TruthValue 
        MAX-ACCESS  read-write 
        STATUS      current 
        DESCRIPTION 
                "This parameter enables and disables the HA forcing all 
                 connections from MNs which support RFC 3519 UDP  
                 tunneling to use tunneling whether or not the 
                 presence of a NAT is detected." 
        REFERENCE  
                "RFC3519, MIP Traversal of NAT Devices, Section 6.3" 
        DEFVAL      { false }   
        ::= { haUdpTunnel 3 } 
 
    haUdpTunnelEncapUnavail OBJECT-TYPE 
        SYNTAX      Counter32 
        MAX-ACCESS  read-only 
        STATUS      current 
        DESCRIPTION 
                "Total number of Registration Requests denied by the 
                 home agent --  Requested UDP tunnel encapsulation 
                 unavailable (code 142)." 
        REFERENCE  
                "RFC3519, MIP Traversal of NAT Devices, Section 3.5" 
        ::= { haUdpTunnel 4 } 

    -- ================================================================= 
    -- faUdpTunnel Group 
 
    faUdpTunnelEnable OBJECT-TYPE 
         SYNTAX      TruthValue 
         MAX-ACCESS  read-write 
         STATUS      current 
         DESCRIPTION 
                 "This parameter enables and disables the RFC 3519 UDP 
                  tunneling function in the FA completely." 
         DEFVAL      { true }   
         ::= { faUdpTunnel 1 } 
 
    faUdpTunnelForce OBJECT-TYPE 
         SYNTAX      TruthValue 
         MAX-ACCESS  read-write 
         STATUS      current 
         DESCRIPTION 
                 "This parameter enables (or disables) the FA to set 
                 the F (force) flag. It indicates that the foreign 
                 agent wants to use traversal regardless of the 
                 outcome of NAT detection performed by the home agent." 
        REFERENCE  
                "RFC3519, MIP Traversal of NAT Devices, Section 3.1.1" 
        DEFVAL      { false }   
         ::= { faUdpTunnel 2 } 
 
    faUdpTunnelKeepaliveInterval OBJECT-TYPE 
        SYNTAX      Unsigned32 
        UNITS       "seconds" 
        MAX-ACCESS  read-write 
        STATUS      current 
        DESCRIPTION 
                "Defines the default NAT keepalive interval that the 
                 foreign agent will use in the case that the HA does 
                 not impose another value by setting the Keepalive 
                 Interval in the UDP Tunnel Reply Extension." 
        REFERENCE 
                "RFC3519, MIP Traversal of NAT Devices, Section 4.9" 
        DEFVAL      { 110 }   
        ::= { faUdpTunnel 3 } 
         
    -- ================================================================= 
    -- MIP Conformance Statements 
    mipUdpTunnelConformance  
        OBJECT IDENTIFIER ::= { mipUdpTunnelMIB 2 } 
 
    mipUdpTunnelGroups  
        OBJECT IDENTIFIER ::= { mipUdpTunnelConformance 1 } 
    mipUdpTunnelCompliances  
        OBJECT IDENTIFIER ::= { mipUdpTunnelConformance 2 } 
 
    -- 
    -- compliance statements 
    -- 
     
    mipUdpTunnelCompliance    MODULE-COMPLIANCE 
        STATUS    current 
        DESCRIPTION 
                "The compliance statement for SNMPv2 entities which 
                implement the Mobile IP UDP Tunnel MIB." 
        MODULE 
             
            GROUP     mnUdpTunnelGroup 
            DESCRIPTION 
                "This group is mandatory for a mobile node." 
 
            GROUP     haUdpTunnelGroup 
            DESCRIPTION 
                "This group is mandatory for a home agent." 
 
            GROUP     faUdpTunnelGroup 
            DESCRIPTION 
                "This group is mandatory for a foreign agent." 
 
       ::= { mipUdpTunnelCompliances 1 } 
 
    -- 
    -- Units of conformance 
    -- 
     
 
    mnUdpTunnelGroup  OBJECT-GROUP 
        OBJECTS   { mnUdpTunnelEnable, mnUdpTunnelForce, 
                    mnUdpTunnelKeepaliveInterval } 
        STATUS      current 
        DESCRIPTION 
                "A collection of objects providing management 
                information for theuse of UDP tunneling according to  
                RFC3519 within a mobile node." 
        ::= { mipUdpTunnelGroups 1 } 

    haUdpTunnelGroup  OBJECT-GROUP 
        OBJECTS   { haUdpTunnelEnable, haUdpTunnelForce, 
                    haUdpTunnelKeepaliveInterval, 
                    haUdpTunnelEncapUnavail } 
        STATUS      current 
        DESCRIPTION 
                "A collection of objects providing management 
                information for theuse of UDP tunneling according to  
                RFC3519 within a home agent." 
        ::= { mipUdpTunnelGroups 2 } 
 
   faUdpTunnelGroup  OBJECT-GROUP 
        OBJECTS   { faUdpTunnelEnable, faUdpTunnelForce, 
                    faUdpTunnelKeepaliveInterval } 
        STATUS      current 
        DESCRIPTION 
                "A collection of objects providing management 
                information for theuse of UDP tunneling according to  
                RFC3519 within a foreign agent." 
        ::= { mipUdpTunnelGroups 3 } 
 
END 

-- 
--    Copyright (C) The IETF Trust (2007). 
-- 
--    This document is subject to the rights, licenses and restrictions 
--    contained in BCP 78, and except as set forth therein, the authors 
--    retain all their rights. 
-- 
--    This document and the information contained herein are provided on an 
--    "AS IS" basis and THE CONTRIBUTOR, THE ORGANIZATION HE/SHE REPRESENTS 
--    OR IS SPONSORED BY (IF ANY), THE INTERNET SOCIETY, THE IETF TRUST AND 
--    THE INTERNET ENGINEERING TASK FORCE DISCLAIM ALL WARRANTIES, EXPRESS 
--    OR IMPLIED, INCLUDING BUT NOT LIMITED TO ANY WARRANTY THAT THE USE OF 
--    THE INFORMATION HEREIN WILL NOT INFRINGE ANY RIGHTS OR ANY IMPLIED 
--    WARRANTIES OF MERCHANTABILITY OR FITNESS FOR A PARTICULAR PURPOSE. 
-- 
-- Acknowledgment 
-- 
--    Funding for the RFC Editor function is currently provided by the IETF 
--    Administrative Support Activity (IASA).
