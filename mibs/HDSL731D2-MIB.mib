-- Copyright 1994 General DataComm Inc., Inc. All Rights Reserved.
--
-- Reproduction of this document is authorized on condition that the
-- foregoing copyright notice is included. This General DataComm, GDC,
-- SNMP Management Information Base Specification embodies GDCs'
-- confidential and proprietary intellectual property. GDC retains all
-- title and ownership in the Specification, including any revisions.
--
-- It is GDCs intent to encourage the widespread use of this Specification
-- in connection with the management of GDC's products. GDC grants vendors,
-- end-users, and other interested parties a non-exclusive license to use
-- this Specification in connection with the management of GDC's products.
--
-- This Specification is supplied "AS IS," and GDC makes no warranty,
-- either expressed or implied, as to the use operation, condition, or
-- performance of the Specification.

-- Revision History
-- Version   Date	Name		Description 
-- 1.00A     17-May-96  S.Sankaran  Initial Revision
-- 1.00B     16-Oct-96   D.Baylis    Added Major and Minor alarms
--
-- 
HDSL731D2-MIB DEFINITIONS ::= BEGIN

IMPORTS
	OBJECT-TYPE			FROM RFC-1212
	DisplayString			FROM RFC1213-MIB
	hdsl731D2                       FROM GDCHDSL-MIB;

hdsl731D2System            OBJECT IDENTIFIER ::= { hdsl731D2 1 }
hdsl731D2Version           OBJECT IDENTIFIER ::= { hdsl731D2System 1 }

-- This MIB module is a subset of the HDSL 730 series products
-- This products are the only one to support a DTE interface.

gdc731D2SystemMIBversion OBJECT-TYPE
    	SYNTAX DisplayString (SIZE (5))
     	ACCESS read-only
     	STATUS mandatory
     	DESCRIPTION
     		"Identifies the version of the MIB. The format of the version
     		is x.yzT, where 'x' identifies the major revision number, 'y'
     		identifies the minor revision number, 'z' identifies the
     		typographical revision, and T identifies the test revision.
     		Acceptable values for the individual revision components are
     		as follows:
 
     		x: 1 - 9
     		y: 0 - 9
     		z: 0 - 9
     		T: A - Z
 
     		Upon formal release, no designation for the test revision will
     		be present."
     	::= { hdsl731D2Version 1 }
 
 
 
-- ********************************************************************
-- GDC Hdsl Alarm Object Identifier Definitions
-- ********************************************************************
hdsl731D2Alarms            OBJECT IDENTIFIER ::= { hdsl731D2 2 }

hdsl731D2NoResponseAlm		OBJECT IDENTIFIER ::= { hdsl731D2Alarms 1 }
hdsl731D2DiagRxErrAlm		OBJECT IDENTIFIER ::= { hdsl731D2Alarms 2 }
hdsl731D2PowerUpAlm		OBJECT IDENTIFIER ::= { hdsl731D2Alarms 3 }
hdsl731D2UnitFailure            OBJECT IDENTIFIER ::= { hdsl731D2Alarms 4 }
hdsl731D2ChecksumCorrupt        OBJECT IDENTIFIER ::= { hdsl731D2Alarms 5 }
hdsl731D2LossofSignal		OBJECT IDENTIFIER ::= { hdsl731D2Alarms 6 }
hdsl731D2UnavailableSec		OBJECT IDENTIFIER ::= { hdsl731D2Alarms 7 }
hdsl731D2ErrorSec		OBJECT IDENTIFIER ::= { hdsl731D2Alarms 8 }
hdsl731D2LossofSyncWord		OBJECT IDENTIFIER ::= { hdsl731D2Alarms 9 }
hdsl731D2MajorBER		OBJECT IDENTIFIER ::= { hdsl731D2Alarms 10 }
hdsl731D2MinorBER		OBJECT IDENTIFIER ::= { hdsl731D2Alarms 11 }
 
 
-- ALARM			Maskable	Valid Interfaces
--===============================================================
--hdslNoResponseAlm		No		Unit
--hdslDiagRxErrAlm              No              Unit
--hdslPowerUpAlm		No		Unit
--hdslUnitFailure               No              Unit
--hdslChecksumCorrupt           No              Unit
--hdslLossofSignal              Yes             L1, L2
--hdslUnavailableSec            Yes             L1, L2
--hdslErrorSec                  Yes             L1, L2
--hdslLossofSyncWord		Yes		L1, L2
--hdslMajorBER          	Yes     	L1, L2 
--hdslMinorBER          	Yes     	L1, L2


END
