-- Title:         Fibronics' MIB  
-- MIB Module :   Private MIB for  fx8724
-- Version    :   V1.0
-- Date       :   Jan 1 1995
-- By         :   Zvi W.
-- Contact    :   Edna Ganon
-- Email:     :   edna@fibronics.co.il 
-- 
-- Description:   Private Mib For FX8724 FDDI Concentrator
 
        FDDI-CONCENTRATOR-MIB DEFINITIONS ::= BEGIN

        IMPORTS enterprises, IpAddress, Counter     FROM RFC1155-SMI
                OBJECT-TYPE     FROM RFC-1212;

        fibronics OBJECT IDENTIFIER ::= { enterprises 22 }

        fddiConcentrator OBJECT IDENTIFIER ::= {fibronics 70}

        -- groups in the FDDI CONCENTRATOR module

        concentratorPORT OBJECT IDENTIFIER ::= { fddiConcentrator 1 }

        concentratorPROCESSOR OBJECT IDENTIFIER ::= { fddiConcentrator 2 }

        concentratorMEMORY OBJECT IDENTIFIER ::= { fddiConcentrator 3 }

        concentratorSERIALPORT OBJECT IDENTIFIER ::= { fddiConcentrator 4 }

        concentratorVERSIONS OBJECT IDENTIFIER ::= { fddiConcentrator 5 }

        concentratorPOWER OBJECT IDENTIFIER ::= { fddiConcentrator 6 }

        concentratorTRAPS OBJECT IDENTIFIER ::= { fddiConcentrator 7 }

        concentratorIDENTIFIER OBJECT IDENTIFIER ::= { fddiConcentrator 8 }

        concentratorTRAFFIC OBJECT IDENTIFIER ::= { fddiConcentrator 9 }

    -- group concentratorPORT
    --***********************
    -- This group is closely related to the fddiPORT group in
    -- standart fddi mib (experimental 8).


          concentratorPORTTable OBJECT-TYPE
              SYNTAX  SEQUENCE OF ConcentratorPORTEntry
              ACCESS  not-accessible
              STATUS  mandatory
              DESCRIPTION
                      "A list of PORT entries.  The number of entries is
                      given by the value of the snmpFddiPORTNumber (see
                                          standard fddi."
              ::= { concentratorPORT  1 }

          concentratorPORTEntry OBJECT-TYPE
              SYNTAX  ConcentratorPORTEntry
              ACCESS  not-accessible
              STATUS  mandatory
              DESCRIPTION
                      "A PORT entry containing information common to a
                      given PORT."
              INDEX   { concentratorPORTSMTIndex, concentratorPORTIndex }
              ::= { concentratorPORTTable 1 }

          ConcentratorPORTEntry ::=
              SEQUENCE {
                  concentratorPORTSMTIndex
                          INTEGER,
                  concentratorPORTIndex
                          INTEGER,
                  concentratorPORTType
                          INTEGER,
                  concentratorPORTStatus
                          INTEGER
              }

          concentratorPORTSMTIndex OBJECT-TYPE
              SYNTAX  INTEGER (1..65535)
              ACCESS  read-only
              STATUS  mandatory
              DESCRIPTION
                      "The value of the SMT index associated with this
                      PORT."
              ::= { concentratorPORTEntry 1 }

          concentratorPORTIndex OBJECT-TYPE
              SYNTAX  INTEGER (1..65535)
              ACCESS  read-only
              STATUS  mandatory
              DESCRIPTION
                      "A unique value for each PORT within a given SMT.
                      Its value ranges between 1 and the sum of the
                      values of concentratorSMTNonMasterCt
                      { concentratorSMTEntry 6 } and concentratorSMTMasterCt
                      { concentratorSMTEntry 7 } on the given SMT.  The
                      value for each PORT must remain constant at least
                      from one re-initialization of the entity's network
                      management system to the next re-initialization."
              ::= { concentratorPORTEntry 2 }


          concentratorPORTType OBJECT-TYPE
              SYNTAX  INTEGER {unknown(1) ,fiber(2) ,utp(3), stp(4), ibm(5), plastic(6), baseT(7), mono(8)}
              ACCESS  read-only
              STATUS  mandatory
              DESCRIPTION
                      "This value specifies the type of selected port"
              ::= { concentratorPORTEntry 3 }

          concentratorPORTStatus OBJECT-TYPE
              SYNTAX  INTEGER {ok(1),failed(2),undefind(3)}
              ACCESS  read-only
              STATUS  mandatory
              DESCRIPTION
                      "This value specifies the status of the selected port"
              ::= { concentratorPORTEntry 4 }

    -- group concentratorPROCESSOR
    --********************************
    -- This group describes the main parameters of the processor

          concentratorPROCESSORType OBJECT-TYPE
              SYNTAX  INTEGER {unkown(1) ,p88(2) ,p86(3),
                               p186(4),p286(5), p386(6), p486(7)}
              ACCESS  read-only
              STATUS  mandatory
              DESCRIPTION
                      "This value specifies the type of processor"
              ::= { concentratorPROCESSOR 1 }

          concentratorPROCESSORFrequency OBJECT-TYPE
              SYNTAX  INTEGER (1..65535)
              ACCESS  read-only
              STATUS  mandatory
              DESCRIPTION
                      "This value specifies the frequency of the microprocessor (in MHz)"
              ::= { concentratorPROCESSOR 2 }


    -- group concentratorMEMORY
    --********************************
    -- This group describes some parameters of the memory

          concentratorSystemMEMORYAvailable OBJECT-TYPE
              SYNTAX  INTEGER (1..65535)
              ACCESS  read-only
              STATUS  mandatory
              DESCRIPTION
                      "This value specifies the amount of memory in kB"
              ::= { concentratorMEMORY 1 }

          concentratorSystemMEMORYFree OBJECT-TYPE
              SYNTAX  INTEGER (1..65535)
              ACCESS  read-only
              STATUS  mandatory
              DESCRIPTION
                      "This value specifies the available amount of free memory in kB"
              ::= { concentratorMEMORY 2 }

          concentratorBufferMEMORYAvailable OBJECT-TYPE
              SYNTAX  INTEGER (1..65535)
              ACCESS  read-only
              STATUS  mandatory
              DESCRIPTION
                      "This value specifies the amount of memory in kB"
              ::= { concentratorMEMORY 3 }


          concentratorMEMORYFlashEPROM OBJECT-TYPE
              SYNTAX  INTEGER { notpresent(1) , present(2) }
              ACCESS  read-only
              STATUS  mandatory
              DESCRIPTION
                      "This value specifies whether the flash EPROM is present or not"
              ::= { concentratorMEMORY 4 }


    -- group concentratorSERIALPORT
    --********************************
    -- This group describes the contents of the control registers and main
    -- parameters for the serial line (baud rate , stop bits ,parity)

          concentratorSERIALPORTBaudRate OBJECT-TYPE
              SYNTAX  INTEGER (1..65535)
              ACCESS  read-write
              STATUS  mandatory
              DESCRIPTION
                      "This value specifies the actual baud rate"
              ::= { concentratorSERIALPORT 1 }

          concentratorSERIALPORTParity OBJECT-TYPE
              SYNTAX  INTEGER {none(1) , odd(2), even(3)}
              ACCESS  read-only
              STATUS  mandatory
              DESCRIPTION
                      "This value specifies the type of parity "
              ::= { concentratorSERIALPORT 2 }

          concentratorSERIALPORTStopBits OBJECT-TYPE
              SYNTAX  INTEGER (1..255)
              ACCESS  read-only
              STATUS  mandatory
              DESCRIPTION
                      "This value specifies the number of stop bits "
              ::= { concentratorSERIALPORT 3 }



    -- group concentratorVERSIONS
    --********************************
    -- This group gives some version numbers of the main parts

          concentratorVERSIONSBoardSerialNumber OBJECT-TYPE
              SYNTAX  OCTET STRING (SIZE(8))
              ACCESS  read-only
              STATUS  mandatory
              DESCRIPTION
                      "This value specifies the serial number of the board"
              ::= { concentratorVERSIONS 1 }

          concentratorVERSIONSNMP OBJECT-TYPE
              SYNTAX  OCTET STRING (SIZE(8))
              ACCESS  read-only
              STATUS  mandatory
              DESCRIPTION
                      "This value specifies the actual SNMP version"
              ::= { concentratorVERSIONS 2 }

          concentratorVERSIONBIOS OBJECT-TYPE
              SYNTAX  OCTET STRING (SIZE(8))
              ACCESS  read-only
              STATUS  mandatory
              DESCRIPTION
                      "This value specifies the actual BIOS version"
              ::= { concentratorVERSIONS 3 }

          concentratorVERSIONSMT OBJECT-TYPE
              SYNTAX  OCTET STRING (SIZE(8))
              ACCESS  read-only
              STATUS  mandatory
              DESCRIPTION
                      "This value specifies the actual SMT version"
              ::= { concentratorVERSIONS 4 }

          concentratorVERSIONMAC OBJECT-TYPE
              SYNTAX  OCTET STRING (SIZE(1))
              ACCESS  read-only
              STATUS  mandatory
              DESCRIPTION
                      "This value specifies the actual MAC version"
              ::= { concentratorVERSIONS 5 }

          concentratorVERSIONHRDWR OBJECT-TYPE
              SYNTAX  OCTET STRING (SIZE(6))
              ACCESS  read-only
              STATUS  mandatory
              DESCRIPTION
                      "This value specifies the actual version of the hardware"
              ::= { concentratorVERSIONS 6 }

          concentratorVERSIONSlotsNumber OBJECT-TYPE
              SYNTAX  INTEGER(1..65535)
              ACCESS  read-only
              STATUS  mandatory
              DESCRIPTION
                      "The number of slots in the concentrator."
              ::= { concentratorVERSIONS  7 }

          concentratorVERSIONSlotsTable OBJECT-TYPE
              SYNTAX  SEQUENCE OF ConcentratorVERSIONSlotEntry
              ACCESS  not-accessible
              STATUS  mandatory
              DESCRIPTION
                      "A list of slot entries.  The number of entries is
                      given by the value of the concentratorVERSIONSlotsNumber."
              ::= { concentratorVERSIONS  8 }

          concentratorVERSIONSlotEntry OBJECT-TYPE
              SYNTAX  ConcentratorVERSIONSlotEntry
              ACCESS  not-accessible
              STATUS  mandatory
              DESCRIPTION
                      "An entry containing information common to a
                      given SLOT number."
              INDEX   { concentratorVERSIONSlotIndex}
              ::= { concentratorVERSIONSlotsTable 1 }

          ConcentratorVERSIONSlotEntry ::=
              SEQUENCE {
                  concentratorVERSIONSlotIndex
                          INTEGER,
                  concentratorVERSIONSlotSerialNumber
                          OCTET STRING (SIZE(6)),
                  concentratorVERSIONSlotId
                          INTEGER,
                  concentratorVERSIONSlotHrdwrStatus
                          INTEGER,
                  concentratorVERSIONSlotRevision
                          INTEGER
              }

          concentratorVERSIONSlotIndex OBJECT-TYPE
              SYNTAX  INTEGER (1..65535)
              ACCESS  read-only
              STATUS  mandatory
              DESCRIPTION
                      "The value of the index associated with this
                      particulary slot."
              ::= { concentratorVERSIONSlotEntry 1 }

          concentratorVERSIONSlotSerialNumber OBJECT-TYPE
              SYNTAX  OCTET STRING  (SIZE(6))
              ACCESS  read-only
              STATUS  mandatory
              DESCRIPTION
                      "The serial number of this slot."
              ::= { concentratorVERSIONSlotEntry 2 }

          concentratorVERSIONSlotId OBJECT-TYPE
              SYNTAX  INTEGER (1..255)
              ACCESS  read-only
              STATUS  mandatory
              DESCRIPTION
                      "The identification number of this slot."
              ::= { concentratorVERSIONSlotEntry 3 }

          concentratorVERSIONSlotHrdwrStatus OBJECT-TYPE
              SYNTAX  INTEGER (1..255)
              ACCESS  read-only
              STATUS  mandatory
              DESCRIPTION
                      "The value specifies the hardware state of the slot."
              ::= { concentratorVERSIONSlotEntry 4 }

          concentratorVERSIONSlotRevision OBJECT-TYPE
              SYNTAX  INTEGER (1..255)
              ACCESS  read-only
              STATUS  mandatory
              DESCRIPTION
                      "Revision."
              ::= { concentratorVERSIONSlotEntry 5 }

    -- group concentratorPOWER
    --********************************

          concentratorPOWERFirstSupplyState OBJECT-TYPE
              SYNTAX  INTEGER {ok (1), failure(2), notpresent(3), reserved(4)}
              ACCESS  read-only
              STATUS  mandatory
              DESCRIPTION
                      "This value specifies the state of the first power supply"
              ::= { concentratorPOWER 1 }

          concentratorPOWERSecondSupplyState OBJECT-TYPE
              SYNTAX  INTEGER {ok (1), failure(2), notpresent(3), reserved(4)}
              ACCESS  read-only
              STATUS  mandatory
              DESCRIPTION
                      "This value specifies the state of the second power supply"
              ::= { concentratorPOWER 2 }

          concentratorPOWERFirstFANState OBJECT-TYPE
              SYNTAX  INTEGER {ok (1), failure(2)}
              ACCESS  read-only
              STATUS  mandatory
              DESCRIPTION
                      "This value specifies the state of the first fan"
              ::= { concentratorPOWER 3 }

          concentratorPOWERSecondFANState OBJECT-TYPE
              SYNTAX  INTEGER {ok (1), failure(2)}
              ACCESS  read-only
              STATUS  mandatory
              DESCRIPTION
                      "This value specifies the state of the second power supply"
              ::= { concentratorPOWER 4 }

          concentratorPOWERTemperature OBJECT-TYPE
              SYNTAX  INTEGER
              ACCESS  read-only
              STATUS  mandatory
              DESCRIPTION
                      "This value specifies the concentrator's temperature (in degrees Celsius)"
              ::= { concentratorPOWER 5 }

          concentratorPOWERBatteryStatus OBJECT-TYPE
              SYNTAX  INTEGER {ok (1), failure(2),notpresent(3)}
              ACCESS  read-only
              STATUS  mandatory
              DESCRIPTION
                      "This value specifies the state of the battery"
              ::= { concentratorPOWER 6 }

    -- group concentratorTRAPS
    --********************************

          concentratorMgrAddress OBJECT-TYPE
              SYNTAX  IpAddress
              ACCESS  read-write
              STATUS  mandatory
              DESCRIPTION
                      " By means of this variable an SNMP manager can put or
                        remove its own address into or out of the internal array of the
                        manager's addresses to where the agent sends traps.An SNMP manager can set
                        itself by SET SNMP operation with its own IP address. An SNMP manager
                        can remove itself by SET SNMP operation with the 0.0.0.0 IP address.
                        Operation GET or GET-NEXT returns the manager's address if the manager is
                        in the internall array or 0.0.0.0 IP address wheneverthe  manager is not in
                        the internal array.

                        Agent returns the following error codes :
                        If a manager tries to set an address IP address different from that of its own
                        address or a manager tries to set 0.0.0.0 IP address when a manager is
                        not present in the internal buffer, the agent returns value BAD VALUE.

                        If a manager tries to set address its own IP address again (when the manager
                        is already in the internal array), the agent returns the value GENERALL ERROR.

                        If this array is already full ,then GENERALL ERROR value is returned."

              ::= { concentratorTRAPS 1 }

    -- group concentratorTRAFFIC
    --********************************

          concentratorTRAFFICSMTTransmits OBJECT-TYPE
              SYNTAX  Counter
              ACCESS  read-only
              STATUS  mandatory
              DESCRIPTION
                      "This value specifies transmitted SMT frames"
              ::= { concentratorTRAFFIC 1 }

          concentratorTRAFFICSMTReceivs OBJECT-TYPE
              SYNTAX  Counter
              ACCESS  read-only
              STATUS  mandatory
              DESCRIPTION
                      "This value specifies the recieved SMT frames"
              ::= { concentratorTRAFFIC 2 }

          concentratorTRAFFICRS232Activity OBJECT-TYPE
              SYNTAX  INTEGER {active(1), nonactive(2)}
              ACCESS  read-only
              STATUS  mandatory
              DESCRIPTION
                      "This value specifies whether the RS 232 is currently active"
              ::= { concentratorTRAFFIC 3 }
        END
