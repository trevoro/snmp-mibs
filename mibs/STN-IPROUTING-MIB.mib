-- *****************************************************************
--
-- stn-iprouting.mib: 
--                Spring Tide Networks IP Extensions file.
--
--
--      Copyright (c) 1999, 2000 by Spring Tide Networks, Inc.
--                      ALL RIGHTS RESERVED       
--
-- *****************************************************************

-- MIB Object definitions for Spring Tide Network IP Extensions 


STN-IPROUTING-MIB DEFINITIONS ::= BEGIN

   IMPORTS
        NOTIFICATION-TYPE, MODULE-IDENTITY, 
        OBJECT-TYPE,
        IpAddress,
        Integer32,
        Counter32,
        Gauge32
               FROM SNMPv2-SMI

        RowStatus, TimeStamp, TEXTUAL-CONVENTION
               FROM SNMPv2-TC
        
        stnEngineSlot, stnEngineCpu,
        stnEngineType, stnCpuIpRouteLimit
               FROM STN-CHASSIS-MIB

        stnRouterIndex
               FROM STN-ROUTER-MIB

        stnSystems
               FROM SPRING-TIDE-NETWORKS-SMI;

   stnIpRouting    MODULE-IDENTITY
        LAST-UPDATED    "0002160000Z"
        ORGANIZATION    "Spring Tide Networks, Inc."
        CONTACT-INFO
                "
                Spring Tide Networks, Inc.
                Customer Service
                Postal: 3 Clock Tower Place
                        Maynard, MA 01754
                Tel:    1 888-786-4357
                Email:  stncs@springtidenet.com
                "
        DESCRIPTION     "This MIB module describes managed objects of the
                         IP Routing subsystems that are proprietary to 
                         Spring Tide Networks."
        ::= { stnSystems 12 }


    --
    -- Top Level STN IP Routing MIB Objects
    --
    stnIp             OBJECT IDENTIFIER ::= { stnIpRouting 1 }
    stnArp            OBJECT IDENTIFIER ::= { stnIpRouting 2 }
    stnRip            OBJECT IDENTIFIER ::= { stnIpRouting 3 }
    stnOspf           OBJECT IDENTIFIER ::= { stnIpRouting 4 }
    stnBgp            OBJECT IDENTIFIER ::= { stnIpRouting 5 }

    stnIpRtCache      OBJECT IDENTIFIER ::= { stnIp 1 }
    -- stnIpCircExtTable ::= { stnIp 2 }
    -- stnIpDetailsTable ::= { stnIp 3 }
    stnIpRoutingVars  OBJECT IDENTIFIER ::= { stnIp 4 }
    stnIpTraps        OBJECT IDENTIFIER ::= { stnIp 5 }

    stnIpTrapVars OBJECT IDENTIFIER ::= { stnIpTraps 1 }
    stnIpNotificationPrefix OBJECT IDENTIFIER ::= { stnIpTraps 2 }
    stnIpNotification OBJECT IDENTIFIER ::= { stnIpNotificationPrefix 0 }

    stnOspfTraps  OBJECT IDENTIFIER ::= { stnOspf 8 }


    --
    -- STN IP Routing Cache 
    --

    stnIpRtCacheEntries OBJECT-TYPE
            SYNTAX          Gauge32
            MAX-ACCESS      read-only
            STATUS          current
            DESCRIPTION 
                        "The number of current cache entries."
            ::= { stnIpRtCache 1 }

    stnIpRtCacheMisses OBJECT-TYPE
            SYNTAX          Counter32
            MAX-ACCESS      read-only
            STATUS          current
            DESCRIPTION 
                "The number of failed attempts to locate an IP address
                  in the route cache."
            ::= { stnIpRtCache 2 }

    stnIpRtCacheHits OBJECT-TYPE
            SYNTAX          Counter32
            MAX-ACCESS      read-only
            STATUS          current
            DESCRIPTION 
                "The number of successful attempts to locate an IP address
                 in the route cache."
            ::= { stnIpRtCache 3 }

    stnIpRtCacheRemovals OBJECT-TYPE
            SYNTAX          Counter32
            MAX-ACCESS      read-only
            STATUS          current
            DESCRIPTION 
                "The number of times an entry has been removed as a result 
                 of the need to insert an entry into a full table."
            ::= { stnIpRtCache 4 }


    --
    -- STN IP Routing Cache Table 
    --

    stnIpRoutingCacheTable OBJECT-TYPE
            SYNTAX          SEQUENCE OF StnIpRtCacheEntry
            MAX-ACCESS      not-accessible
            STATUS          current
            DESCRIPTION     "Table of IP routing cache entries."
            ::= { stnIpRtCache 5 }

    stnIpRtCacheEntry OBJECT-TYPE
            SYNTAX          StnIpRtCacheEntry
            MAX-ACCESS      not-accessible
            STATUS          current
            DESCRIPTION     "An IP routing cache entry."
            INDEX           {stnIpRtCacheIpAddress, stnIpRtCacheIpMask  }
            ::= { stnIpRoutingCacheTable 1 }

    StnIpRtCacheEntry ::= 
        SEQUENCE {
                    stnIpRtCacheIpAddress
                            IpAddress,
                    stnIpRtCacheIpMask
                            IpAddress,
                    stnIpRtCacheNextHop
                            IpAddress,
                    stnIpRtCacheIfIndex
                            Integer32,
                    stnIpRtCacheRouteType
                            INTEGER,
                    stnIpRtCacheStatus
                            RowStatus
            }

    stnIpRtCacheIpAddress OBJECT-TYPE
            SYNTAX          IpAddress
            MAX-ACCESS      read-only
            STATUS          current
            DESCRIPTION 
                "The destination IP address of this route."
            ::= { stnIpRtCacheEntry 1 }

    stnIpRtCacheIpMask OBJECT-TYPE
            SYNTAX          IpAddress
            MAX-ACCESS      read-only
            STATUS          current
            DESCRIPTION 
                "Indicate the mask to be logical-ANDed with the
                 destination  address  before  being compared to
                 the value  in  the  ipCidrRouteDest  field."
            ::= { stnIpRtCacheEntry 2 }

    stnIpRtCacheNextHop OBJECT-TYPE
            SYNTAX          IpAddress
            MAX-ACCESS      read-only
            STATUS          current
            DESCRIPTION 
                "On remote routes, the address of the next sys-
                 tem en route; Otherwise, 0.0.0.0."
            ::= { stnIpRtCacheEntry 3 }

    stnIpRtCacheIfIndex OBJECT-TYPE
            SYNTAX          Integer32
            MAX-ACCESS      read-only
            STATUS          current
            DESCRIPTION 
                "The ifIndex value which identifies the local interface
                 through which the next hop of this route should be   
                 reached"
            ::= { stnIpRtCacheEntry 4 }

    stnIpRtCacheRouteType OBJECT-TYPE
            SYNTAX          INTEGER {
                              other     (1), 
                              reject    (2),
                              local     (3),
                              remote    (4)
                            }
            MAX-ACCESS      read-only
            STATUS          current
            DESCRIPTION 
                "The type of route as described in RFC 2096"
            ::= { stnIpRtCacheEntry 5 }

    stnIpRtCacheStatus OBJECT-TYPE
            SYNTAX          RowStatus
                MAX-ACCESS      read-create
                STATUS          current
            DESCRIPTION     
                "The row status variable, used according to
                 row installation and removal conventions."
            ::= { stnIpRtCacheEntry 6 }


    --
    -- STN IP Circuits Table
    --

    stnIpCircExtTable OBJECT-TYPE
            SYNTAX          SEQUENCE OF StnIpCircExtEntry
            MAX-ACCESS      not-accessible
            STATUS          current
            DESCRIPTION     "Table of IP circuit parameters."
            ::= { stnIp 2 }

    stnIpCircExtEntry OBJECT-TYPE
            SYNTAX          StnIpCircExtEntry
            MAX-ACCESS      not-accessible
            STATUS          current
            DESCRIPTION     "An IP circuits entry"
            INDEX { stnIpCircExtIfIndex }
            ::= { stnIpCircExtTable 1 }

    StnIpCircExtEntry ::= 
        SEQUENCE {
                    stnIpCircExtIfIndex
                            Integer32,
                    stnIpCircExtAdminState
                            INTEGER,
                    stnIpCircExtOperState
                            INTEGER,
                    stnIpCircExtIpAddress
                            IpAddress,
                    stnIpCircExtIpMask
                            IpAddress,
                    stnIpCircExtMaxReasm
                            INTEGER,
                    stnIpCircExtMaxMtu
                            Integer32,
                    stnIpCircExtBcastAddr
                            IpAddress
            }

    stnIpCircExtIfIndex OBJECT-TYPE
            SYNTAX          Integer32
            MAX-ACCESS      read-only
            STATUS          current
            DESCRIPTION 
                "An index value which uniquely identifies the local physical 
                 interface which this circuit uses. This value identifies the 
                 same interface identified by ifIndex in MIB-2."
            ::= { stnIpCircExtEntry 1 }

    stnIpCircExtAdminState OBJECT-TYPE
            SYNTAX          INTEGER {
                                        enabled(1),     -- operation enabled
                                        disabled(2)     -- operation disabled
                                }
            MAX-ACCESS      read-write
            STATUS          current
            DESCRIPTION 
                "Enable or disable the operation of IP on the specified 
                 interface."
            ::= { stnIpCircExtEntry 2 }

    stnIpCircExtOperState OBJECT-TYPE
            SYNTAX          INTEGER{
                                        off(1),     -- circuit not up
                                        on(2)       -- circuit up
                                }
            MAX-ACCESS      read-only
            STATUS          current
            DESCRIPTION 
                "The operational state of the circuit. May or may not be the 
                 same as administrative state."
            ::= { stnIpCircExtEntry 3 }

    stnIpCircExtIpAddress OBJECT-TYPE
            SYNTAX          IpAddress   
            MAX-ACCESS      read-only
            STATUS          current
            DESCRIPTION
                "The IP address of the interface. For unnumbered interfaces
                 this will be 0.0.0.0."
            ::= { stnIpCircExtEntry 4 }

    stnIpCircExtIpMask OBJECT-TYPE
            SYNTAX          IpAddress   
            MAX-ACCESS      read-only
            STATUS          current
            DESCRIPTION
                      "The subnet mask associated with the IP address of
                      this entry.  The value of the mask is an IP
                      address with all the network bits set to 1 and all
                      the hosts bits set to 0."
            ::= { stnIpCircExtEntry 5 }

    stnIpCircExtMaxReasm OBJECT-TYPE
              SYNTAX        INTEGER (0..65535)
              MAX-ACCESS    read-only
              STATUS        current
              DESCRIPTION
                      "The size of the largest IP datagram which this
                      entity can re-assemble from incoming IP fragmented
                      datagrams received on this interface."
              ::= { stnIpCircExtEntry 6 }

    stnIpCircExtMaxMtu OBJECT-TYPE
              SYNTAX        Integer32 
              MAX-ACCESS    read-only
              STATUS        current
              DESCRIPTION
                      "The size of the largest datagram which can be
                      sent/received on the interface, specified in
                      octets.  For interfaces that are used for
                      transmitting network datagrams, this is the size
                      of the largest network datagram that can be sent
                      on the interface."
              ::= { stnIpCircExtEntry 7 }

    stnIpCircExtBcastAddr OBJECT-TYPE
            SYNTAX          IpAddress   
            MAX-ACCESS      read-only
            STATUS          current
            DESCRIPTION
                      "The value of the least-significant bit in the IP
                      broadcast address used for sending datagrams on
                      the (logical) interface associated with the IP
                      address of this entry.  For example, when the
                      Internet standard all-ones broadcast address is
                      used, the value will be 1.  This value applies to
                      both the subnet and network broadcasts addresses
                      used by the entity on this (logical) interface."
            ::= { stnIpCircExtEntry 8 }


    --
    -- STN IP Details Table
    --

    stnIpDetailsTable OBJECT-TYPE
            SYNTAX          SEQUENCE OF StnIpDetailsEntry
            MAX-ACCESS      not-accessible
            STATUS          current
            DESCRIPTION
                   "This table provides additional information about 
                    failed ip messages and icmp messages. When the 
                    table reaches its maximum size and a new entry 
                    needs to be added, the entire table will be cleared." 
            ::= { stnIp 3 }

    stnIpDetailsEntry OBJECT-TYPE
            SYNTAX          StnIpDetailsEntry
            MAX-ACCESS      not-accessible
            STATUS          current
            DESCRIPTION
                    "An entry within the STN IP Details Table."
            INDEX {stnIpDetailsIndex }
            ::= { stnIpDetailsTable 1 }

    StnIpDetailsEntry ::=
            SEQUENCE {
                  stnIpDetailsIndex
	            Integer32,
                stnIpDetailsSource
                    IpAddress,
                stnIpDetailsDest
                    IpAddress,
                stnIpDetailsType
                    INTEGER,
                stnIpDetailsTimeStamp
                    TimeStamp,
                stnIpDetailsHeader
                    OCTET STRING
    }

    stnIpDetailsIndex OBJECT-TYPE
            SYNTAX          Integer32
            MAX-ACCESS      not-accessible
            STATUS          current
            DESCRIPTION
                    "A unique index for this table."
            ::= { stnIpDetailsEntry 1 }

    stnIpDetailsSource OBJECT-TYPE
            SYNTAX           IpAddress
            MAX-ACCESS       read-only
            STATUS           current
            DESCRIPTION
                    "The source address within the packet."
            ::= { stnIpDetailsEntry 2 }

    stnIpDetailsDest OBJECT-TYPE
            SYNTAX         IpAddress
            MAX-ACCESS     read-only
            STATUS         current
            DESCRIPTION
                    "The destination address within the packet."
            ::= { stnIpDetailsEntry 3 }

    stnIpDetailsType OBJECT-TYPE
            SYNTAX         INTEGER {
                    header-error(1),            -- header error
                    unknown-proto(2),           -- unknown protocol
                    no-route(3),                -- no route
                    ttl-exceed(4),              -- TTL exceeded
                    param-problem(5),           -- parameter problem
                    redirect(6)                 -- redirect
        }

            MAX-ACCESS     read-only
            STATUS         current
            DESCRIPTION
                    "Indicates either an IP address or header error, 
                     or ICMP problem message."
            ::= { stnIpDetailsEntry 4 }

    stnIpDetailsTimeStamp OBJECT-TYPE
            SYNTAX        TimeStamp
            MAX-ACCESS    read-only
            STATUS        current
            DESCRIPTION
                    "Value of sysUpTime when this entry was added."
            ::= { stnIpDetailsEntry 5 }

    stnIpDetailsHeader OBJECT-TYPE
            SYNTAX        OCTET STRING (SIZE (60))
            MAX-ACCESS    read-only
            STATUS        current
            DESCRIPTION
                    "IP header of this error packet."
            ::= { stnIpDetailsEntry 6 }


    --
    -- STN IP Globals
    --

    stnIpMaxRoutingTableSize OBJECT-TYPE
        SYNTAX          Integer32
        MAX-ACCESS      read-only
        STATUS          current
        DESCRIPTION     "Maximum size of the ip routing table."
        ::= { stnIpRoutingVars 1 }

    stnIpCurrentRoutingTableSize OBJECT-TYPE
        SYNTAX          Integer32
        MAX-ACCESS      read-only
        STATUS          current
        DESCRIPTION     "Current size of the ip routing table."
        ::= { stnIpRoutingVars 2 }

    --
    -- STN IP Traps
    --

    stnIpRouterRouteLimitExceeded NOTIFICATION-TYPE
        OBJECTS   {
                        stnEngineSlot,
                        stnEngineCpu,
                        stnRouterIndex,
                        stnIpMaxRoutingTableSize
        }
        STATUS          current
        DESCRIPTION     "A stnIpRouterRouteLimitExceeded signifies that
                         a route add operation failed due to reaching
                         maximum number of routes in the routing table
                         as specified by the stnIpMaxRoutingTableSize variable."
        ::= { stnIpNotification 1 }

    stnIpEngineRouteLimitExceeded NOTIFICATION-TYPE
        OBJECTS   {
                        stnEngineSlot,
                        stnEngineCpu,
                        stnEngineType,
                        stnRouterIndex,
                        stnCpuIpRouteLimit
        }
        STATUS          current
        DESCRIPTION     "A stnIpEngineRouteLimitExceeded signifies that
                         a route add operation failed due to reaching
                         maximum number of routes on the router's engine
                         as specified by the stnCpuIpRouteLimit variable."
        ::= { stnIpNotification 2 }

    --
    -- STN ARP Statistics Group
    --

    stnArpExtTtl OBJECT-TYPE
            SYNTAX          Integer32
            MAX-ACCESS      read-write
            STATUS          current
            DESCRIPTION 
                "The lifetime of an ARP entry within the router."
            ::= { stnArp 1 }

    stnArpExtRcvdRequests OBJECT-TYPE
            SYNTAX          Counter32
            MAX-ACCESS      read-only
            STATUS          current
            DESCRIPTION 
                "The number of ARP received requests within the router."
            ::= { stnArp 2 }

    stnArpExtRcvdReplies OBJECT-TYPE
            SYNTAX          Counter32
            MAX-ACCESS      read-only
            STATUS          current
            DESCRIPTION 
                "The number of ARP received replies within the router."
            ::= { stnArp 3 }

    stnArpExtSendRequests OBJECT-TYPE
            SYNTAX          Counter32
            MAX-ACCESS      read-only
            STATUS          current
            DESCRIPTION 
                "The number of ARP send requests within the router."
            ::= { stnArp 4 }

    stnArpExtSendReplies OBJECT-TYPE
            SYNTAX          Counter32
            MAX-ACCESS      read-only
            STATUS          current
            DESCRIPTION 
                "The number of ARP send replies within the router."
            ::= { stnArp 5 }


    --
    -- STN ARP Circuits Table
    --

    stnArpCircExtTable OBJECT-TYPE
            SYNTAX          SEQUENCE OF StnArpCircExtEntry
            MAX-ACCESS      not-accessible
            STATUS          current
            DESCRIPTION 
                "Table of ARP circuit parameters"
            ::= { stnArp 6 }

    stnArpCircExtEntry OBJECT-TYPE
            SYNTAX          StnArpCircExtEntry
            MAX-ACCESS      not-accessible
            STATUS          current
            DESCRIPTION 
                "A circuits ARP parameters"
            INDEX {stnArpCircExtIfIndex}
            ::= { stnArpCircExtTable 1 }

    StnArpCircExtEntry ::= 
        SEQUENCE {
                    stnArpCircExtIfIndex
                            Integer32,
                    stnArpCircExtDoProxy
                            INTEGER,
                    stnArpCircExtDoResp
                            INTEGER,
                    stnArpCircExtWanProxy
                            INTEGER
            }

    stnArpCircExtIfIndex OBJECT-TYPE
            SYNTAX          Integer32
            MAX-ACCESS      read-only
            STATUS          current
            DESCRIPTION 
                "An index value which uniquely identifies the local physical 
                 interface which this circuit uses. This value identifies the 
                 same interface identified by ifIndex in MIB-2."
            ::= { stnArpCircExtEntry 1 }

    stnArpCircExtDoProxy OBJECT-TYPE
            SYNTAX          INTEGER {
                                        enabled(1),     -- operation enabled
                                        disabled(2)     -- operation disabled
                                }
            MAX-ACCESS      read-write
            STATUS          current
            DESCRIPTION 
                "Enable or disable ARP proxy responses on the specified 
                 interface."
            ::= { stnArpCircExtEntry 2 }

    stnArpCircExtDoResp OBJECT-TYPE
            SYNTAX          INTEGER {
                                        enabled(1),     -- operation enabled
                                        disabled(2)     -- operation disabled
                                }
            MAX-ACCESS      read-only
            STATUS          current
            DESCRIPTION 
                "Enable or disable the sending of ARP responses on specified 
                 circuit."
            ::= { stnArpCircExtEntry 3 }

    stnArpCircExtWanProxy OBJECT-TYPE
            SYNTAX          INTEGER {
                                        enabled(1),     -- operation enabled
                                        disabled(2)     -- operation disabled
                                }
            MAX-ACCESS      read-write
            STATUS          current
            DESCRIPTION 
                "Enable or disable ARP WAN proxy responses on the specified 
                 interface."
            ::= { stnArpCircExtEntry 4 }


    --
    -- STN RIP Attributes Group
    --

    stnRipExtAdminState OBJECT-TYPE
            SYNTAX          INTEGER{
                                        enabled(1),     -- operation enabled
                                        disabled(2)     -- operation disabled
                                }
            MAX-ACCESS      read-write
            STATUS          current
            DESCRIPTION 
                "Enable or disable the operation of RIP on all interfaces."
            ::= { stnRip 1 }

    stnRipExtUpdateTime OBJECT-TYPE
            SYNTAX          Integer32
            MAX-ACCESS      read-write
            STATUS          current
            DESCRIPTION 
                "The time between transmission of RIP updates."
            ::= { stnRip 2 }


    --
    -- STN RIP Circuits Table
    --

    stnRipCircExtTable OBJECT-TYPE
            SYNTAX          SEQUENCE OF StnRipCircExtEntry
            MAX-ACCESS      not-accessible
            STATUS          current
            DESCRIPTION 
                "Table of RIP circuit parameters"
            ::= { stnRip 3 }

    stnRipCircExtEntry OBJECT-TYPE
            SYNTAX          StnRipCircExtEntry
            MAX-ACCESS      not-accessible
            STATUS          current
            DESCRIPTION 
                "A circuits RIP parameters"
            INDEX { stnRipCircExtIfIndex }
            ::= { stnRipCircExtTable 1 }

    StnRipCircExtEntry ::= 
        SEQUENCE {
                    stnRipCircExtIfIndex
                            Integer32,
                    stnRipCircExtTalk
                            INTEGER,
                    stnRipCircExtListen
                            INTEGER,
                    stnRipCircExtPoison
                            INTEGER
            }

    stnRipCircExtIfIndex OBJECT-TYPE
            SYNTAX          Integer32
            MAX-ACCESS      read-only
            STATUS          current
            DESCRIPTION 
                "An index value which uniquely identifies the local physical 
                 interface which this circuit uses. This value identifies the
                 same interface identified by ifIndex in MIB-2."
            ::= { stnRipCircExtEntry 1 }

    stnRipCircExtTalk OBJECT-TYPE
            SYNTAX          INTEGER {
                                        enabled(1),     -- operation enabled
                                        disabled(2)     -- operation disabled
                            }
            MAX-ACCESS      read-write
            STATUS          current
            DESCRIPTION 
                "Enable or disable RIP transmission
                         on the specified interface."
            ::= { stnRipCircExtEntry 2 }

    stnRipCircExtListen OBJECT-TYPE
            SYNTAX          INTEGER {
                                        enabled(1),     -- operation enabled
                                        disabled(2)     -- operation disabled
                            }
            MAX-ACCESS      read-write
            STATUS          current
            DESCRIPTION 
                "Enable or disable RIP reception
                         on the specified interface."
            ::= { stnRipCircExtEntry 3 }

    stnRipCircExtPoison OBJECT-TYPE
            SYNTAX          INTEGER {
                                        enabled(1),     -- operation enabled
                                        disabled(2)     -- operation disabled
                            }
            MAX-ACCESS      read-write
            STATUS          current
            DESCRIPTION 
                "Enable or disable operation of poison
                 reverse on the specified interface. If poison
                 is disabled, split-horizon operation is enabled."
            ::= { stnRipCircExtEntry 4 }


    --
    -- STN RIP Details Table
    --

    stnRipDetailsTable OBJECT-TYPE
            SYNTAX          SEQUENCE OF StnRipDetailsEntry
            MAX-ACCESS      not-accessible
            STATUS          current
            DESCRIPTION
                   "This table provides additional information about 
                    failed rip messages. When the table reaches its
                    maximum size and a new entry needs to be added, 
                    the entire table will be cleared."
            ::= { stnRip 4 }

    stnRipDetailsEntry OBJECT-TYPE
            SYNTAX          StnRipDetailsEntry
            MAX-ACCESS      not-accessible
            STATUS          current
            DESCRIPTION
                    "An entry within the STN RIP Details Table."
            INDEX {stnRipDetailsIndex }
            ::= { stnRipDetailsTable 1 }

    StnRipDetailsEntry ::=
            SEQUENCE {
                  stnRipDetailsIndex
	                Integer32,
                stnRipDetailsSource
                    IpAddress,
                stnRipDetailsDest
                    IpAddress,
                stnRipDetailsType
                    INTEGER,
                stnRipDetailsTimeStamp
                    TimeStamp,
                stnRipDetailsHeader
                    OCTET STRING
    }

    stnRipDetailsIndex OBJECT-TYPE
            SYNTAX          Integer32
            MAX-ACCESS      not-accessible
            STATUS          current
            DESCRIPTION
                    "A unique index for this table."
            ::= { stnRipDetailsEntry 1 }

    stnRipDetailsSource OBJECT-TYPE
            SYNTAX           IpAddress
            MAX-ACCESS       read-only
            STATUS           current
            DESCRIPTION
                    "The source address within the packet."
            ::= { stnRipDetailsEntry 2 }

    stnRipDetailsDest OBJECT-TYPE
            SYNTAX         IpAddress
            MAX-ACCESS     read-only
            STATUS         current
            DESCRIPTION
                    "The destination address within the packet."
            ::= { stnRipDetailsEntry 3 }

    stnRipDetailsType OBJECT-TYPE
            SYNTAX         INTEGER {
                    bad-packet(1)         -- RIP bad packet
                    }
            MAX-ACCESS     read-only
            STATUS         current
            DESCRIPTION
                    "Indicates the type of error" 
            ::= { stnRipDetailsEntry 4 }

    stnRipDetailsTimeStamp OBJECT-TYPE
            SYNTAX        TimeStamp
            MAX-ACCESS    read-only
            STATUS        current
            DESCRIPTION
                    "Value of sysUpTime when this entry was added."
            ::= { stnRipDetailsEntry 5 }

    stnRipDetailsHeader OBJECT-TYPE
            SYNTAX        OCTET STRING (SIZE (60))
            MAX-ACCESS    read-only
            STATUS        current
            DESCRIPTION
                    "IP header of this error packet."
            ::= { stnRipDetailsEntry 6 }


    --
    -- STN OSPF Statistics Group
    --

    stnOspfRouterLsaCount OBJECT-TYPE
        SYNTAX   Gauge32        
        MAX-ACCESS   read-only
        STATUS   current
        DESCRIPTION
           "The number of router (LS type 1) link-state advertisements in 
           the link-state database."
       ::= { stnOspf 1 }

    stnOspfNetworkLsaCount OBJECT-TYPE
        SYNTAX   Gauge32        
        MAX-ACCESS   read-only
        STATUS   current
        DESCRIPTION
           "The number of network (LS type 2) link-state advertisements in 
           the link-state database."
       ::= { stnOspf 2 }

    stnOspfSummaryLsaCount OBJECT-TYPE
        SYNTAX   Gauge32        
        MAX-ACCESS   read-only
        STATUS   current
        DESCRIPTION
           "The number of summary (LS type 3) link-state advertisements in 
           the link-state database."
       ::= { stnOspf 3 }

    stnOspfASBRSummaryLsaCount OBJECT-TYPE
        SYNTAX   Gauge32        
        MAX-ACCESS   read-only
        STATUS   current
        DESCRIPTION
           "The number of ASBR-summary (LS type 4) link-state advertisements 
           in the link-state database."
       ::= { stnOspf 4 }

    stnOspfExternLsaCount OBJECT-TYPE
        SYNTAX   Gauge32        
        MAX-ACCESS   read-only
        STATUS   current
        DESCRIPTION
           "The number of AS-external (LS type 5) link-state advertisements in
           the link-state database."
       ::= { stnOspf 5 }

    stnOspfMcastGroupLsaCount OBJECT-TYPE
        SYNTAX   Gauge32        
        MAX-ACCESS   read-only
        STATUS   current
        DESCRIPTION
           "The number of group-membership (LS type 6) link-state 
           advertisements in the link-state database."
       ::= { stnOspf 6 }

    stnOspfExternT7LsaCount OBJECT-TYPE
        SYNTAX   Gauge32        
        MAX-ACCESS   read-only
        STATUS   current
        DESCRIPTION
           "The number of Type-7 link-state advertisements in the link-state 
           database."
       ::= { stnOspf 7 }

    --
    -- STN OSPF Details Table
    --

    stnOspfDetailsTable OBJECT-TYPE
            SYNTAX          SEQUENCE OF StnOspfDetailsEntry
            MAX-ACCESS      not-accessible
            STATUS          current
            DESCRIPTION
                   "This table provides additional information about 
                    failed Ospf messages. When the 
                    table reaches its maximum size and a new entry 
                    needs to be added, the entire table will be cleared." 
            ::= { stnOspf 9 }

    stnOspfDetailsEntry OBJECT-TYPE
            SYNTAX          StnOspfDetailsEntry
            MAX-ACCESS      not-accessible
            STATUS          current
            DESCRIPTION
                    "An entry within the STN OSPF Details Table."
            INDEX {stnOspfDetailsIndex }
            ::= { stnOspfDetailsTable 1 }

    StnOspfDetailsEntry ::=
            SEQUENCE {
                stnOspfDetailsIndex
	                Integer32,
                stnOspfDetailsPacketType
                    Integer32,
                stnOspfDetailsRouterId
                    Integer32,
                stnOspfDetailsAreaId
                    Integer32,
                stnOspfDetailsErrorType
                    INTEGER,
                stnOspfDetailsTimeStamp
                    TimeStamp,
                stnOspfDetailsHeader
                    OCTET STRING
    }

    stnOspfDetailsIndex OBJECT-TYPE
            SYNTAX          Integer32
            MAX-ACCESS      not-accessible
            STATUS          current
            DESCRIPTION
                    "A unique index for this table."
            ::= { stnOspfDetailsEntry 1 }

    stnOspfDetailsPacketType OBJECT-TYPE
            SYNTAX           Integer32
            MAX-ACCESS       read-only
            STATUS           current
            DESCRIPTION
                    "The OSPF packet type."
            ::= { stnOspfDetailsEntry 2 }

    stnOspfDetailsRouterId OBJECT-TYPE
            SYNTAX         Integer32
            MAX-ACCESS     read-only
            STATUS         current
            DESCRIPTION
                    "The router ID within the packet."
            ::= { stnOspfDetailsEntry 3 }

    stnOspfDetailsAreaId OBJECT-TYPE
            SYNTAX         Integer32
            MAX-ACCESS     read-only
            STATUS         current
            DESCRIPTION
                    "The area ID within the packet."
            ::= { stnOspfDetailsEntry 4 }

    stnOspfDetailsErrorType OBJECT-TYPE
            SYNTAX         INTEGER {
                    badVersion (1),
                    areaMismatch (2),
                    unknownNbmaNbr (3),
                    unknownVirtualNbr (4),
                    authTypeMismatch(5),
                    authFailure (6),
                    netMaskMismatch (7),
                    helloIntervalMismatch (8),
                    deadIntervalMismatch (9),
                    optionMismatch (10),
                    lanSubnetMismatch (11),
                    designatedRouterMismatch (12),
                    myRouterId (13),
                    invalidLength (14),
                    neighborNotFound (15),
                    md5SequenceError (16)                    
        }

            MAX-ACCESS     read-only
            STATUS         current
            DESCRIPTION
                    "The type of errors caused this packet being dropped."
            ::= { stnOspfDetailsEntry 5 }

    stnOspfDetailsTimeStamp OBJECT-TYPE
            SYNTAX        TimeStamp
            MAX-ACCESS    read-only
            STATUS        current
            DESCRIPTION
                    "Value of sysUpTime when this entry was added."
            ::= { stnOspfDetailsEntry 6 }

    stnOspfDetailsHeader OBJECT-TYPE
            SYNTAX        OCTET STRING (SIZE (60))
            MAX-ACCESS    read-only
            STATUS        current
            DESCRIPTION
                    "OSPF header of this error packet."
            ::= { stnOspfDetailsEntry 7 }

END
