Nortel-Magellan-Passport-AtmIispMIB
DEFINITIONS ::= BEGIN



IMPORTS

      OBJECT-TYPE
   FROM RFC-1212

      passportMIBs
   FROM Nortel-Magellan-Passport-UsefulDefinitionsMIB

      Counter32,
      DisplayString,
      StorageType,
      RowStatus,
      Gauge32,
      Integer32,
      Unsigned32
   FROM Nortel-Magellan-Passport-StandardTextualConventionsMIB

      Hex,
      NonReplicated,
      AsciiStringIndex
   FROM Nortel-Magellan-Passport-TextualConventionsMIB

      atmIfVptIndex,
      atmIfVpt,
      atmIfIndex,
      atmIf
   FROM Nortel-Magellan-Passport-AtmCoreMIB;




-- LAST-UPDATED   "9808030000Z"
-- ORGANIZATION   "Nortel"
-- CONTACT-INFO   "
--         Nortel Magellan Network Management
--         
--         Postal: P.O. Box 5080, Station F 
--                 Ottawa, Ontario 
--                 Canada  K2C 3T1
--         
--         Email:  nm_plm@nt.com"
-- DESCRIPTION
--    "The module describing the Nortel Magellan Passport
--     AtmIisp Enterprise MIB."

atmIispMIB OBJECT IDENTIFIER ::= { passportMIBs 70 }










-- AtmIf/n Iisp
-- This component represents an ATM Interim Inter-switch Signaling 
-- Protocol (IISP) interface. If this component is provisioned, the Uni 
-- component can not be provisioned under the same AtmIf 
-- component. If this component is deleted, then all associated Vcc 
-- components are deleted.

atmIfIisp OBJECT IDENTIFIER ::= { atmIf 7 }



atmIfIispRowStatusTable OBJECT-TYPE
   SYNTAX     SEQUENCE OF AtmIfIispRowStatusEntry
   ACCESS     not-accessible
   STATUS     mandatory
   DESCRIPTION
     "This entry controls the addition and deletion of 
      atmIfIisp components."
::= { atmIfIisp 1 }

atmIfIispRowStatusEntry OBJECT-TYPE
   SYNTAX     AtmIfIispRowStatusEntry
   ACCESS     not-accessible
   STATUS     mandatory
   DESCRIPTION
     "A single entry in the table represents a single 
      atmIfIisp component."
   INDEX {
      atmIfIndex,
      atmIfIispIndex }
::= { atmIfIispRowStatusTable 1 }

AtmIfIispRowStatusEntry ::= SEQUENCE {
   atmIfIispRowStatus
      RowStatus,
   atmIfIispComponentName
      DisplayString,
   atmIfIispStorageType
      StorageType,
   atmIfIispIndex
      NonReplicated }

atmIfIispRowStatus OBJECT-TYPE
   SYNTAX     RowStatus 
   ACCESS     read-write
   STATUS     mandatory
   DESCRIPTION
     "This variable is used as the basis for SNMP naming of
      atmIfIisp components.
      These components can be added and deleted."
::= { atmIfIispRowStatusEntry 1 }

atmIfIispComponentName OBJECT-TYPE
   SYNTAX     DisplayString 
   ACCESS     read-only
   STATUS     mandatory
   DESCRIPTION
     "This variable provides the component's string name for
      use with the ASCII Console Interface"
::= { atmIfIispRowStatusEntry 2 }

atmIfIispStorageType OBJECT-TYPE
   SYNTAX     StorageType 
   ACCESS     read-only
   STATUS     mandatory
   DESCRIPTION
     "This variable represents the storage type value for the
      atmIfIisp tables."
::= { atmIfIispRowStatusEntry 4 }

atmIfIispIndex OBJECT-TYPE
   SYNTAX     NonReplicated 
   ACCESS     not-accessible
   STATUS     mandatory
   DESCRIPTION
     "This variable represents the index for the atmIfIisp tables."
::= { atmIfIispRowStatusEntry 10 }

atmIfIispProvTable OBJECT-TYPE
   SYNTAX     SEQUENCE OF AtmIfIispProvEntry
   ACCESS     not-accessible
   STATUS     mandatory
   DESCRIPTION
     "This group contains the provisionable attributes for the Iisp 
      component."
::= { atmIfIisp 10 }

atmIfIispProvEntry OBJECT-TYPE
   SYNTAX     AtmIfIispProvEntry
   ACCESS     not-accessible
   STATUS     mandatory
   DESCRIPTION
     "An entry in the atmIfIispProvTable."
   INDEX {
      atmIfIndex,
      atmIfIispIndex }
::= { atmIfIispProvTable 1 }

AtmIfIispProvEntry ::= SEQUENCE {
   atmIfIispVersion
      INTEGER,
   atmIfIispSide
      INTEGER,
   atmIfIispSoftPvcRetryPeriod
      Unsigned32,
   atmIfIispSoftPvpAndPvcRetryPeriod
      Unsigned32,
   atmIfIispSoftPvpAndPvcHoldOffTime
      Unsigned32 }

atmIfIispVersion OBJECT-TYPE
   SYNTAX     INTEGER  {
                 iisp10Sig30(2),
                 iisp10Sig31(3) }
   ACCESS     read-write
   STATUS     mandatory
   DESCRIPTION
     "This attribute indicates which specification the IISP interface 
      complies with. The options are iisp10Sig30 which refers to IISP 
      version 1.0 with 3.0 signalling and iisp10Sig31 which refers to IISP 
      version 1.0 with 3.1 signalling. If this attribute is changed, all 
      switched Vcc components in this interface are cleared due to the 
      fact that the two versions are incompatible."
   DEFVAL     { iisp10Sig31 }
::= { atmIfIispProvEntry 1 }

atmIfIispSide OBJECT-TYPE
   SYNTAX     INTEGER  {
                 networkSide(0),
                 userSide(1) }
   ACCESS     read-write
   STATUS     mandatory
   DESCRIPTION
     "This attribute indicates which side the interface is, user or network."
   DEFVAL     { networkSide }
::= { atmIfIispProvEntry 2 }

atmIfIispSoftPvcRetryPeriod OBJECT-TYPE
   SYNTAX     Unsigned32 (20..999999)
   ACCESS     read-write
   STATUS     obsolete
   DESCRIPTION
     "This attribute specifies the time to wait between call set up retries. 
      The resolution is to the nearest 10 seconds.
      This attribute has been obsoleted and is replaced by the 
      softPvpAndPvcRetryPeriod attribute."
   DEFVAL     { 60 }
::= { atmIfIispProvEntry 3 }

atmIfIispSoftPvpAndPvcRetryPeriod OBJECT-TYPE
   SYNTAX     Unsigned32 (20..999999)
   ACCESS     read-write
   STATUS     mandatory
   DESCRIPTION
     "This attribute specifies the time to wait between soft PVP or soft 
      PVC call setup retries. The resolution is to the nearest 10 seconds."
   DEFVAL     { 60 }
::= { atmIfIispProvEntry 4 }

atmIfIispSoftPvpAndPvcHoldOffTime OBJECT-TYPE
   SYNTAX     Unsigned32 (0 | 50..20000)
   ACCESS     read-write
   STATUS     mandatory
   DESCRIPTION
     "This attribute specifies how long to hold off retries following a 
      release or the connection. The resolution is to the nearest 50 ms."
   DEFVAL     { 0 }
::= { atmIfIispProvEntry 5 }

atmIfIispAcctOptTable OBJECT-TYPE
   SYNTAX     SEQUENCE OF AtmIfIispAcctOptEntry
   ACCESS     not-accessible
   STATUS     mandatory
   DESCRIPTION
     "This group contains the provisionable attributes for accounting."
::= { atmIfIisp 11 }

atmIfIispAcctOptEntry OBJECT-TYPE
   SYNTAX     AtmIfIispAcctOptEntry
   ACCESS     not-accessible
   STATUS     mandatory
   DESCRIPTION
     "An entry in the atmIfIispAcctOptTable."
   INDEX {
      atmIfIndex,
      atmIfIispIndex }
::= { atmIfIispAcctOptTable 1 }

AtmIfIispAcctOptEntry ::= SEQUENCE {
   atmIfIispAccountCollection
      OCTET STRING,
   atmIfIispAccountConnectionType
      INTEGER,
   atmIfIispAccountClass
      Unsigned32,
   atmIfIispServiceExchange
      Unsigned32 }

atmIfIispAccountCollection OBJECT-TYPE
   SYNTAX     OCTET STRING (SIZE (1))
   ACCESS     read-write
   STATUS     mandatory
   DESCRIPTION
     "This attribute is used to turn accounting on or off for SVC and 
      SPVC connections. It also specifies the reason(s) for which 
      accounting data is collected: billing, test, study, audit, or force.
      
      If the set of reasons is not empty then accounting records will be 
      generated by this interface in the following situations:
      - on a TODA changeover if TODA is enabled;
      - every 12 hours (per connection) if TODA is disabled;
      - on every call clear (a call record with final cell counts).
      
      If none of the reasons is present, then accounting will be 
      suppressed.
      
      The reason for collection is recorded in the accounting record, in 
      the attribute callingCollectReason or calledCollectReason as 
      appropriate.

      Description of bits:
      bill(0)
      test(1)
      study(2)
      audit(3)
      force(4)"
::= { atmIfIispAcctOptEntry 1 }

atmIfIispAccountConnectionType OBJECT-TYPE
   SYNTAX     INTEGER  {
                 origTerm(0),
                 intermediate(1) }
   ACCESS     read-write
   STATUS     mandatory
   DESCRIPTION
     "This attribute specifies whether accounting records generated by 
      this interface should be marked as originating, terminating or 
      intermediate. This attribute, in combination with the direction of the 
      call, determines the value of attribute connPointType of the 
      accounting record and may be used by downstream accounting 
      processes to correlate the records.
      
      If the value is origTerm then records generated for incoming calls 
      will be marked as originating and records generated for outgoing 
      calls will be marked as terminating.
      
      If the value is intermediate then records generated for all calls will 
      be marked as intermediate."
   DEFVAL     { intermediate }
::= { atmIfIispAcctOptEntry 2 }

atmIfIispAccountClass OBJECT-TYPE
   SYNTAX     Unsigned32 (0..255)
   ACCESS     read-write
   STATUS     mandatory
   DESCRIPTION
     "This attribute specifies the accounting class associated with the 
      interface. Its meaning is determined by the network operator.
      
      Its value is simply recorded in the accounting records generated by 
      this interface, in the attribute callingServiceType or 
      calledServiceType as appropriate."
   DEFVAL     { 0 }
::= { atmIfIispAcctOptEntry 3 }

atmIfIispServiceExchange OBJECT-TYPE
   SYNTAX     Unsigned32 (0..255)
   ACCESS     read-write
   STATUS     mandatory
   DESCRIPTION
     "This attribute specifies the data service exchange associated with 
      this interface. Its meaning is determined by the network operator.
      
      Its value is simply recorded in the accounting records generated by 
      this interface, in the attribute callingDse or calledDse as 
      appropriate."
   DEFVAL     { 0 }
::= { atmIfIispAcctOptEntry 4 }


-- AtmIf/n Iisp Signalling
-- AtmIf/n Uni Signalling
-- AtmIf/n Pnni Signalling
-- AtmIf/n Vpt/m Iisp Signalling
-- AtmIf/n Vpt/m Uni Signalling
-- AtmIf/n Vpt/m Pnni Signalling
-- 
-- This component represents the signalling entities for the interface.

atmIfIispSig OBJECT IDENTIFIER ::= { atmIfIisp 3 }



atmIfIispSigRowStatusTable OBJECT-TYPE
   SYNTAX     SEQUENCE OF AtmIfIispSigRowStatusEntry
   ACCESS     not-accessible
   STATUS     mandatory
   DESCRIPTION
     "This entry controls the addition and deletion of 
      atmIfIispSig components."
::= { atmIfIispSig 1 }

atmIfIispSigRowStatusEntry OBJECT-TYPE
   SYNTAX     AtmIfIispSigRowStatusEntry
   ACCESS     not-accessible
   STATUS     mandatory
   DESCRIPTION
     "A single entry in the table represents a single 
      atmIfIispSig component."
   INDEX {
      atmIfIndex,
      atmIfIispIndex,
      atmIfIispSigIndex }
::= { atmIfIispSigRowStatusTable 1 }

AtmIfIispSigRowStatusEntry ::= SEQUENCE {
   atmIfIispSigRowStatus
      RowStatus,
   atmIfIispSigComponentName
      DisplayString,
   atmIfIispSigStorageType
      StorageType,
   atmIfIispSigIndex
      NonReplicated }

atmIfIispSigRowStatus OBJECT-TYPE
   SYNTAX     RowStatus 
   ACCESS     read-only
   STATUS     mandatory
   DESCRIPTION
     "This variable is used as the basis for SNMP naming of
      atmIfIispSig components.
      These components cannot be added nor deleted."
::= { atmIfIispSigRowStatusEntry 1 }

atmIfIispSigComponentName OBJECT-TYPE
   SYNTAX     DisplayString 
   ACCESS     read-only
   STATUS     mandatory
   DESCRIPTION
     "This variable provides the component's string name for
      use with the ASCII Console Interface"
::= { atmIfIispSigRowStatusEntry 2 }

atmIfIispSigStorageType OBJECT-TYPE
   SYNTAX     StorageType 
   ACCESS     read-only
   STATUS     mandatory
   DESCRIPTION
     "This variable represents the storage type value for the
      atmIfIispSig tables."
::= { atmIfIispSigRowStatusEntry 4 }

atmIfIispSigIndex OBJECT-TYPE
   SYNTAX     NonReplicated 
   ACCESS     not-accessible
   STATUS     mandatory
   DESCRIPTION
     "This variable represents the index for the atmIfIispSig tables."
::= { atmIfIispSigRowStatusEntry 10 }

atmIfIispSigProvTable OBJECT-TYPE
   SYNTAX     SEQUENCE OF AtmIfIispSigProvEntry
   ACCESS     not-accessible
   STATUS     mandatory
   DESCRIPTION
     "This attribute group contains the provisionable attributes for the 
      Signalling component."
::= { atmIfIispSig 10 }

atmIfIispSigProvEntry OBJECT-TYPE
   SYNTAX     AtmIfIispSigProvEntry
   ACCESS     not-accessible
   STATUS     mandatory
   DESCRIPTION
     "An entry in the atmIfIispSigProvTable."
   INDEX {
      atmIfIndex,
      atmIfIispIndex,
      atmIfIispSigIndex }
::= { atmIfIispSigProvTable 1 }

AtmIfIispSigProvEntry ::= SEQUENCE {
   atmIfIispSigVci
      Unsigned32,
   atmIfIispSigAddressConversion
      INTEGER }

atmIfIispSigVci OBJECT-TYPE
   SYNTAX     Unsigned32 (0..65535)
   ACCESS     read-write
   STATUS     mandatory
   DESCRIPTION
     "This attribute specifies the signalling channel number."
   DEFVAL     { 5 }
::= { atmIfIispSigProvEntry 1 }

atmIfIispSigAddressConversion OBJECT-TYPE
   SYNTAX     INTEGER  {
                 none(0),
                 nativeE164(1),
                 nsap(2) }
   ACCESS     read-write
   STATUS     mandatory
   DESCRIPTION
     "This attribute specifies the address conversion on the outgoing 
      signalling PDUs. The options are none, nativeE164, or nsap. The 
      none option is the default and if this option is chosen then nothing 
      is done to the address information element (IE) in the outgoing 
      signalling message. If nativeE164 option is chosen, then only 
      NSAP encapsulated E.164 addresses with zeros in the ESI are 
      converted to native E.164 format in the outgoing signalling 
      message. If the NSAP address is not encapsulated E.164 or the ESI 
      field is not zeros and the nativeE164 option is chosen, then the call 
      is cleared. If the nsap option is chosen, then native E.164 addresses 
      are converted to NSAP E.164 with zeros in the ESI field; otherwise 
      the address is in NSAP format and is not changed."
   DEFVAL     { none }
::= { atmIfIispSigProvEntry 2 }

atmIfIispSigStateTable OBJECT-TYPE
   SYNTAX     SEQUENCE OF AtmIfIispSigStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { atmIfIispSig 11 }

atmIfIispSigStateEntry OBJECT-TYPE
   SYNTAX     AtmIfIispSigStateEntry
   ACCESS     not-accessible
   STATUS     mandatory
   DESCRIPTION
     "An entry in the atmIfIispSigStateTable."
   INDEX {
      atmIfIndex,
      atmIfIispIndex,
      atmIfIispSigIndex }
::= { atmIfIispSigStateTable 1 }

AtmIfIispSigStateEntry ::= SEQUENCE {
   atmIfIispSigAdminState
      INTEGER,
   atmIfIispSigOperationalState
      INTEGER,
   atmIfIispSigUsageState
      INTEGER }

atmIfIispSigAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { atmIfIispSigStateEntry 1 }

atmIfIispSigOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { atmIfIispSigStateEntry 2 }

atmIfIispSigUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { atmIfIispSigStateEntry 3 }

atmIfIispSigOperTable OBJECT-TYPE
   SYNTAX     SEQUENCE OF AtmIfIispSigOperEntry
   ACCESS     not-accessible
   STATUS     mandatory
   DESCRIPTION
     "This attribute contains the operational attributes for the 
      AtmSignalling component."
::= { atmIfIispSig 12 }

atmIfIispSigOperEntry OBJECT-TYPE
   SYNTAX     AtmIfIispSigOperEntry
   ACCESS     not-accessible
   STATUS     mandatory
   DESCRIPTION
     "An entry in the atmIfIispSigOperTable."
   INDEX {
      atmIfIndex,
      atmIfIispIndex,
      atmIfIispSigIndex }
::= { atmIfIispSigOperTable 1 }

AtmIfIispSigOperEntry ::= SEQUENCE {
   atmIfIispSigLastTxCauseCode
      Unsigned32,
   atmIfIispSigLastTxDiagCode
      Hex,
   atmIfIispSigLastRxCauseCode
      Unsigned32,
   atmIfIispSigLastRxDiagCode
      Hex }

atmIfIispSigLastTxCauseCode OBJECT-TYPE
   SYNTAX     Unsigned32 (0..255)
   ACCESS     read-only
   STATUS     mandatory
   DESCRIPTION
     "This attribute indicates the cause code in the last transmitted 
      signalling message that contains the CAUSE information element. 
      The cause code is used to describe the reason for generating certain 
      signalling messages."
::= { atmIfIispSigOperEntry 1 }

atmIfIispSigLastTxDiagCode OBJECT-TYPE
   SYNTAX     Hex (0..255)
   ACCESS     read-only
   STATUS     mandatory
   DESCRIPTION
     "This attribute contains the diagnostic code in the last transmitted 
      signalling message. The diagnostic code is contained in the CAUSE 
      information element and identifies an information element type or 
      timer type. The diagnostic code is present only if a procedural error 
      is detected by the signalling protocol. A diagnostic code is always 
      accompanied by the cause code. If there is no failure, this attribute 
      is set to 0."
::= { atmIfIispSigOperEntry 2 }

atmIfIispSigLastRxCauseCode OBJECT-TYPE
   SYNTAX     Unsigned32 (0..255)
   ACCESS     read-only
   STATUS     mandatory
   DESCRIPTION
     "This attribute contains the cause code in the last received signalling 
      message that contains the CAUSE information element. The cause 
      code is used to describe the reason for generating certain signalling 
      messages."
::= { atmIfIispSigOperEntry 3 }

atmIfIispSigLastRxDiagCode OBJECT-TYPE
   SYNTAX     Hex (0..255)
   ACCESS     read-only
   STATUS     mandatory
   DESCRIPTION
     "This attribute contains the diagnostic code in the last received 
      signalling message. The diagnostic code is contained in the CAUSE 
      information element and identifies an information element type or 
      timer type. The diagnostic code is present only if a procedural error 
      is detected by the signalling protocol. A diagnostic code is always 
      accompanied by the cause code. If there is no failure, this attribute 
      is set to 0."
::= { atmIfIispSigOperEntry 4 }

atmIfIispSigStatsTable OBJECT-TYPE
   SYNTAX     SEQUENCE OF AtmIfIispSigStatsEntry
   ACCESS     not-accessible
   STATUS     mandatory
   DESCRIPTION
     "This attribute group contains the statistics associated with the 
      AtmSignalling component."
::= { atmIfIispSig 13 }

atmIfIispSigStatsEntry OBJECT-TYPE
   SYNTAX     AtmIfIispSigStatsEntry
   ACCESS     not-accessible
   STATUS     mandatory
   DESCRIPTION
     "An entry in the atmIfIispSigStatsTable."
   INDEX {
      atmIfIndex,
      atmIfIispIndex,
      atmIfIispSigIndex }
::= { atmIfIispSigStatsTable 1 }

AtmIfIispSigStatsEntry ::= SEQUENCE {
   atmIfIispSigCurrentConnections
      Counter32,
   atmIfIispSigPeakConnections
      Gauge32,
   atmIfIispSigSuccessfulConnections
      Counter32,
   atmIfIispSigFailedConnections
      Counter32,
   atmIfIispSigTxPdus
      Counter32,
   atmIfIispSigRxPdus
      Counter32,
   atmIfIispSigCurrentPmpConnections
      Gauge32,
   atmIfIispSigPeakPmpConnections
      Gauge32,
   atmIfIispSigSuccessfulPmpConnections
      Counter32,
   atmIfIispSigFailedPmpConnections
      Counter32,
   atmIfIispSigNewCurrentConnections
      Gauge32 }

atmIfIispSigCurrentConnections OBJECT-TYPE
   SYNTAX     Counter32 
   ACCESS     read-only
   STATUS     obsolete
   DESCRIPTION
     "This attribute indicates the total number of currently active 
      connections."
::= { atmIfIispSigStatsEntry 1 }

atmIfIispSigPeakConnections OBJECT-TYPE
   SYNTAX     Gauge32 (0..4294967295)
   ACCESS     read-only
   STATUS     mandatory
   DESCRIPTION
     "This attribute indicates the high water mark of active point-to-
      point and point-to-multipoint connections."
::= { atmIfIispSigStatsEntry 2 }

atmIfIispSigSuccessfulConnections OBJECT-TYPE
   SYNTAX     Counter32 
   ACCESS     read-only
   STATUS     mandatory
   DESCRIPTION
     "This attribute counts the total number of switched point-to-
      point and point-to-multipoint connections that were successfully 
      established. The counter wraps to 0 when the maximum value is 
      exceeded."
::= { atmIfIispSigStatsEntry 3 }

atmIfIispSigFailedConnections OBJECT-TYPE
   SYNTAX     Counter32 
   ACCESS     read-only
   STATUS     mandatory
   DESCRIPTION
     "This attribute counts the total number of switched connections that 
      were not successfully established.The counter wraps to 0 when the 
      maximum value is exceeded."
::= { atmIfIispSigStatsEntry 4 }

atmIfIispSigTxPdus OBJECT-TYPE
   SYNTAX     Counter32 
   ACCESS     read-only
   STATUS     mandatory
   DESCRIPTION
     "This attribute counts the number of transmitted signalling 
      PDUs.The counter wraps to 0 when the maximum value is 
      exceeded."
::= { atmIfIispSigStatsEntry 5 }

atmIfIispSigRxPdus OBJECT-TYPE
   SYNTAX     Counter32 
   ACCESS     read-only
   STATUS     mandatory
   DESCRIPTION
     "This attribute counts the number of received signalling PDUs.The 
      counter wraps to 0 when the maximum value is exceeded."
::= { atmIfIispSigStatsEntry 6 }

atmIfIispSigCurrentPmpConnections OBJECT-TYPE
   SYNTAX     Gauge32 (0..4294967295)
   ACCESS     read-only
   STATUS     mandatory
   DESCRIPTION
     "This attribute indicates the number of currently active point-to-
      multipoint connections."
::= { atmIfIispSigStatsEntry 7 }

atmIfIispSigPeakPmpConnections OBJECT-TYPE
   SYNTAX     Gauge32 (0..4294967295)
   ACCESS     read-only
   STATUS     mandatory
   DESCRIPTION
     "This attribute indicates the high water mark of active point-to-
      multipoint connections."
::= { atmIfIispSigStatsEntry 8 }

atmIfIispSigSuccessfulPmpConnections OBJECT-TYPE
   SYNTAX     Counter32 
   ACCESS     read-only
   STATUS     mandatory
   DESCRIPTION
     "This attribute counts the total number of switched point-to-
      multipoint connections that were successfully established. 
      The counter wraps to 0 when the maximum value is 
      exceeded."
::= { atmIfIispSigStatsEntry 9 }

atmIfIispSigFailedPmpConnections OBJECT-TYPE
   SYNTAX     Counter32 
   ACCESS     read-only
   STATUS     mandatory
   DESCRIPTION
     "This attribute counts the number of switched point-to-
      multipoint connections that were not successfully 
      established.The counter wraps to 0 when the maximum value 
      is exceeded."
::= { atmIfIispSigStatsEntry 10 }

atmIfIispSigNewCurrentConnections OBJECT-TYPE
   SYNTAX     Gauge32 (0..4294967295)
   ACCESS     read-only
   STATUS     mandatory
   DESCRIPTION
     "This attribute indicates the total number of currently active point-to-
      point and point-to-multipoint connections."
::= { atmIfIispSigStatsEntry 11 }


-- AtmIf/n Uni Sig VirtualChannelDescriptor
-- AtmIf/n Uni Ilmi VirtualChannelDescriptor
-- AtmIf/n Iisp Sig VirtualChannelDescriptor
-- AtmIf/n Pnni Sig VirtualChannelDescriptor
-- AtmIf/n Pnni Rcc VirtualChannelDescriptor
-- AtmIf/n Vpt/m Uni Sig VirtualChannelDescriptor
-- AtmIf/n Vpt/m Iisp Sig VirtualChannelDescriptor
-- AtmIf/n Vpt/m Pnni Sig VirtualChannelDescriptor
-- AtmIf/n Vpt/m Pnni Rcc VirtualChannelDescriptor
-- 
-- This component contains the provisionable traffic parameters for a 
-- control channel (Sig, Ilmi or Rcc component).

atmIfIispSigVcd OBJECT IDENTIFIER ::= { atmIfIispSig 2 }



atmIfIispSigVcdRowStatusTable OBJECT-TYPE
   SYNTAX     SEQUENCE OF AtmIfIispSigVcdRowStatusEntry
   ACCESS     not-accessible
   STATUS     mandatory
   DESCRIPTION
     "This entry controls the addition and deletion of 
      atmIfIispSigVcd components."
::= { atmIfIispSigVcd 1 }

atmIfIispSigVcdRowStatusEntry OBJECT-TYPE
   SYNTAX     AtmIfIispSigVcdRowStatusEntry
   ACCESS     not-accessible
   STATUS     mandatory
   DESCRIPTION
     "A single entry in the table represents a single 
      atmIfIispSigVcd component."
   INDEX {
      atmIfIndex,
      atmIfIispIndex,
      atmIfIispSigIndex,
      atmIfIispSigVcdIndex }
::= { atmIfIispSigVcdRowStatusTable 1 }

AtmIfIispSigVcdRowStatusEntry ::= SEQUENCE {
   atmIfIispSigVcdRowStatus
      RowStatus,
   atmIfIispSigVcdComponentName
      DisplayString,
   atmIfIispSigVcdStorageType
      StorageType,
   atmIfIispSigVcdIndex
      NonReplicated }

atmIfIispSigVcdRowStatus OBJECT-TYPE
   SYNTAX     RowStatus 
   ACCESS     read-write
   STATUS     mandatory
   DESCRIPTION
     "This variable is used as the basis for SNMP naming of
      atmIfIispSigVcd components.
      These components can be added and deleted."
::= { atmIfIispSigVcdRowStatusEntry 1 }

atmIfIispSigVcdComponentName OBJECT-TYPE
   SYNTAX     DisplayString 
   ACCESS     read-only
   STATUS     mandatory
   DESCRIPTION
     "This variable provides the component's string name for
      use with the ASCII Console Interface"
::= { atmIfIispSigVcdRowStatusEntry 2 }

atmIfIispSigVcdStorageType OBJECT-TYPE
   SYNTAX     StorageType 
   ACCESS     read-only
   STATUS     mandatory
   DESCRIPTION
     "This variable represents the storage type value for the
      atmIfIispSigVcd tables."
::= { atmIfIispSigVcdRowStatusEntry 4 }

atmIfIispSigVcdIndex OBJECT-TYPE
   SYNTAX     NonReplicated 
   ACCESS     not-accessible
   STATUS     mandatory
   DESCRIPTION
     "This variable represents the index for the atmIfIispSigVcd tables."
::= { atmIfIispSigVcdRowStatusEntry 10 }

atmIfIispSigVcdProvTable OBJECT-TYPE
   SYNTAX     SEQUENCE OF AtmIfIispSigVcdProvEntry
   ACCESS     not-accessible
   STATUS     mandatory
   DESCRIPTION
     "This group contains the provisionable traffic attributes for a control 
      channel."
::= { atmIfIispSigVcd 10 }

atmIfIispSigVcdProvEntry OBJECT-TYPE
   SYNTAX     AtmIfIispSigVcdProvEntry
   ACCESS     not-accessible
   STATUS     mandatory
   DESCRIPTION
     "An entry in the atmIfIispSigVcdProvTable."
   INDEX {
      atmIfIndex,
      atmIfIispIndex,
      atmIfIispSigIndex,
      atmIfIispSigVcdIndex }
::= { atmIfIispSigVcdProvTable 1 }

AtmIfIispSigVcdProvEntry ::= SEQUENCE {
   atmIfIispSigVcdTrafficDescType
      INTEGER,
   atmIfIispSigVcdAtmServiceCategory
      INTEGER,
   atmIfIispSigVcdQosClass
      INTEGER,
   atmIfIispSigVcdTrafficShaping
      INTEGER,
   atmIfIispSigVcdUnshapedTransmitQueueing
      INTEGER,
   atmIfIispSigVcdUsageParameterControl
      INTEGER }

atmIfIispSigVcdTrafficDescType OBJECT-TYPE
   SYNTAX     INTEGER  {
                 n3(3),
                 n6(6),
                 n7(7),
                 n8(8) }
   ACCESS     read-write
   STATUS     mandatory
   DESCRIPTION
     "This attribute specifies the type of traffic management which is 
      applied to both the transmit and receive direction of this connection 
      as defined in the ATM Forum. The trafficDescType determines the 
      number and meaning of the parameters in the trafficDescParm 
      attribute."
   DEFVAL     { n6 }
::= { atmIfIispSigVcdProvEntry 1 }

atmIfIispSigVcdAtmServiceCategory OBJECT-TYPE
   SYNTAX     INTEGER  {
                 unspecifiedBitRate(0),
                 constantBitRate(1),
                 rtVariableBitRate(2),
                 nrtVariableBitRate(3) }
   ACCESS     read-write
   STATUS     mandatory
   DESCRIPTION
     "This attribute specifies the ATM service category for both directions 
      of the connection. 
      
      The constantBitRate service category is intended for real time 
      applications, that is those requiring tightly constrained delay and 
      delay variation, as would be appropriate for voice and video 
      applications. The consistent availability of a fixed quantity of 
      bandwidth is considered appropriate for CBR service. Cells which 
      are delayed beyond the value specified by CellTransfer Delay are 
      assumed to be of significantly reduce value to the application.
      
      The rtVariableBitRate service category is intended for real time 
      applications, that is those requiring tightly constrained delay and 
      delay variation, as would be appropriate for voice and video 
      applications. Sources are expected to transmit at a rate which varies 
      with time. Equivalently, the source can be described as 'bursty'. 
      Cells which are delayed beyond the value specified by CTD are 
      assumed to be of significantly reduced value to the application. Real 
      time VBR service may support statistical multiplexing of real time 
      sources.
      
      The nrtVariableBitRate service category is intended for non-real 
      time applications which have bursty traffic characteristics and which 
      can be characterized in terms of a PCR, SCR, and MBS. For those 
      cells which are transferred within the traffic contract, the application 
      expects a low cell loss ratio. For all connections, it expects a bound 
      on the mean cell transfer delay. Non-real time VBR service may 
      support statistical multiplexing of connections.
      
      The unspecifiedBitRate service is intended for non-real time 
      applications; that is, those not requiring tightly constrained delay 
      and delay variation. UBR sources are expected to be bursty. UBR 
      service supports a high degree of statistical multiplexing among 
      sources. UBR service does not specify traffic related service 
      guarantees. No numerical commitments are made with respect to 
      the cell loss ratio experienced by a UBR connection, or as to the 
      cell transfer delay experienced by cells on the connection."
   DEFVAL     { rtVariableBitRate }
::= { atmIfIispSigVcdProvEntry 3 }

atmIfIispSigVcdQosClass OBJECT-TYPE
   SYNTAX     INTEGER  {
                 n0(0),
                 n1(1),
                 n2(2),
                 n3(3),
                 n4(4) }
   ACCESS     read-write
   STATUS     mandatory
   DESCRIPTION
     "This attribute specifies the quality of service for both the forward 
      and backward direction for this connection.
      
      Class 1 supports a QOS that meets Service Class A performance 
      requirements (Circuit emulation, constant bit rate video).
      
      Class 2 supports a QOS that meets Service Class B performance 
      requirements (Variable bit rate audio and video).
      
      Class 3 supports a QOS that meets Service Class C performance 
      requirements (Connection-Oriented Data Transfer).
      
      Class 4 supports a QOS that meets Service Class D performance 
      requirements (Connectionless Data Transfer).
      
      Class 0 is the unspecified bit rate QOS class; no objective is 
      specified for the performance parameters."
   DEFVAL     { n2 }
::= { atmIfIispSigVcdProvEntry 21 }

atmIfIispSigVcdTrafficShaping OBJECT-TYPE
   SYNTAX     INTEGER  {
                 disabled(1),
                 sameAsCa(2) }
   ACCESS     read-write
   STATUS     mandatory
   DESCRIPTION
     "This attribute specifies whether this connection uses traffic shaping 
      when transmitting traffic to the ATM interface.
      
      When sameAsCa is selected, traffic shaping for this connection is 
      based on the trafficShaping attribute of the connection's service 
      category component under the AtmIf CA. If the service category has 
      traffic shaping enabled, then traffic shaping is enabled for the 
      connection. Note that enabling traffic shaping may have no effect 
      under certain cases. These cases are listed in the description of the 
      trafficShaping operational attribute, which is under the Vcc Tm and 
      Vpc Tm components.
      
      When disabled is selected, traffic shaping for this connection is 
      disabled."
   DEFVAL     { disabled }
::= { atmIfIispSigVcdProvEntry 50 }

atmIfIispSigVcdUnshapedTransmitQueueing OBJECT-TYPE
   SYNTAX     INTEGER  {
                 common(1),
                 sameAsCa(3) }
   ACCESS     read-write
   STATUS     mandatory
   DESCRIPTION
     "This attribute only applies when this connection is unshaped. This 
      attribute specifies the transmit queueing method for this connection 
      if it is unshaped. Refer to the unshapedTransmitQueueing attribute 
      under the AtmIf CA service category subcomponent for more details 
      on the meaning of this attribute. 
      
      When this attribute is set to sameAsCa, the transmit queueing 
      method for the connection is based on the 
      unshapedTransmitQueueing attribute of the connection's service 
      category component under the ConnectionAdministrator. 
      
      When this attribute is set to common, transmit traffic on this 
      unshaped connection is destined for the common queue. 
      
      The value sameAsInterface is for migration from previous software 
      releases, but should no longer be used"
   DEFVAL     { sameAsCa }
::= { atmIfIispSigVcdProvEntry 60 }

atmIfIispSigVcdUsageParameterControl OBJECT-TYPE
   SYNTAX     INTEGER  {
                 disabled(1),
                 sameAsCa(2) }
   ACCESS     read-write
   STATUS     mandatory
   DESCRIPTION
     "This attribute specifies whether this connection enforces usage 
      parameter control when receiving traffic from the ATM interface.
      
      When sameAsCa is selected, UPC for the connection is based on 
      the usageParameterControl attribute of the connection's service 
      category component under the ConnectionAdministrator. If the 
      service category has UPC enabled, then UPC is enabled for the 
      connection. Note that enabling UPC may have no effect under 
      certain cases. These cases are listed in the description of the 
      usageParameterControl operational attribute, which is under the 
      Vcc Tm or Vpc Tm component.
      
      When disabled is selected, UPC for this connection is disabled.
      
      The value sameAsInterface is for migration from previous software 
      releases, but should no longer be used"
   DEFVAL     { disabled }
::= { atmIfIispSigVcdProvEntry 70 }

atmIfIispSigVcdTdpTable OBJECT-TYPE
   SYNTAX     SEQUENCE OF AtmIfIispSigVcdTdpEntry
   ACCESS     not-accessible
   STATUS     mandatory
   DESCRIPTION
     "This attribute is a vector of five traffic parameters whose meanings 
      are defined by the trafficDescType attribute. The values of peak cell 
      rate (PCR), sustained cell rate (SCR) and requested shaping rate are 
      expressed in cell/s. Maximum burst size (MBS) is expressed in 
      cells. CDVT is expressed in microseconds. The values of PCR, 
      SCR, MBS and CDVT are used for connection admission control 
      (CAC). The value of CDVT is only used for connections where the 
      atmServiceCategory is constantBitRate. For all other values of 
      atmServiceCategory, CDVT is ignored. The values of PCR, SCR 
      and requested shaping rate are used to determine the actual shaping 
      rate where traffic shaping is enabled.
      
      When trafficDescType is 3, parameter 1 represents the PCR for CLP 
      equal to 0 and 1 traffic; parameter 4 represents the CDVT; and 
      parameter 5 represents the requested shaping rate. A non-zero value 
      in parameter 5 overrides any value in parameter 1. This result is 
      used as the PCR. Parameter 1 must be non-zero. Parameters 2 and 3 
      must be zero.
      
      When trafficDescType is 6, parameter 1 represents the PCR for CLP 
      equal to 0 and 1 traffic; parameter 2 represents the SCR for CLP 
      equal to 0 and 1 traffic; parameter 3 represents the MBS for CLP 
      equal to 0 and 1 traffic; parameter 4 represents the CDVT; and 
      parameter 5 represents the requested shaping rate. A non-zero value 
      in parameter 5 overrides any value in parameter 1. This result is 
      used as the PCR. Parameters 1, 2, and 3 must be non-zero. 
      Parameter 1 must be greater than or equal to parameter 2. Parameter 
      5 must either be zero (unused) or greater than or equal to parameter 
      2.
      
      When trafficDescType is 7, parameter 1 represents the PCR for CLP 
      equal to 0 and 1 traffic; parameter 2 represents the SCR for CLP 
      equal to 0 with cell discard; parameter 3 represents the MBS for 
      CLP equal to 0 traffic; parameter 4 represents the CDVT; and 
      parameter 5 represents the requested shaping rate. A non-zero value 
      in parameter 5 overrides any value in parameter 1. This result is 
      used as the PCR. Parameters 1, 2, and 3 must be non-zero. 
      Parameter 1 must be greater than or equal to parameter 2. Parameter 
      5 must either be zero (unused) or greater than or equal to parameter 
      2.
      
      When trafficDescType is 8, parameter 1 represents the PCR for CLP 
      equal to 0 and 1 traffic; parameter 2 represents the SCR for CLP 
      equal to 0 traffic with cell tagging; parameter 3 represents the MBS 
      for CLP equal to 0 traffic; parameter 4 represents the CDVT; and 
      parameter 5 represents the requested shaping rate. A non-zero value 
      in parameter 5 overrides any value in parameter 1. This result is 
      used as the PCR. Parameters 1, 2, and 3 must be non-zero. 
      Parameter 1 must be greater than or equal to parameter 2. Parameter 
      5 must either be zero (unused) or greater than or equal to parameter 
      2.
      
      Whenever it is valid for PCR to be specified, parameter 5 may also 
      be used to specify a requested shaping rate. A non-zero value in 
      parameter 5 overrides the value in parameter 1 and is used as the 
      peak cell rate in calculations of CAC and shaping rate.
      
      For trafficDescType 3 the traffic is shaped at the next rate less than 
      the PCR. 
      
      For trafficDescType 6, 7, and 8, the traffic is shaped at the highest 
      available rate which is between PCR and SCR. However, if there is 
      no available shaping rate between PCR and SCR, traffic is shaped at 
      the next rate above the PCR."
::= { atmIfIispSigVcd 387 }

atmIfIispSigVcdTdpEntry OBJECT-TYPE
   SYNTAX     AtmIfIispSigVcdTdpEntry
   ACCESS     not-accessible
   STATUS     mandatory
   DESCRIPTION
     "An entry in the atmIfIispSigVcdTdpTable."
   INDEX {
      atmIfIndex,
      atmIfIispIndex,
      atmIfIispSigIndex,
      atmIfIispSigVcdIndex,
      atmIfIispSigVcdTdpIndex }
::= { atmIfIispSigVcdTdpTable 1 }

AtmIfIispSigVcdTdpEntry ::= SEQUENCE {
   atmIfIispSigVcdTdpIndex
      Integer32,
   atmIfIispSigVcdTdpValue
      Unsigned32 }

atmIfIispSigVcdTdpIndex OBJECT-TYPE
   SYNTAX     Integer32 (1..5)
   ACCESS     not-accessible
   STATUS     mandatory
   DESCRIPTION
     "This variable represents the atmIfIispSigVcdTdpTable
      specific index for the atmIfIispSigVcdTdpTable."
::= { atmIfIispSigVcdTdpEntry 1 }

atmIfIispSigVcdTdpValue OBJECT-TYPE
   SYNTAX     Unsigned32 (0..2147483647)
   ACCESS     read-write
   STATUS     mandatory
   DESCRIPTION
     "This variable represents an individual value for the
      atmIfIispSigVcdTdpTable."
::= { atmIfIispSigVcdTdpEntry 2 }


-- AtmIf/n Iisp Address/address,type
-- AtmIf/n Uni Address/address,type
-- AtmIf/n Pnni Address/address,type
-- AtmIf/n Vpt/m Iisp Address/address,type
-- AtmIf/n Vpt/m Uni Address/address,type
-- AtmIf/n Vpt/m Pnni Address/address,type
-- 
-- This component represents an address (dynamic or static) 
-- associated with the interface. The index is a string of 1 to 40 hex 
-- digits or a single wildcard ('?'), and a type. The type identifies 
-- whether the Address component is for a primary, alternate, 
-- registered, or default address. 
-- 
-- The types primary and alternate are used for provisioned addresses. 
-- The type registered is used for dynamic addresses registered 
-- through ILMI. The type default is used for Soft PVP and Soft PVC 
-- addresses.Virtual interfaces do not have addresses of 
-- type default.
-- 
-- The wildcard is only valid for provisioned addresses. If the address 
-- is a single wildcard, then that indicates that the interface supports 
-- all addresses. If there is no better match, then this interface may be 
-- chosen in the routing. If there is more than one interface with a 
-- single wildcard static address, then the choice is driven through a 
-- round robin algorithm. 
-- 
-- The round robin algorithm tries the primary routes and then the 
-- alternate routes if none of the primary routes succeed.
-- If this node participates in a PNNI hierarchy, then a PnniInfo 
-- subcomponent can be provisioned under the AtmAddress 
-- component to specify the level to which this address will be 
-- advertised.

atmIfIispAddr OBJECT IDENTIFIER ::= { atmIfIisp 4 }



atmIfIispAddrRowStatusTable OBJECT-TYPE
   SYNTAX     SEQUENCE OF AtmIfIispAddrRowStatusEntry
   ACCESS     not-accessible
   STATUS     mandatory
   DESCRIPTION
     "This entry controls the addition and deletion of 
      atmIfIispAddr components."
::= { atmIfIispAddr 1 }

atmIfIispAddrRowStatusEntry OBJECT-TYPE
   SYNTAX     AtmIfIispAddrRowStatusEntry
   ACCESS     not-accessible
   STATUS     mandatory
   DESCRIPTION
     "A single entry in the table represents a single 
      atmIfIispAddr component."
   INDEX {
      atmIfIndex,
      atmIfIispIndex,
      atmIfIispAddrAddressIndex,
      atmIfIispAddrAddressTypeIndex }
::= { atmIfIispAddrRowStatusTable 1 }

AtmIfIispAddrRowStatusEntry ::= SEQUENCE {
   atmIfIispAddrRowStatus
      RowStatus,
   atmIfIispAddrComponentName
      DisplayString,
   atmIfIispAddrStorageType
      StorageType,
   atmIfIispAddrAddressIndex
      AsciiStringIndex,
   atmIfIispAddrAddressTypeIndex
      INTEGER }

atmIfIispAddrRowStatus OBJECT-TYPE
   SYNTAX     RowStatus 
   ACCESS     read-write
   STATUS     mandatory
   DESCRIPTION
     "This variable is used as the basis for SNMP naming of
      atmIfIispAddr components.
      These components can be added and deleted."
::= { atmIfIispAddrRowStatusEntry 1 }

atmIfIispAddrComponentName OBJECT-TYPE
   SYNTAX     DisplayString 
   ACCESS     read-only
   STATUS     mandatory
   DESCRIPTION
     "This variable provides the component's string name for
      use with the ASCII Console Interface"
::= { atmIfIispAddrRowStatusEntry 2 }

atmIfIispAddrStorageType OBJECT-TYPE
   SYNTAX     StorageType 
   ACCESS     read-only
   STATUS     mandatory
   DESCRIPTION
     "This variable represents the storage type value for the
      atmIfIispAddr tables."
::= { atmIfIispAddrRowStatusEntry 4 }

atmIfIispAddrAddressIndex OBJECT-TYPE
   SYNTAX     AsciiStringIndex (SIZE (1..40))
   ACCESS     not-accessible
   STATUS     mandatory
   DESCRIPTION
     "This variable represents an index for the atmIfIispAddr tables."
::= { atmIfIispAddrRowStatusEntry 10 }

atmIfIispAddrAddressTypeIndex OBJECT-TYPE
   SYNTAX     INTEGER  {
                 primary(0),
                 alternate(1),
                 default(3) }
   ACCESS     not-accessible
   STATUS     mandatory
   DESCRIPTION
     "This variable represents an index for the atmIfIispAddr tables."
::= { atmIfIispAddrRowStatusEntry 11 }

atmIfIispAddrOperTable OBJECT-TYPE
   SYNTAX     SEQUENCE OF AtmIfIispAddrOperEntry
   ACCESS     not-accessible
   STATUS     mandatory
   DESCRIPTION
     "This attribute group contains the operational attributes for the 
      Address component."
::= { atmIfIispAddr 10 }

atmIfIispAddrOperEntry OBJECT-TYPE
   SYNTAX     AtmIfIispAddrOperEntry
   ACCESS     not-accessible
   STATUS     mandatory
   DESCRIPTION
     "An entry in the atmIfIispAddrOperTable."
   INDEX {
      atmIfIndex,
      atmIfIispIndex,
      atmIfIispAddrAddressIndex,
      atmIfIispAddrAddressTypeIndex }
::= { atmIfIispAddrOperTable 1 }

AtmIfIispAddrOperEntry ::= SEQUENCE {
   atmIfIispAddrScope
      INTEGER,
   atmIfIispAddrReachability
      INTEGER }

atmIfIispAddrScope OBJECT-TYPE
   SYNTAX     INTEGER (-1..104)
   ACCESS     read-only
   STATUS     mandatory
   DESCRIPTION
     "This attribute indicates the scope of the ATM address, which is the 
      highest level to which this address will be advertised in the PNNI 
      hierarchy. If no PnniInfo subcomponent has been provisioned, then 
      the scope will default to the level of this node in the PNNI 
      hierarchy. If this node does not participate in a PNNI hierarchy, then 
      this attribute will have the value of -1."
::= { atmIfIispAddrOperEntry 1 }

atmIfIispAddrReachability OBJECT-TYPE
   SYNTAX     INTEGER  {
                 internal(0),
                 exterior(1) }
   ACCESS     read-only
   STATUS     mandatory
   DESCRIPTION
     "This attribute indicates whether the address is internal or exterior. 
      An internal reachable address is an address of a destination that is 
      directly attached to the logical node advertising the address. An 
      exterior reachable address is an address that can be reached 
      through a PNNI routing domain, but which is not located in that 
      PNNI routing domain."
::= { atmIfIispAddrOperEntry 2 }


-- AtmIf/n Iisp Address/address,type TerminateSPvpAndSPvc
-- AtmIf/n Uni Address/address,type TerminateSPvpAndSPvc
-- AtmIf/n Pnni Address/address,type TerminateSPvpAndSPvc
-- AtmIf/n Vpt/m Iisp Address/address,type TerminateSPvpAndSPvc
-- AtmIf/n Vpt/m Uni Address/address,type TerminateSPvpAndSPvc
-- AtmIf/n Vpt/m Pnni Address/address,type TerminateSPvpAndSPvc
-- 
-- The presence of this subcomponent indicates that SPvp and SPvc 
-- call setups terminate at this node if the destination address of the 
-- SPVP or SPVC matches the Address instance.

atmIfIispAddrTermSP OBJECT IDENTIFIER ::= { atmIfIispAddr 2 }



atmIfIispAddrTermSPRowStatusTable OBJECT-TYPE
   SYNTAX     SEQUENCE OF AtmIfIispAddrTermSPRowStatusEntry
   ACCESS     not-accessible
   STATUS     mandatory
   DESCRIPTION
     "This entry controls the addition and deletion of 
      atmIfIispAddrTermSP components."
::= { atmIfIispAddrTermSP 1 }

atmIfIispAddrTermSPRowStatusEntry OBJECT-TYPE
   SYNTAX     AtmIfIispAddrTermSPRowStatusEntry
   ACCESS     not-accessible
   STATUS     mandatory
   DESCRIPTION
     "A single entry in the table represents a single 
      atmIfIispAddrTermSP component."
   INDEX {
      atmIfIndex,
      atmIfIispIndex,
      atmIfIispAddrAddressIndex,
      atmIfIispAddrAddressTypeIndex,
      atmIfIispAddrTermSPIndex }
::= { atmIfIispAddrTermSPRowStatusTable 1 }

AtmIfIispAddrTermSPRowStatusEntry ::= SEQUENCE {
   atmIfIispAddrTermSPRowStatus
      RowStatus,
   atmIfIispAddrTermSPComponentName
      DisplayString,
   atmIfIispAddrTermSPStorageType
      StorageType,
   atmIfIispAddrTermSPIndex
      NonReplicated }

atmIfIispAddrTermSPRowStatus OBJECT-TYPE
   SYNTAX     RowStatus 
   ACCESS     read-write
   STATUS     mandatory
   DESCRIPTION
     "This variable is used as the basis for SNMP naming of
      atmIfIispAddrTermSP components.
      These components can be added and deleted."
::= { atmIfIispAddrTermSPRowStatusEntry 1 }

atmIfIispAddrTermSPComponentName OBJECT-TYPE
   SYNTAX     DisplayString 
   ACCESS     read-only
   STATUS     mandatory
   DESCRIPTION
     "This variable provides the component's string name for
      use with the ASCII Console Interface"
::= { atmIfIispAddrTermSPRowStatusEntry 2 }

atmIfIispAddrTermSPStorageType OBJECT-TYPE
   SYNTAX     StorageType 
   ACCESS     read-only
   STATUS     mandatory
   DESCRIPTION
     "This variable represents the storage type value for the
      atmIfIispAddrTermSP tables."
::= { atmIfIispAddrTermSPRowStatusEntry 4 }

atmIfIispAddrTermSPIndex OBJECT-TYPE
   SYNTAX     NonReplicated 
   ACCESS     not-accessible
   STATUS     mandatory
   DESCRIPTION
     "This variable represents the index for the atmIfIispAddrTermSP tables."
::= { atmIfIispAddrTermSPRowStatusEntry 10 }


-- AtmIf/n Iisp Addr/address,type PnniInfo
-- AtmIf/n Uni Addr/address,type PnniInfo
-- AtmIf/n Pnni Addr/address,type PnniInfo
-- AtmIf/n Vpt/m Iisp Addr/address,type PnniInfo
-- AtmIf/n Vpt/m Uni Addr/address,type PnniInfo
-- AtmIf/n Vpt/m Pnni Addr/address,type PnniInfo
-- 
-- This component contains provisioned information associated with 
-- the ATM address related to PNNI. This component appears only 
-- under provisioned Address components.

atmIfIispAddrPnniInfo OBJECT IDENTIFIER ::= { atmIfIispAddr 3 }



atmIfIispAddrPnniInfoRowStatusTable OBJECT-TYPE
   SYNTAX     SEQUENCE OF AtmIfIispAddrPnniInfoRowStatusEntry
   ACCESS     not-accessible
   STATUS     mandatory
   DESCRIPTION
     "This entry controls the addition and deletion of 
      atmIfIispAddrPnniInfo components."
::= { atmIfIispAddrPnniInfo 1 }

atmIfIispAddrPnniInfoRowStatusEntry OBJECT-TYPE
   SYNTAX     AtmIfIispAddrPnniInfoRowStatusEntry
   ACCESS     not-accessible
   STATUS     mandatory
   DESCRIPTION
     "A single entry in the table represents a single 
      atmIfIispAddrPnniInfo component."
   INDEX {
      atmIfIndex,
      atmIfIispIndex,
      atmIfIispAddrAddressIndex,
      atmIfIispAddrAddressTypeIndex,
      atmIfIispAddrPnniInfoIndex }
::= { atmIfIispAddrPnniInfoRowStatusTable 1 }

AtmIfIispAddrPnniInfoRowStatusEntry ::= SEQUENCE {
   atmIfIispAddrPnniInfoRowStatus
      RowStatus,
   atmIfIispAddrPnniInfoComponentName
      DisplayString,
   atmIfIispAddrPnniInfoStorageType
      StorageType,
   atmIfIispAddrPnniInfoIndex
      NonReplicated }

atmIfIispAddrPnniInfoRowStatus OBJECT-TYPE
   SYNTAX     RowStatus 
   ACCESS     read-write
   STATUS     mandatory
   DESCRIPTION
     "This variable is used as the basis for SNMP naming of
      atmIfIispAddrPnniInfo components.
      These components can be added and deleted."
::= { atmIfIispAddrPnniInfoRowStatusEntry 1 }

atmIfIispAddrPnniInfoComponentName OBJECT-TYPE
   SYNTAX     DisplayString 
   ACCESS     read-only
   STATUS     mandatory
   DESCRIPTION
     "This variable provides the component's string name for
      use with the ASCII Console Interface"
::= { atmIfIispAddrPnniInfoRowStatusEntry 2 }

atmIfIispAddrPnniInfoStorageType OBJECT-TYPE
   SYNTAX     StorageType 
   ACCESS     read-only
   STATUS     mandatory
   DESCRIPTION
     "This variable represents the storage type value for the
      atmIfIispAddrPnniInfo tables."
::= { atmIfIispAddrPnniInfoRowStatusEntry 4 }

atmIfIispAddrPnniInfoIndex OBJECT-TYPE
   SYNTAX     NonReplicated 
   ACCESS     not-accessible
   STATUS     mandatory
   DESCRIPTION
     "This variable represents the index for the atmIfIispAddrPnniInfo tables."
::= { atmIfIispAddrPnniInfoRowStatusEntry 10 }

atmIfIispAddrPnniInfoProvTable OBJECT-TYPE
   SYNTAX     SEQUENCE OF AtmIfIispAddrPnniInfoProvEntry
   ACCESS     not-accessible
   STATUS     mandatory
   DESCRIPTION
     "This attribute group contains the provisioned attributes relating to 
      PNNI for a PnniInfo component."
::= { atmIfIispAddrPnniInfo 10 }

atmIfIispAddrPnniInfoProvEntry OBJECT-TYPE
   SYNTAX     AtmIfIispAddrPnniInfoProvEntry
   ACCESS     not-accessible
   STATUS     mandatory
   DESCRIPTION
     "An entry in the atmIfIispAddrPnniInfoProvTable."
   INDEX {
      atmIfIndex,
      atmIfIispIndex,
      atmIfIispAddrAddressIndex,
      atmIfIispAddrAddressTypeIndex,
      atmIfIispAddrPnniInfoIndex }
::= { atmIfIispAddrPnniInfoProvTable 1 }

AtmIfIispAddrPnniInfoProvEntry ::= SEQUENCE {
   atmIfIispAddrPnniInfoScope
      INTEGER,
   atmIfIispAddrPnniInfoReachability
      INTEGER }

atmIfIispAddrPnniInfoScope OBJECT-TYPE
   SYNTAX     INTEGER (-1..104)
   ACCESS     read-write
   STATUS     mandatory
   DESCRIPTION
     "This attribute specifies the scope of the ATM address, which is the 
      highest level up to which this address will be advertised in the 
      PNNI hierarchy. The scope must be set to a value numerically less 
      than or equal to the level of the lowest level peer group containing 
      this node. Setting the scope to 0 will cause the address to be 
      advertised globally within this PNNI routing domain."
   DEFVAL     { -1 }
::= { atmIfIispAddrPnniInfoProvEntry 1 }

atmIfIispAddrPnniInfoReachability OBJECT-TYPE
   SYNTAX     INTEGER  {
                 internal(0),
                 exterior(1) }
   ACCESS     read-write
   STATUS     mandatory
   DESCRIPTION
     "This attribute indicates whether the address is internal or exterior. 
      An internal reachable address is an address of a destination that is 
      directly attached to the logical node advertising the address. An 
      exterior reachable address is an address that can be reached 
      through a PNNI routing domain, but which is not located in that 
      PNNI routing domain."
   DEFVAL     { internal }
::= { atmIfIispAddrPnniInfoProvEntry 2 }


-- AtmIf/n VirtualPathTerminator/m Iisp
-- This component represents a virtual ATM Interim Inter-switch 
-- Signaling Protocol (IISP) interface. If this component is 
-- provisioned, neither a Uni component nor a Pnni component can be 
-- provisioned under the same Vpt component. If this component is 
-- deleted, then all associated Vcc components are deleted.

atmIfVptIisp OBJECT IDENTIFIER ::= { atmIfVpt 6 }



atmIfVptIispRowStatusTable OBJECT-TYPE
   SYNTAX     SEQUENCE OF AtmIfVptIispRowStatusEntry
   ACCESS     not-accessible
   STATUS     mandatory
   DESCRIPTION
     "This entry controls the addition and deletion of 
      atmIfVptIisp components."
::= { atmIfVptIisp 1 }

atmIfVptIispRowStatusEntry OBJECT-TYPE
   SYNTAX     AtmIfVptIispRowStatusEntry
   ACCESS     not-accessible
   STATUS     mandatory
   DESCRIPTION
     "A single entry in the table represents a single 
      atmIfVptIisp component."
   INDEX {
      atmIfIndex,
      atmIfVptIndex,
      atmIfVptIispIndex }
::= { atmIfVptIispRowStatusTable 1 }

AtmIfVptIispRowStatusEntry ::= SEQUENCE {
   atmIfVptIispRowStatus
      RowStatus,
   atmIfVptIispComponentName
      DisplayString,
   atmIfVptIispStorageType
      StorageType,
   atmIfVptIispIndex
      NonReplicated }

atmIfVptIispRowStatus OBJECT-TYPE
   SYNTAX     RowStatus 
   ACCESS     read-write
   STATUS     mandatory
   DESCRIPTION
     "This variable is used as the basis for SNMP naming of
      atmIfVptIisp components.
      These components can be added and deleted."
::= { atmIfVptIispRowStatusEntry 1 }

atmIfVptIispComponentName OBJECT-TYPE
   SYNTAX     DisplayString 
   ACCESS     read-only
   STATUS     mandatory
   DESCRIPTION
     "This variable provides the component's string name for
      use with the ASCII Console Interface"
::= { atmIfVptIispRowStatusEntry 2 }

atmIfVptIispStorageType OBJECT-TYPE
   SYNTAX     StorageType 
   ACCESS     read-only
   STATUS     mandatory
   DESCRIPTION
     "This variable represents the storage type value for the
      atmIfVptIisp tables."
::= { atmIfVptIispRowStatusEntry 4 }

atmIfVptIispIndex OBJECT-TYPE
   SYNTAX     NonReplicated 
   ACCESS     not-accessible
   STATUS     mandatory
   DESCRIPTION
     "This variable represents the index for the atmIfVptIisp tables."
::= { atmIfVptIispRowStatusEntry 10 }

atmIfVptIispProvTable OBJECT-TYPE
   SYNTAX     SEQUENCE OF AtmIfVptIispProvEntry
   ACCESS     not-accessible
   STATUS     mandatory
   DESCRIPTION
     "This group contains the provisionable attributes for the Iisp 
      component."
::= { atmIfVptIisp 10 }

atmIfVptIispProvEntry OBJECT-TYPE
   SYNTAX     AtmIfVptIispProvEntry
   ACCESS     not-accessible
   STATUS     mandatory
   DESCRIPTION
     "An entry in the atmIfVptIispProvTable."
   INDEX {
      atmIfIndex,
      atmIfVptIndex,
      atmIfVptIispIndex }
::= { atmIfVptIispProvTable 1 }

AtmIfVptIispProvEntry ::= SEQUENCE {
   atmIfVptIispVersion
      INTEGER,
   atmIfVptIispSide
      INTEGER,
   atmIfVptIispSoftPvcRetryPeriod
      Unsigned32,
   atmIfVptIispSoftPvpAndPvcRetryPeriod
      Unsigned32,
   atmIfVptIispSoftPvpAndPvcHoldOffTime
      Unsigned32 }

atmIfVptIispVersion OBJECT-TYPE
   SYNTAX     INTEGER  {
                 iisp10Sig30(2),
                 iisp10Sig31(3) }
   ACCESS     read-write
   STATUS     mandatory
   DESCRIPTION
     "This attribute indicates which specification the IISP interface 
      complies with. The options are iisp10Sig30 which refers to IISP 
      version 1.0 with 3.0 signalling and iisp10Sig31 which refers to IISP 
      version 1.0 with 3.1 signalling. If this attribute is changed, all 
      switched Vcc components in this interface are cleared due to the 
      fact that the two versions are incompatible."
   DEFVAL     { iisp10Sig31 }
::= { atmIfVptIispProvEntry 1 }

atmIfVptIispSide OBJECT-TYPE
   SYNTAX     INTEGER  {
                 networkSide(0),
                 userSide(1) }
   ACCESS     read-write
   STATUS     mandatory
   DESCRIPTION
     "This attribute indicates which side the interface is, user or network."
   DEFVAL     { networkSide }
::= { atmIfVptIispProvEntry 2 }

atmIfVptIispSoftPvcRetryPeriod OBJECT-TYPE
   SYNTAX     Unsigned32 (20..999999)
   ACCESS     read-write
   STATUS     obsolete
   DESCRIPTION
     "This attribute specifies the time to wait between call set up retries. 
      The resolution is to the nearest 10 seconds.
      This attribute has been obsoleted and is replaced by the 
      softPvpAndPvcRetryPeriod attribute."
   DEFVAL     { 60 }
::= { atmIfVptIispProvEntry 3 }

atmIfVptIispSoftPvpAndPvcRetryPeriod OBJECT-TYPE
   SYNTAX     Unsigned32 (20..999999)
   ACCESS     read-write
   STATUS     mandatory
   DESCRIPTION
     "This attribute specifies the time to wait between soft PVP or soft 
      PVC call setup retries. The resolution is to the nearest 10 seconds."
   DEFVAL     { 60 }
::= { atmIfVptIispProvEntry 4 }

atmIfVptIispSoftPvpAndPvcHoldOffTime OBJECT-TYPE
   SYNTAX     Unsigned32 (0 | 50..20000)
   ACCESS     read-write
   STATUS     mandatory
   DESCRIPTION
     "This attribute specifies how long to hold off retries following a 
      release or the connection. The resolution is to the nearest 50 ms."
   DEFVAL     { 0 }
::= { atmIfVptIispProvEntry 5 }

atmIfVptIispAcctOptTable OBJECT-TYPE
   SYNTAX     SEQUENCE OF AtmIfVptIispAcctOptEntry
   ACCESS     not-accessible
   STATUS     mandatory
   DESCRIPTION
     "This group contains the provisionable attributes for accounting."
::= { atmIfVptIisp 11 }

atmIfVptIispAcctOptEntry OBJECT-TYPE
   SYNTAX     AtmIfVptIispAcctOptEntry
   ACCESS     not-accessible
   STATUS     mandatory
   DESCRIPTION
     "An entry in the atmIfVptIispAcctOptTable."
   INDEX {
      atmIfIndex,
      atmIfVptIndex,
      atmIfVptIispIndex }
::= { atmIfVptIispAcctOptTable 1 }

AtmIfVptIispAcctOptEntry ::= SEQUENCE {
   atmIfVptIispAccountCollection
      OCTET STRING,
   atmIfVptIispAccountConnectionType
      INTEGER,
   atmIfVptIispAccountClass
      Unsigned32,
   atmIfVptIispServiceExchange
      Unsigned32 }

atmIfVptIispAccountCollection OBJECT-TYPE
   SYNTAX     OCTET STRING (SIZE (1))
   ACCESS     read-write
   STATUS     mandatory
   DESCRIPTION
     "This attribute is used to turn accounting on or off for SVC and 
      SPVC connections. It also specifies the reason(s) for which 
      accounting data is collected: billing, test, study, audit, or force.
      
      If the set of reasons is not empty then accounting records will be 
      generated by this interface in the following situations:
      - on a TODA changeover if TODA is enabled;
      - every 12 hours (per connection) if TODA is disabled;
      - on every call clear (a call record with final cell counts).
      
      If none of the reasons is present, then accounting will be 
      suppressed.
      
      The reason for collection is recorded in the accounting record, in 
      the attribute callingCollectReason or calledCollectReason as 
      appropriate.

      Description of bits:
      bill(0)
      test(1)
      study(2)
      audit(3)
      force(4)"
::= { atmIfVptIispAcctOptEntry 1 }

atmIfVptIispAccountConnectionType OBJECT-TYPE
   SYNTAX     INTEGER  {
                 origTerm(0),
                 intermediate(1) }
   ACCESS     read-write
   STATUS     mandatory
   DESCRIPTION
     "This attribute specifies whether accounting records generated by 
      this interface should be marked as originating, terminating or 
      intermediate. This attribute, in combination with the direction of the 
      call, determines the value of attribute connPointType of the 
      accounting record and may be used by downstream accounting 
      processes to correlate the records.
      
      If the value is origTerm then records generated for incoming calls 
      will be marked as originating and records generated for outgoing 
      calls will be marked as terminating.
      
      If the value is intermediate then records generated for all calls will 
      be marked as intermediate."
   DEFVAL     { intermediate }
::= { atmIfVptIispAcctOptEntry 2 }

atmIfVptIispAccountClass OBJECT-TYPE
   SYNTAX     Unsigned32 (0..255)
   ACCESS     read-write
   STATUS     mandatory
   DESCRIPTION
     "This attribute specifies the accounting class associated with the 
      interface. Its meaning is determined by the network operator.
      
      Its value is simply recorded in the accounting records generated by 
      this interface, in the attribute callingServiceType or 
      calledServiceType as appropriate."
   DEFVAL     { 0 }
::= { atmIfVptIispAcctOptEntry 3 }

atmIfVptIispServiceExchange OBJECT-TYPE
   SYNTAX     Unsigned32 (0..255)
   ACCESS     read-write
   STATUS     mandatory
   DESCRIPTION
     "This attribute specifies the data service exchange associated with 
      this interface. Its meaning is determined by the network operator.
      
      Its value is simply recorded in the accounting records generated by 
      this interface, in the attribute callingDse or calledDse as 
      appropriate."
   DEFVAL     { 0 }
::= { atmIfVptIispAcctOptEntry 4 }

atmIfVptIispVProvTable OBJECT-TYPE
   SYNTAX     SEQUENCE OF AtmIfVptIispVProvEntry
   ACCESS     not-accessible
   STATUS     mandatory
   DESCRIPTION
     "This group contains the provisionable attributes for the Iisp 
      component which are specific to virtual IISP interfaces."
::= { atmIfVptIisp 12 }

atmIfVptIispVProvEntry OBJECT-TYPE
   SYNTAX     AtmIfVptIispVProvEntry
   ACCESS     not-accessible
   STATUS     mandatory
   DESCRIPTION
     "An entry in the atmIfVptIispVProvTable."
   INDEX {
      atmIfIndex,
      atmIfVptIndex,
      atmIfVptIispIndex }
::= { atmIfVptIispVProvTable 1 }

AtmIfVptIispVProvEntry ::= SEQUENCE {
   atmIfVptIispVpci
      Unsigned32 }

atmIfVptIispVpci OBJECT-TYPE
   SYNTAX     Unsigned32 (0..255)
   ACCESS     read-write
   STATUS     mandatory
   DESCRIPTION
     "This attribute specifies the Virtual Path Connection Identifier 
      (VPCI) to be used between this signalling entity and its peer. The 
      VPCI of the peer virtual IISP must have the same value for 
      switched connections to be set up across the interface."
   DEFVAL     { 0 }
::= { atmIfVptIispVProvEntry 1 }


-- AtmIf/n Iisp Signalling
-- AtmIf/n Uni Signalling
-- AtmIf/n Pnni Signalling
-- AtmIf/n Vpt/m Iisp Signalling
-- AtmIf/n Vpt/m Uni Signalling
-- AtmIf/n Vpt/m Pnni Signalling
-- 
-- This component represents the signalling entities for the interface.

atmIfVptIispSig OBJECT IDENTIFIER ::= { atmIfVptIisp 3 }



atmIfVptIispSigRowStatusTable OBJECT-TYPE
   SYNTAX     SEQUENCE OF AtmIfVptIispSigRowStatusEntry
   ACCESS     not-accessible
   STATUS     mandatory
   DESCRIPTION
     "This entry controls the addition and deletion of 
      atmIfVptIispSig components."
::= { atmIfVptIispSig 1 }

atmIfVptIispSigRowStatusEntry OBJECT-TYPE
   SYNTAX     AtmIfVptIispSigRowStatusEntry
   ACCESS     not-accessible
   STATUS     mandatory
   DESCRIPTION
     "A single entry in the table represents a single 
      atmIfVptIispSig component."
   INDEX {
      atmIfIndex,
      atmIfVptIndex,
      atmIfVptIispIndex,
      atmIfVptIispSigIndex }
::= { atmIfVptIispSigRowStatusTable 1 }

AtmIfVptIispSigRowStatusEntry ::= SEQUENCE {
   atmIfVptIispSigRowStatus
      RowStatus,
   atmIfVptIispSigComponentName
      DisplayString,
   atmIfVptIispSigStorageType
      StorageType,
   atmIfVptIispSigIndex
      NonReplicated }

atmIfVptIispSigRowStatus OBJECT-TYPE
   SYNTAX     RowStatus 
   ACCESS     read-only
   STATUS     mandatory
   DESCRIPTION
     "This variable is used as the basis for SNMP naming of
      atmIfVptIispSig components.
      These components cannot be added nor deleted."
::= { atmIfVptIispSigRowStatusEntry 1 }

atmIfVptIispSigComponentName OBJECT-TYPE
   SYNTAX     DisplayString 
   ACCESS     read-only
   STATUS     mandatory
   DESCRIPTION
     "This variable provides the component's string name for
      use with the ASCII Console Interface"
::= { atmIfVptIispSigRowStatusEntry 2 }

atmIfVptIispSigStorageType OBJECT-TYPE
   SYNTAX     StorageType 
   ACCESS     read-only
   STATUS     mandatory
   DESCRIPTION
     "This variable represents the storage type value for the
      atmIfVptIispSig tables."
::= { atmIfVptIispSigRowStatusEntry 4 }

atmIfVptIispSigIndex OBJECT-TYPE
   SYNTAX     NonReplicated 
   ACCESS     not-accessible
   STATUS     mandatory
   DESCRIPTION
     "This variable represents the index for the atmIfVptIispSig tables."
::= { atmIfVptIispSigRowStatusEntry 10 }

atmIfVptIispSigProvTable OBJECT-TYPE
   SYNTAX     SEQUENCE OF AtmIfVptIispSigProvEntry
   ACCESS     not-accessible
   STATUS     mandatory
   DESCRIPTION
     "This attribute group contains the provisionable attributes for the 
      Signalling component."
::= { atmIfVptIispSig 10 }

atmIfVptIispSigProvEntry OBJECT-TYPE
   SYNTAX     AtmIfVptIispSigProvEntry
   ACCESS     not-accessible
   STATUS     mandatory
   DESCRIPTION
     "An entry in the atmIfVptIispSigProvTable."
   INDEX {
      atmIfIndex,
      atmIfVptIndex,
      atmIfVptIispIndex,
      atmIfVptIispSigIndex }
::= { atmIfVptIispSigProvTable 1 }

AtmIfVptIispSigProvEntry ::= SEQUENCE {
   atmIfVptIispSigVci
      Unsigned32,
   atmIfVptIispSigAddressConversion
      INTEGER }

atmIfVptIispSigVci OBJECT-TYPE
   SYNTAX     Unsigned32 (0..65535)
   ACCESS     read-write
   STATUS     mandatory
   DESCRIPTION
     "This attribute specifies the signalling channel number."
   DEFVAL     { 5 }
::= { atmIfVptIispSigProvEntry 1 }

atmIfVptIispSigAddressConversion OBJECT-TYPE
   SYNTAX     INTEGER  {
                 none(0),
                 nativeE164(1),
                 nsap(2) }
   ACCESS     read-write
   STATUS     mandatory
   DESCRIPTION
     "This attribute specifies the address conversion on the outgoing 
      signalling PDUs. The options are none, nativeE164, or nsap. The 
      none option is the default and if this option is chosen then nothing 
      is done to the address information element (IE) in the outgoing 
      signalling message. If nativeE164 option is chosen, then only 
      NSAP encapsulated E.164 addresses with zeros in the ESI are 
      converted to native E.164 format in the outgoing signalling 
      message. If the NSAP address is not encapsulated E.164 or the ESI 
      field is not zeros and the nativeE164 option is chosen, then the call 
      is cleared. If the nsap option is chosen, then native E.164 addresses 
      are converted to NSAP E.164 with zeros in the ESI field; otherwise 
      the address is in NSAP format and is not changed."
   DEFVAL     { none }
::= { atmIfVptIispSigProvEntry 2 }

atmIfVptIispSigStateTable OBJECT-TYPE
   SYNTAX     SEQUENCE OF AtmIfVptIispSigStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { atmIfVptIispSig 11 }

atmIfVptIispSigStateEntry OBJECT-TYPE
   SYNTAX     AtmIfVptIispSigStateEntry
   ACCESS     not-accessible
   STATUS     mandatory
   DESCRIPTION
     "An entry in the atmIfVptIispSigStateTable."
   INDEX {
      atmIfIndex,
      atmIfVptIndex,
      atmIfVptIispIndex,
      atmIfVptIispSigIndex }
::= { atmIfVptIispSigStateTable 1 }

AtmIfVptIispSigStateEntry ::= SEQUENCE {
   atmIfVptIispSigAdminState
      INTEGER,
   atmIfVptIispSigOperationalState
      INTEGER,
   atmIfVptIispSigUsageState
      INTEGER }

atmIfVptIispSigAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { atmIfVptIispSigStateEntry 1 }

atmIfVptIispSigOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { atmIfVptIispSigStateEntry 2 }

atmIfVptIispSigUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { atmIfVptIispSigStateEntry 3 }

atmIfVptIispSigOperTable OBJECT-TYPE
   SYNTAX     SEQUENCE OF AtmIfVptIispSigOperEntry
   ACCESS     not-accessible
   STATUS     mandatory
   DESCRIPTION
     "This attribute contains the operational attributes for the 
      AtmSignalling component."
::= { atmIfVptIispSig 12 }

atmIfVptIispSigOperEntry OBJECT-TYPE
   SYNTAX     AtmIfVptIispSigOperEntry
   ACCESS     not-accessible
   STATUS     mandatory
   DESCRIPTION
     "An entry in the atmIfVptIispSigOperTable."
   INDEX {
      atmIfIndex,
      atmIfVptIndex,
      atmIfVptIispIndex,
      atmIfVptIispSigIndex }
::= { atmIfVptIispSigOperTable 1 }

AtmIfVptIispSigOperEntry ::= SEQUENCE {
   atmIfVptIispSigLastTxCauseCode
      Unsigned32,
   atmIfVptIispSigLastTxDiagCode
      Hex,
   atmIfVptIispSigLastRxCauseCode
      Unsigned32,
   atmIfVptIispSigLastRxDiagCode
      Hex }

atmIfVptIispSigLastTxCauseCode OBJECT-TYPE
   SYNTAX     Unsigned32 (0..255)
   ACCESS     read-only
   STATUS     mandatory
   DESCRIPTION
     "This attribute indicates the cause code in the last transmitted 
      signalling message that contains the CAUSE information element. 
      The cause code is used to describe the reason for generating certain 
      signalling messages."
::= { atmIfVptIispSigOperEntry 1 }

atmIfVptIispSigLastTxDiagCode OBJECT-TYPE
   SYNTAX     Hex (0..255)
   ACCESS     read-only
   STATUS     mandatory
   DESCRIPTION
     "This attribute contains the diagnostic code in the last transmitted 
      signalling message. The diagnostic code is contained in the CAUSE 
      information element and identifies an information element type or 
      timer type. The diagnostic code is present only if a procedural error 
      is detected by the signalling protocol. A diagnostic code is always 
      accompanied by the cause code. If there is no failure, this attribute 
      is set to 0."
::= { atmIfVptIispSigOperEntry 2 }

atmIfVptIispSigLastRxCauseCode OBJECT-TYPE
   SYNTAX     Unsigned32 (0..255)
   ACCESS     read-only
   STATUS     mandatory
   DESCRIPTION
     "This attribute contains the cause code in the last received signalling 
      message that contains the CAUSE information element. The cause 
      code is used to describe the reason for generating certain signalling 
      messages."
::= { atmIfVptIispSigOperEntry 3 }

atmIfVptIispSigLastRxDiagCode OBJECT-TYPE
   SYNTAX     Hex (0..255)
   ACCESS     read-only
   STATUS     mandatory
   DESCRIPTION
     "This attribute contains the diagnostic code in the last received 
      signalling message. The diagnostic code is contained in the CAUSE 
      information element and identifies an information element type or 
      timer type. The diagnostic code is present only if a procedural error 
      is detected by the signalling protocol. A diagnostic code is always 
      accompanied by the cause code. If there is no failure, this attribute 
      is set to 0."
::= { atmIfVptIispSigOperEntry 4 }

atmIfVptIispSigStatsTable OBJECT-TYPE
   SYNTAX     SEQUENCE OF AtmIfVptIispSigStatsEntry
   ACCESS     not-accessible
   STATUS     mandatory
   DESCRIPTION
     "This attribute group contains the statistics associated with the 
      AtmSignalling component."
::= { atmIfVptIispSig 13 }

atmIfVptIispSigStatsEntry OBJECT-TYPE
   SYNTAX     AtmIfVptIispSigStatsEntry
   ACCESS     not-accessible
   STATUS     mandatory
   DESCRIPTION
     "An entry in the atmIfVptIispSigStatsTable."
   INDEX {
      atmIfIndex,
      atmIfVptIndex,
      atmIfVptIispIndex,
      atmIfVptIispSigIndex }
::= { atmIfVptIispSigStatsTable 1 }

AtmIfVptIispSigStatsEntry ::= SEQUENCE {
   atmIfVptIispSigCurrentConnections
      Counter32,
   atmIfVptIispSigPeakConnections
      Gauge32,
   atmIfVptIispSigSuccessfulConnections
      Counter32,
   atmIfVptIispSigFailedConnections
      Counter32,
   atmIfVptIispSigTxPdus
      Counter32,
   atmIfVptIispSigRxPdus
      Counter32,
   atmIfVptIispSigCurrentPmpConnections
      Gauge32,
   atmIfVptIispSigPeakPmpConnections
      Gauge32,
   atmIfVptIispSigSuccessfulPmpConnections
      Counter32,
   atmIfVptIispSigFailedPmpConnections
      Counter32,
   atmIfVptIispSigNewCurrentConnections
      Gauge32 }

atmIfVptIispSigCurrentConnections OBJECT-TYPE
   SYNTAX     Counter32 
   ACCESS     read-only
   STATUS     obsolete
   DESCRIPTION
     "This attribute indicates the total number of currently active 
      connections."
::= { atmIfVptIispSigStatsEntry 1 }

atmIfVptIispSigPeakConnections OBJECT-TYPE
   SYNTAX     Gauge32 (0..4294967295)
   ACCESS     read-only
   STATUS     mandatory
   DESCRIPTION
     "This attribute indicates the high water mark of active point-to-
      point and point-to-multipoint connections."
::= { atmIfVptIispSigStatsEntry 2 }

atmIfVptIispSigSuccessfulConnections OBJECT-TYPE
   SYNTAX     Counter32 
   ACCESS     read-only
   STATUS     mandatory
   DESCRIPTION
     "This attribute counts the total number of switched point-to-
      point and point-to-multipoint connections that were successfully 
      established. The counter wraps to 0 when the maximum value is 
      exceeded."
::= { atmIfVptIispSigStatsEntry 3 }

atmIfVptIispSigFailedConnections OBJECT-TYPE
   SYNTAX     Counter32 
   ACCESS     read-only
   STATUS     mandatory
   DESCRIPTION
     "This attribute counts the total number of switched connections that 
      were not successfully established.The counter wraps to 0 when the 
      maximum value is exceeded."
::= { atmIfVptIispSigStatsEntry 4 }

atmIfVptIispSigTxPdus OBJECT-TYPE
   SYNTAX     Counter32 
   ACCESS     read-only
   STATUS     mandatory
   DESCRIPTION
     "This attribute counts the number of transmitted signalling 
      PDUs.The counter wraps to 0 when the maximum value is 
      exceeded."
::= { atmIfVptIispSigStatsEntry 5 }

atmIfVptIispSigRxPdus OBJECT-TYPE
   SYNTAX     Counter32 
   ACCESS     read-only
   STATUS     mandatory
   DESCRIPTION
     "This attribute counts the number of received signalling PDUs.The 
      counter wraps to 0 when the maximum value is exceeded."
::= { atmIfVptIispSigStatsEntry 6 }

atmIfVptIispSigCurrentPmpConnections OBJECT-TYPE
   SYNTAX     Gauge32 (0..4294967295)
   ACCESS     read-only
   STATUS     mandatory
   DESCRIPTION
     "This attribute indicates the number of currently active point-to-
      multipoint connections."
::= { atmIfVptIispSigStatsEntry 7 }

atmIfVptIispSigPeakPmpConnections OBJECT-TYPE
   SYNTAX     Gauge32 (0..4294967295)
   ACCESS     read-only
   STATUS     mandatory
   DESCRIPTION
     "This attribute indicates the high water mark of active point-to-
      multipoint connections."
::= { atmIfVptIispSigStatsEntry 8 }

atmIfVptIispSigSuccessfulPmpConnections OBJECT-TYPE
   SYNTAX     Counter32 
   ACCESS     read-only
   STATUS     mandatory
   DESCRIPTION
     "This attribute counts the total number of switched point-to-
      multipoint connections that were successfully established. 
      The counter wraps to 0 when the maximum value is 
      exceeded."
::= { atmIfVptIispSigStatsEntry 9 }

atmIfVptIispSigFailedPmpConnections OBJECT-TYPE
   SYNTAX     Counter32 
   ACCESS     read-only
   STATUS     mandatory
   DESCRIPTION
     "This attribute counts the number of switched point-to-
      multipoint connections that were not successfully 
      established.The counter wraps to 0 when the maximum value 
      is exceeded."
::= { atmIfVptIispSigStatsEntry 10 }

atmIfVptIispSigNewCurrentConnections OBJECT-TYPE
   SYNTAX     Gauge32 (0..4294967295)
   ACCESS     read-only
   STATUS     mandatory
   DESCRIPTION
     "This attribute indicates the total number of currently active point-to-
      point and point-to-multipoint connections."
::= { atmIfVptIispSigStatsEntry 11 }


-- AtmIf/n Uni Sig VirtualChannelDescriptor
-- AtmIf/n Uni Ilmi VirtualChannelDescriptor
-- AtmIf/n Iisp Sig VirtualChannelDescriptor
-- AtmIf/n Pnni Sig VirtualChannelDescriptor
-- AtmIf/n Pnni Rcc VirtualChannelDescriptor
-- AtmIf/n Vpt/m Uni Sig VirtualChannelDescriptor
-- AtmIf/n Vpt/m Iisp Sig VirtualChannelDescriptor
-- AtmIf/n Vpt/m Pnni Sig VirtualChannelDescriptor
-- AtmIf/n Vpt/m Pnni Rcc VirtualChannelDescriptor
-- 
-- This component contains the provisionable traffic parameters for a 
-- control channel (Sig, Ilmi or Rcc component).

atmIfVptIispSigVcd OBJECT IDENTIFIER ::= { atmIfVptIispSig 2 }



atmIfVptIispSigVcdRowStatusTable OBJECT-TYPE
   SYNTAX     SEQUENCE OF AtmIfVptIispSigVcdRowStatusEntry
   ACCESS     not-accessible
   STATUS     mandatory
   DESCRIPTION
     "This entry controls the addition and deletion of 
      atmIfVptIispSigVcd components."
::= { atmIfVptIispSigVcd 1 }

atmIfVptIispSigVcdRowStatusEntry OBJECT-TYPE
   SYNTAX     AtmIfVptIispSigVcdRowStatusEntry
   ACCESS     not-accessible
   STATUS     mandatory
   DESCRIPTION
     "A single entry in the table represents a single 
      atmIfVptIispSigVcd component."
   INDEX {
      atmIfIndex,
      atmIfVptIndex,
      atmIfVptIispIndex,
      atmIfVptIispSigIndex,
      atmIfVptIispSigVcdIndex }
::= { atmIfVptIispSigVcdRowStatusTable 1 }

AtmIfVptIispSigVcdRowStatusEntry ::= SEQUENCE {
   atmIfVptIispSigVcdRowStatus
      RowStatus,
   atmIfVptIispSigVcdComponentName
      DisplayString,
   atmIfVptIispSigVcdStorageType
      StorageType,
   atmIfVptIispSigVcdIndex
      NonReplicated }

atmIfVptIispSigVcdRowStatus OBJECT-TYPE
   SYNTAX     RowStatus 
   ACCESS     read-write
   STATUS     mandatory
   DESCRIPTION
     "This variable is used as the basis for SNMP naming of
      atmIfVptIispSigVcd components.
      These components can be added and deleted."
::= { atmIfVptIispSigVcdRowStatusEntry 1 }

atmIfVptIispSigVcdComponentName OBJECT-TYPE
   SYNTAX     DisplayString 
   ACCESS     read-only
   STATUS     mandatory
   DESCRIPTION
     "This variable provides the component's string name for
      use with the ASCII Console Interface"
::= { atmIfVptIispSigVcdRowStatusEntry 2 }

atmIfVptIispSigVcdStorageType OBJECT-TYPE
   SYNTAX     StorageType 
   ACCESS     read-only
   STATUS     mandatory
   DESCRIPTION
     "This variable represents the storage type value for the
      atmIfVptIispSigVcd tables."
::= { atmIfVptIispSigVcdRowStatusEntry 4 }

atmIfVptIispSigVcdIndex OBJECT-TYPE
   SYNTAX     NonReplicated 
   ACCESS     not-accessible
   STATUS     mandatory
   DESCRIPTION
     "This variable represents the index for the atmIfVptIispSigVcd tables."
::= { atmIfVptIispSigVcdRowStatusEntry 10 }

atmIfVptIispSigVcdProvTable OBJECT-TYPE
   SYNTAX     SEQUENCE OF AtmIfVptIispSigVcdProvEntry
   ACCESS     not-accessible
   STATUS     mandatory
   DESCRIPTION
     "This group contains the provisionable traffic attributes for a control 
      channel."
::= { atmIfVptIispSigVcd 10 }

atmIfVptIispSigVcdProvEntry OBJECT-TYPE
   SYNTAX     AtmIfVptIispSigVcdProvEntry
   ACCESS     not-accessible
   STATUS     mandatory
   DESCRIPTION
     "An entry in the atmIfVptIispSigVcdProvTable."
   INDEX {
      atmIfIndex,
      atmIfVptIndex,
      atmIfVptIispIndex,
      atmIfVptIispSigIndex,
      atmIfVptIispSigVcdIndex }
::= { atmIfVptIispSigVcdProvTable 1 }

AtmIfVptIispSigVcdProvEntry ::= SEQUENCE {
   atmIfVptIispSigVcdTrafficDescType
      INTEGER,
   atmIfVptIispSigVcdAtmServiceCategory
      INTEGER,
   atmIfVptIispSigVcdQosClass
      INTEGER,
   atmIfVptIispSigVcdTrafficShaping
      INTEGER,
   atmIfVptIispSigVcdUnshapedTransmitQueueing
      INTEGER,
   atmIfVptIispSigVcdUsageParameterControl
      INTEGER }

atmIfVptIispSigVcdTrafficDescType OBJECT-TYPE
   SYNTAX     INTEGER  {
                 n3(3),
                 n6(6),
                 n7(7),
                 n8(8) }
   ACCESS     read-write
   STATUS     mandatory
   DESCRIPTION
     "This attribute specifies the type of traffic management which is 
      applied to both the transmit and receive direction of this connection 
      as defined in the ATM Forum. The trafficDescType determines the 
      number and meaning of the parameters in the trafficDescParm 
      attribute."
   DEFVAL     { n6 }
::= { atmIfVptIispSigVcdProvEntry 1 }

atmIfVptIispSigVcdAtmServiceCategory OBJECT-TYPE
   SYNTAX     INTEGER  {
                 unspecifiedBitRate(0),
                 constantBitRate(1),
                 rtVariableBitRate(2),
                 nrtVariableBitRate(3) }
   ACCESS     read-write
   STATUS     mandatory
   DESCRIPTION
     "This attribute specifies the ATM service category for both directions 
      of the connection. 
      
      The constantBitRate service category is intended for real time 
      applications, that is those requiring tightly constrained delay and 
      delay variation, as would be appropriate for voice and video 
      applications. The consistent availability of a fixed quantity of 
      bandwidth is considered appropriate for CBR service. Cells which 
      are delayed beyond the value specified by CellTransfer Delay are 
      assumed to be of significantly reduce value to the application.
      
      The rtVariableBitRate service category is intended for real time 
      applications, that is those requiring tightly constrained delay and 
      delay variation, as would be appropriate for voice and video 
      applications. Sources are expected to transmit at a rate which varies 
      with time. Equivalently, the source can be described as 'bursty'. 
      Cells which are delayed beyond the value specified by CTD are 
      assumed to be of significantly reduced value to the application. Real 
      time VBR service may support statistical multiplexing of real time 
      sources.
      
      The nrtVariableBitRate service category is intended for non-real 
      time applications which have bursty traffic characteristics and which 
      can be characterized in terms of a PCR, SCR, and MBS. For those 
      cells which are transferred within the traffic contract, the application 
      expects a low cell loss ratio. For all connections, it expects a bound 
      on the mean cell transfer delay. Non-real time VBR service may 
      support statistical multiplexing of connections.
      
      The unspecifiedBitRate service is intended for non-real time 
      applications; that is, those not requiring tightly constrained delay 
      and delay variation. UBR sources are expected to be bursty. UBR 
      service supports a high degree of statistical multiplexing among 
      sources. UBR service does not specify traffic related service 
      guarantees. No numerical commitments are made with respect to 
      the cell loss ratio experienced by a UBR connection, or as to the 
      cell transfer delay experienced by cells on the connection."
   DEFVAL     { rtVariableBitRate }
::= { atmIfVptIispSigVcdProvEntry 3 }

atmIfVptIispSigVcdQosClass OBJECT-TYPE
   SYNTAX     INTEGER  {
                 n0(0),
                 n1(1),
                 n2(2),
                 n3(3),
                 n4(4) }
   ACCESS     read-write
   STATUS     mandatory
   DESCRIPTION
     "This attribute specifies the quality of service for both the forward 
      and backward direction for this connection.
      
      Class 1 supports a QOS that meets Service Class A performance 
      requirements (Circuit emulation, constant bit rate video).
      
      Class 2 supports a QOS that meets Service Class B performance 
      requirements (Variable bit rate audio and video).
      
      Class 3 supports a QOS that meets Service Class C performance 
      requirements (Connection-Oriented Data Transfer).
      
      Class 4 supports a QOS that meets Service Class D performance 
      requirements (Connectionless Data Transfer).
      
      Class 0 is the unspecified bit rate QOS class; no objective is 
      specified for the performance parameters."
   DEFVAL     { n2 }
::= { atmIfVptIispSigVcdProvEntry 21 }

atmIfVptIispSigVcdTrafficShaping OBJECT-TYPE
   SYNTAX     INTEGER  {
                 disabled(1),
                 sameAsCa(2) }
   ACCESS     read-write
   STATUS     mandatory
   DESCRIPTION
     "This attribute specifies whether this connection uses traffic shaping 
      when transmitting traffic to the ATM interface.
      
      When sameAsCa is selected, traffic shaping for this connection is 
      based on the trafficShaping attribute of the connection's service 
      category component under the AtmIf CA. If the service category has 
      traffic shaping enabled, then traffic shaping is enabled for the 
      connection. Note that enabling traffic shaping may have no effect 
      under certain cases. These cases are listed in the description of the 
      trafficShaping operational attribute, which is under the Vcc Tm and 
      Vpc Tm components.
      
      When disabled is selected, traffic shaping for this connection is 
      disabled."
   DEFVAL     { disabled }
::= { atmIfVptIispSigVcdProvEntry 50 }

atmIfVptIispSigVcdUnshapedTransmitQueueing OBJECT-TYPE
   SYNTAX     INTEGER  {
                 common(1),
                 sameAsCa(3) }
   ACCESS     read-write
   STATUS     mandatory
   DESCRIPTION
     "This attribute only applies when this connection is unshaped. This 
      attribute specifies the transmit queueing method for this connection 
      if it is unshaped. Refer to the unshapedTransmitQueueing attribute 
      under the AtmIf CA service category subcomponent for more details 
      on the meaning of this attribute. 
      
      When this attribute is set to sameAsCa, the transmit queueing 
      method for the connection is based on the 
      unshapedTransmitQueueing attribute of the connection's service 
      category component under the ConnectionAdministrator. 
      
      When this attribute is set to common, transmit traffic on this 
      unshaped connection is destined for the common queue. 
      
      The value sameAsInterface is for migration from previous software 
      releases, but should no longer be used"
   DEFVAL     { sameAsCa }
::= { atmIfVptIispSigVcdProvEntry 60 }

atmIfVptIispSigVcdUsageParameterControl OBJECT-TYPE
   SYNTAX     INTEGER  {
                 disabled(1),
                 sameAsCa(2) }
   ACCESS     read-write
   STATUS     mandatory
   DESCRIPTION
     "This attribute specifies whether this connection enforces usage 
      parameter control when receiving traffic from the ATM interface.
      
      When sameAsCa is selected, UPC for the connection is based on 
      the usageParameterControl attribute of the connection's service 
      category component under the ConnectionAdministrator. If the 
      service category has UPC enabled, then UPC is enabled for the 
      connection. Note that enabling UPC may have no effect under 
      certain cases. These cases are listed in the description of the 
      usageParameterControl operational attribute, which is under the 
      Vcc Tm or Vpc Tm component.
      
      When disabled is selected, UPC for this connection is disabled.
      
      The value sameAsInterface is for migration from previous software 
      releases, but should no longer be used"
   DEFVAL     { disabled }
::= { atmIfVptIispSigVcdProvEntry 70 }

atmIfVptIispSigVcdTdpTable OBJECT-TYPE
   SYNTAX     SEQUENCE OF AtmIfVptIispSigVcdTdpEntry
   ACCESS     not-accessible
   STATUS     mandatory
   DESCRIPTION
     "This attribute is a vector of five traffic parameters whose meanings 
      are defined by the trafficDescType attribute. The values of peak cell 
      rate (PCR), sustained cell rate (SCR) and requested shaping rate are 
      expressed in cell/s. Maximum burst size (MBS) is expressed in 
      cells. CDVT is expressed in microseconds. The values of PCR, 
      SCR, MBS and CDVT are used for connection admission control 
      (CAC). The value of CDVT is only used for connections where the 
      atmServiceCategory is constantBitRate. For all other values of 
      atmServiceCategory, CDVT is ignored. The values of PCR, SCR 
      and requested shaping rate are used to determine the actual shaping 
      rate where traffic shaping is enabled.
      
      When trafficDescType is 3, parameter 1 represents the PCR for CLP 
      equal to 0 and 1 traffic; parameter 4 represents the CDVT; and 
      parameter 5 represents the requested shaping rate. A non-zero value 
      in parameter 5 overrides any value in parameter 1. This result is 
      used as the PCR. Parameter 1 must be non-zero. Parameters 2 and 3 
      must be zero.
      
      When trafficDescType is 6, parameter 1 represents the PCR for CLP 
      equal to 0 and 1 traffic; parameter 2 represents the SCR for CLP 
      equal to 0 and 1 traffic; parameter 3 represents the MBS for CLP 
      equal to 0 and 1 traffic; parameter 4 represents the CDVT; and 
      parameter 5 represents the requested shaping rate. A non-zero value 
      in parameter 5 overrides any value in parameter 1. This result is 
      used as the PCR. Parameters 1, 2, and 3 must be non-zero. 
      Parameter 1 must be greater than or equal to parameter 2. Parameter 
      5 must either be zero (unused) or greater than or equal to parameter 
      2.
      
      When trafficDescType is 7, parameter 1 represents the PCR for CLP 
      equal to 0 and 1 traffic; parameter 2 represents the SCR for CLP 
      equal to 0 with cell discard; parameter 3 represents the MBS for 
      CLP equal to 0 traffic; parameter 4 represents the CDVT; and 
      parameter 5 represents the requested shaping rate. A non-zero value 
      in parameter 5 overrides any value in parameter 1. This result is 
      used as the PCR. Parameters 1, 2, and 3 must be non-zero. 
      Parameter 1 must be greater than or equal to parameter 2. Parameter 
      5 must either be zero (unused) or greater than or equal to parameter 
      2.
      
      When trafficDescType is 8, parameter 1 represents the PCR for CLP 
      equal to 0 and 1 traffic; parameter 2 represents the SCR for CLP 
      equal to 0 traffic with cell tagging; parameter 3 represents the MBS 
      for CLP equal to 0 traffic; parameter 4 represents the CDVT; and 
      parameter 5 represents the requested shaping rate. A non-zero value 
      in parameter 5 overrides any value in parameter 1. This result is 
      used as the PCR. Parameters 1, 2, and 3 must be non-zero. 
      Parameter 1 must be greater than or equal to parameter 2. Parameter 
      5 must either be zero (unused) or greater than or equal to parameter 
      2.
      
      Whenever it is valid for PCR to be specified, parameter 5 may also 
      be used to specify a requested shaping rate. A non-zero value in 
      parameter 5 overrides the value in parameter 1 and is used as the 
      peak cell rate in calculations of CAC and shaping rate.
      
      For trafficDescType 3 the traffic is shaped at the next rate less than 
      the PCR. 
      
      For trafficDescType 6, 7, and 8, the traffic is shaped at the highest 
      available rate which is between PCR and SCR. However, if there is 
      no available shaping rate between PCR and SCR, traffic is shaped at 
      the next rate above the PCR."
::= { atmIfVptIispSigVcd 387 }

atmIfVptIispSigVcdTdpEntry OBJECT-TYPE
   SYNTAX     AtmIfVptIispSigVcdTdpEntry
   ACCESS     not-accessible
   STATUS     mandatory
   DESCRIPTION
     "An entry in the atmIfVptIispSigVcdTdpTable."
   INDEX {
      atmIfIndex,
      atmIfVptIndex,
      atmIfVptIispIndex,
      atmIfVptIispSigIndex,
      atmIfVptIispSigVcdIndex,
      atmIfVptIispSigVcdTdpIndex }
::= { atmIfVptIispSigVcdTdpTable 1 }

AtmIfVptIispSigVcdTdpEntry ::= SEQUENCE {
   atmIfVptIispSigVcdTdpIndex
      Integer32,
   atmIfVptIispSigVcdTdpValue
      Unsigned32 }

atmIfVptIispSigVcdTdpIndex OBJECT-TYPE
   SYNTAX     Integer32 (1..5)
   ACCESS     not-accessible
   STATUS     mandatory
   DESCRIPTION
     "This variable represents the atmIfVptIispSigVcdTdpTable
      specific index for the atmIfVptIispSigVcdTdpTable."
::= { atmIfVptIispSigVcdTdpEntry 1 }

atmIfVptIispSigVcdTdpValue OBJECT-TYPE
   SYNTAX     Unsigned32 (0..2147483647)
   ACCESS     read-write
   STATUS     mandatory
   DESCRIPTION
     "This variable represents an individual value for the
      atmIfVptIispSigVcdTdpTable."
::= { atmIfVptIispSigVcdTdpEntry 2 }


-- AtmIf/n Iisp Address/address,type
-- AtmIf/n Uni Address/address,type
-- AtmIf/n Pnni Address/address,type
-- AtmIf/n Vpt/m Iisp Address/address,type
-- AtmIf/n Vpt/m Uni Address/address,type
-- AtmIf/n Vpt/m Pnni Address/address,type
-- 
-- This component represents an address (dynamic or static) 
-- associated with the interface. The index is a string of 1 to 40 hex 
-- digits or a single wildcard ('?'), and a type. The type identifies 
-- whether the Address component is for a primary, alternate, 
-- registered, or default address. 
-- 
-- The types primary and alternate are used for provisioned addresses. 
-- The type registered is used for dynamic addresses registered 
-- through ILMI. The type default is used for Soft PVP and Soft PVC 
-- addresses.Virtual interfaces do not have addresses of 
-- type default.
-- 
-- The wildcard is only valid for provisioned addresses. If the address 
-- is a single wildcard, then that indicates that the interface supports 
-- all addresses. If there is no better match, then this interface may be 
-- chosen in the routing. If there is more than one interface with a 
-- single wildcard static address, then the choice is driven through a 
-- round robin algorithm. 
-- 
-- The round robin algorithm tries the primary routes and then the 
-- alternate routes if none of the primary routes succeed.
-- If this node participates in a PNNI hierarchy, then a PnniInfo 
-- subcomponent can be provisioned under the AtmAddress 
-- component to specify the level to which this address will be 
-- advertised.

atmIfVptIispAddr OBJECT IDENTIFIER ::= { atmIfVptIisp 4 }



atmIfVptIispAddrRowStatusTable OBJECT-TYPE
   SYNTAX     SEQUENCE OF AtmIfVptIispAddrRowStatusEntry
   ACCESS     not-accessible
   STATUS     mandatory
   DESCRIPTION
     "This entry controls the addition and deletion of 
      atmIfVptIispAddr components."
::= { atmIfVptIispAddr 1 }

atmIfVptIispAddrRowStatusEntry OBJECT-TYPE
   SYNTAX     AtmIfVptIispAddrRowStatusEntry
   ACCESS     not-accessible
   STATUS     mandatory
   DESCRIPTION
     "A single entry in the table represents a single 
      atmIfVptIispAddr component."
   INDEX {
      atmIfIndex,
      atmIfVptIndex,
      atmIfVptIispIndex,
      atmIfVptIispAddrAddressIndex,
      atmIfVptIispAddrAddressTypeIndex }
::= { atmIfVptIispAddrRowStatusTable 1 }

AtmIfVptIispAddrRowStatusEntry ::= SEQUENCE {
   atmIfVptIispAddrRowStatus
      RowStatus,
   atmIfVptIispAddrComponentName
      DisplayString,
   atmIfVptIispAddrStorageType
      StorageType,
   atmIfVptIispAddrAddressIndex
      AsciiStringIndex,
   atmIfVptIispAddrAddressTypeIndex
      INTEGER }

atmIfVptIispAddrRowStatus OBJECT-TYPE
   SYNTAX     RowStatus 
   ACCESS     read-write
   STATUS     mandatory
   DESCRIPTION
     "This variable is used as the basis for SNMP naming of
      atmIfVptIispAddr components.
      These components can be added and deleted."
::= { atmIfVptIispAddrRowStatusEntry 1 }

atmIfVptIispAddrComponentName OBJECT-TYPE
   SYNTAX     DisplayString 
   ACCESS     read-only
   STATUS     mandatory
   DESCRIPTION
     "This variable provides the component's string name for
      use with the ASCII Console Interface"
::= { atmIfVptIispAddrRowStatusEntry 2 }

atmIfVptIispAddrStorageType OBJECT-TYPE
   SYNTAX     StorageType 
   ACCESS     read-only
   STATUS     mandatory
   DESCRIPTION
     "This variable represents the storage type value for the
      atmIfVptIispAddr tables."
::= { atmIfVptIispAddrRowStatusEntry 4 }

atmIfVptIispAddrAddressIndex OBJECT-TYPE
   SYNTAX     AsciiStringIndex (SIZE (1..40))
   ACCESS     not-accessible
   STATUS     mandatory
   DESCRIPTION
     "This variable represents an index for the atmIfVptIispAddr tables."
::= { atmIfVptIispAddrRowStatusEntry 10 }

atmIfVptIispAddrAddressTypeIndex OBJECT-TYPE
   SYNTAX     INTEGER  {
                 primary(0),
                 alternate(1),
                 default(3) }
   ACCESS     not-accessible
   STATUS     mandatory
   DESCRIPTION
     "This variable represents an index for the atmIfVptIispAddr tables."
::= { atmIfVptIispAddrRowStatusEntry 11 }

atmIfVptIispAddrOperTable OBJECT-TYPE
   SYNTAX     SEQUENCE OF AtmIfVptIispAddrOperEntry
   ACCESS     not-accessible
   STATUS     mandatory
   DESCRIPTION
     "This attribute group contains the operational attributes for the 
      Address component."
::= { atmIfVptIispAddr 10 }

atmIfVptIispAddrOperEntry OBJECT-TYPE
   SYNTAX     AtmIfVptIispAddrOperEntry
   ACCESS     not-accessible
   STATUS     mandatory
   DESCRIPTION
     "An entry in the atmIfVptIispAddrOperTable."
   INDEX {
      atmIfIndex,
      atmIfVptIndex,
      atmIfVptIispIndex,
      atmIfVptIispAddrAddressIndex,
      atmIfVptIispAddrAddressTypeIndex }
::= { atmIfVptIispAddrOperTable 1 }

AtmIfVptIispAddrOperEntry ::= SEQUENCE {
   atmIfVptIispAddrScope
      INTEGER,
   atmIfVptIispAddrReachability
      INTEGER }

atmIfVptIispAddrScope OBJECT-TYPE
   SYNTAX     INTEGER (-1..104)
   ACCESS     read-only
   STATUS     mandatory
   DESCRIPTION
     "This attribute indicates the scope of the ATM address, which is the 
      highest level to which this address will be advertised in the PNNI 
      hierarchy. If no PnniInfo subcomponent has been provisioned, then 
      the scope will default to the level of this node in the PNNI 
      hierarchy. If this node does not participate in a PNNI hierarchy, then 
      this attribute will have the value of -1."
::= { atmIfVptIispAddrOperEntry 1 }

atmIfVptIispAddrReachability OBJECT-TYPE
   SYNTAX     INTEGER  {
                 internal(0),
                 exterior(1) }
   ACCESS     read-only
   STATUS     mandatory
   DESCRIPTION
     "This attribute indicates whether the address is internal or exterior. 
      An internal reachable address is an address of a destination that is 
      directly attached to the logical node advertising the address. An 
      exterior reachable address is an address that can be reached 
      through a PNNI routing domain, but which is not located in that 
      PNNI routing domain."
::= { atmIfVptIispAddrOperEntry 2 }


-- AtmIf/n Iisp Address/address,type TerminateSPvpAndSPvc
-- AtmIf/n Uni Address/address,type TerminateSPvpAndSPvc
-- AtmIf/n Pnni Address/address,type TerminateSPvpAndSPvc
-- AtmIf/n Vpt/m Iisp Address/address,type TerminateSPvpAndSPvc
-- AtmIf/n Vpt/m Uni Address/address,type TerminateSPvpAndSPvc
-- AtmIf/n Vpt/m Pnni Address/address,type TerminateSPvpAndSPvc
-- 
-- The presence of this subcomponent indicates that SPvp and SPvc 
-- call setups terminate at this node if the destination address of the 
-- SPVP or SPVC matches the Address instance.

atmIfVptIispAddrTermSP OBJECT IDENTIFIER ::= { atmIfVptIispAddr 2 }



atmIfVptIispAddrTermSPRowStatusTable OBJECT-TYPE
   SYNTAX     SEQUENCE OF AtmIfVptIispAddrTermSPRowStatusEntry
   ACCESS     not-accessible
   STATUS     mandatory
   DESCRIPTION
     "This entry controls the addition and deletion of 
      atmIfVptIispAddrTermSP components."
::= { atmIfVptIispAddrTermSP 1 }

atmIfVptIispAddrTermSPRowStatusEntry OBJECT-TYPE
   SYNTAX     AtmIfVptIispAddrTermSPRowStatusEntry
   ACCESS     not-accessible
   STATUS     mandatory
   DESCRIPTION
     "A single entry in the table represents a single 
      atmIfVptIispAddrTermSP component."
   INDEX {
      atmIfIndex,
      atmIfVptIndex,
      atmIfVptIispIndex,
      atmIfVptIispAddrAddressIndex,
      atmIfVptIispAddrAddressTypeIndex,
      atmIfVptIispAddrTermSPIndex }
::= { atmIfVptIispAddrTermSPRowStatusTable 1 }

AtmIfVptIispAddrTermSPRowStatusEntry ::= SEQUENCE {
   atmIfVptIispAddrTermSPRowStatus
      RowStatus,
   atmIfVptIispAddrTermSPComponentName
      DisplayString,
   atmIfVptIispAddrTermSPStorageType
      StorageType,
   atmIfVptIispAddrTermSPIndex
      NonReplicated }

atmIfVptIispAddrTermSPRowStatus OBJECT-TYPE
   SYNTAX     RowStatus 
   ACCESS     read-write
   STATUS     mandatory
   DESCRIPTION
     "This variable is used as the basis for SNMP naming of
      atmIfVptIispAddrTermSP components.
      These components can be added and deleted."
::= { atmIfVptIispAddrTermSPRowStatusEntry 1 }

atmIfVptIispAddrTermSPComponentName OBJECT-TYPE
   SYNTAX     DisplayString 
   ACCESS     read-only
   STATUS     mandatory
   DESCRIPTION
     "This variable provides the component's string name for
      use with the ASCII Console Interface"
::= { atmIfVptIispAddrTermSPRowStatusEntry 2 }

atmIfVptIispAddrTermSPStorageType OBJECT-TYPE
   SYNTAX     StorageType 
   ACCESS     read-only
   STATUS     mandatory
   DESCRIPTION
     "This variable represents the storage type value for the
      atmIfVptIispAddrTermSP tables."
::= { atmIfVptIispAddrTermSPRowStatusEntry 4 }

atmIfVptIispAddrTermSPIndex OBJECT-TYPE
   SYNTAX     NonReplicated 
   ACCESS     not-accessible
   STATUS     mandatory
   DESCRIPTION
     "This variable represents the index for the atmIfVptIispAddrTermSP tables."
::= { atmIfVptIispAddrTermSPRowStatusEntry 10 }


-- AtmIf/n Iisp Addr/address,type PnniInfo
-- AtmIf/n Uni Addr/address,type PnniInfo
-- AtmIf/n Pnni Addr/address,type PnniInfo
-- AtmIf/n Vpt/m Iisp Addr/address,type PnniInfo
-- AtmIf/n Vpt/m Uni Addr/address,type PnniInfo
-- AtmIf/n Vpt/m Pnni Addr/address,type PnniInfo
-- 
-- This component contains provisioned information associated with 
-- the ATM address related to PNNI. This component appears only 
-- under provisioned Address components.

atmIfVptIispAddrPnniInfo OBJECT IDENTIFIER ::= { atmIfVptIispAddr 3 }



atmIfVptIispAddrPnniInfoRowStatusTable OBJECT-TYPE
   SYNTAX     SEQUENCE OF AtmIfVptIispAddrPnniInfoRowStatusEntry
   ACCESS     not-accessible
   STATUS     mandatory
   DESCRIPTION
     "This entry controls the addition and deletion of 
      atmIfVptIispAddrPnniInfo components."
::= { atmIfVptIispAddrPnniInfo 1 }

atmIfVptIispAddrPnniInfoRowStatusEntry OBJECT-TYPE
   SYNTAX     AtmIfVptIispAddrPnniInfoRowStatusEntry
   ACCESS     not-accessible
   STATUS     mandatory
   DESCRIPTION
     "A single entry in the table represents a single 
      atmIfVptIispAddrPnniInfo component."
   INDEX {
      atmIfIndex,
      atmIfVptIndex,
      atmIfVptIispIndex,
      atmIfVptIispAddrAddressIndex,
      atmIfVptIispAddrAddressTypeIndex,
      atmIfVptIispAddrPnniInfoIndex }
::= { atmIfVptIispAddrPnniInfoRowStatusTable 1 }

AtmIfVptIispAddrPnniInfoRowStatusEntry ::= SEQUENCE {
   atmIfVptIispAddrPnniInfoRowStatus
      RowStatus,
   atmIfVptIispAddrPnniInfoComponentName
      DisplayString,
   atmIfVptIispAddrPnniInfoStorageType
      StorageType,
   atmIfVptIispAddrPnniInfoIndex
      NonReplicated }

atmIfVptIispAddrPnniInfoRowStatus OBJECT-TYPE
   SYNTAX     RowStatus 
   ACCESS     read-write
   STATUS     mandatory
   DESCRIPTION
     "This variable is used as the basis for SNMP naming of
      atmIfVptIispAddrPnniInfo components.
      These components can be added and deleted."
::= { atmIfVptIispAddrPnniInfoRowStatusEntry 1 }

atmIfVptIispAddrPnniInfoComponentName OBJECT-TYPE
   SYNTAX     DisplayString 
   ACCESS     read-only
   STATUS     mandatory
   DESCRIPTION
     "This variable provides the component's string name for
      use with the ASCII Console Interface"
::= { atmIfVptIispAddrPnniInfoRowStatusEntry 2 }

atmIfVptIispAddrPnniInfoStorageType OBJECT-TYPE
   SYNTAX     StorageType 
   ACCESS     read-only
   STATUS     mandatory
   DESCRIPTION
     "This variable represents the storage type value for the
      atmIfVptIispAddrPnniInfo tables."
::= { atmIfVptIispAddrPnniInfoRowStatusEntry 4 }

atmIfVptIispAddrPnniInfoIndex OBJECT-TYPE
   SYNTAX     NonReplicated 
   ACCESS     not-accessible
   STATUS     mandatory
   DESCRIPTION
     "This variable represents the index for the atmIfVptIispAddrPnniInfo tables."
::= { atmIfVptIispAddrPnniInfoRowStatusEntry 10 }

atmIfVptIispAddrPnniInfoProvTable OBJECT-TYPE
   SYNTAX     SEQUENCE OF AtmIfVptIispAddrPnniInfoProvEntry
   ACCESS     not-accessible
   STATUS     mandatory
   DESCRIPTION
     "This attribute group contains the provisioned attributes relating to 
      PNNI for a PnniInfo component."
::= { atmIfVptIispAddrPnniInfo 10 }

atmIfVptIispAddrPnniInfoProvEntry OBJECT-TYPE
   SYNTAX     AtmIfVptIispAddrPnniInfoProvEntry
   ACCESS     not-accessible
   STATUS     mandatory
   DESCRIPTION
     "An entry in the atmIfVptIispAddrPnniInfoProvTable."
   INDEX {
      atmIfIndex,
      atmIfVptIndex,
      atmIfVptIispIndex,
      atmIfVptIispAddrAddressIndex,
      atmIfVptIispAddrAddressTypeIndex,
      atmIfVptIispAddrPnniInfoIndex }
::= { atmIfVptIispAddrPnniInfoProvTable 1 }

AtmIfVptIispAddrPnniInfoProvEntry ::= SEQUENCE {
   atmIfVptIispAddrPnniInfoScope
      INTEGER,
   atmIfVptIispAddrPnniInfoReachability
      INTEGER }

atmIfVptIispAddrPnniInfoScope OBJECT-TYPE
   SYNTAX     INTEGER (-1..104)
   ACCESS     read-write
   STATUS     mandatory
   DESCRIPTION
     "This attribute specifies the scope of the ATM address, which is the 
      highest level up to which this address will be advertised in the 
      PNNI hierarchy. The scope must be set to a value numerically less 
      than or equal to the level of the lowest level peer group containing 
      this node. Setting the scope to 0 will cause the address to be 
      advertised globally within this PNNI routing domain."
   DEFVAL     { -1 }
::= { atmIfVptIispAddrPnniInfoProvEntry 1 }

atmIfVptIispAddrPnniInfoReachability OBJECT-TYPE
   SYNTAX     INTEGER  {
                 internal(0),
                 exterior(1) }
   ACCESS     read-write
   STATUS     mandatory
   DESCRIPTION
     "This attribute indicates whether the address is internal or exterior. 
      An internal reachable address is an address of a destination that is 
      directly attached to the logical node advertising the address. An 
      exterior reachable address is an address that can be reached 
      through a PNNI routing domain, but which is not located in that 
      PNNI routing domain."
   DEFVAL     { internal }
::= { atmIfVptIispAddrPnniInfoProvEntry 2 }




-- 
-- Version and Compliance statements
-- 



-- Object-Group Statement:
-- A list of all current accessible leaf objects.

-- OBJECTS { atmIfIispAccountConnectionType,
--           atmIfIispAddrPnniInfoStorageType,
--           atmIfIispSigFailedPmpConnections,
--           atmIfVptIispSigTxPdus,
--           atmIfVptIispSigFailedConnections,
--           atmIfVptIispAddrScope,
--           atmIfVptIispSigUsageState,
--           atmIfIispSigAddressConversion,
--           atmIfVptIispSigVcdQosClass,
--           atmIfIispAddrPnniInfoReachability,
--           atmIfIispAddrTermSPRowStatus,
--           atmIfIispSigComponentName,
--           atmIfIispSigVcdRowStatus,
--           atmIfVptIispAddrPnniInfoReachability,
--           atmIfVptIispSigCurrentPmpConnections,
--           atmIfIispAddrTermSPStorageType,
--           atmIfVptIispSigVcdComponentName,
--           atmIfIispAddrPnniInfoRowStatus,
--           atmIfVptIispSigVcdUsageParameterControl,
--           atmIfVptIispSoftPvpAndPvcRetryPeriod,
--           atmIfVptIispAddrPnniInfoComponentName,
--           atmIfIispAccountCollection,
--           atmIfVptIispSigRxPdus,
--           atmIfIispVersion,
--           atmIfIispAddrStorageType,
--           atmIfIispStorageType,
--           atmIfVptIispSigLastTxDiagCode,
--           atmIfVptIispSigLastRxDiagCode,
--           atmIfVptIispSigLastTxCauseCode,
--           atmIfVptIispSigPeakPmpConnections,
--           atmIfIispSigSuccessfulPmpConnections,
--           atmIfIispAddrReachability,
--           atmIfVptIispAddrPnniInfoStorageType,
--           atmIfVptIispSigSuccessfulConnections,
--           atmIfVptIispSigNewCurrentConnections,
--           atmIfIispAddrRowStatus,
--           atmIfIispRowStatus,
--           atmIfIispSigStorageType,
--           atmIfVptIispSide,
--           atmIfVptIispSigAddressConversion,
--           atmIfVptIispComponentName,
--           atmIfVptIispAccountClass,
--           atmIfVptIispSigVcdTrafficShaping,
--           atmIfVptIispSigLastRxCauseCode,
--           atmIfVptIispVpci,
--           atmIfVptIispSigVcdStorageType,
--           atmIfIispAddrPnniInfoScope,
--           atmIfIispSigVcdUnshapedTransmitQueueing,
--           atmIfVptIispAccountConnectionType,
--           atmIfVptIispSigVcdTdpValue,
--           atmIfIispSigAdminState,
--           atmIfVptIispSigFailedPmpConnections,
--           atmIfIispSigRowStatus,
--           atmIfIispServiceExchange,
--           atmIfIispSigPeakConnections,
--           atmIfVptIispSigVci,
--           atmIfIispSigTxPdus,
--           atmIfVptIispAddrComponentName,
--           atmIfVptIispSigVcdUnshapedTransmitQueueing,
--           atmIfVptIispAddrTermSPRowStatus,
--           atmIfVptIispSigComponentName,
--           atmIfVptIispSigVcdRowStatus,
--           atmIfIispSigRxPdus,
--           atmIfIispSigUsageState,
--           atmIfVptIispAddrPnniInfoRowStatus,
--           atmIfIispSoftPvpAndPvcHoldOffTime,
--           atmIfIispSigFailedConnections,
--           atmIfIispAddrScope,
--           atmIfIispSigVcdUsageParameterControl,
--           atmIfIispSigVcdQosClass,
--           atmIfIispSigVcdAtmServiceCategory,
--           atmIfIispSigLastTxDiagCode,
--           atmIfIispSoftPvpAndPvcRetryPeriod,
--           atmIfIispSigOperationalState,
--           atmIfVptIispAddrStorageType,
--           atmIfVptIispStorageType,
--           atmIfIispSigCurrentPmpConnections,
--           atmIfIispAddrTermSPComponentName,
--           atmIfIispSigVcdComponentName,
--           atmIfVptIispSigSuccessfulPmpConnections,
--           atmIfVptIispVersion,
--           atmIfVptIispAddrReachability,
--           atmIfIispAddrPnniInfoComponentName,
--           atmIfVptIispSigVcdTrafficDescType,
--           atmIfIispSigVcdTrafficShaping,
--           atmIfVptIispAccountCollection,
--           atmIfVptIispSigOperationalState,
--           atmIfIispSigLastRxDiagCode,
--           atmIfVptIispRowStatus,
--           atmIfIispSigLastTxCauseCode,
--           atmIfIispSigPeakPmpConnections,
--           atmIfVptIispSoftPvpAndPvcHoldOffTime,
--           atmIfVptIispSigPeakConnections,
--           atmIfIispSigSuccessfulConnections,
--           atmIfVptIispSigVcdAtmServiceCategory,
--           atmIfVptIispAddrPnniInfoScope,
--           atmIfIispSigVci,
--           atmIfVptIispAddrTermSPStorageType,
--           atmIfVptIispServiceExchange,
--           atmIfIispSigNewCurrentConnections,
--           atmIfVptIispAddrTermSPComponentName,
--           atmIfVptIispSigAdminState,
--           atmIfIispAccountClass,
--           atmIfVptIispAddrRowStatus,
--           atmIfIispSide,
--           atmIfIispSigVcdTdpValue,
--           atmIfIispAddrComponentName,
--           atmIfIispComponentName,
--           atmIfVptIispSigRowStatus,
--           atmIfIispSigVcdTrafficDescType,
--           atmIfIispSigLastRxCauseCode,
--           atmIfIispSigVcdStorageType,
--           atmIfVptIispSigStorageType }
-- STATUS  mandatory
-- DESCRIPTION
--   "A list of all current accessible leaf objects."

atmIispGroup OBJECT IDENTIFIER ::= { atmIispMIB 1 }
atmIispGroupBE OBJECT IDENTIFIER ::= { atmIispGroup 5 }
atmIispGroupBE00 OBJECT IDENTIFIER ::= { atmIispGroupBE 1 }
atmIispGroupBE00A OBJECT IDENTIFIER ::= { atmIispGroupBE00 2 }



-- Agent-Capabilities Statement:

-- PRODUCT-RELEASE "Passport Release 7.0 AtmIisp."
-- STATUS          mandatory
-- DESCRIPTION     "AtmIisp MIB: MIB Version BE00A,
--                  Software Version BG00S4C."
-- SUPPORTS        Nortel-Magellan-Passport-AtmIispMIB
--    INCLUDES     { atmIispGroupBE00A }

atmIispCapabilities OBJECT IDENTIFIER ::= { atmIispMIB 3 }
atmIispCapabilitiesBE OBJECT IDENTIFIER ::= { atmIispCapabilities 5 }
atmIispCapabilitiesBE00 OBJECT IDENTIFIER ::= { atmIispCapabilitiesBE 1 }
atmIispCapabilitiesBE00A OBJECT IDENTIFIER ::= { atmIispCapabilitiesBE00 2 }





END
