APERTUS-UA-ROUND-ROBIN-MIB DEFINITIONS ::= BEGIN

	IMPORTS
		mib-2
			FROM RFC1213-MIB
		MODULE-IDENTITY, OBJECT-TYPE, OBJECT-IDENTITY,
		TimeTicks, IpAddress, Counter32, Gauge32
			FROM SNMPv2-SMI
		TEXTUAL-CONVENTION, RowStatus, DisplayString, TruthValue
			FROM SNMPv2-TC
		MODULE-COMPLIANCE, OBJECT-GROUP
			FROM SNMPv2-CONF;

internet      OBJECT IDENTIFIER ::= { iso org(3) dod(6) 1 }

directory     OBJECT IDENTIFIER ::= { internet 1 }

mgmt          OBJECT IDENTIFIER ::= { internet 2 }

experimental  OBJECT IDENTIFIER ::= { internet 3 }

private       OBJECT IDENTIFIER ::= { internet 4 }
enterprises   OBJECT IDENTIFIER ::= { private 1 }


	apertus OBJECT IDENTIFIER ::= { enterprises 543 }

	isg OBJECT IDENTIFIER ::= { apertus 3 }

	aperua OBJECT IDENTIFIER ::= { isg 3 }

	aperroundrobin OBJECT IDENTIFIER ::= { aperua 4 }

	aperRoundRobinMIB OBJECT IDENTIFIER ::= { aperroundrobin 1 }

	aperRoundRobinMIBObjects       OBJECT IDENTIFIER ::= { aperRoundRobinMIB 1 }

	-- (Old-style) groups in the apertus Threshold extension

	aperRoundRobinConfig  OBJECT IDENTIFIER ::= { aperRoundRobinMIBObjects 1 }
	aperRoundRobinDomain  OBJECT IDENTIFIER ::= { aperRoundRobinMIBObjects 2 }
	aperRoundRobinNode  OBJECT IDENTIFIER ::= { aperRoundRobinMIBObjects 3 }

	-- RoundRobinold config information group
	aperRoundRobinConfigStatus OBJECT-TYPE
		SYNTAX      INTEGER {	ready(1),
								loading(2),
								down(3) }
		ACCESS  read-only
		STATUS      mandatory
		DESCRIPTION
               "Status of Universal Access server"
		::= { aperRoundRobinConfig 1 }

	aperRoundRobinConfigUpTime OBJECT-TYPE
		SYNTAX      TimeTicks
		ACCESS  read-only
		STATUS      mandatory
		DESCRIPTION
               "This value represents the time elapsed since the server
                was started in 1/100nths of a second."
		::= { aperRoundRobinConfig 2 }

	-- RoundRobinold zone information group

	aperRoundRobinDomainTable OBJECT-TYPE
		SYNTAX      SEQUENCE OF AperRoundRobinDomainEntry
		ACCESS  not-accessible
		STATUS      mandatory
		DESCRIPTION
	               "Domain information broken down domain name."
		::= { aperRoundRobinDomain 1 }

	aperRoundRobinDomainEntry OBJECT-TYPE
		SYNTAX      AperRoundRobinDomainEntry
		ACCESS  not-accessible
		STATUS      mandatory
		DESCRIPTION
               "This table contains information on each of the load balance
				domains under its control."
		INDEX     { aperRoundRobinDomainName }
		::= { aperRoundRobinDomainTable 1 }

	AperRoundRobinDomainEntry ::=
		SEQUENCE {
			aperRoundRobinDomainName
				DisplayString,
			aperRoundRobinDomainLastHostIndex
				INTEGER,
			aperRoundRobinDomainUpServers
				INTEGER,
			aperRoundRobinDomainDownServers
				INTEGER
		    }

	aperRoundRobinDomainName OBJECT-TYPE
		SYNTAX		DisplayString
		ACCESS  read-only	
		STATUS		mandatory
		DESCRIPTION
			"The zone name for this load-balance domain."
		::= { aperRoundRobinDomainEntry 1 }

	aperRoundRobinDomainLastHostIndex OBJECT-TYPE
		SYNTAX		INTEGER ( -1..2147483647 )
		ACCESS	read-only
		STATUS		mandatory
		DESCRIPTION
			"The host index number (from round robin node table) that
			 was given out at the last query.  A value of -1 is used
			 to indicate that no value has ever been returned for this
			 domain."
		::= { aperRoundRobinDomainEntry 2 }

	aperRoundRobinDomainUpServers OBJECT-TYPE
		SYNTAX		INTEGER ( -2147483648..2147483647 )
		ACCESS	read-only
		STATUS		mandatory
		DESCRIPTION
			"The number of servers that are up at this time."
		::= { aperRoundRobinDomainEntry 3 }

	aperRoundRobinDomainDownServers OBJECT-TYPE
		SYNTAX		INTEGER ( -2147483648..2147483647 )
		ACCESS	read-only
		STATUS		mandatory
		DESCRIPTION
			"The number of servers in list that are marked as down at this
			 time."
		::= { aperRoundRobinDomainEntry 4 }


	-- RoundRobinold zone information group

	aperRoundRobinNodeTable OBJECT-TYPE
		SYNTAX      SEQUENCE OF AperRoundRobinNodeEntry
		ACCESS  not-accessible
		STATUS      mandatory
		DESCRIPTION
               "Node information broken down domain name and IP address"
		::= { aperRoundRobinNode 1 }

	aperRoundRobinNodeEntry OBJECT-TYPE
		SYNTAX      AperRoundRobinNodeEntry
		ACCESS  not-accessible
		STATUS      mandatory
		DESCRIPTION
               "This table contains information on each of the machines
				in the different laod balance zones."
		INDEX     { aperRoundRobinNodeName,
					aperRoundRobinNodeIP }
		::= { aperRoundRobinNodeTable 1 }

	AperRoundRobinNodeEntry ::=
		SEQUENCE {
			aperRoundRobinNodeName
				DisplayString,
			aperRoundRobinNodeIP
				IpAddress,
			aperRoundRobinNodeHostIndex
				INTEGER,
			aperRoundRobinNodePoolIndex
				INTEGER,
			aperRoundRobinNodeStatus
				INTEGER,
			aperRoundRobinNodeResponseTime
				TimeTicks
		    }

	aperRoundRobinNodeName OBJECT-TYPE
		SYNTAX		DisplayString
		ACCESS  read-only	
		STATUS		mandatory
		DESCRIPTION
			"The zone name for this Node."
		::= { aperRoundRobinNodeEntry 1 }

	aperRoundRobinNodeIP OBJECT-TYPE
		SYNTAX		IpAddress
		ACCESS  read-only	
		STATUS		mandatory
		DESCRIPTION
			"The IP address of the NODE."
		::= { aperRoundRobinNodeEntry 2 }

	aperRoundRobinNodeHostIndex OBJECT-TYPE
		SYNTAX      INTEGER (0..2147483647 )
		ACCESS  read-only
		STATUS      mandatory
		DESCRIPTION
			"This value is the host index within the domain.  The lower the
			 number, the higher the preference towards using the node for all
			 name to address mappings."
		::= { aperRoundRobinNodeEntry 3 }

	aperRoundRobinNodePoolIndex OBJECT-TYPE
		SYNTAX		INTEGER (0..255)
		ACCESS	read-only
		STATUS		mandatory
		DESCRIPTION
			"This value is the pool index.  When all nodes with a lower index
			are down, the items with next highest pool index are considered
			for roundRobin usage."
		::= { aperRoundRobinNodeEntry 4 }


	aperRoundRobinNodeStatus OBJECT-TYPE
		SYNTAX		INTEGER {	up(1),
								down(2),
								notqueried(3) }
		ACCESS	read-only
		STATUS		mandatory
		DESCRIPTION
			"Indicates the status of the node.  Up(1) shows that the node is
			 up and is being considered for use.  Down(2) indicates that
			 the last query to the NODE image resulted in a down marker for
			 the node.  Admindown(3) indicates that an administrator took
			 the node offline manually (from the UA server end).
			 Notqueried(4) is used to indicate that a node has never been
			 queried."
		::= { aperRoundRobinNodeEntry 5 }

	aperRoundRobinNodeResponseTime OBJECT-TYPE
		SYNTAX      TimeTicks
		ACCESS  read-only
		STATUS      mandatory
		DESCRIPTION
               "Response time in MS of last node access.  A value of 0 is
                returned if NodeStatus is not ready(1) or if the node
				has never been queried"
		::= { aperRoundRobinNodeEntry 6 }

END
