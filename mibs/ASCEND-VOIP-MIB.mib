--			Ascend VOIP MIB
--
--			Ascend Communications, Inc
--			1275 Harbor Bay Pkwy
--			Alameda, CA 94502
--			+1 510 769 6001
--			info@ascend.com
--
--		Copyright (c) 1993-1997 Lucent Technologies, Inc.
--		All rights reserved.
--
-- $Id: voip.mib,v 29.1.6.1 1999/08/12 23:12:48 mkrasnic Exp $
-- 27 July 99:    Initial release

ASCEND-VOIP-MIB DEFINITIONS ::= BEGIN

    IMPORTS
	voipGroup
	    FROM ASCEND-MIB
	IpAddress
	    FROM RFC1155-SMI
	OBJECT-TYPE
	    FROM RFC-1212;

	--
	-- Ascend voip Group
	--
	-- This group contains MIBs related to voice over IP.
	--

    voipCfgGroup		OBJECT IDENTIFIER ::= { voipGroup 1 }

    voipCfgGkGroup		OBJECT IDENTIFIER ::= { voipCfgGroup 1 }

    voipCfgGwGroup		OBJECT IDENTIFIER ::= { voipCfgGroup 2 }

    voipCfgGkTable		OBJECT-TYPE
	SYNTAX			SEQUENCE OF VoipCfgGkEntry
	ACCESS			not-accessible
	STATUS			mandatory
	DESCRIPTION		"A list of entries for H323 network Gatekeeper."
	::= { voipCfgGkGroup 1 }

    voipCfgGkEntry		OBJECT-TYPE
	SYNTAX			VoipCfgGkEntry
	ACCESS			not-accessible
	STATUS			mandatory
	DESCRIPTION		"An entry holding information about the 
				 Gatekeepers for the system."
	INDEX			{ voipCfgGkIndex }
	::= { voipCfgGkTable 1 }

    VoipCfgGkEntry ::=
	SEQUENCE {
		voipCfgGkIndex		INTEGER,
		voipCfgGkStatus		INTEGER,
		voipCfgGkIpAddress	IpAddress
	}

    voipCfgGkIndex		OBJECT-TYPE
	SYNTAX			INTEGER
	ACCESS			read-only
	STATUS			mandatory
	DESCRIPTION		"This number uniquely identifies the Gatekeeper." 	
	::= { voipCfgGkEntry 1 }

    voipCfgGkStatus		OBJECT-TYPE
	SYNTAX			INTEGER {
					  registered(1),
					  not-registered(2)
				}
	ACCESS			read-only
	STATUS			mandatory
	DESCRIPTION		"This value indicates whether the gateway
				 is registered with the Gatekeeper."
	::= { voipCfgGkEntry 2 }

    voipCfgGkIpAddress		OBJECT-TYPE
	SYNTAX			IpAddress
	ACCESS			read-only
	STATUS			mandatory
	DESCRIPTION		"The IP address of the Gatekeeper."
	::= { voipCfgGkEntry 3 }

    voipCfgGwVpnMode		OBJECT-TYPE
	SYNTAX			INTEGER { 
				         no (1),
					 yes(2)
				}
	ACCESS			read-only
	STATUS			mandatory
	DESCRIPTION		"Virtual Private Network Toggle Switch."
	::= { voipCfgGwGroup 1 }

    voipCfgGwPktAudioMode	OBJECT-TYPE
	SYNTAX			INTEGER {
					  other(1),
					  g711-ulaw(2),
					  g711-alaw(3),
					  g723(4),
					  g729(5),
					  g723-6-4kps(6)
				}
	ACCESS			read-only
	STATUS			mandatory
	DESCRIPTION		"Audio Coder to be used for voice packetization."
	::= { voipCfgGwGroup 2 }

END
