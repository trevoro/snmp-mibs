-- extracted from draft-bierman-conf-mib-00.txt
-- at Sat Jun  1 06:08:59 2002

CONFORMANCE-MIB DEFINITIONS ::= BEGIN

IMPORTS
        MODULE-IDENTITY, OBJECT-TYPE, mib-2
                FROM SNMPv2-SMI
        MODULE-COMPLIANCE, OBJECT-GROUP
                FROM SNMPv2-CONF
        TEXTUAL-CONVENTION, TimeStamp
                FROM SNMPv2-TC;

conformanceMIB MODULE-IDENTITY
    LAST-UPDATED    "200205300000Z"
    ORGANIZATION    "IETF OPS-NM Area"
    CONTACT-INFO
            "        Andy Bierman
                     Cisco Systems, Inc.
                Tel: +1 408 527-3711
             E-mail: abierman@cisco.com
             Postal: 170 West Tasman Drive
                     San Jose, CA USA 95134

             Send comments to <mibs@ops.ietf.org>"
    DESCRIPTION
            "Contains objects which describe the conformance
             level for specific data objects."
    REVISION  "200205300000Z"
       DESCRIPTION
            "Initial version."
  ::= { mib-2 1 }   -- unassigned


confMibObjects       OBJECT IDENTIFIER ::= { conformanceMIB 1 }
confMibNotifications OBJECT IDENTIFIER ::= { conformanceMIB 2 }
confMibConformance   OBJECT IDENTIFIER ::= { conformanceMIB 3 }

confMibConformanceObjects OBJECT IDENTIFIER
                                       ::= { confMibObjects 1 }

--
-- Textual Conventions
--

ConformanceLevel ::= TEXTUAL-CONVENTION
    STATUS current
    DESCRIPTION
            "An indication of the conformance level for a particular set
            of MIB objects.

            The value 'noConf' indicates that the agent does not
            implement any of the required semantics for the associated
            set of objects.  Usually this means the object is not
            implemented at all.  However, it also indicates the special
            case in which incorrect values are returned, e.g., counter
            objects that always return zero, string objects that always
            return a zero-length string (but should not), hard-wired
            (potentially incorrect) enumerations or gauges.

            The value 'otherConf' indicates that the implementation
            complies with the semantics of the associated set of objects
            in a manner that varies from the specification in some way.

            The value 'minConf' indicates that the implementation
            complies with the semantics of the associated set of objects
            as refined by a GROUP clause or an OBJECT clause within a
            MODULE-COMPLIANCE macro.

            The value 'fullConf' indicates that the implementation
            complies with the semantics of the associated set of objects
            as defined by an indicated compliance statement for the set
            of objects.

            The value 'completeConf' indicates that the implementation
            complies with the full semantics of the associated set of
            objects as defined by the data definitions for the objects.
            This may be greater than than the conformance level
            indicated by the 'fullConf' enumeration if the indicated
            compliance statement does not require full implementation of
            the entire set of objects."
    REFERENCE
       "RFC 2580, section 5."
    SYNTAX INTEGER {
                    noConf(1),
                    otherConf(2),
                    minConf(3),
                    fullConf(4),
                    completeConf(5)
                   }


ConformanceString ::= TEXTUAL-CONVENTION
    STATUS current
    DESCRIPTION
            "An administrative string identifying conformance
            information.

            An object of this type SHOULD follow the encoding rules for
            an SnmpAdminString, except its length is limited to 1024
            octets instead of 255 octets."
    REFERENCE
       "RFC 2571, section 5."
    SYNTAX OCTET STRING (SIZE (0..1024))    -- SnmpAdminString

--
-- Conformance Group scalars
--

confLastUpdateTime OBJECT-TYPE
    SYNTAX      TimeStamp
    MAX-ACCESS  read-only
    STATUS      current
    DESCRIPTION
            "The value of sysUpTime when the agent last added, deleted,
            or modified an entry in the confTable."
    ::= { confMibConformanceObjects 1 }

--
-- Conformance Table
--

confTable OBJECT-TYPE
    SYNTAX      SEQUENCE OF ConfEntry
    MAX-ACCESS  not-accessible
    STATUS      current
    DESCRIPTION
            "A list of entries describing the MIB conformance for this
            agent."
    ::= { confMibConformanceObjects 2 }

confEntry OBJECT-TYPE
    SYNTAX      ConfEntry
    MAX-ACCESS  not-accessible
    STATUS      current
    DESCRIPTION
            "A conceptual row in the confTable. Entries SHOULD be
            created by the agent at system reinitialization time.
            However, agents MAY create, delete, or modify entries in
            this table to support dynamic loading and unloading of MIB
            modules. It is possible that overlapping entries will exist
            in this table, in which case the more specific entry (i.e.,
            the one with the longest confSubTree INDEX) takes
            precedence."
    INDEX { confSubTree }
    ::= { confTable 1 }


ConfEntry ::= SEQUENCE {
    confSubTree                      OBJECT IDENTIFIER,
    confModuleCompliance             OBJECT IDENTIFIER,
    confLevel                        ConformanceLevel,
    confVarSyntax                    ConformanceString }

confSubTree OBJECT-TYPE
    SYNTAX      OBJECT IDENTIFIER
    MAX-ACCESS  not-accessible
    STATUS      current
    DESCRIPTION
            "The root of the MIB sub-tree associated with this entry.
            This object SHOULD identify an interior node to indicate
            multiple MIB objects or a leaf node to indicate a single MIB
            object."
    ::= { confEntry 1 }

confModuleCompliance OBJECT-TYPE
    SYNTAX      OBJECT IDENTIFIER
    MAX-ACCESS  read-only
    STATUS      current
    DESCRIPTION
            "Identifies the MODULE-COMPLIANCE macro name for the
            associated set of MIB objects. If no appropriate value can
            be determined, then the agent will return '0.0'."
    REFERENCE
            "RFC 2580, section 5.5."
    ::= { confEntry 2 }

confLevel OBJECT-TYPE
    SYNTAX      ConformanceLevel
    MAX-ACCESS  read-only
    STATUS      current
    DESCRIPTION
            "Indicates the basic level of conformance for the associated
            set of MIB objects.

            If this object contains the value 'otherConf', then the
            confVarSyntax object SHOULD be present for the associated
            entry.

            If this object contains the value 'fullConf', 'minConf', or
            'noConf' then the confVarSyntax object MAY be present for
            the associated entry.

            If this object contains the value 'completeConf' then the
            confVarSyntax object SHOULD NOT be present for the
            associated entry."
    REFERENCE
            "RFC 2580, section 5."
    ::= { confEntry 3 }

confVarSyntax OBJECT-TYPE
    SYNTAX      ConformanceString
    MAX-ACCESS  read-only
    STATUS      current
    DESCRIPTION
            "A textual representation of the syntactical variation
            described by this variation structure.

            If the associated confLevel object is equal to 'otherConf',
            then this string SHOULD contain the the same value as the
            SYNTAX clause within a VARIATION clause of an AGENT-
            CAPABILITIES macro.

            If the associated confLevel object is equal to 'minConf',
            and this entry identifies a set of MIB objects, then this
            string MAY identify the applicable GROUP clause(s)
            associated with the entry.

            For all entries in which the associated confLevel object is
            equal to 'minConf', this string SHOULD contain the same
            value as the SYNTAX, WRITE-SYNTAX, and/or MIN-ACCESS clauses
            present within the OBJECT clause of a MODULE-COMPLIANCE
            macro. The actual keyword (e.g., 'SYNTAX') SHOULD precede
            the quoted string value.  Multiple clauses MAY be
            concatenated within a single string, and SHOULD be separated
            by whitespace.  If this entry identifies multiple objects,
            then the same clause(s) must apply to all objects.

            The agent MAY return a zero-length string instead of a
            noSuchInstance exception."
    REFERENCE
            "RFC 2580, sections 5.4.3 and 6.5.2."
    ::= { confEntry 4 }

--
-- Notification Section  (none defined)
--

--
-- Conformance Section
--

confMibCompliances OBJECT IDENTIFIER ::= { confMibConformance 1 }
confMibGroups      OBJECT IDENTIFIER ::= { confMibConformance 2 }

confMibCompliance MODULE-COMPLIANCE
    STATUS  current
    DESCRIPTION
            "Describes the requirements for conformance to the
            Conformance MIB."
    MODULE  -- this module
        MANDATORY-GROUPS { confMibConformanceGroup }

    ::= { confMibCompliances 1 }

-- Object Groups

confMibConformanceGroup OBJECT-GROUP
    OBJECTS {
             confLastUpdateTime,
             confModuleCompliance,
             confLevel,
             confVarSyntax
    }
    STATUS  current
    DESCRIPTION
            "A collection of objects used to describe the conformance
            level of the MIB objects supported by an agent."
    ::= { confMibGroups 1 }

END

-- 
-- Copyright (C) The Internet Society (2002).  All Rights Reserved.
-- 
-- This document and translations of it may be copied and furnished to
-- others, and derivative works that comment on or otherwise explain it or
-- assist in its implementation may be prepared, copied, published and
-- distributed, in whole or in part, without restriction of any kind,
-- provided that the above copyright notice and this paragraph are included
-- on all such copies and derivative works.  However, this document itself
-- may not be modified in any way, such as by removing the copyright notice
-- or references to the Internet Society or other Internet organizations,
-- except as needed for the purpose of developing Internet standards in
-- which case the procedures for copyrights defined in the Internet
-- Standards process must be followed, or as required to translate it into
-- languages other than English.
-- 
-- The limited permissions granted above are perpetual and will not be
-- revoked by the Internet Society or its successors or assigns.
-- 
-- This document and the information contained herein is provided on an "AS
-- IS" basis and THE INTERNET SOCIETY AND THE INTERNET ENGINEERING TASK
-- FORCE DISCLAIMS ALL WARRANTIES, EXPRESS OR IMPLIED, INCLUDING BUT NOT
-- LIMITED TO ANY WARRANTY THAT THE USE OF THE INFORMATION HEREIN WILL NOT
-- INFRINGE ANY RIGHTS OR ANY IMPLIED WARRANTIES OF MERCHANTABILITY OR
-- FITNESS FOR A PARTICULAR PURPOSE.
