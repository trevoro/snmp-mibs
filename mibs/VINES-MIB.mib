--
-- Syntax errors fixed by HP 5/19/95 : See all lines w/ string "Original MIB".
-- Also had to change the TRAP-TYPE formatting to be consistent with that used
-- by Novell, Compaq and others.
--
VINES-MIB --{ iso org(3) dod(6) internet(1) private(4) enterprises(1) 130 }

DEFINITIONS ::= BEGIN

IMPORTS
	enterprises, OBJECT-TYPE, NetworkAddress, IpAddress, Counter, 
	Gauge, TimeTicks
		FROM RFC1155-SMI
	TRAP-TYPE
		FROM RFC-1215;

-- banyan specific objects

banyan OBJECT IDENTIFIER ::= { enterprises 130 }

vinesmibs OBJECT IDENTIFIER ::= { banyan 1 }
mib1      OBJECT IDENTIFIER ::= { vinesmibs 1 }
mib2      OBJECT IDENTIFIER ::= { vinesmibs 2 }

systemsummary	OBJECT IDENTIFIER ::= { mib2 1 }
services	OBJECT IDENTIFIER ::= { mib2 2 }
peripherals	OBJECT IDENTIFIER ::= { mib2 3 }
filesystem	OBJECT IDENTIFIER ::= { mib2 4 }
commresources	OBJECT IDENTIFIER ::= { mib2 5 }
vip		OBJECT IDENTIFIER ::= { mib2 6 }
vrtp		OBJECT IDENTIFIER ::= { mib2 7 }
vspp		OBJECT IDENTIFIER ::= { mib2 8 }
vinterfaces	OBJECT IDENTIFIER ::= { mib2 9 }
os		OBJECT IDENTIFIER ::= { mib2 10 }
ossysstats	OBJECT IDENTIFIER ::= { os 1 }
osinfo		OBJECT IDENTIFIER ::= { os 2 }
ossummstats	OBJECT IDENTIFIER ::= { os 3 }
nmthresholds    OBJECT IDENTIFIER ::= { mib2 11 }
trapdata        OBJECT IDENTIFIER ::= { mib2 12 }
ams             OBJECT IDENTIFIER ::= { mib2 13 }
mailservice     OBJECT IDENTIFIER ::= { mib2 14 }
vlogs           OBJECT IDENTIFIER ::= { mib2 15 }

-- This data type is used for encoding an interface type. 

-- object types

-- the systemsummary group

ssName OBJECT-TYPE
	SYNTAX  OCTET STRING
	ACCESS  read-only
	STATUS  mandatory
	DESCRIPTION
		"The StreetTalk name of the server, up to 15 characters long."
	::= { systemsummary 1 }

ssNetid OBJECT-TYPE
	SYNTAX  INTEGER
	ACCESS  read-only
	STATUS  mandatory
	DESCRIPTION
		"The VINES network ID of the server, which is equal
		to the server's serial number.  This ID may be up to
		4 bytes in length."
	::= { systemsummary 2 }

ssSwRev OBJECT-TYPE
	SYNTAX  OCTET STRING
	ACCESS  read-only
	STATUS  mandatory
	DESCRIPTION
		"The VINES software revision for this server."
	::= { systemsummary 3 }

ssLoadAvg1 OBJECT-TYPE
	SYNTAX  INTEGER
	ACCESS  read-only
	STATUS  mandatory
	DESCRIPTION
		"The one minute exponential decaying average of server load."
	::= { systemsummary 4 }

ssLoadAvg5 OBJECT-TYPE
	SYNTAX  INTEGER
	ACCESS  read-only
	STATUS  mandatory
	DESCRIPTION
		"The five minute exponential decaying average of server load."
	::= { systemsummary 5 }

ssLoadAvg15 OBJECT-TYPE
	SYNTAX  INTEGER
	ACCESS  read-only
	STATUS  mandatory
	DESCRIPTION
		"The 15 minute exponential decaying average of server load."
	::= { systemsummary 6 }

ssMsgAvg1 OBJECT-TYPE
	SYNTAX  INTEGER
	ACCESS  read-only
	STATUS  mandatory
	DESCRIPTION
		"The one minute exponential decaying average of network 
		messages sent and received per second."
	::= { systemsummary 7 }

ssMsgsIn OBJECT-TYPE
	SYNTAX  Counter
	ACCESS  read-only
	STATUS  mandatory
	DESCRIPTION
		"The total number of network messages that the server has 
		received over the network since the last reboot."
	::= { systemsummary 8 }

ssMsgsOut OBJECT-TYPE
	SYNTAX  Counter
	ACCESS  read-only
	STATUS  mandatory
	DESCRIPTION
		"The total number of network messages that the server has sent
		over the network since the last reboot."
	::= { systemsummary 9 }

ssDrops OBJECT-TYPE
	SYNTAX  Counter
	ACCESS  read-only
	STATUS  mandatory
	DESCRIPTION
		"The total number of received messages that could not be 
		processed due to a lack of communications buffer space."
	::= { systemsummary 10 }

ssSwapAvg OBJECT-TYPE
	SYNTAX  INTEGER
	ACCESS  read-only
	STATUS  mandatory
	DESCRIPTION
		"An exponential decaying average of the number of times a 
		process was swapped to or from disk per second over a one 
		minute period."
	::= { systemsummary 11 }

ssProcType OBJECT-TYPE
	SYNTAX  INTEGER {
		other(1),
		i386(2),
		i486(3)
		}
	ACCESS  read-only
	STATUS  mandatory
	DESCRIPTION
		"The type of the processor."
	::= { systemsummary 12 }

ssProdType OBJECT-TYPE
	SYNTAX  INTEGER {
		unused(1),
		cns(2),
		pcvines(3)
		}
	ACCESS  read-only
	STATUS  mandatory
	DESCRIPTION
		"The type of banyan product."
	::= { systemsummary 13 }

ssProdDescr OBJECT-TYPE
	SYNTAX  OCTET STRING
	ACCESS  read-only
	STATUS  mandatory
	DESCRIPTION
		"The description of the product type."
	::= { systemsummary 14 }

ssRealMemory OBJECT-TYPE
	SYNTAX  INTEGER
	ACCESS  read-only
	STATUS  mandatory
	DESCRIPTION
		"The total amount of RAM, in kilobytes, configured
		in the server."
	::= { systemsummary 15 }

ssOsType OBJECT-TYPE
	SYNTAX  INTEGER {
		unixsystemv(1)
		}
	ACCESS  read-only
	STATUS  mandatory
	DESCRIPTION
		"The type of server OS.  UNIX is the only
		operating system supported."
	::= { systemsummary 16 }

ssOsRev OBJECT-TYPE
	SYNTAX  OCTET STRING
	ACCESS  read-only
	STATUS  mandatory
	DESCRIPTION
		"The operating system version."
	::= { systemsummary 17 }

ssSystemUptime OBJECT-TYPE
	SYNTAX  TimeTicks
	ACCESS  read-only
	STATUS  mandatory
	DESCRIPTION
		"The amount time since this host was last initialized. Note
		that this is different from sysUpTime because sysUpTime is
		the uptime of the network management portion of the system."
	::= { systemsummary 18 }

ssSystemDate OBJECT-TYPE
	SYNTAX  INTEGER
	ACCESS  read-only
	STATUS  mandatory
	DESCRIPTION
		"The current time on the server."
	::= { systemsummary 19 }

ssSystemStatus OBJECT-TYPE
        SYNTAX INTEGER {
            running(1),
            shutdown(2),
            reboot(3)
        }
	ACCESS  read-write
	STATUS  mandatory
	DESCRIPTION
		"The status of the server. When the server is initialized
		this field will get set to running.  When a shutdown
		is requested the server will shutdown all services and
		await a manual reboot. A reboot request will shut down
		all services and automatically reboot the machine."
	::= { systemsummary 20 }

ssUserLicenseCfg OBJECT-TYPE
	SYNTAX  INTEGER
	ACCESS  read-only
	STATUS  mandatory
	DESCRIPTION
		"The user limit license for this server."
	::= { systemsummary 21 }

-- the services group

svcNumber OBJECT-TYPE
	SYNTAX  INTEGER
	ACCESS  read-only
	STATUS  mandatory
	DESCRIPTION
		"The number of services in the svcTable."
	::= { services 1 }

svcTable OBJECT-TYPE
	SYNTAX  SEQUENCE OF SvcEntry
	ACCESS  not-accessible
	STATUS  mandatory
	DESCRIPTION
		"A list of services on the server."
	::= { services 2 }

svcEntry OBJECT-TYPE
	SYNTAX  SvcEntry  
	ACCESS  not-accessible
	STATUS  mandatory
	DESCRIPTION
		"Each entry contains a set of statistics for one service."
	INDEX	{ svcIndex }
	::= { svcTable 1 }

SvcEntry ::= SEQUENCE {
    svcIndex
	INTEGER,
    svcName
	OCTET STRING,
    svcStatus
	INTEGER,
    svcUpTime
	TimeTicks,
    svcMsgsIn
	Counter,
    svcMsgsOut
	Counter,
    svcLocIn
	Counter,
    svcLocOut
	Counter,
    svcActSess
	INTEGER,
    svcTotSess
	Counter,
    svcCategory
	INTEGER,
    svcCpuTime
	TimeTicks,
    svcSize
	INTEGER,
    svcSockets
	INTEGER,
    svcSPPs
	INTEGER,
    svcLogMask
	INTEGER,
    svcDiskName
	OCTET STRING
}

svcIndex OBJECT-TYPE
	SYNTAX  INTEGER
	ACCESS  read-only
	STATUS  mandatory
	DESCRIPTION
		"A unique value for each service used by SNMP to keep track of
		service table entries.  This value may vary if the table 
		changes."
	::= { svcEntry 1 }

svcName OBJECT-TYPE
	SYNTAX  OCTET STRING
	ACCESS  read-only
	STATUS  mandatory
	DESCRIPTION
		"The StreetTalk name of the service, the names are of the form
		'item@group@organization'."
	::= { svcEntry 2 }

svcStatus OBJECT-TYPE
	SYNTAX  INTEGER {
	        running(1),     
	        initializing(2),
	        crashing(3),
	        inconsistent(4),
		stopped(5)
	    }
	ACCESS  read-write
	STATUS  mandatory
	DESCRIPTION
		"The status of the service.  
		Running - available to users.
		Initializing - starting and will be available shortly.
		Crashing - not functioning properly.
		Inconsistent - the name cannot be found.
		Stopped - not running.
		Only running and stopped are valid for sets."
	::= { svcEntry 3 }

svcUpTime OBJECT-TYPE
	SYNTAX  TimeTicks
	ACCESS  read-only
	STATUS  mandatory
	DESCRIPTION
		"The amount of time that the service has been running."
	::= { svcEntry 4 }

svcMsgsIn OBJECT-TYPE
	SYNTAX  Counter
	ACCESS  read-only
	STATUS  mandatory
	DESCRIPTION
		"The total number of messages that the service has received 
		over the network since the service was last started."
	::= { svcEntry 5 }

svcMsgsOut OBJECT-TYPE
	SYNTAX  Counter
	ACCESS  read-only
	STATUS  mandatory
	DESCRIPTION
		"The total number of messages that the service has sent
		over the network since the service was last started."
	::= { svcEntry 6 }

svcLocIn OBJECT-TYPE
	SYNTAX  Counter
	ACCESS  read-only
	STATUS  mandatory
	DESCRIPTION
		"The number of messages received by the service that were sent
		by entities that are local to the service's server since the
		service was last started."
	::= { svcEntry 7 }

svcLocOut OBJECT-TYPE
	SYNTAX  Counter
	ACCESS  read-only
	STATUS  mandatory
	DESCRIPTION
		"The number of messages sent by the service to entities that 
		are local to the service's server since the service was last 
		started."
	::= { svcEntry 8 }

svcActSess OBJECT-TYPE
	SYNTAX  INTEGER
	ACCESS  read-only
	STATUS  mandatory
	DESCRIPTION
		"The number of active sessions with the service."
	::= { svcEntry 9 }

svcTotSess OBJECT-TYPE
	SYNTAX  Counter
	ACCESS  read-only
	STATUS  mandatory
	DESCRIPTION
		"The total number of sessions that the service has handled
		since it was last started."
	::= { svcEntry 10 }

svcCategory OBJECT-TYPE
	SYNTAX  INTEGER
	ACCESS  read-only
	STATUS  mandatory
	DESCRIPTION
		"The type of service defined as follows:
		1 Server Service
		2 File Service or DOS/UNIX bridge file service
		3 Print Service
		4 Mail Service
		5 StreetTalk Service
		6 Time
		7 File Transfer Protocol (FTP)
		8 Semaphore Service
		9 System Network Architecture Service
		10 Virtual Terminal Service
		11 Asynchronous Terminal Service
		12 Netbios Service
		13 PC-Based Service
		14 Bisynchronous Service
		15 APPC Service(APPCCAT)
		16 Network Management Service
		17 VINES Security Service
		18 StreetTalk Directory Assistance Service
		19 AppleTalk Filing Protocol (AFP)
		20 VINES Configuration Service
		21 Event Management Service
		22 Link Service
		23 Backup Service
		24 Unused
		25 VINES Remote Service
		26 Remote Execution Service
		27 Tree Service
		28 VINES Proxy Agent Service
		29 WAN Configuration Service
		30 AppleTalk Agent Service
		31 Alert Management Service
		32 Unused
		33 Unused
		34 Unused
		35 Remote Program Load Service
		36 StreetTalk Agent Service
		37 NetWare Print Queue Service
		38 NetWare Print Service
		39 NetWare File Service
		100 AdminList
		1986 VINES Assistant Service
		1888 SMTP Service
		Third-party services return values from 1000 to 1899."
	::= { svcEntry 11 }

svcCpuTime OBJECT-TYPE
	SYNTAX  TimeTicks
	ACCESS  read-only
	STATUS  mandatory
	DESCRIPTION
		"The amount of current CPU use that the service is generating."
	::= { svcEntry 12 }

svcSize OBJECT-TYPE
	SYNTAX  INTEGER
	ACCESS  read-only
	STATUS  mandatory
	DESCRIPTION
		"The  amount of virtual memory that is allocated to the 
		service."
	::= { svcEntry 13 }

svcSockets OBJECT-TYPE
	SYNTAX  INTEGER
	ACCESS  read-only
	STATUS  mandatory
	DESCRIPTION
		"The number of VINES sockets that the service is currently
		consuming."
	::= { svcEntry 14 }

svcSPPs OBJECT-TYPE
	SYNTAX  INTEGER
	ACCESS  read-only
	STATUS  mandatory
	DESCRIPTION
		"The number of SPP connections that the service is currently
		consuming."
	::= { svcEntry 15 }

svcLogMask OBJECT-TYPE
	SYNTAX  INTEGER {
	    maskdef(1),
	    masklow(2),
	    maskmed(3),
	    maskhigh(4) 
	}
	ACCESS  read-write
	STATUS  mandatory
	DESCRIPTION
		"The current log mask of a service."
	::= { svcEntry 16 }

svcDiskName  OBJECT-TYPE
	SYNTAX  OCTET STRING
	ACCESS  read-only
	STATUS  mandatory
	DESCRIPTION
		"The location of the service."
	::= { svcEntry 17 }

svcUserTable OBJECT-TYPE
	SYNTAX  SEQUENCE OF SvcUserEntry
	ACCESS  not-accessible
	STATUS  mandatory
	DESCRIPTION
		"A list of the users for the services."
	::= { services 3 }

svcUserEntry OBJECT-TYPE
	SYNTAX  SvcUserEntry  
	ACCESS  not-accessible
	STATUS  mandatory
	DESCRIPTION
		"An entry in the list of service users."
	INDEX	{ svcUserSvcIndex,
		  svcUserIndex }
	::= { svcUserTable 1 }

SvcUserEntry ::= SEQUENCE {
    svcUserSvcIndex
	INTEGER,
    svcUserIndex
	INTEGER,
    svcUserSvcName
	OCTET STRING,
    svcUserName
	OCTET STRING
}

svcUserSvcIndex OBJECT-TYPE
	SYNTAX  INTEGER
	ACCESS  read-only
	STATUS  mandatory
	DESCRIPTION
		"A unique value for each service on the server, used by SNMP 
		to order the list."
	::= { svcUserEntry 1 }

svcUserIndex OBJECT-TYPE
	SYNTAX  INTEGER
	ACCESS  read-only
	STATUS  mandatory
	DESCRIPTION
		"A unique value for each user of a service.  This value will
		change as new users are added and old users deleted from the
		service."
	::= { svcUserEntry 2 }

svcUserSvcName OBJECT-TYPE
	SYNTAX  OCTET STRING
	ACCESS  read-only
	STATUS  mandatory
	DESCRIPTION
		"The StreetTalk name of the service."
	::= { svcUserEntry 3 }

svcUserName OBJECT-TYPE
	SYNTAX  OCTET STRING
	ACCESS  read-only
	STATUS  mandatory
	DESCRIPTION
		"The StreetTalk name of the user of the service."
	::= { svcUserEntry 4 }

-- the Peripherals group  

dskNumber OBJECT-TYPE
	SYNTAX  INTEGER
	ACCESS  read-only
	STATUS  mandatory
	DESCRIPTION
		"The number of disks in the disk table."
	::= { peripherals 1 }

dskTable OBJECT-TYPE
	SYNTAX  SEQUENCE OF DskEntry
	ACCESS  not-accessible
	STATUS  mandatory
	DESCRIPTION
		"A list of statistics for the disks on this server."
	::= { peripherals 2 }

dskEntry OBJECT-TYPE
	SYNTAX  DskEntry
	ACCESS  not-accessible
	STATUS  mandatory
	DESCRIPTION
		"The statistics for one disk."
	INDEX	{ dskIndex }
	::= { dskTable 1 }

DskEntry ::= SEQUENCE {
    dskIndex
	INTEGER,
    dskName
	OCTET STRING,
    dskUtil
	INTEGER,
    dskDemand
	INTEGER,
    dskSizeMB
	INTEGER,
    dskBlkSize
	INTEGER,
    dskUsedPct
	INTEGER,
    dskStatus
	INTEGER,
    dskNOperations
	Counter,
    dskNBlocks
	Counter,
    dskResp
	TimeTicks,
    dskActive
	TimeTicks,
    dskNMisc
	Counter,
    dskNErrs
	Counter,
    dskPctBusy
	INTEGER,
    dskAvgWait
	INTEGER,
    dskAvgService
	INTEGER
}

dskIndex OBJECT-TYPE
	SYNTAX  INTEGER
	ACCESS  read-only
	STATUS  mandatory
	DESCRIPTION
		"A unique value for each disk on the server, used by SNMP to 
		order the table."
	::= { dskEntry 1 }

dskName OBJECT-TYPE
	SYNTAX  OCTET STRING
	ACCESS  read-only
	STATUS  mandatory
	DESCRIPTION
		"The name of the disk unit."
	::= { dskEntry 2 }

dskUtil OBJECT-TYPE
	SYNTAX  INTEGER
	ACCESS  not-accessible
	STATUS  mandatory
	DESCRIPTION
		"A five minute exponential decaying average showing the 
		percentage of time that the disk unit was in use transferring
		data."
	::= { dskEntry 3 }

dskDemand OBJECT-TYPE
	SYNTAX 	INTEGER
	ACCESS  not-accessible
	STATUS  mandatory
	DESCRIPTION
		"A five minute exponential decaying average showing the 
		percentage of time that the disk unit needed to be used to 
		satisfy all requests."
	::= { dskEntry 4 }

dskSizeMB OBJECT-TYPE
	SYNTAX  INTEGER
	ACCESS  read-only
	STATUS  mandatory
	DESCRIPTION
		"The size of the disk in megabytes."
	::= { dskEntry 5 }

dskUsedPct OBJECT-TYPE
	SYNTAX  INTEGER
	ACCESS  read-only
	STATUS  mandatory
	DESCRIPTION
		"The percentage of disk space that is currently in use."
	::= { dskEntry 6 }

dskStatus OBJECT-TYPE
	SYNTAX  INTEGER {
	        down(1),     
	        up(2)
	    }
	ACCESS  read-only
	STATUS  mandatory
	DESCRIPTION
		"The disks status, 1 is non-operational, 2 is operational."
	::= { dskEntry 7 }

dskNOperations OBJECT-TYPE
	SYNTAX  Counter
	ACCESS  read-only
	STATUS  mandatory
	DESCRIPTION
		"The total number of reads and writes for the disk since the
		server was last booted."
	::= { dskEntry 8 }

dskNBlocks OBJECT-TYPE
	SYNTAX  Counter
	ACCESS  read-only
	STATUS  mandatory
	DESCRIPTION
		"The total number of 1-kilobyte data blocks transferred to and
		from the disk since the server was last booted."
	::= { dskEntry 9 }

dskResp OBJECT-TYPE
	SYNTAX  TimeTicks
	ACCESS  read-only
	STATUS  mandatory
	DESCRIPTION
		"The total amount of time processes spent waiting for a
		response from the disks."
	::= { dskEntry 10 }

dskActive OBJECT-TYPE
	SYNTAX  TimeTicks
	ACCESS  read-only
	STATUS  mandatory
	DESCRIPTION
		"The total amount of the disk was active."
	::= { dskEntry 11 }

dskBlkSize OBJECT-TYPE
	SYNTAX  INTEGER
	ACCESS  read-only
	STATUS  mandatory
	DESCRIPTION
		"The block size in megabytes."
	::= { dskEntry 12 }

dskNMisc OBJECT-TYPE
	SYNTAX  Counter
	ACCESS  read-only
	STATUS  mandatory
	DESCRIPTION
		"The total number of miscellaneous disk operations since the
		server was last booted."
	::= { dskEntry 13 }

dskNErrs OBJECT-TYPE
	SYNTAX  Counter
	ACCESS  read-only
	STATUS  mandatory
	DESCRIPTION
		"The total number of disk errors that were not logged since
		the server was last booted."
	::= { dskEntry 14 }

dskPctBusy OBJECT-TYPE
	SYNTAX 	INTEGER
	ACCESS  read-only
	STATUS  optional
	DESCRIPTION
		"A five minute exponential decaying average showing the 
		percentage of time that the disk spent servicing data 
		transfer requests."
	::= { dskEntry 15 }

dskAvgWait OBJECT-TYPE
	SYNTAX  INTEGER
	ACCESS  read-only
	STATUS  optional
	DESCRIPTION
		"A five minute exponential decaying average showing the 
		average amount of time that read and write requests waited
		on the request queue to be serviced."
	::= { dskEntry 16 }

dskAvgService OBJECT-TYPE
	SYNTAX  INTEGER
	ACCESS  read-only
	STATUS  optional
	DESCRIPTION
		"A five minute exponential decaying average showing the 
		average amount of time that the disk took to service read
		and write requests."
	::= { dskEntry 17 }


-- the Filesystem group  

fsTotCache OBJECT-TYPE
	SYNTAX  INTEGER
	ACCESS  read-write
	STATUS  mandatory
	DESCRIPTION
		"The amount of server RAM, in kilobytes, that is used for
		caching purposes.  This is configurable from the server's
		console.
	 	Note: The setting of this object will not take 
		effect until the server is rebooted."
	::= { filesystem 1 }

fsCacheBufSize OBJECT-TYPE
	SYNTAX  INTEGER
	ACCESS  read-write
	STATUS  mandatory
	DESCRIPTION
		"The amount of server RAM, in kilobytes, that makes up a file 
		system cache buffer.  Also configurable from the console.
	 	Note: The setting of this object will not take 
		effect until the server is rebooted."
	::= { filesystem 2 }

fsMaxOpenFiles OBJECT-TYPE
	SYNTAX  INTEGER
	ACCESS  read-only
	STATUS  mandatory
	DESCRIPTION
		"The largest number of open files on the server at a single
		point in time."
	::= { filesystem 3 }

fsOpenFiles OBJECT-TYPE
	SYNTAX  INTEGER
	ACCESS  read-only
	STATUS  mandatory
	DESCRIPTION
		"The number of files currently open."
	::= { filesystem 4 }

fsMaxOpensOnFiles OBJECT-TYPE
	SYNTAX  INTEGER
	ACCESS  read-only
	STATUS  mandatory
	DESCRIPTION
		"The largest number of open operations on files at a single
		point in time.  There can be more than one open operation on
		an open file.  For example, two users may open the same file.
		This file would count as one open file and two open operations
		on the file."
	::= { filesystem 5 }

fsOpensOnFiles OBJECT-TYPE
	SYNTAX  INTEGER
	ACCESS  read-only
	STATUS  mandatory
	DESCRIPTION
		"The current number of open operations on files."
	::= { filesystem 6 }

fsRecLocks OBJECT-TYPE
	SYNTAX  INTEGER
	ACCESS  read-only
	STATUS  mandatory
	DESCRIPTION
		"The current number of record locks."
	::= { filesystem 7 }

fsMaxRecLocks OBJECT-TYPE
	SYNTAX  INTEGER
	ACCESS  read-only
	STATUS  mandatory
	DESCRIPTION
		"The largest number of simultaneous record locks."
	::= { filesystem 8 }

fsPctCacheHits OBJECT-TYPE
	SYNTAX  INTEGER
	ACCESS  read-only
	STATUS  mandatory
	DESCRIPTION
		"The percentage of cache buffer requests that the system was
		able to service using existing cache buffers, without reading
		new data from disk."
	::= { filesystem 9 }

fsCacheUnavail OBJECT-TYPE
	SYNTAX  Counter
	ACCESS  read-only
	STATUS  mandatory
	DESCRIPTION
		"The number of cache buffer requests that the server was 
		unable to service without reading new data from disk."
	::= { filesystem 10 }

-- the Commresources group  

commTotBufs OBJECT-TYPE
	SYNTAX  INTEGER
	ACCESS  read-write
	STATUS  mandatory
	DESCRIPTION
		"The total communications buffer space (the amount of server
		RAM used for network communications) in kilobytes.  This is
		configurable from the server's console.
	 	Note: The setting of this object will not take 
		effect until the servers is rebooted."
	::= { commresources 1 }

commBufUsage OBJECT-TYPE
	SYNTAX  INTEGER
	ACCESS  read-only
	STATUS  mandatory
	DESCRIPTION
		"The percentage of the communications buffer space currently 
		in use."
	::= { commresources 2 }

commAllocsFailed OBJECT-TYPE
	SYNTAX  Counter
	ACCESS  read-only
	STATUS  mandatory
	DESCRIPTION
		"The cumulative total of the number of buffers that could not
		be allocated since the server was last booted."
	::= { commresources 3 }

commSocksCfg OBJECT-TYPE
	SYNTAX  INTEGER
	ACCESS  read-write
	STATUS  mandatory
	DESCRIPTION
		"The maximum number of sockets that can be open at one time.
		Configurable from the server console.
	 	Note: The setting of this object will not take 
		effect until the servers is rebooted."
	::= { commresources 4 }

commSocksInUse OBJECT-TYPE
	SYNTAX  INTEGER
	ACCESS  read-only
	STATUS  mandatory
	DESCRIPTION
		"The percentage of the maximum configured sockets in use."
	::= { commresources 5 }

commMaxOpenSocks OBJECT-TYPE
	SYNTAX  INTEGER
	ACCESS  read-only
	STATUS  mandatory
	DESCRIPTION
		"The maximum number of sockets in use since the server was
		last booted."
	::= { commresources 6 }

-- the VIP group

vipTotIn OBJECT-TYPE
	SYNTAX  Counter
	ACCESS  read-only
	STATUS  mandatory
	DESCRIPTION
		"The total number of VINES IP packets that the server has
		received since the server was last booted."
	::= { vip 1 }

vipTotOut OBJECT-TYPE
	SYNTAX  Counter
	ACCESS  read-only
	STATUS  mandatory
	DESCRIPTION
		"The total number of VINES IP packets that the server has
		sent since the server was last booted."
	::= { vip 2 }

vipBad OBJECT-TYPE
	SYNTAX  Counter
	ACCESS  read-only
	STATUS  mandatory
	DESCRIPTION
		"The number of packets that the server has received since the 
		server was last booted that had an incorrect checksum."
	::= { vip 3 }

vipRouted OBJECT-TYPE
	SYNTAX  Counter
	ACCESS  read-only
	STATUS  mandatory
	DESCRIPTION
		"The total number of packets that were routed to another node
		since the server was last booted."
	::= { vip 4 }

vipRoutedHWM OBJECT-TYPE
	SYNTAX  INTEGER
	ACCESS  read-only
	STATUS  mandatory
	DESCRIPTION
		"The largest number of packets routed in 1 second since the 
		server was last booted."
	::= { vip 5 }

vipBcast OBJECT-TYPE
	SYNTAX  Counter
	ACCESS  read-only
	STATUS  mandatory
	DESCRIPTION
		"The number of VINES IP broadcast packets sent, both generated
		from the server and routed from other nodes."
	::= { vip 6 }

vipBcastHWM OBJECT-TYPE
	SYNTAX  INTEGER
	ACCESS  read-only
	STATUS  mandatory
	DESCRIPTION
		"The largest number of packets broadcast in 1 second since the
		server was last booted."
	::= { vip 7 }

vipReass OBJECT-TYPE
	SYNTAX  Counter
	ACCESS  read-only
	STATUS  mandatory
	DESCRIPTION
		"The number of times packets were reassembled since the server
		was last booted.  One VINES IP packet being broken into three
		message fragments is counted as one fragmentation.  The three
		fragments being reassembled into one VINES IP packet counts as
		one reassembly."
	::= { vip 8 }

vipFrags OBJECT-TYPE
	SYNTAX  Counter
	ACCESS  read-only
	STATUS  mandatory
	DESCRIPTION
		"The number of packet fragmentations performed since the server
		was last booted."
	::= { vip 9 }

vipToDodIP OBJECT-TYPE
	SYNTAX  Counter
	ACCESS  read-only
	STATUS  mandatory
	DESCRIPTION
		"The number of packets that VINES IP passed to DARPA IP 
		(TCP/IP) for encapsulation in IP headers since the server was
		last booted."
	::= { vip 10 }

vipFromDodIP OBJECT-TYPE
	SYNTAX  Counter
	ACCESS  read-only
	STATUS  mandatory
	DESCRIPTION
		"The number of packets that VINES IP received from DARPA IP
		(TCP/IP) since the server was last booted."
	::= { vip 11 }

vipInFragments OBJECT-TYPE
	SYNTAX  Counter
	ACCESS  read-only
	STATUS  mandatory
	DESCRIPTION
		"The number of fragments received since the server was last
		booted."
	::= { vip 12 }

vipTooSmall OBJECT-TYPE
	SYNTAX  Counter
	ACCESS  read-only
	STATUS  mandatory
	DESCRIPTION
		"The number of packets that the server has received since the 
		server was last booted that were too small."
	::= { vip 13 }

vipBadLength OBJECT-TYPE
	SYNTAX  Counter
	ACCESS  read-only
	STATUS  mandatory
	DESCRIPTION
		"The number of packets that the server has received since the 
		server was last booted that had an invalid packet length in
		the packet length field of the VINES IP header."
	::= { vip 14 }

vipNoBuffers OBJECT-TYPE
	SYNTAX  Counter
	ACCESS  read-only
	STATUS  mandatory
	DESCRIPTION
		"The number of packets that the server could not send, 
		receive or route due to a lack of communication buffers
		since the server was last booted."
	::= { vip 15 }

-- the VRTP group

vrtpNbrNumber  OBJECT-TYPE
	SYNTAX  INTEGER
	ACCESS  read-only
	STATUS  mandatory
	DESCRIPTION
		"The number of entries in the neighbor table (NbrTable)."
	::= { vrtp 1 }

vrtpNbrTable OBJECT-TYPE
	SYNTAX  SEQUENCE OF NbrEntry
	ACCESS  not-accessible
	STATUS  mandatory
	DESCRIPTION
		"A list of information about neighbors of this server."
	::= { vrtp 2 }

vrtpNbrEntry OBJECT-TYPE
	SYNTAX  NbrEntry
	ACCESS  not-accessible
	STATUS  mandatory
	DESCRIPTION
		"The information for each entry in the table."
	INDEX	{ vrtpNbrNetid,
		  vrtpNbrSubNetid,
		  vrtpNbrIfType,
		  vrtpNbrLocSlot,
		  vrtpNbrLocLine }
	::= { vrtpNbrTable 1 }

NbrEntry ::= SEQUENCE {
    vrtpNbrNetid
	INTEGER,
    vrtpNbrSubNetid
	INTEGER,
    vrtpNbrType
	INTEGER, 
    vrtpNbrIfType
	INTEGER,
    vrtpNbrRemAddress
	OCTET STRING,
    vrtpNbrLocAddress
	OCTET STRING,
    vrtpNbrLocSlot
	INTEGER,
    vrtpNbrLocLine
	INTEGER,
    vrtpNbrSvrName
	OCTET STRING
}

vrtpNbrNetid OBJECT-TYPE
	SYNTAX  INTEGER
	ACCESS  read-only
	STATUS  mandatory
	DESCRIPTION
		"The network ID of the neighbor, which is the first part of
		the neighbor's VINES internet address.  If the neighbor is a
		server the network number is the server's serial number."
	::= { vrtpNbrEntry 1 }

vrtpNbrSubNetid OBJECT-TYPE
	SYNTAX  INTEGER
	ACCESS  read-only
	STATUS  mandatory
	DESCRIPTION
		"The subnetwork ID of the neighbor, which is the second part of
		the neighbor's VINES internet address.  If the neighbor is a
		server the subnetwork number is 1."
	::= { vrtpNbrEntry 2 }

vrtpNbrType OBJECT-TYPE
	SYNTAX  INTEGER {
	        server(1),
	        workstation(2)
	    }
	ACCESS  read-only
	STATUS  mandatory
	DESCRIPTION
		"The type of the neighbor (workstation = pc)."
	::= { vrtpNbrEntry 3 }

vrtpNbrIfType OBJECT-TYPE
	SYNTAX  INTEGER {
		    ethernet3Com(1),
		    ethernetNI5010(2),
		    ethernetBICC(3),
		    ethernetUB(4),
		    omninetCorvus(5),
		    arcnetSMC(6),
		    pcnetSytek(7),
		    proNetProteon(8),
		    frag(9),
		    prsystctrl(10),
		    hdlc(11),
		    blkAsync(12),
		    intersys(13),
		    x25EICON(14),
		    tokenRingIBM(15),	
		    x25(16),
		    tokenRingUB(17),
		    ipaDavidSys(18),
		    tokenRingPronet4(19),
		    ethernetEplus3Com(20),
		    lanLinkNT(21),
		    ctrllerGanges(22),
		    ethernetNI5210(23),
		    ipTCPIP(24),
		    ipBanyan(25),
		    hdlcTCPIP(26),
		    starlanWDigital(27),
		    ethernetWDigital(28),
		    starlanATT(29),	
		    starlanNI5210(30),
		    ethernet3Com3C503(31), 
		    ethernet3Com3C523(32),
		    tokenRing3Com3C603(33),
		    lanLinkNTMC(34),
		    serialVGsystems(35),
		    ethernetIntelPC586E(36),
		    starlanATT10(37),
		    pronetProteonMC(38),
		    arcnetSMCMC(39),
		    tokenRingIBMMC(40),
		    ethernetNI9210MC(41),
		    ethernetICAMC(42),
		    pseudoIBM(43),
		    starlanATT10MC(44),
		    ps2UBNICMC(45),
		    llTurboNT(46),
		    tokenRingProteon(47),
		    ethernetNovellNE(48),
		    ctrlerDATACO(49),
		    hughes(50),
		    ethernetNDIS(51),
		    gatewayAPI(52),
		    tokenRingMadge(53),
		    ethernetIBMMC(54),
		    tokenRingIBMBM(55),
		    ethernetWDigitalMC(56),
		    interlanEISA(57),
		    ethernetBICC(58),
		    ethernetNT2R15(59),
		    ethernetNTMC(60),
		    ethernetNTTurbo(61),
		    tokenRingPronet(62),
		    tokenRingCompaq(63),
		    isoSvrSvr(64),
		    ethernetNovellNE3200(65),
		    ethernetPureData(66),
		    ethernetPureDataMC(67),
		    ethernetCabletron(68),
		    ftp(69),
		    arcnetNDIS(70),
		    tokenRingNDIS(71),
		    starlanATTEISA(72),
		    appleTalk(73),
		    localTalk(74),
		    etherLink3COM16(75),
		    interlanNI6510(76),
		    tokenRingProteonP1890(77),
		    ethernetBICCMC(78),
		    icaPlus(79),
		    ipNSRouting(80),
		    etherExpressIntel(81),
		    tokenRingOlicom(82),
		    tokenRingOlicomMC(83),
		    tokenRingOlicamEISA(84),
		    tokenExpressIntelISA(85),
		    tokenExpressIntelMC(86),
		    tokenExpressIntelEISA(87),
		    tokenRingIrmaTracPCAT(88),
		    tokenRingIrmaTracMCA(89),
		    ethernetDGCODE(90),
		    isdnBRIDatavoice(91),
		    wavelanNCR(92),
		    unused(93),
		    unused(94),
		    unused(95),
		    unused(96),
		    unused(97),
		    unused(98),
		    unused(99),
		    promptusT1(100),
		    promptusE1(101),
		    lapdT1(102),
		    isdnDchannel(103)
		}	
	ACCESS  read-only
	STATUS  mandatory
	DESCRIPTION
		"The type of interface that the server uses to reach the 
		neighbor."
	::= { vrtpNbrEntry 4 }

vrtpNbrRemAddress OBJECT-TYPE
	SYNTAX  OCTET STRING
	ACCESS  read-only
	STATUS  mandatory
	DESCRIPTION
		"The address of the neighbor's physical interface, such as a 
		LAN address.  If the neighbor is connected via an HDLC or 
		asynchronous line this object specifies an internal ID."
	::= { vrtpNbrEntry 5 }

vrtpNbrLocAddress OBJECT-TYPE
	SYNTAX  OCTET STRING
	ACCESS  read-only
	STATUS  mandatory
	DESCRIPTION
		"The address of the server's physical interface, such as a 
		LAN address."
	::= { vrtpNbrEntry 6 }

vrtpNbrLocSlot OBJECT-TYPE
	SYNTAX  INTEGER
	ACCESS  read-only
	STATUS  mandatory
	DESCRIPTION
		"The slot number of the interface card that the server uses to
		reach the neighbor."
	::= { vrtpNbrEntry 7 }

vrtpNbrLocLine OBJECT-TYPE
	SYNTAX  INTEGER
	ACCESS  read-only
	STATUS  mandatory
	DESCRIPTION
		"The number of the line on the serial card that the server uses
		to reach the neighbor.  It does not apply to neighbors that are
		reached over LANs."
	::= { vrtpNbrEntry 8 }

vrtpNbrSvrName OBJECT-TYPE
	SYNTAX  OCTET STRING
	ACCESS  read-only
	STATUS  optional
	DESCRIPTION
		"The name of the neighbor.  If the neighbor is a workstation
		then this object has no meaning."
	::= { vrtpNbrEntry 9 }

vrtpRtNumber  OBJECT-TYPE
	SYNTAX  INTEGER
	ACCESS  read-only
	STATUS  mandatory
	DESCRIPTION
		"The number of entires in the route table (RtTable)."
	::= { vrtp 3 }

vrtpRtTable OBJECT-TYPE
	SYNTAX  SEQUENCE OF RtEntry
	ACCESS  not-accessible
	STATUS  mandatory
	DESCRIPTION
		"A list of networks and the routing information to find them."
	::= { vrtp 4 }

vrtpRtEntry OBJECT-TYPE
	SYNTAX  RtEntry
	ACCESS  not-accessible
	STATUS  mandatory
	DESCRIPTION
		"An entry for one network."
	INDEX	{ vrtpRtNetid }
	::= { vrtpRtTable 1 }

RtEntry ::= SEQUENCE {
    vrtpRtNetid
	INTEGER,
    vrtpRtMetric
	INTEGER,
    vrtpRtIdle
	INTEGER,
    vrtpRtGateNetid
	INTEGER,
    vrtpRtSvrName
	OCTET STRING,
    vrtpRtGateSvrName
	OCTET STRING
}

vrtpRtNetid OBJECT-TYPE
	SYNTAX  INTEGER
	ACCESS  read-only
	STATUS  mandatory
	DESCRIPTION
		"The network ID of the route's destination server."
	::= { vrtpRtEntry 1 }

vrtpRtMetric OBJECT-TYPE
	SYNTAX  INTEGER
	ACCESS  read-only
	STATUS  mandatory
	DESCRIPTION
		"The routing metric used by the called server to reach the
		destination.  The metric reflects the cost of the path to
		the destination, it is in 200-millisecond units."
	::= { vrtpRtEntry 2 }

vrtpRtIdle OBJECT-TYPE
	SYNTAX  INTEGER 
	ACCESS  read-only
	STATUS  mandatory
	DESCRIPTION
		"The time to live timer for this route's entry.  This value 
		indicicates the amount of time before the entry is removed 
		from the called server's routing table.  The value is returned
		in 90 second units."
	::= { vrtpRtEntry 3 }

vrtpRtGateNetid OBJECT-TYPE
	SYNTAX  INTEGER
	ACCESS  read-only
	STATUS  mandatory
	DESCRIPTION
		"The network ID of the server that acts as the router for 
		reaching the destination server."
	::= { vrtpRtEntry 4 }

vrtpRtSvrName OBJECT-TYPE
	SYNTAX  OCTET STRING
	ACCESS  read-only
	STATUS  optional
	DESCRIPTION
		"The name of the destination server."
	::= { vrtpRtEntry 5 }

vrtpRtGateSvrName OBJECT-TYPE
	SYNTAX  OCTET STRING
	ACCESS  read-only
	STATUS  optional
	DESCRIPTION
		"The name of the server that acts as the router for reaching
		the destination server."
	::= { vrtpRtEntry 6 }

vrtpTotIn  OBJECT-TYPE
	SYNTAX  Counter
	ACCESS  read-only
	STATUS  mandatory
	DESCRIPTION
		"The number of VINES VRTP packets received since the 
		server was last booted."
	::= { vrtp 5 }

vrtpTotOut  OBJECT-TYPE
	SYNTAX  Counter
	ACCESS  read-only
	STATUS  mandatory
	DESCRIPTION
		"The number of VINES VRTP packets sent since the server 
		was last booted."
	::= { vrtp 6 }

vrtpErrsIn  OBJECT-TYPE
	SYNTAX  Counter
	ACCESS  read-only
	STATUS  mandatory
	DESCRIPTION
		"The number of errors the VRTP protocol encountered while
		receiving packets, since the server was last booted."
	::= { vrtp 7 }

vrtpNoBuffersIn  OBJECT-TYPE
	SYNTAX  Counter
	ACCESS  read-only
	STATUS  optional
	DESCRIPTION
		"The number of times that no communication buffers were
		available to process received RTP packets or create
		routine table entries."
	::= { vrtp 8 }

vrtpUpdatesIn  OBJECT-TYPE
	SYNTAX  Counter
	ACCESS  read-only
	STATUS  optional
	DESCRIPTION
		"The total number of update packets received."
	::= { vrtp 9 }

vrtpResponsesIn  OBJECT-TYPE
	SYNTAX  Counter
	ACCESS  read-only
	STATUS  optional
	DESCRIPTION
		"The number of responses received."
	::= { vrtp 10 }

vrtpRqstsIn  OBJECT-TYPE
	SYNTAX  Counter
	ACCESS  read-only
	STATUS  optional
	DESCRIPTION
		"The number of requests received."
	::= { vrtp 11 }

vrtpRqstLkUpIn  OBJECT-TYPE
	SYNTAX  Counter
	ACCESS  read-only
	STATUS  optional
	DESCRIPTION
		"The number of packets received that requested routing
		information."
	::= { vrtp 12 }

vrtpRqstSlrInfoIn  OBJECT-TYPE
	SYNTAX  Counter
	ACCESS  read-only
	STATUS  optional
	DESCRIPTION
		"The number of request packets received that requested VINES
		routine metric information on a source-level route (Sequenced
		Only)."
	::= { vrtp 13 }

vrtpReinitIn  OBJECT-TYPE
	SYNTAX  Counter
	ACCESS  read-only
	STATUS  optional
	DESCRIPTION
		"The number reinitialization packets received
		(Sequenced Only)."
	::= { vrtp 14 }

vrtpResyncIn  OBJECT-TYPE
	SYNTAX  Counter
	ACCESS  read-only
	STATUS  optional
	DESCRIPTION
		"The number of resynchronization operations or update
		packets received that contained information for 
		synchronizing routing table entries."	
	::= { vrtp 15 }

vrtpRedirIn  OBJECT-TYPE
	SYNTAX  Counter
	ACCESS  read-only
	STATUS  optional
	DESCRIPTION
		"The number of redirect packets received."
	::= { vrtp 16 }

vrtpFragsIn  OBJECT-TYPE
	SYNTAX  Counter
	ACCESS  read-only
	STATUS  optional
	DESCRIPTION
		"The number of update or response fragments received
		(Sequenced Only)."
	::= { vrtp 17 }

vrtpFragsDropIn  OBJECT-TYPE
	SYNTAX  Counter
	ACCESS  read-only
	STATUS  optional
	DESCRIPTION
		"The number of packets dropped due to either the time
		taken to reassemble was too long or no communication
		buffer were available(SEQUENCED ONLY)."
	::= { vrtp 18 }

vrtpFragsBadIn  OBJECT-TYPE
	SYNTAX  Counter
	ACCESS  read-only
	STATUS  optional
	DESCRIPTION
		"The number of RTP fragments discarded because they
		had packet IDs that were out-of-sequence (SEQUENCED 
		ONLY)."
	::= { vrtp 19 }

vrtpFragsDupIn  OBJECT-TYPE
	SYNTAX  Counter
	ACCESS  read-only
	STATUS  optional
	DESCRIPTION
		"The number of RTP fragments that were dropped because
		they were duplicates of other fragments (SEQUENCED ONLY)."
	::= { vrtp 20 }

vrtpFragsDoneIn  OBJECT-TYPE
	SYNTAX  Counter
	ACCESS  read-only
	STATUS  optional
	DESCRIPTION
		"The number of updates and responses that were fragmented
		or reassembled successfully(SEQUENCED ONLY)."
	::= { vrtp 21 }

vrtpReassBadIn  OBJECT-TYPE
	SYNTAX  Counter
	ACCESS  read-only
	STATUS  optional
	DESCRIPTION
		"The number of updates and responses that were not 
		successfully fragmented or reassembled (SEQUENCED ONLY)."
	::= { vrtp 22 }

vrtpOutdatedIn  OBJECT-TYPE
	SYNTAX  Counter
	ACCESS  read-only
	STATUS  optional
	DESCRIPTION
		"The number of received RTP packets discarded because they
		were outdated (SEQUENCED ONLY)."
	::= { vrtp 23 }

vrtpNetInfoBad  OBJECT-TYPE
	SYNTAX  Counter
	ACCESS  read-only
	STATUS  optional
	DESCRIPTION
		"The number of received outdated entries for logical networks 
		(SEQUENCED ONLY)."
	::= { vrtp 24 }

vrtpBadRdrs  OBJECT-TYPE
	SYNTAX  Counter
	ACCESS  read-only
	STATUS  optional
	DESCRIPTION
		"The number of redirect packets discarded because of a bad
		length."
	::= { vrtp 25 }

vrtpBdcstIn  OBJECT-TYPE
	SYNTAX  Counter
	ACCESS  read-only
	STATUS  optional
	DESCRIPTION
		"The number of broadcasted RTP update packets received."
	::= { vrtp 26 }

vrtpNoBuffersOut  OBJECT-TYPE
	SYNTAX  Counter
	ACCESS  read-only
	STATUS  optional
	DESCRIPTION
		"The number of times that no communication buffers were
		available to send RTP packets."
	::= { vrtp 27 }

vrtpUpdatesOut  OBJECT-TYPE
	SYNTAX  Counter
	ACCESS  read-only
	STATUS  optional
	DESCRIPTION
		"The total number of update packets sent."
	::= { vrtp 28 }

vrtpRqstLkUpOut  OBJECT-TYPE
	SYNTAX  Counter
	ACCESS  read-only
	STATUS  optional
	DESCRIPTION
		"The number of packets sent that requested routing
		information."
	::= { vrtp 29 }

vrtpRqstSlrInfoOut  OBJECT-TYPE
	SYNTAX  Counter
	ACCESS  read-only
	STATUS  optional
	DESCRIPTION
		"The number of request packets sent that requested VINES
		routine metric information on a source-level route (SEQUENCED
		ONLY)."
	::= { vrtp 30 }

vrtpRqstsOut  OBJECT-TYPE
	SYNTAX  Counter
	ACCESS  read-only
	STATUS  optional
	DESCRIPTION
		"The number of requests sent."
	::= { vrtp 31}

vrtpReinitOut  OBJECT-TYPE
	SYNTAX  Counter
	ACCESS  read-only
	STATUS  optional
	DESCRIPTION
		"The number reinitialization packets sent (SEQUENCED ONLY)."
	::= { vrtp 32 }

vrtpResyncOut  OBJECT-TYPE
	SYNTAX  Counter
	ACCESS  read-only
	STATUS  optional
	DESCRIPTION
		"The number of resynchronization operations or update
		packets sent that contained information for 
		synchronizing routing table entries."	
	::= { vrtp 33 }

vrtpRedirOut  OBJECT-TYPE
	SYNTAX  Counter
	ACCESS  read-only
	STATUS  optional
	DESCRIPTION
		"The number of redirect packets sent."
	::= { vrtp 34 }

vrtpFragsOut  OBJECT-TYPE
	SYNTAX  Counter
	ACCESS  read-only
	STATUS  optional
	DESCRIPTION
		"The number of update or response fragments sent
		(SEQUENCED ONLY)."
	::= { vrtp 35 }

vrtpFragsDoneOut  OBJECT-TYPE
	SYNTAX  Counter
	ACCESS  read-only
	STATUS  optional
	DESCRIPTION
		"The number of updates and responses that were fragmented
		successfully (SEQUENCED ONLY)."
	::= { vrtp 36 }

vrtpFragsBadOut  OBJECT-TYPE
	SYNTAX  Counter
	ACCESS  read-only
	STATUS  optional
	DESCRIPTION
		"The number of updates and responses that were fragmented
		unsuccessfully (SEQUENCED ONLY)."
	::= { vrtp 37 }

vrtpFragsDropOut  OBJECT-TYPE
	SYNTAX  Counter
	ACCESS  read-only
	STATUS  optional
	DESCRIPTION
		"The number of packets dropped due to either the time
		taken to fragment the message was too long or no communication
		buffer were available (SEQUENCED ONLY)."
	::= { vrtp 38 }

vrtpBdcstOut  OBJECT-TYPE
	SYNTAX  Counter
	ACCESS  read-only
	STATUS  optional
	DESCRIPTION
		"The number of broadcasted RTP update packets sent."
	::= { vrtp 39 }

vrtpRtCr  OBJECT-TYPE
	SYNTAX  Counter
	ACCESS  read-only
	STATUS  optional
	DESCRIPTION
		"The number of routes created by redirect packets."
	::= { vrtp 40 }

vrtpRtMod  OBJECT-TYPE
	SYNTAX  Counter
	ACCESS  read-only
	STATUS  optional
	DESCRIPTION
		"The number of routes modified by redirect packets."
	::= { vrtp 41 }

vrtpNbrAnchors  OBJECT-TYPE
	SYNTAX  Counter
	ACCESS  read-only
	STATUS  optional
	DESCRIPTION
		"The total entries in the neighbor table or total
		paths to all neighbors."
	::= { vrtp 42 }

vrtpNbrEntries  OBJECT-TYPE
	SYNTAX  Counter
	ACCESS  read-only
	STATUS  optional
	DESCRIPTION
		"The total entries in the neighbor table or total
		paths to all neighbors."
	::= { vrtp 43 }

vrtpNetEntries  OBJECT-TYPE
	SYNTAX  Counter
	ACCESS  read-only
	STATUS  optional
	DESCRIPTION
		"The total entries for networks in this server's network
		table."
	::= { vrtp 44 }

vrtpLkUp  OBJECT-TYPE
	SYNTAX  Counter
	ACCESS  read-only
	STATUS  optional
	DESCRIPTION
		"The number of calls to look up network table entries 
		by the server."
	::= { vrtp 45 }

vrtpBadLkUp  OBJECT-TYPE
	SYNTAX  Counter
	ACCESS  read-only
	STATUS  optional
	DESCRIPTION
		"The number of calls to look up network table entries 
		by the server that failed."
	::= { vrtp 46 }

vrtpNonSeqTotIn  OBJECT-TYPE
	SYNTAX  Counter
	ACCESS  read-only
	STATUS  optional
	DESCRIPTION
		"The number of non-sequenced RTP packets received."
	::= { vrtp 47 }

vrtpNonSeqTotOut  OBJECT-TYPE
	SYNTAX  Counter
	ACCESS  read-only
	STATUS  optional
	DESCRIPTION
		"The number of non-sequenced RTP packets sent."
	::= { vrtp 48 }

vrtpNonSeqErrsIn  OBJECT-TYPE
	SYNTAX  Counter
	ACCESS  read-only
	STATUS  optional
	DESCRIPTION
		"The number of errors while receiving non-sequenced RTP
		packets."
	::= { vrtp 49 }

vrtpNonSeqUpdIn  OBJECT-TYPE
	SYNTAX  Counter
	ACCESS  read-only
	STATUS  optional
	DESCRIPTION
		"The number of non-sequenced update packets received."
	::= { vrtp 50 }

vrtpNonSeqRspIn  OBJECT-TYPE
	SYNTAX  Counter
	ACCESS  read-only
	STATUS  optional
	DESCRIPTION
		"The number of non-sequenced responses received."
	::= { vrtp 51 }

vrtpNonSeqRqstIn  OBJECT-TYPE
	SYNTAX  Counter
	ACCESS  read-only
	STATUS  optional
	DESCRIPTION
		"The number of non-sequenced requests received."
	::= { vrtp 52 }

vrtpNonSeqRdrIn  OBJECT-TYPE
	SYNTAX  Counter
	ACCESS  read-only
	STATUS  optional
	DESCRIPTION
		"The number of non-sequenced redirect packets received."
	::= { vrtp 53 }

vrtpBadNonSeqRdrIn  OBJECT-TYPE
	SYNTAX  Counter
	ACCESS  read-only
	STATUS  optional
	DESCRIPTION
		"The number of invalid non-sequenced redirect packets
		received."
	::= { vrtp 54 }

vrtpNonSeqBdcstIn  OBJECT-TYPE
	SYNTAX  Counter
	ACCESS  read-only
	STATUS  optional
	DESCRIPTION
		"The number of non-sequenced broadcast packets received."
	::= { vrtp 55 }

vrtpNonSeqUpdOut  OBJECT-TYPE
	SYNTAX  Counter
	ACCESS  read-only
	STATUS  optional
	DESCRIPTION
		"The number of non-sequenced update packets sent."
	::= { vrtp 56 }

vrtpNonSeqRspOut  OBJECT-TYPE
	SYNTAX  Counter
	ACCESS  read-only
	STATUS  optional
	DESCRIPTION
		"The number of non-sequenced responses sent."
	::= { vrtp 57 }

vrtpNonSeqRqstOut  OBJECT-TYPE
	SYNTAX  Counter
	ACCESS  read-only
	STATUS  optional
	DESCRIPTION
		"The number of non-sequenced requests sent."
	::= { vrtp 58 }

vrtpNonSeqRdrOut  OBJECT-TYPE
	SYNTAX  Counter
	ACCESS  read-only
	STATUS  optional
	DESCRIPTION
		"The number of non-sequenced redirect packets sent."
	::= { vrtp 59 }

vrtpNonSeqBdcstOut  OBJECT-TYPE
	SYNTAX  Counter
	ACCESS  read-only
	STATUS  optional
	DESCRIPTION
		"The number of non-sequenced broadcast packets sent."
	::= { vrtp 60 }

vrtpResponsesOut  OBJECT-TYPE
	SYNTAX  Counter
	ACCESS  read-only
	STATUS  optional
	DESCRIPTION
		"The number of responses sent."
	::= { vrtp 61 }

-- the VSPP group

vsppConnsInUse OBJECT-TYPE
	SYNTAX  INTEGER
	ACCESS  read-only
	STATUS  mandatory
	DESCRIPTION
		"The number of SPP connections currently in use by processes
		on the server."
	::= { vspp 1 }

vsppConnsCfg OBJECT-TYPE
	SYNTAX  INTEGER
	ACCESS  read-write
	STATUS  mandatory
	DESCRIPTION
		"The allowable maximum number of SPP connections that 
		can be in use by processes on the server at one time.
	 	Note: The setting of this object will not take 
		effect until the servers is rebooted."
	::=  { vspp 2 }

vsppMaxConns OBJECT-TYPE
	SYNTAX  INTEGER
	ACCESS  read-only
	STATUS  mandatory
	DESCRIPTION
		"The maximum number of SPP connections in use at a single
		point in time since the server was last booted."
	::= { vspp 3 }

vsppTotIn OBJECT-TYPE
	SYNTAX  Counter
	ACCESS  read-only
	STATUS  mandatory
	DESCRIPTION
		"The total number of VINES SPP packets that the server has
		received since the server was last booted."
	::= { vspp 4 }

vsppTotOut OBJECT-TYPE
	SYNTAX  Counter
	ACCESS  read-only
	STATUS  mandatory
	DESCRIPTION
		"The total number of VINES SPP packets that the server has
		sent since the server was last booted."
	::= { vspp 5 }

vsppInErrs OBJECT-TYPE
	SYNTAX  Counter
	ACCESS  read-only
	STATUS  optional
	DESCRIPTION
		"The number of SPP errors encountered while
		receiving packets, since the server was last booted."
	::= { vspp 6 }

vsppBadType OBJECT-TYPE
	SYNTAX  Counter
	ACCESS  read-only
	STATUS  optional
	DESCRIPTION
		"The total number of packets received on SPP connections 
		that had invalid SPP packet types."
	::= { vspp 7 }

vsppNoBuffers OBJECT-TYPE
	SYNTAX  Counter
	ACCESS  read-only
	STATUS  optional
	DESCRIPTION
		"The number of packets that the server could not send, 
		receive or route due to a lack of communication buffers
		since the server was last booted."
	::= { vspp 8 }

vsppNoPort OBJECT-TYPE
	SYNTAX  Counter
	ACCESS  read-only
	STATUS  optional
	DESCRIPTION
		"The number of incoming packets that the server dropped 
		due to an unmatched destination port or an unmatched
		connection ID."
	::= { vspp 9 }

vsppDups OBJECT-TYPE
	SYNTAX  Counter
	ACCESS  read-only
	STATUS  optional
	DESCRIPTION
		"The number of incoming packets that were duplicates
		of other packets."
	::= { vspp 10 }

vsppBadOrder OBJECT-TYPE
	SYNTAX  Counter
	ACCESS  read-only
	STATUS  optional
	DESCRIPTION
		"The number of incoming packets that were received
		out of order."
	::= { vspp 11 }

vsppDataIn OBJECT-TYPE
	SYNTAX  Counter
	ACCESS  read-only
	STATUS  optional
	DESCRIPTION
		"The number of packets received on SPP connections."
	::= { vspp 12 }

vsppAcksIn OBJECT-TYPE
	SYNTAX  Counter
	ACCESS  read-only
	STATUS  optional
	DESCRIPTION
		"The number of acknowledgement packets received."
	::= { vspp 13 }

vsppDiscIn OBJECT-TYPE
	SYNTAX  Counter
	ACCESS  read-only
	STATUS  optional
	DESCRIPTION
		"The number of disconnected packets received on SPP 
		connections."
	::= { vspp 14 }

vsppProbesIn OBJECT-TYPE
	SYNTAX  Counter
	ACCESS  read-only
	STATUS  optional
	DESCRIPTION
		"The number of probe packets received on SPP connections."
	::= { vspp 15 }

vsppDataOut OBJECT-TYPE
	SYNTAX  Counter
	ACCESS  read-only
	STATUS  optional
	DESCRIPTION
		"The number of data packets sent on SPP connections."
	::= { vspp 16 }

vsppAcksOut OBJECT-TYPE
	SYNTAX  Counter
	ACCESS  read-only
	STATUS  optional
	DESCRIPTION
		"The number of acknowledgement packets sent."
	::= { vspp 17 }

vsppDiscOut OBJECT-TYPE
	SYNTAX  Counter
	ACCESS  read-only
	STATUS  optional
	DESCRIPTION
		"The number of disconnected packets sent on SPP 
		connections."
	::= { vspp 18 }

vsppProbesOut OBJECT-TYPE
	SYNTAX  Counter
	ACCESS  read-only
	STATUS  optional
	DESCRIPTION
		"The number of probe packets sent on SPP connections."
	::= { vspp 19 }

vsppAbortsOut OBJECT-TYPE
	SYNTAX  Counter
	ACCESS  read-only
	STATUS  optional
	DESCRIPTION
		"The number of data packets that had the abort bit
		set."
	::= { vspp 20 }

vsppLocal OBJECT-TYPE
	SYNTAX  Counter
	ACCESS  read-only
	STATUS  optional
	DESCRIPTION
		"The number of packets sent locally using SPP.
		connections."
	::= { vspp 21 }

-- the Vinterfaces group

vifNumber OBJECT-TYPE
	SYNTAX  INTEGER
	ACCESS  read-only
	STATUS  mandatory
	DESCRIPTION
		"The number of VINES interfaces configured on the server."
	::= { vinterfaces 1 }

vifTable OBJECT-TYPE
	SYNTAX  SEQUENCE OF IfEntry
	ACCESS  not-accessible
	STATUS  mandatory
	DESCRIPTION
		"List of interfaces with some statistics about each interface."
	::= { vinterfaces 2 }

vifEntry OBJECT-TYPE
	SYNTAX  IfEntry
	ACCESS  not-accessible
	STATUS  mandatory
	DESCRIPTION
		"Information about one interface."
	INDEX	{ vifSlot }
	::= { vifTable 1 }

IfEntry ::= SEQUENCE {
    vifSlot
	INTEGER,
    vifType
	INTEGER, 
    vifDescr
	OCTET STRING,
    vifAddress
	OCTET STRING,
    vifInPkts
	Counter,
    vifInErrs
	Counter,
    vifOutPkts
	Counter,
    vifOutErrs
	Counter
}

vifSlot OBJECT-TYPE
	SYNTAX  INTEGER
	ACCESS  read-only
	STATUS  mandatory
	DESCRIPTION
		"The slot number of the interface's communications card."
	::= { vifEntry 1 }

vifType OBJECT-TYPE
	SYNTAX  INTEGER {
		    ethernet3Com(1),
		    ethernetNI5010(2),
		    ethernetBICC(3),
		    ethernetUB(4),
		    omninetCorvus(5),
		    arcnetSMC(6),
		    pcnetSytek(7),
		    proNetProteon(8),
		    frag(9),
		    prsystctrl(10),
		    hdlc(11),
		    blkAsync(12),
		    intersys(13),
		    x25EICON(14),
		    tokenRingIBM(15),	
		    x25(16),
		    tokenRingUB(17),
		    ipaDavidSys(18),
		    tokenRingPronet4(19),
		    ethernetEplus3Com(20),
		    lanLinkNT(21),
		    ctrllerGanges(22),
		    ethernetNI5210(23),
		    ipTCPIP(24),
		    ipBanyan(25),
		    hdlcTCPIP(26),
		    starlanWDigital(27),
		    ethernetWDigital(28),
		    starlanATT(29),	
		    starlanNI5210(30),
		    ethernet3Com3C503(31), 
		    ethernet3Com3C523(32),
		    tokenRing3Com3C603(33),
		    lanLinkNTMC(34),
		    serialVGsystems(35),
		    ethernetIntelPC586E(36),
		    starlanATT10(37),
		    pronetProteonMC(38),
		    arcnetSMCMC(39),
		    tokenRingIBMMC(40),
		    ethernetNI9210MC(41),
		    ethernetICAMC(42),
		    pseudoIBM(43),
		    starlanATT10MC(44),
		    ps2UBNICMC(45),
		    llTurboNT(46),
		    tokenRingProteon(47),
		    ethernetNovellNE(48),
		    ctrlerDATACO(49),
		    hughes(50),
		    ethernetNDIS(51),
		    gatewayAPI(52),
		    tokenRingMadge(53),
		    ethernetIBMMC(54),
		    tokenRingIBMBM(55),
		    ethernetWDigitalMC(56),
		    interlanEISA(57),
		    ethernetBICC(58),
		    ethernetNT2R15(59),
		    ethernetNTMC(60),
		    ethernetNTTurbo(61),
		    tokenRingPronet(62),
		    tokenRingCompaq(63),
		    isoSvrSvr(64),
		    ethernetNovellNE3200(65),
		    ethernetPureData(66),
		    ethernetPureDataMC(67),
		    ethernetCabletron(68),
		    ftp(69),
		    arcnetNDIS(70),
		    tokenRingNDIS(71),
		    starlanATTEISA(72),
		    appleTalk(73),
		    localTalk(74),
		    etherLink3COM16(75),
		    interlanNI6510(76),
		    tokenRingProteonP1890(77),
		    ethernetBICCMC(78),
		    icaPlus(79),
		    ipNSRouting(80),
		    etherExpressIntel(81),
		    tokenRingOlicom(82),
		    tokenRingOlicomMC(83),
		    tokenRingOlicamEISA(84),
		    tokenExpressIntelISA(85),
		    tokenExpressIntelMC(86),
		    tokenExpressIntelEISA(87),
		    tokenRingIrmaTracPCAT(88),
		    tokenRingIrmaTracMCA(89),
		    ethernetDGCODE(90),
		    isdnBRIDatavoice(91),
		    wavelanNCR(92),
		    unused(93),
		    unused(94),
		    unused(95),
		    unused(96),
		    unused(97),
		    unused(98),
		    unused(99),
		    promptusT1(100),
		    promptusE1(101),
		    lapdT1(102),
		    isdnDchannel(103)
		}	
	ACCESS  read-only
	STATUS  mandatory
	DESCRIPTION
		"The interface type, types are the same as defined for 
		vrtpNbrIfType in the vrtp neighbor table."
	::= { vifEntry 2 }


vifDescr OBJECT-TYPE
	SYNTAX  OCTET STRING
	ACCESS  read-only
	STATUS  mandatory
	DESCRIPTION
		"A textual description of the interface."
	::= { vifEntry 3 }

vifAddress OBJECT-TYPE
	SYNTAX  OCTET STRING
	ACCESS  read-only
	STATUS  mandatory
	DESCRIPTION
		"The physical address of the interface, applies to LAN
		interfaces only."
	::= { vifEntry 4 }

vifInPkts OBJECT-TYPE
	SYNTAX  Counter
	ACCESS  read-only
	STATUS  mandatory
	DESCRIPTION
		"The total number of VINES IP packets that the server
		received since the last reboot."
	::= { vifEntry 5 }

vifInErrs OBJECT-TYPE
	SYNTAX  Counter
	ACCESS  read-only
	STATUS  mandatory
	DESCRIPTION
		"The total number of received VINES IP packets that contained
		errors since the last reboot."
	::= { vifEntry 6 }

vifOutPkts OBJECT-TYPE
	SYNTAX  Counter
	ACCESS  read-only
	STATUS  mandatory
	DESCRIPTION
		"The total number of VINES IP packets that the server
		sent since the last reboot."
	::= { vifEntry 7 }

vifOutErrs OBJECT-TYPE
	SYNTAX  Counter
	ACCESS  read-only
	STATUS  mandatory
	DESCRIPTION
		"The total number of transmitted VINES IP packets that 
		contained errors since the last reboot."
	::= { vifEntry 8 }

vifLnkNumber OBJECT-TYPE
	SYNTAX  INTEGER
	ACCESS  read-only
	STATUS  mandatory
	DESCRIPTION
		"The number of serial links connected to the server."
	::= { vinterfaces 3 }

vifLnkTable OBJECT-TYPE
	SYNTAX  SEQUENCE OF LnkEntry
	ACCESS  not-accessible
	STATUS  mandatory
	DESCRIPTION
		"Data link level statistics for the serial lines on 
		this server."
	::= { vinterfaces 4 }

vifLnkEntry OBJECT-TYPE
	SYNTAX  LnkEntry
	ACCESS  not-accessible
	STATUS  mandatory
	DESCRIPTION
		"Stats for one serial line."
	INDEX	{ vifLnkSlot,
		  vifLnkLine }
	::= { vifLnkTable 1 }

LnkEntry ::= SEQUENCE {
    vifLnkSlot
	INTEGER,
    vifLnkLine
	INTEGER,
    vifLnkType
	INTEGER,
    vifLnkTotIn
	Counter,
    vifLnkTotOut
	Counter,
    vifLnkRetrans
	Counter,
    vifLnkCRCErrs
	Counter,
    vifLnkDrops
	Counter,
    vifLnkUnders
	Counter,
    vifLnkOvers
	Counter,
    vifLnkFrmErrs
	Counter
}

vifLnkSlot OBJECT-TYPE
	SYNTAX  INTEGER
	ACCESS  read-only
	STATUS  mandatory
	DESCRIPTION
		"The slot number of the serial communications card to which
		the serial line is connected."
	::= { vifLnkEntry 1 }

vifLnkLine OBJECT-TYPE
	SYNTAX  INTEGER
	ACCESS  read-only
	STATUS  mandatory
	DESCRIPTION
		"The line number of the line on the serial communications 
		card."
	::= { vifLnkEntry 2 }

vifLnkType OBJECT-TYPE
	SYNTAX  INTEGER {
		ate(1),
		unused2(2),
		unused3(3),
		unused4(4),
		unused5(5),
		unused6(6),
	        blkasynch(7),
	        hdlc(8),
	        x25(9),
	        sdlcv1(10),
	        bsc3270(11),
	        sdlcv2(12)
	    }
	ACCESS  read-only
	STATUS  mandatory
	DESCRIPTION
		"The type of data link level protocol used on this line.
		1 Asynchronous Terminal Emulation.
		7 Block asynchronous.
		8 High-level Data Link Control (HDLC).
		9 X.25
		10 Synchronous DataLink Control (SDLC) 1.
		11 3270/BSC bisynchronous communication.
		12 Same as SDLC1 except line is connected to an ICA card."
	::= { vifLnkEntry 3 }

vifLnkTotIn OBJECT-TYPE
	SYNTAX  Counter
	ACCESS  read-only
	STATUS  mandatory
	DESCRIPTION
		"The total number of frames received."
	::= { vifLnkEntry 4 }

vifLnkTotOut OBJECT-TYPE
	SYNTAX  Counter
	ACCESS  read-only
	STATUS  mandatory
	DESCRIPTION
		"The total number of frames transmitted."
	::= { vifLnkEntry 5 }

vifLnkRetrans OBJECT-TYPE
	SYNTAX  Counter
	ACCESS  read-only
	STATUS  mandatory
	DESCRIPTION
		"The total number of frames retransmitted."
	::= { vifLnkEntry 6 }

vifLnkCRCErrs OBJECT-TYPE
	SYNTAX  Counter
	ACCESS  read-only
	STATUS  mandatory
	DESCRIPTION
		"The number of errors due to CRC or frames that the card
		dropped."
	::= { vifLnkEntry 7 }

vifLnkDrops OBJECT-TYPE
	SYNTAX  Counter
	ACCESS  read-only
	STATUS  mandatory
	DESCRIPTION
		"The number of frames that the server could not receive due to
		a lack of communications buffers."
	::= { vifLnkEntry 8 }

vifLnkUnders OBJECT-TYPE
	SYNTAX  Counter
	ACCESS  read-only
	STATUS  mandatory
	DESCRIPTION
		"The total number of transmitter underrun errors on receive."
	::= { vifLnkEntry 9 }

vifLnkOvers OBJECT-TYPE
	SYNTAX  Counter
	ACCESS  read-only
	STATUS  mandatory
	DESCRIPTION
		"The total number of receiver overrun errors on receive."
	::= { vifLnkEntry 10 }

vifLnkFrmErrs OBJECT-TYPE
	SYNTAX  Counter
	ACCESS  read-only
	STATUS  mandatory
	DESCRIPTION
		"The total number of framing errors."
	::= { vifLnkEntry 11 }

vifX25VCNumber OBJECT-TYPE
	SYNTAX  INTEGER
	ACCESS  read-only
	STATUS  mandatory
	DESCRIPTION
		"The number of X.25 virtual circuits that are available to
		the server."
	::= { vinterfaces 5 }

vifX25VCTable OBJECT-TYPE
	SYNTAX  SEQUENCE OF X25VCEntry
	ACCESS  not-accessible
	STATUS  mandatory
	DESCRIPTION
		"A list of X.25 packet level statistics for the virtual 
		circuit."
	::= { vinterfaces 6 }

vifX25VCEntry OBJECT-TYPE
	SYNTAX  X25VCEntry
	ACCESS  not-accessible
	STATUS  mandatory
	DESCRIPTION
		"Statistics for one virtual circuit."
	INDEX	{ vifX25VCSlot,
		  vifX25VCLine,
		  vifX25VCSession }
	::= { vifX25VCTable 1 }

X25VCEntry ::= SEQUENCE {
    vifX25VCSlot
	INTEGER,
    vifX25VCLine
	INTEGER,
    vifX25VCSession
	INTEGER,
    vifX25VCTotIn
	Counter,
    vifX25VCTotOut
	Counter,
    vifX25VCInErrs
	Counter,
    vifX25VCOutErrs
	Counter,
    vifX25VCPktsOut
	Counter,
    vifX25VCPktsAwaitAck
	INTEGER,
    vifX25VCBytesOut
	Counter,
    vifX25VCBytesAwaitAck
	INTEGER,
    vifX25VCPktsIn
	Counter,
    vifX25VCBytesIn
	Counter,
    vifX25VCResetsIn
	Counter,
    vifX25VCResetsOut
	Counter,
    vifX25VCLogChnNum
	INTEGER,
    vifX25VCRemAddr
	OCTET STRING
}

vifX25VCSlot OBJECT-TYPE
	SYNTAX  INTEGER
	ACCESS  read-only
	STATUS  mandatory
	DESCRIPTION
		"The slot number of the serial communications card to which
		the virtual circuit's line is connected."
	::= { vifX25VCEntry 1 }

vifX25VCLine OBJECT-TYPE
	SYNTAX  INTEGER
	ACCESS  read-only
	STATUS  mandatory
	DESCRIPTION
		"The number of the X.25 line configured on the serial 
		communications card."
	::= { vifX25VCEntry 2 }

vifX25VCSession OBJECT-TYPE
	SYNTAX  INTEGER
	ACCESS  read-only
	STATUS  mandatory
	DESCRIPTION
		"The local session number of the virtual circuit."
	::= { vifX25VCEntry 3 }

vifX25VCTotIn OBJECT-TYPE
	SYNTAX  Counter
	ACCESS  read-only
	STATUS  mandatory
	DESCRIPTION
		"The total number of VINES IP packets received on this VC."
	::= { vifX25VCEntry 4 }

vifX25VCTotOut OBJECT-TYPE
	SYNTAX  Counter
	ACCESS  read-only
	STATUS  mandatory
	DESCRIPTION
		"The total number of VINES IP packets sent on this VC."
	::= { vifX25VCEntry 5 }

vifX25VCInErrs OBJECT-TYPE
	SYNTAX  Counter
	ACCESS  read-only
	STATUS  mandatory
	DESCRIPTION
		"The total number of received X.25 packets that contained 
		errors."
	::= { vifX25VCEntry 6 }

vifX25VCOutErrs OBJECT-TYPE
	SYNTAX  Counter
	ACCESS  read-only
	STATUS  mandatory
	DESCRIPTION
		"The total number of transmitted X.25 packets that contained
		errors."
	::= { vifX25VCEntry 7 }

vifX25VCPktsOut OBJECT-TYPE
	SYNTAX  Counter
	ACCESS  read-only
	STATUS  mandatory
	DESCRIPTION
		"The total number of X.25 packets transmitted."
	::= { vifX25VCEntry 8 }

vifX25VCPktsAwaitAck OBJECT-TYPE
	SYNTAX  INTEGER
	ACCESS  read-only
	STATUS  mandatory
	DESCRIPTION
		"The total number of X.25 packets transmitted that are 
		awaiting acknowledgement."
	::= { vifX25VCEntry 9 }

vifX25VCBytesOut OBJECT-TYPE
	SYNTAX  Counter
	ACCESS  read-only
	STATUS  mandatory
	DESCRIPTION
		"The total number of bytes transmitted."
	::= { vifX25VCEntry 10 }

vifX25VCBytesAwaitAck OBJECT-TYPE
	SYNTAX  INTEGER
	ACCESS  read-only
	STATUS  mandatory
	DESCRIPTION
		"The total number of bytes transmitted that are awaiting
		acknowledgement."
	::= { vifX25VCEntry 11 }

vifX25VCPktsIn OBJECT-TYPE
	SYNTAX  Counter
	ACCESS  read-only
	STATUS  mandatory
	DESCRIPTION
		"The total number of X.25 packets that have been received."
	::= { vifX25VCEntry 12 }

vifX25VCBytesIn OBJECT-TYPE
	SYNTAX  Counter
	ACCESS  read-only
	STATUS  mandatory
	DESCRIPTION
		"The total number of bytes received."
	::= { vifX25VCEntry 13 }

vifX25VCResetsIn OBJECT-TYPE
	SYNTAX  Counter
	ACCESS  read-only
	STATUS  mandatory
	DESCRIPTION
		"The total number of X.25 reset packets received."
	::= { vifX25VCEntry 14 }

vifX25VCResetsOut OBJECT-TYPE
	SYNTAX  Counter
	ACCESS  read-only
	STATUS  mandatory
	DESCRIPTION
		"The total number of X.25 reset packets transmitted."
	::= { vifX25VCEntry 15 }

vifX25VCLogChnNum OBJECT-TYPE
	SYNTAX  INTEGER
	ACCESS  read-only
	STATUS  mandatory
	DESCRIPTION
		"The logical channel number of the X.25 VC."
	::= { vifX25VCEntry 16 }

vifX25VCRemAddr OBJECT-TYPE
	SYNTAX  OCTET STRING
	ACCESS  read-only
	STATUS  mandatory
	DESCRIPTION
		"The DTE address of the remote server on the other 
		end of the VC."
	::= { vifX25VCEntry 17 }

vifStatsList OBJECT-TYPE
	SYNTAX  SEQUENCE OF VifStatEntry
	ACCESS  not-accessible
	STATUS  mandatory
	DESCRIPTION
		"A list of statistics for each LAN card in the server.  The
		type and quantity of statistics depend on the type of the 
		card."
	::= { vinterfaces 7 }

vifStatEntry OBJECT-TYPE
	SYNTAX  VifStatEntry
	ACCESS  not-accessible
	STATUS  mandatory
	DESCRIPTION
		"The statistics for one card."
	INDEX	{ vifStatSlot,
		  vifStatIndex }
	::= { vifStatsList 1 }

VifStatEntry ::= SEQUENCE {
    vifStatSlot
	INTEGER,
    vifStatIndex
	INTEGER,
    vifStatDescr
	OCTET STRING,
    vifStatValue
	INTEGER
}

vifStatSlot OBJECT-TYPE
	SYNTAX  INTEGER
	ACCESS  read-only
	STATUS  mandatory
	DESCRIPTION
		"The slot number of the LAN interface card."
	::= { vifStatEntry 1 }

vifStatIndex OBJECT-TYPE
	SYNTAX  INTEGER
	ACCESS  read-only
	STATUS  mandatory
	DESCRIPTION
		"A unique value for each statistic, used by SNMP to order
		the table."
	::= { vifStatEntry 2 }

vifStatDescr OBJECT-TYPE
	SYNTAX  OCTET STRING
	ACCESS  read-only
	STATUS  mandatory
	DESCRIPTION
		"A brief description of the statistic."
	::= { vifStatEntry 3 }

vifStatValue OBJECT-TYPE
	SYNTAX  INTEGER
	ACCESS  read-only
	STATUS  mandatory
	DESCRIPTION
		"The value of the statistic."
	::= { vifStatEntry 4 }

-- the os group 

oscpuNum OBJECT-TYPE
	SYNTAX  INTEGER
	ACCESS  read-only
	STATUS  mandatory
	DESCRIPTION
		"The number of processors."
	::= { ossysstats 1 }

oscpuTable OBJECT-TYPE
	SYNTAX  SEQUENCE OF CpuEntry
	ACCESS  not-accessible
	STATUS  mandatory
	DESCRIPTION
		"A list of processors on the server."
	::= { ossysstats 2 }

oscpuEntry OBJECT-TYPE
	SYNTAX  CpuEntry  
	ACCESS  not-accessible
	STATUS  mandatory
	DESCRIPTION
		"Each entry contains a set of statistics for one CPU."
	INDEX	{ cpuIndex }
	::= { oscpuTable 1 }

CpuEntry ::= SEQUENCE {
    cpuIndex
	INTEGER,
    cpuIdleUsage 
	TimeTicks,
    cpuUserUsage 
	TimeTicks,
    cpuSysUsage 
	TimeTicks,
    cpuWIOUserUsage
	TimeTicks,
    cpuProcSwappedOut
	TimeTicks,
    cpuWIOUsage
	TimeTicks,
    cpuWSUsage
	TimeTicks,
    cpuWPIOUsage
	TimeTicks
}

cpuIndex OBJECT-TYPE
	SYNTAX  INTEGER
	ACCESS  read-only
	STATUS  mandatory
	DESCRIPTION
		"A unique value for each processor on the server."
	::= { oscpuEntry 1 }

cpuIdleUsage OBJECT-TYPE
	SYNTAX	TimeTicks
	ACCESS	read-only
	STATUS	mandatory
	DESCRIPTION
		"The amount of time that the CPU was completely idle since
		boot time."
	::= { oscpuEntry 2 }

cpuUserUsage OBJECT-TYPE
	SYNTAX	TimeTicks
	ACCESS	read-only
	STATUS	mandatory
	DESCRIPTION
		"The amount of time the CPU spent running processes that
		run in user space since boot time."
	::= { oscpuEntry 3 }

cpuSysUsage OBJECT-TYPE
	SYNTAX	TimeTicks
	ACCESS	read-only
	STATUS	mandatory
	DESCRIPTION
		"The amount of time the CPU spent running processes that
		run in system mode since boottime."
	::= { oscpuEntry 4 }

cpuWIOUserUsage OBJECT-TYPE
	SYNTAX	TimeTicks
	ACCESS	read-only
	STATUS	mandatory
	DESCRIPTION
		"The amount of time that the CPU was idle, but at least
		one process was waiting for an I/O operation to complete,
		since boot time."
	::= { oscpuEntry 5 }

cpuProcSwappedOut OBJECT-TYPE
	SYNTAX	TimeTicks
	ACCESS	read-only
	STATUS	mandatory
	DESCRIPTION
		"The amount of time that the CPU had processes swapped out."
	::= { oscpuEntry 6 }

cpuWIOUsage OBJECT-TYPE
	SYNTAX	TimeTicks
	ACCESS	read-only
	STATUS	mandatory
	DESCRIPTION
		"The amout of time that the CPU waited for I/O to occur."
	::= { oscpuEntry 7 }

cpuWSUsage OBJECT-TYPE
	SYNTAX	TimeTicks
	ACCESS	read-only
	STATUS	mandatory
	DESCRIPTION
		"The amout of time that the CPU waited for a swap to occur."
	::= { oscpuEntry 8 }

cpuWPIOUsage OBJECT-TYPE
	SYNTAX	TimeTicks
	ACCESS	read-only
	STATUS	mandatory
	DESCRIPTION
		"The amout of time that the CPU waited for device I/O to 
		occur."
	::= { oscpuEntry 9 }

osBReads OBJECT-TYPE
	SYNTAX	Counter
	ACCESS	read-only
	STATUS	mandatory
	DESCRIPTION
		"The number of transfers from disk to system buffers since
		boot time."
	::= { ossysstats 3 }

osBWrites OBJECT-TYPE
	SYNTAX	Counter
	ACCESS	read-only
	STATUS	mandatory
	DESCRIPTION
		"The number of transfers from system buffers to disk since
		boot time."
	::= { ossysstats 4 }

osLReads OBJECT-TYPE
	SYNTAX	Counter
	ACCESS	read-only
	STATUS	mandatory
	DESCRIPTION
		"The number of reads on the system buffers since boot time."
	::= { ossysstats 5 }

osLWrites OBJECT-TYPE
	SYNTAX	Counter
	ACCESS	read-only
	STATUS	mandatory
	DESCRIPTION
		"The number of writes on the system buffers since boot time."
	::= { ossysstats 6 }

osPReads OBJECT-TYPE
	SYNTAX	Counter
	ACCESS	read-only
	STATUS	mandatory
	DESCRIPTION
		"The number of reads via the raw (physical) device mechanism
		since boot time."
	::= { ossysstats 7 }

osPWrites OBJECT-TYPE
	SYNTAX	Counter
	ACCESS	read-only
	STATUS	mandatory
	DESCRIPTION
		"The number of writes via the raw (physical) device mechanism
		since boot time."
	::= { ossysstats 8 }

osInSwaps OBJECT-TYPE
	SYNTAX	Counter
	ACCESS	read-only
	STATUS	mandatory
	DESCRIPTION
		"The number of swaps in since boot time."
	::= { ossysstats 9 }

osOutSwaps OBJECT-TYPE
	SYNTAX	Counter
	ACCESS	read-only
	STATUS	mandatory
	DESCRIPTION
		"The number of swaps out since boot time."
	::= { ossysstats 10 }

osInBSwaps OBJECT-TYPE
	SYNTAX	Counter
	ACCESS	read-only
	STATUS	mandatory
	DESCRIPTION
		"The number of 4 KB buffers transferred in since boot time."
	::= { ossysstats 11 }

osOutBSwaps OBJECT-TYPE
	SYNTAX	Counter
	ACCESS	read-only
	STATUS	mandatory
	DESCRIPTION
		"The number of 4 KB buffers transferred out since boot time."
	::= { ossysstats 12 }

osProcessSwitches OBJECT-TYPE
	SYNTAX	Counter
	ACCESS	read-only
	STATUS	mandatory
	DESCRIPTION
		"The number of process switches since boot time."
	::= { ossysstats 13 }

osSystemCalls OBJECT-TYPE
	SYNTAX	Counter
	ACCESS	read-only
	STATUS	mandatory
	DESCRIPTION
		"The number of system calls since boot time."
	::= { ossysstats 14 }

osSystemRead OBJECT-TYPE
	SYNTAX	Counter
	ACCESS	read-only
	STATUS	mandatory
	DESCRIPTION
		"The number of system read calls."
	::= { ossysstats 15 }

osSystemWrite OBJECT-TYPE
	SYNTAX	Counter
	ACCESS	read-only
	STATUS	mandatory
	DESCRIPTION
		"The number of system write calls."
	::= { ossysstats 16 }

osSystemFork OBJECT-TYPE
	SYNTAX	Counter
	ACCESS	read-only
	STATUS	mandatory
	DESCRIPTION
		"The number of system fork calls."
	::= { ossysstats 17 }

osSystemExec OBJECT-TYPE
	SYNTAX	Counter
	ACCESS	read-only
	STATUS	mandatory
	DESCRIPTION
		"The number of system exec calls."
	::= { ossysstats 18 }

osRunQueue OBJECT-TYPE
	SYNTAX	Counter
	ACCESS	read-only
	STATUS	mandatory
	DESCRIPTION
		"The number of processes on the run queue."
	::= { ossysstats 19 }

osRunQueueOcc OBJECT-TYPE
	SYNTAX	TimeTicks
	ACCESS	read-only
	STATUS	mandatory
	DESCRIPTION
		"The amount of time that processes were on the run queue."
	::= { ossysstats 20 }

osSwapQueueTotals OBJECT-TYPE
	SYNTAX	Counter
	ACCESS	read-only
	STATUS	mandatory
	DESCRIPTION
		"The number of processes on the swap queue."
	::= { ossysstats 21 }

osSwapQueueOcc OBJECT-TYPE
	SYNTAX	TimeTicks
	ACCESS	read-only
	STATUS	mandatory
	DESCRIPTION
		"The amount of time that processes were on the swap queue."
	::= { ossysstats 22 }

osIPCMsgOps OBJECT-TYPE
	SYNTAX	Counter
	ACCESS	read-only
	STATUS	mandatory
	DESCRIPTION
		"The number of times a System V IPC message operation occurred."
	::= { ossysstats 23 }

osSemOps OBJECT-TYPE
	SYNTAX	Counter
	ACCESS	read-only
	STATUS	mandatory
	DESCRIPTION
		"The number of semaphore operations performed by processes."
	::= { ossysstats 24 }

osPnpFault OBJECT-TYPE
	SYNTAX	Counter
	ACCESS	read-only
	STATUS	mandatory
	DESCRIPTION
		"The number of times a process accessed a page which had not
		been page faulted in."
	::= { ossysstats 25 }

osWrtFault OBJECT-TYPE
	SYNTAX	Counter
	ACCESS	read-only
	STATUS	mandatory
	DESCRIPTION
		"The number of times processes attempted to write to a page 
		marked as copy-on-write."
	::= { ossysstats 26 }

osCurrentInodes OBJECT-TYPE
	SYNTAX	INTEGER
	ACCESS	read-only
	STATUS	mandatory
	DESCRIPTION
		"The number of inode table entries currently in the inode
		table."
	::= { ossysstats 27 }

osHWInodes OBJECT-TYPE
	SYNTAX	INTEGER
	ACCESS	read-only
	STATUS	mandatory
	DESCRIPTION
		"The high water mark of inode table entries in use since the
		last reboot of the called server."
	::= { ossysstats 28 }


osCurrentFiles OBJECT-TYPE
	SYNTAX	INTEGER
	ACCESS	read-only
	STATUS	mandatory
	DESCRIPTION
		"The number of open file table entries currently in the open
		file table."
	::= { ossysstats 29 }


osHWFiles OBJECT-TYPE
	SYNTAX	INTEGER
	ACCESS	read-only
	STATUS	mandatory
	DESCRIPTION
		"The high water mark of open file table entries in use since
		the last reboot of the called server."
	::= { ossysstats 30 }

osMaxInodes OBJECT-TYPE
	SYNTAX	INTEGER
	ACCESS	read-only
	STATUS	mandatory
	DESCRIPTION
		"The maximum number of inode table entries in the inode table."
	::= { osinfo 1 }

osMaxFiles OBJECT-TYPE
	SYNTAX	INTEGER
	ACCESS	read-only
	STATUS	mandatory
	DESCRIPTION
		"The maximum number of open file table entries in the open
		file table."
	::= { osinfo 2 }

osMaxProcesses OBJECT-TYPE
	SYNTAX	INTEGER
	ACCESS	read-only
	STATUS	mandatory
	DESCRIPTION
		"The maximum number of process table entries that UNIX on
		the server allocates."
	::= { osinfo 3 }

osSwapSpaceAvailable OBJECT-TYPE
	SYNTAX	INTEGER
	ACCESS	read-only
	STATUS	mandatory
	DESCRIPTION
		"The amount of swap space available in 512 byte blocks."
	::= { osinfo 4 }

osFreeMemoryTotal OBJECT-TYPE
	SYNTAX	INTEGER
	ACCESS	read-only
	STATUS	mandatory
	DESCRIPTION
		"The total amount of executable space in kilobytes."
	::= { osinfo 5 }

osIOBufs OBJECT-TYPE
	SYNTAX	INTEGER
	ACCESS	read-only
	STATUS	mandatory
	DESCRIPTION
		"The number of 1 KB system buffers that make up UNIX cache
		on the server."
	::= { osinfo 6 }

osMounts OBJECT-TYPE
	SYNTAX	INTEGER
	ACCESS	read-only
	STATUS	mandatory
	DESCRIPTION
		"The number of mount table entries that UNIX on the server
		allocates."
	::= { osinfo 7 }

osUserMaxPu OBJECT-TYPE
	SYNTAX	INTEGER
	ACCESS	read-only
	STATUS	mandatory
	DESCRIPTION
		"The maximum number of concurrent UNIX processes that can
		be run by users other than the superuser."
	::= { osinfo 8 }

osUserMaxFp OBJECT-TYPE
	SYNTAX	INTEGER
	ACCESS	read-only
	STATUS	mandatory
	DESCRIPTION
		"The maximum number of open files per process."
	::= { osinfo 9 }

osCurrentProcesses OBJECT-TYPE
	SYNTAX	INTEGER
	ACCESS	read-only
	STATUS	mandatory
	DESCRIPTION
		"The current number of entries in the process table."
	::= { ossummstats 1 }

osSwapSpaceUsed OBJECT-TYPE
	SYNTAX	INTEGER
	ACCESS	read-only
	STATUS	mandatory
	DESCRIPTION
		"The amount of swap space in use in 512 byte blocks."
	::= { ossummstats 2 }

osFreeMemoryAvailable OBJECT-TYPE
	SYNTAX	INTEGER
	ACCESS	read-only
	STATUS	mandatory
	DESCRIPTION
		"The amount of executable space, in kilobytes, currently 
		available."
	::= { ossummstats 3 }

osUserUsagePct OBJECT-TYPE
	SYNTAX	INTEGER
	ACCESS	read-only
	STATUS	optional
	DESCRIPTION
		"The percentage of time the CPU spent running processes that
		run in user space over the last five minutes."
	::= { ossummstats 4 }

osSysUsagePct OBJECT-TYPE
	SYNTAX	INTEGER
	ACCESS	read-only
	STATUS	mandatory
	DESCRIPTION
		"The percentage of time the CPU spent running processes that
		run in system mode over the last five minutes."
	::= { ossummstats 5 }

osWIOUsagePct OBJECT-TYPE
	SYNTAX	INTEGER
	ACCESS	read-only
	STATUS	mandatory
	DESCRIPTION
		"The percentage of time that the CPU was idle, but at least
		one process was waiting for an I/O operation to complete, over
		the last five minutes."
	::= { ossummstats 6 }

osIdleUsagePct OBJECT-TYPE
	SYNTAX	INTEGER
	ACCESS	read-only
	STATUS	mandatory
	DESCRIPTION
		"The percentage of time that the CPU was idle over
		the last five minutes."
	::= { ossummstats 7 }

osRunOccPct OBJECT-TYPE
	SYNTAX	INTEGER
	ACCESS	read-only
	STATUS	mandatory
	DESCRIPTION
		"The percentage of time that processes occupied the run queue
		over the last five minutes."
	::= { ossummstats 8 }

osSwapOccPct OBJECT-TYPE
	SYNTAX	INTEGER
	ACCESS	read-only
	STATUS	mandatory
	DESCRIPTION
		"The percentage of time that processes occupied the swap queue
		over the last five minutes."
	::= { ossummstats 9 }

osBuffRdRate OBJECT-TYPE
	SYNTAX	INTEGER
	ACCESS	read-only
	STATUS	mandatory
	DESCRIPTION
		"The average number of times per second that data was read from
		disk into UNIX system buffers over the last five minutes."
	::= { ossummstats 10 }

osRdCachePct OBJECT-TYPE
	SYNTAX	INTEGER
	ACCESS	read-only
	STATUS	mandatory
	DESCRIPTION
		"The percentage of read requests for UNIX system buffers that
		the kernel was able to service using existing UNIX system 
		buffers, without reading new data from disk over the last 
		five minutes."
	::= { ossummstats 11 }

osBuffWrRate OBJECT-TYPE
	SYNTAX	INTEGER
	ACCESS	read-only
	STATUS	mandatory
	DESCRIPTION
		"The average number of times per second that data was written 
	 	from UNIX system buffers to disk over the last five minutes."
	::= { ossummstats 12 }

osWrCachePct OBJECT-TYPE
	SYNTAX	INTEGER
	ACCESS	read-only
	STATUS	mandatory
	DESCRIPTION
		"The percentage of write requests for UNIX system buffers that
		the kernel was able to service using existing UNIX system 
		buffers, without writing new data to disk over the last 
		five minutes."
	::= { ossummstats 13 }

osBswpInRate OBJECT-TYPE
	SYNTAX	INTEGER
	ACCESS	read-only
	STATUS	mandatory
	DESCRIPTION
		"The average number of 4 KB pages that were swapped or paged
	 	from disk to main memory per second over the last five 
		minutes."
	::= { ossummstats 14 }

osBswpOutRate OBJECT-TYPE
	SYNTAX	INTEGER
	ACCESS	read-only
	STATUS	mandatory
	DESCRIPTION
		"The average number of 4 KB pages that were swapped or paged
	 	from main memory to disk per second over the last five 
		minutes."
	::= { ossummstats 15 }

osVfltRate OBJECT-TYPE
	SYNTAX	INTEGER
	ACCESS	read-only
	STATUS	mandatory
	DESCRIPTION
		"The average number of validity faults per second over the last
	 	five minutes."
	::= { ossummstats 16 }

osSwitchRate OBJECT-TYPE
	SYNTAX	INTEGER
	ACCESS	read-only
	STATUS	mandatory
	DESCRIPTION
		"The average number of process switches per second over the
		last five minutes."
	::= { ossummstats 17 }

osSysCallRate OBJECT-TYPE
	SYNTAX	INTEGER
	ACCESS	read-only
	STATUS	mandatory
	DESCRIPTION
		"The average number of UNIX system calls that processes issued
		per second over the last five minutes."
	::= { ossummstats 18 }

-- the NM thresholds group

nmLoadAvg15HighThres    OBJECT-TYPE
			SYNTAX  INTEGER
			ACCESS  read-write
			STATUS  mandatory
			DESCRIPTION
				"A High threshold value for the 15-minute
				 average of server load (ssLoadAvg15). If
				 the value of ssLoadAvg15 goes above this,
				 a VINES alert and a nmLoadAvgHigh Trap are
				 generated."

			::= { nmthresholds 1 }


nmSockInUseHighThres    OBJECT-TYPE
			SYNTAX  INTEGER
			ACCESS  read-write
			STATUS  mandatory
			DESCRIPTION
				"A High threshold value for the percentage
				 of maximum configured sockets currently in
				 use (commSocksInUse).  If the value of
				 commSocksInUse goes above this, a VINES alert
				 and a nmSockInUseHigh Trap are generated."

			::= { nmthresholds 2 }

nmDiskUseHighThres      OBJECT-TYPE
			SYNTAX  INTEGER
			ACCESS  read-write
			STATUS  mandatory
			DESCRIPTION
				"A High threshold value for the percentage
				 of disk space in use on any given disk
				 (dskUsedPct).  If the value of dskUsedPct
				 goes above this, a VINES alert and a
				 nmDiskFull Trap are generated."

			::= { nmthresholds 3 }

nmSwapAvgHighThres      OBJECT-TYPE
			SYNTAX  INTEGER
			ACCESS  read-write
			STATUS  mandatory
			DESCRIPTION
				"A High threshold value for the 1-minute
				 average of process swapping (ssSwapAvg). If
				 the value of ssSwapAvg goes above this,
				 a VINES alert and a nmSwapAvgHigh Trap are
				 generated."

			::= { nmthresholds 4 }


nmDropsHighThres        OBJECT-TYPE
			SYNTAX  INTEGER
			ACCESS  read-write
			STATUS  mandatory
			DESCRIPTION
				"A High threshold value for the no. of
				 messages dropped due to lack of comm
				 buffer space (ssDrops). If the value of
				 ssDrops goes above this, a VINES alert and
				 a nmDropsHigh Trap are generated."

			::= { nmthresholds 5 }


nmSwapSpaceLowThres     OBJECT-TYPE
			SYNTAX  INTEGER
			ACCESS  read-write
			STATUS  mandatory
			DESCRIPTION
				"A Low threshold value for the amount of
				 swap space available (osSwapSpaceAvailable).
				 If the value of osSwapSpaceAvailable drops
				 below this, a VINES alert and a nmFreeSwapLow
				 Trap are generated."

			::= { nmthresholds 6 }


nmFreeMemLowThres       OBJECT-TYPE
			SYNTAX  INTEGER
			ACCESS  read-write
			STATUS  mandatory
			DESCRIPTION
				"A Low threshold value for the amount of
				 memory free (osFreeMemoryAvailable).
				 If the value of osFreeMemoryAvailable drops
				 below this, a VINES alert and a nmFreeMemLow
				 Trap are generated."

			::= { nmthresholds 7 }


nmCommBuffHighThres     OBJECT-TYPE
			SYNTAX  INTEGER
			ACCESS  read-write
			STATUS  mandatory
			DESCRIPTION
				"A High threshold value for the percentage
				 of total comms buffer space currently in
				 use (commBufUsage).  If the value of
				 commBufUsage goes above this, a VINES alert
				 and a nmCommBuffHigh Trap are generated."

			::= { nmthresholds 8 }

nmAllocFailHighThres    OBJECT-TYPE
			SYNTAX  INTEGER
			ACCESS  read-write
			STATUS  mandatory
			DESCRIPTION
				"A High threshold value for the total of 
				 comm. buffers that could not be allocated
				 since the last reboot (commAllocsFailed).
				 If the value of commAllocsFailed goes above
				 this, a VINES alert and a nmAllocFailHigh
				 Trap are generated."

			::= { nmthresholds 9 }

nmCacheHitsLowThres     OBJECT-TYPE
			SYNTAX  INTEGER
			ACCESS  read-write
			STATUS  mandatory
			DESCRIPTION
				"A Low threshold value for the percentage
				 of cache buffer requests that the system 
				 was able to service using existing cache
				 buffers (fsPctCacheHits).  If the value of
				 fsPctCacheHits falls below this, a VINES
				 alert and a nmCacheHitsLow Trap are generated."

			::= { nmthresholds 10 }

nmDiskBusyHighThres     OBJECT-TYPE
			SYNTAX  INTEGER
			ACCESS  read-write
			STATUS  mandatory
			DESCRIPTION
				"A High threshold value for the 5-minute
				 average of the percentage of time a
				 disk was in use transferring data
				 (dskPctBusy).  If the value of dskPctBusy
				 rises above this, a VINES alert and a
				 nmDiskBusy Trap are generated."

			::= { nmthresholds 11 }

nmMsgAvgHighThres       OBJECT-TYPE
			SYNTAX  INTEGER
			ACCESS  read-write
			STATUS  mandatory
			DESCRIPTION
				"A High threshold value for the 1-minute
				 average of network messages sent/received
				 per second (ssMsgAvg1).  If the value of
				 ssMsgAvg1 goes above this, a VINES alert
				 and a nmMsgAvgHigh Trap are generated."

			::= { nmthresholds 12 }


nmInodeUseHighThres     OBJECT-TYPE
			SYNTAX  INTEGER
			ACCESS  read-write
			STATUS  mandatory
			DESCRIPTION
				"A High threshold value for the number
				 of inode table entries currently in the
				 inode table (osCurrentInodes).  If the
				 value of osCurrentInodes rises above this,
				 a VINES alert and a nmInodesHigh Trap are
				 generated."

			::= { nmthresholds 13 }


--  Objects used for Trap variables


tpAlertTime            OBJECT-TYPE
			SYNTAX  INTEGER
			ACCESS  not-accessible
			STATUS  mandatory
			DESCRIPTION
				"The system time when alert was issued to
				 the Alert Management Service, as specified
				 in UNIX time() format."

			::= { trapdata 1 }      


tpErrorCode            OBJECT-TYPE
			SYNTAX  INTEGER
			ACCESS  not-accessible
			STATUS  mandatory
			DESCRIPTION
				"A VINES error code." 

			::= { trapdata 2 }      


tpUserName             OBJECT-TYPE
			SYNTAX  OCTET STRING
			ACCESS  not-accessible
			STATUS  mandatory
			DESCRIPTION
				"A VINES StreetTalk user name." 

			::= { trapdata 3 }      


tpSvcName              OBJECT-TYPE
			SYNTAX  OCTET STRING
			ACCESS  not-accessible
			STATUS  mandatory
			DESCRIPTION
				"The StreetTalk Service name which issued
				 the trap."

			::= { trapdata 4 }


tpSvrName              OBJECT-TYPE
			SYNTAX  OCTET STRING
			ACCESS  not-accessible
			STATUS  mandatory
			DESCRIPTION
				"The name of the Server on which the trap
				 was issued."

			::= { trapdata 5 }


tpRefSvcName		OBJECT-TYPE
			SYNTAX  OCTET STRING
			ACCESS  not-accessible
			STATUS  mandatory
			DESCRIPTION
				"A StreetTalk Service name."

			::= { trapdata 6 }


tpRefSvrName		OBJECT-TYPE
			SYNTAX  OCTET STRING
			ACCESS  not-accessible
			STATUS  mandatory
			DESCRIPTION
				"The name of a Server."

			::= { trapdata 7 }


tpJobId                 OBJECT-TYPE
			SYNTAX  INTEGER
			ACCESS  not-accessible
			STATUS  mandatory
			DESCRIPTION
				"The Job Identifier for a particular job
				 in the Print Service." 

			::= { trapdata 8 }


tpPaperFormat           OBJECT-TYPE
			SYNTAX  OCTET STRING
			ACCESS  not-accessible
			STATUS  mandatory
			DESCRIPTION
				"The paper format type specified for a
				 print job." 

			::= { trapdata 9 }


tpJobTotal              OBJECT-TYPE
			SYNTAX INTEGER
			ACCESS not-accessible
			STATUS mandatory
			DESCRIPTION
				"The current number of jobs in the print
				 queue."

			::= { trapdata 10 }


tpConnId                OBJECT-TYPE
			SYNTAX INTEGER
			ACCESS not-accessible
			STATUS mandatory
			DESCRIPTION
				"A PostScript print service connection ID."

			::= { trapdata 11 }


tpMailSender            OBJECT-TYPE
			SYNTAX OCTET STRING
			ACCESS not-accessible
			STATUS mandatory
			DESCRIPTION
				"The StreetTalk user name of a mail sender."

			::= { trapdata 12 }


tpPortId                OBJECT-TYPE
			SYNTAX OCTET STRING
			ACCESS not-accessible
			STATUS mandatory
			DESCRIPTION
				"The Port ID being reported by VINES Security
				is the scene of a possible security breach."

			::= { trapdata 13 }


tpRtnName               OBJECT-TYPE
			SYNTAX OCTET STRING
			ACCESS not-accessible
			STATUS mandatory
			DESCRIPTION
				"The name of the executing routine when
				 the STDA service encountered a fatal error."

			::= { trapdata 14 }


tp162erravg             OBJECT-TYPE
			SYNTAX INTEGER
			ACCESS not-accessible
			STATUS mandatory
			DESCRIPTION
				"The current average of 162 errors."

			::= { trapdata 15 }


tp162errThresHigh       OBJECT-TYPE
			SYNTAX INTEGER
			ACCESS not-accessible
			STATUS mandatory
			DESCRIPTION
				"The High Threshold for 162 errors in ST."

			::= { trapdata 16 }


tp162errTotal           OBJECT-TYPE
			SYNTAX INTEGER
			ACCESS not-accessible
			STATUS mandatory
			DESCRIPTION
				"The current total of 162 errors in ST."

			::= { trapdata 17 }


tpGrpName               OBJECT-TYPE
			SYNTAX OCTET STRING
			ACCESS not-accessible
			STATUS mandatory
			DESCRIPTION
				"A StreetTalk Group Name."

			::= { trapdata 18 }


tpNumGrps               OBJECT-TYPE
			SYNTAX  INTEGER
			ACCESS  not-accessible
			STATUS  mandatory
			DESCRIPTION
				"The number of groups being maintained
				 by StreetTalk on a given server (as a
				 percentage of the maximum allowed no."

			::= { trapdata 19 }


tpGrpLimit              OBJECT-TYPE
			SYNTAX  INTEGER
			ACCESS  not-accessible
			STATUS  mandatory
			DESCRIPTION
				"The maximum number of groups allowed on
				 a server."

			::= { trapdata 20 }


tpOldSerNum             OBJECT-TYPE
			SYNTAX  INTEGER
			ACCESS  not-accessible
			STATUS  mandatory
			DESCRIPTION
				"A server's old serial number."

			::= { trapdata 21 }


tpNewSerNum             OBJECT-TYPE
			SYNTAX  INTEGER
			ACCESS  not-accessible
			STATUS  mandatory
			DESCRIPTION
				"A server's new serial number."

			::= { trapdata 22 }


tpDiskSpaceLeft         OBJECT-TYPE
                        SYNTAX  INTEGER
                        ACCESS  not-accessible
                        STATUS  mandatory
                        DESCRIPTION
                                "The amount of disk space left (KB)
                                 available to the Mail Service."

                        ::= { trapdata 23 }


tpMailMessageId         OBJECT-TYPE
                        SYNTAX  OCTET STRING
                        ACCESS  not-accessible
                        STATUS  mandatory
                        DESCRIPTION
                                "The internal message ID of an item in
                                 the mail service."

                        ::= { trapdata 24 }


tpSockOvFlowNum         OBJECT-TYPE
                        SYNTAX  INTEGER
                        ACCESS  not-accessible
                        STATUS  mandatory
                        DESCRIPTION
                                "The number of packets dropped due
                                 to a socket overflow."

                        ::= { trapdata 25 }


tpDiskNName		OBJECT-TYPE
                        SYNTAX  OCTET STRING
                        ACCESS  not-accessible
                        STATUS  mandatory
                        DESCRIPTION
                                "The name of a disk unit."

                        ::= { trapdata 26 }


tpSvrNetId		OBJECT-TYPE
			SYNTAX	INTEGER
			ACCESS	not-accessible
			STATUS	mandatory
			DESCRIPTION
				"The server NetID."

			::= { trapdata 27 }	


tpSubNetId		OBJECT-TYPE
			SYNTAX	INTEGER
			ACCESS	not-accessible
			STATUS	mandatory
			DESCRIPTION
				"A VINES subnetwork ID."

			::= { trapdata 28 }


tpSlotNum		OBJECT-TYPE
			SYNTAX	INTEGER
			ACCESS	not-accessible
			STATUS	mandatory
			DESCRIPTION
				"The Slot Number of a particular interface
				 card."

			::= { trapdata 29 }


tpLineNum		OBJECT-TYPE
			SYNTAX	INTEGER
			ACCESS	not-accessible
			STATUS	mandatory
			DESCRIPTION
				"The Line Number on the interface board."

			::= { trapdata 30 }


tpFRcvd			OBJECT-TYPE
			SYNTAX	INTEGER
			ACCESS	not-accessible
			STATUS	mandatory
			DESCRIPTION
				"The number of frames received."

			::= { trapdata 31 }


tpFXmtd			OBJECT-TYPE
			SYNTAX	INTEGER
			ACCESS	not-accessible
			STATUS	mandatory
			DESCRIPTION
				"The number of frames transmitted."

			::= { trapdata 32 }


tpLnkDropsThres		OBJECT-TYPE
			SYNTAX	INTEGER
			ACCESS	not-accessible
			STATUS	mandatory
			DESCRIPTION
				"The threshold value for link-level drops
				 - when exceeded an alert is issued."

			::= { trapdata 33 }


tpLnkReXtThres		OBJECT-TYPE
			SYNTAX	INTEGER
			ACCESS	not-accessible
			STATUS	mandatory
			DESCRIPTION
				"The threshold value for link-level
				 re-transmits - when exceeded an alert
				 is isssued."

			::= { trapdata 34 }




--  Alert Management Service group

amsRegTable             OBJECT-TYPE
			SYNTAX  SEQUENCE OF AmsRegEntry
			ACCESS  not-accessible
			STATUS  mandatory
			DESCRIPTION
				"The Table containing entries for each
				 seperate registration with AMS to receive
				 alerts."

			::= { ams 1 }


amsRegEntry             OBJECT-TYPE
			SYNTAX  AmsRegEntry
			ACCESS  not-accessible
			STATUS  mandatory
			DESCRIPTION
				"Entry into amsRegTable."
			INDEX { amsRegIndex }

			::= { amsRegTable 1 }


AmsRegEntry             ::= SEQUENCE {
				amsRegIndex
					INTEGER,
				amsRegIdInstance
					OCTET STRING,
				amsRegIdClass
					INTEGER,
				amsRegIdTid
					INTEGER,
				amsRegPort
					OCTET STRING,
				amsRegWhoAdded
					OCTET STRING,
				amsRegAlertee
					OCTET STRING,
				amsRegAction
					INTEGER
			}


amsRegIndex             OBJECT-TYPE
			SYNTAX  INTEGER
			ACCESS  read-only
			STATUS  mandatory
			DESCRIPTION
				"The index value into the amsRegTable
				 used by SNMP."

			::= { amsRegEntry 1 }


amsRegIdInstance        OBJECT-TYPE
			SYNTAX  OCTET STRING
			ACCESS  read-only
			STATUS  mandatory
			DESCRIPTION
				"The alert instance string that the registered
				 party is interested in."

			::= { amsRegEntry 2 }


amsRegIdClass   OBJECT-TYPE
			SYNTAX  INTEGER
			ACCESS  read-only
			STATUS  mandatory
			DESCRIPTION
				"The application class that the registered
				 party is interested in receiving alerts from."

			::= { amsRegEntry 3 }


amsRegIdTid             OBJECT-TYPE
			SYNTAX  INTEGER
			ACCESS  read-only
			STATUS  mandatory
			DESCRIPTION
				"The alert template identifier that the
				 registered party is interested in."

			::= { amsRegEntry 4 }


amsRegPort              OBJECT-TYPE
			SYNTAX  OCTET STRING
			ACCESS  read-only
			STATUS  mandatory
			DESCRIPTION
				"The Port to which the alerts are to be
				 sent.  This will be NULL if amsRegAction is
				 something other than a notification sent to 
				 an IPC Port."

			::= { amsRegEntry 5 }


amsRegWhoAdded          OBJECT-TYPE
			SYNTAX  OCTET STRING
			ACCESS  read-only
			STATUS  mandatory
			DESCRIPTION
				"The StreetTalk name of the user who added
				 this particular entry to the table."

			::= { amsRegEntry 6 }


amsRegAlertee           OBJECT-TYPE
			SYNTAX  OCTET STRING
			ACCESS  read-only
			STATUS  mandatory
			DESCRIPTION
				"The StreetTalk name of the user to whom
				 the alerts are to be sent.  This will
				 be NULL if the amsRegAction for this
				 entry is 'sendipcport'."

			::= { amsRegEntry 7 }


amsRegAction            OBJECT-TYPE
			SYNTAX  INTEGER {
					sendipcport(1),
					bleepstname(2)
					}       
			ACCESS  read-only
			STATUS  mandatory
			DESCRIPTION
				"The action to perform with alerts that
				 match for this entry.  The available
				 options are :
				
				 sendipcport  -  Pass the alert to the 
						 specific registered IPC
						 port, as specified in
						 'amsRegPort'.

				 bleepstname  -  Send a 25th-line message
						 containing the alert to the
						 user 'amsRegAlertee'."

			::= { amsRegEntry 8 }


amsAlertLogTable	OBJECT-TYPE
			SYNTAX  SEQUENCE OF AmsLogEntry
			ACCESS  not-accessible
			STATUS  mandatory
			DESCRIPTION
				"The Table containing entries for each
				 each record written into each of the AMS
				 alert log files."

			::= { ams 2 }

amsLogEntry             OBJECT-TYPE
			SYNTAX  AmsLogEntry
			ACCESS  not-accessible
			STATUS  mandatory
			DESCRIPTION
				"Entry into amsAlertLogTable."
			INDEX { amsLogFileIndex,
				amsLogRecIndex }

			::= { amsAlertLogTable 1 }


AmsLogEntry             ::= SEQUENCE {
				amsLogFileIndex
					INTEGER,
				amsLogRecIndex
					INTEGER,
				amsLogIdInstance
					OCTET STRING,
				amsLogIdClass
					INTEGER,
				amsLogIdTid
					INTEGER,
				amsLogAlertTime
					TimeTicks,
				amsLogAlertString
					OCTET STRING
				}


amsLogFileIndex		OBJECT-TYPE
			SYNTAX  INTEGER {
					previous(1),
					current(2)
					}
			ACCESS  read-only
			STATUS  mandatory
			DESCRIPTION
				"The index value into the amsRegTable
				 used to distinguish between the alert
				 log files kept by AMS.  Options are:

					previous - The previous day's log.

					current - Today's log file.

				 The log files are switched at 12:00am
				 each night, when 'today' becomes 'yesterday'
				 and 'yesterday' is emptied and becomes
				 'today'."

			::= { amsLogEntry 1 }


amsLogRecIndex		OBJECT-TYPE
			SYNTAX  INTEGER
			ACCESS  read-only
			STATUS  mandatory
			DESCRIPTION
				"The index value into the amsAlertLogTable
				 used to uniquely identify each record in
				 a given alert log."

			::= { amsLogEntry 2 }


amsLogIdInstance        OBJECT-TYPE
			SYNTAX  OCTET STRING
			ACCESS  read-only
			STATUS  mandatory
			DESCRIPTION
				"The alert instance string of the AlertID in
				 the alert record."

			::= { amsLogEntry 3 }


amsLogIdClass		OBJECT-TYPE
			SYNTAX  INTEGER
			ACCESS  read-only
			STATUS  mandatory
			DESCRIPTION
				"The application class of the AlertID in
				 the alert record."

			::= { amsLogEntry 4 }


amsLogIdTid             OBJECT-TYPE
			SYNTAX  INTEGER
			ACCESS  read-only
			STATUS  mandatory
			DESCRIPTION
				"The template identifier of the AlertID
				 in the alert record."

			::= { amsLogEntry 5 }


amsLogAlertTime		OBJECT-TYPE
			SYNTAX  TimeTicks
			ACCESS  read-only
			STATUS  mandatory
			DESCRIPTION
				"The time at which the alert was originally
				 issued."

			::= { amsLogEntry 6 }


amsLogAlertString	OBJECT-TYPE
			SYNTAX  OCTET STRING
			ACCESS  read-only
			STATUS  mandatory
			DESCRIPTION
				"The textual string description of the
				 alert including all data values."

			::= { amsLogEntry 7 }



--  Mail Service group

mlMailBoxTable          OBJECT-TYPE
			SYNTAX  SEQUENCE OF MlMailBoxTableEntry
			ACCESS  not-accessible
			STATUS  mandatory
			DESCRIPTION
				"The Table containing entries for each
				 Mailbox maintained by the Mail Service."

			::= { mailservice 1 }


mlMailBoxTableEntry     OBJECT-TYPE
			SYNTAX  MlMailBoxTableEntry
			ACCESS  not-accessible
			STATUS  mandatory
			DESCRIPTION
				"Entry into mlMailBoxTable."
			INDEX { mlMBTableIndex }

			::= { mlMailBoxTable 1 }


MlMailBoxTableEntry     ::= SEQUENCE {
				mlMBTableIndex
					INTEGER,
				mlMBTableMBOwner
					OCTET STRING,
				mlMBTableUnreadMsgs
					INTEGER,
				mlMBTableTotalMsgs
					INTEGER
				}


mlMBTableIndex          OBJECT-TYPE
			SYNTAX  INTEGER
			ACCESS  read-only
			STATUS  mandatory
			DESCRIPTION
				"The index value into the mlMailBoxTable
				 used by SNMP."

			::= { mlMailBoxTableEntry 1 }


mlMBTableMBOwner        OBJECT-TYPE
			SYNTAX  OCTET STRING
			ACCESS  read-only
			STATUS  mandatory
			DESCRIPTION
				"The StreetTalk name of the user to whom
				 this mailbox relates."

			::= { mlMailBoxTableEntry 2 }


mlMBTableUnreadMsgs     OBJECT-TYPE
			SYNTAX  INTEGER
			ACCESS  read-only
			STATUS  mandatory
			DESCRIPTION
				"The number of unread messages in this
				 mailbox."

			::= { mlMailBoxTableEntry 3 }


mlMBTableTotalMsgs      OBJECT-TYPE
			SYNTAX  INTEGER
			ACCESS  read-only
			STATUS  mandatory
			DESCRIPTION
				"The total number of messages in this
				 mailbox."

			::= { mlMailBoxTableEntry 4 }

-- logs group

vlogsTable	OBJECT-TYPE
		SYNTAX  SEQUENCE OF VlogsEntry
		ACCESS  not-accessible
		STATUS  mandatory
		DESCRIPTION
			"The Table containing entries for each log."
		::= { vlogs 1 }

vlogsEntry             OBJECT-TYPE
			SYNTAX  VlogsEntry
			ACCESS  not-accessible
			STATUS  mandatory
			DESCRIPTION
				"Entry into vlogsEntry."
			INDEX { vlogsFileIndex }
			::= { vlogsTable 1 }


VlogsEntry          ::= SEQUENCE {
				vlogsFileIndex
					INTEGER,
				vlogsDescr
					OCTET STRING
				}


vlogsFileIndex		OBJECT-TYPE
			SYNTAX  INTEGER {
				patch(1),
				backup(2)
			}
			ACCESS  read-only
			STATUS  mandatory
			DESCRIPTION
				"The index value into the vlogsTable."
			::= { vlogsEntry 1 }

vlogsDescr		OBJECT-TYPE
			SYNTAX  OCTET STRING
			ACCESS  read-only
			STATUS  mandatory
			DESCRIPTION
				"The record entry for the log."
			::= { vlogsEntry 2 }



-- This part of the MIB module defines the traps that VINES Services issue.
-- It is split into sections for each Service component.


-- Network Management Traps

nmLoadAvgHigh	TRAP-TYPE
		ENTERPRISE  mib2
		VARIABLES  { tpSvrName, tpSvcName, tpAlertTime,
			     nmLoadAvg15HighThres }
		DESCRIPTION
			"The 15 minute load average on the specified server
			 has exceeded the specified threshold value."
                --#TYPE ""
		--#SUMMARY "15 min Server load average exceeded %lu/100"
		--#ARGUMENTS { 3 }
		--#SEVERITY INFORMATIONAL
		--#TIMEINDEX 0
		--#SYMBOL SNM_LDAVG_HIGH

		::= 1


nmSwapAvgHigh	TRAP-TYPE
		ENTERPRISE  mib2 
		VARIABLES  { tpSvrName, tpSvcName, tpAlertTime,
			     nmSwapAvgHighThres }
		DESCRIPTION
			"The 15 minute swap average on the specified server
			 has exceeded the specified threshold value."
                --#TYPE ""
		--#SUMMARY "15 min Server swap average exceeded %lu/100"
		--#ARGUMENTS { 3 }
		--#SEVERITY INFORMATIONAL
		--#TIMEINDEX 0
		--#SYMBOL SNM_SWAVG_HIGH

		::= 2


nmDropsHigh	TRAP-TYPE
		ENTERPRISE  mib2
		VARIABLES  { tpSvrName, tpSvcName, tpAlertTime,
			     nmDropsHighThres }
		DESCRIPTION
			"The 15 minute average of dropped messages (due to
			 lack of comms buffers) on the specified server
			 has exceeded the specified threshold value."
                --#TYPE ""
		--#SUMMARY "15 min Server drops average exceeded %lu per"
		--#SUMMARY "	minute"
		--#ARGUMENTS { 3 }
		--#SEVERITY INFORMATIONAL
		--#TIMEINDEX 0
		--#SYMBOL SNM_DROPS_HIGH

		::= 3


nmFreeSwapLow	TRAP-TYPE
		ENTERPRISE  mib2
		VARIABLES  { tpSvrName, tpSvcName, tpAlertTime,
			     nmSwapSpaceLowThres }
		DESCRIPTION
			"The Free Swap space on the specified server fell
			 below the specified threshold value."
                --#TYPE ""
		--#SUMMARY "Server free swap space below %lu percent"
		--#ARGUMENTS { 3 }
		--#SEVERITY INFORMATIONAL
		--#TIMEINDEX 0
		--#SYMBOL SNM_FREESWAP_LOW

		::= 4


nmFreeMemLow	TRAP-TYPE
		ENTERPRISE  mib2
		VARIABLES  {  tpSvrName, tpSvcName, tpAlertTime,
			      nmFreeMemLowThres }
		DESCRIPTION
			"The Free Process memory space on the specified
			 server fell below the specified threshold value."
                --#TYPE ""
		--#SUMMARY "Server free process memory space below %lu"
		--#SUMMARY "	kilobytes"
		--#ARGUMENTS { 3 }
		--#SEVERITY INFORMATIONAL
		--#TIMEINDEX 0
		--#SYMBOL SNM_FREEMEM_LOW

		::= 5

nmCommBuffHigh	TRAP-TYPE
		ENTERPRISE  mib2
		VARIABLES  {  tpSvrName, tpSvcName, tpAlertTime,
			      nmCommBuffHighThres }
		DESCRIPTION
			"The communications buffer usage on the specified
			 server exceeded the specified threshold value."
                --#TYPE ""
		--#SUMMARY "Server comm buffer usage exceeded %u percent"
		--#ARGUMENTS { 3 }
		--#SEVERITY INFORMATIONAL
		--#TIMEINDEX 0
		--#SYMBOL SNM_COMMBUFFUSE_HIGH

		::= 6


nmSockInUseHigh	TRAP-TYPE
		ENTERPRISE  mib2
		VARIABLES  {  tpSvrName, tpSvcName, tpAlertTime,
			      nmSockInUseHighThres }
		DESCRIPTION
			"The sockets in use on the specified
			 server exceeded the specified threshold value."
                --#TYPE ""
		--#SUMMARY "Server sockets in use exceeded %u percent"
		--#ARGUMENTS { 3 }
		--#SEVERITY INFORMATIONAL
		--#TIMEINDEX 0
		--#SYMBOL SNM_SOCKINUSE_HIGH

		::= 7


--Original MIB had "nmSockOvFlowNum" in VARIABLES.  Change to tpSockOvFlowNum.
nmSockOvflow	TRAP-TYPE
		ENTERPRISE  mib2
		VARIABLES  {  tpSvrName, tpSvcName, tpAlertTime,
			      tpRefSvcName, tpSockOvFlowNum }
		DESCRIPTION
			"Socket overflow for the specified service.  The
			 number of packets dropped is also provided."
                --#TYPE ""
		--#SUMMARY "Socket overflow for service %s; %lu"
		--#SUMMARY "	packets dropped"
		--#ARGUMENTS { 3, 4 }
		--#SEVERITY INFORMATIONAL
		--#TIMEINDEX 0
		--#SYMBOL SNM_SKT_OVFLOW

		::= 8


nmMsgAvgHigh	TRAP-TYPE
		ENTERPRISE  mib2
		VARIABLES  { tpSvrName, tpSvcName, tpAlertTime,
			     nmMsgAvgHighThres }
		DESCRIPTION
			"The 15 minute average of message activity
			 on the specified server has exceeded the
			 specified threshold value."
                --#TYPE ""
		--#SUMMARY "15 min Server message average exceeded "
		--#SUMMARY "	%lu/second"
		--#ARGUMENTS { 3 }
		--#SEVERITY INFORMATIONAL
		--#TIMEINDEX 0
		--#SYMBOL SNM_MSGAVG_HIGH

		::= 9


nmAllocFail-High	TRAP-TYPE
		ENTERPRISE  mib2
		VARIABLES  {  tpSvrName, tpSvcName, tpAlertTime,
			      nmAllocFailHighThres }
		DESCRIPTION
			"The number of failed communication buffer
			 allocations on the specified server exceeded
			 the specified threshold value."
                --#TYPE ""
		--#SUMMARY "15 min Server allocation failure rate"
		--#SUMMARY "	exceeded %lu per min"
		--#ARGUMENTS { 3 }
		--#SEVERITY INFORMATIONAL
		--#TIMEINDEX 0
		--#SYMBOL SNM_ALLOCFAIL_HIGH

		::= 10


nmCacheHits-Low	TRAP-TYPE
		ENTERPRISE  mib2
		VARIABLES  {  tpSvrName, tpSvcName, tpAlertTime,
			      nmCacheHitsLowThres }
		DESCRIPTION
			"The percentage of cache buffer requests
			 that the specified server was able to service
			 using existing cache buffers, without reading
			 new data from the disk, fell below the specified
			 threshold value."
                --#TYPE ""
		--#SUMMARY "Server cache hits average below %u percent"
		--#ARGUMENTS { 3 }
		--#SEVERITY INFORMATIONAL
		--#TIMEINDEX 0
		--#SYMBOL SNM_CACHEHITS_LOW

		::= 11


nmDiskFull	TRAP-TYPE
		ENTERPRISE  mib2
		VARIABLES  {  tpSvrName, tpSvcName, tpAlertTime,
			      tpDiskNName, nmDiskUseHighThres }
		DESCRIPTION
			"The percentage of disk space in use on the
			 specified disk exceeded the threshold."
                --#TYPE ""
		--#SUMMARY "For server disk %s, the used disk space"
		--#SUMMARY "	exceeded %lu percent"
		--#ARGUMENTS { 3, 4 }
		--#SEVERITY INFORMATIONAL
		--#TIMEINDEX 0
		--#SYMBOL SNM_DISK_FULL

		::= 12


nmDiskBusy	TRAP-TYPE
		ENTERPRISE  mib2
		VARIABLES  {  tpSvrName, tpSvcName, tpAlertTime,
			      tpDiskNName, nmDiskBusyHighThres }
		DESCRIPTION
			"The 5 minute average of percentage of time
			 the specified disk was in use exceeded the
			 threshold."
                --#TYPE ""
		--#SUMMARY "Server disk %s busy more than %lu %%"
		--#SUMMARY "	over last 5 min"
		--#ARGUMENTS { 3, 4 }
		--#SEVERITY INFORMATIONAL
		--#TIMEINDEX 0
		--#SYMBOL SNM_DISK_BUSY

		::= 13


nmInodesHigh	TRAP-TYPE
		ENTERPRISE  mib2
		VARIABLES  {  tpSvrName, tpSvcName, tpAlertTime,
			      nmInodeUseHighThres }
		DESCRIPTION
			"The number of inodes in use on the specified
			 server exceeded the threshold value."
                --#TYPE ""
		--#SUMMARY "Server inodes in use exceeded %lu percent"
		--#ARGUMENTS { 3 }
		--#SEVERITY INFORMATIONAL
		--#TIMEINDEX 0
		--#SYMBOL SNM_INODES_HIGH

		::= 14


nmProcsHigh	TRAP-TYPE
		ENTERPRISE  mib2
		VARIABLES  {  tpSvrName, tpSvcName, tpAlertTime }

		DESCRIPTION
			"The specified server cannot run any more
			 processes."
                --#TYPE ""
		--#SUMMARY "Server cannot run any more processes"
		--#ARGUMENTS { }
		--#SEVERITY INFORMATIONAL
		--#TIMEINDEX 0
		--#SYMBOL SNM_PROCS_HIGH

		::= 15


nmTKRingOpen	TRAP-TYPE
		ENTERPRISE  mib2
		VARIABLES  {  tpSvrName, tpSvcName, tpAlertTime,
			      tpSlotNum }

		DESCRIPTION
			"The token ring adapter in the specified slot
			 has an open/short circuit detected."
                --#TYPE ""
		--#SUMMARY "Open or short circuit detected; token"
		--#SUMMARY "	ring adapter in slot %u"
		--#ARGUMENTS { 3 }
		--#SEVERITY INFORMATIONAL
		--#TIMEINDEX 0
		--#SYMBOL SNM_TK_OPEN

		::= 16


nmTKRingSigLoss	TRAP-TYPE
		ENTERPRISE  mib2
		VARIABLES  {  tpSvrName, tpSvcName, tpAlertTime,
			      tpSlotNum }

		DESCRIPTION
			"The token ring adapter in the specified slot
			 has been detected with a Signal Loss."
                --#TYPE ""
		--#SUMMARY "Signal loss detected; token"
		--#SUMMARY "	ring adapter in slot %u"
		--#ARGUMENTS { 3 }
		--#SEVERITY INFORMATIONAL
		--#TIMEINDEX 0
		--#SYMBOL SNM_TK_SIGNALLOSS

		::= 17


nmTKRingHardErr	TRAP-TYPE
		ENTERPRISE  mib2
		VARIABLES  {  tpSvrName, tpSvcName, tpAlertTime,
			      tpSlotNum }

		DESCRIPTION
			"The token ring adapter in the specified slot
			 has been detected with a Hard Error."
                --#TYPE ""
		--#SUMMARY "Hard error detected; token"
		--#SUMMARY "	ring adapter in slot %u"
		--#ARGUMENTS { 3 }
		--#SEVERITY INFORMATIONAL
		--#TIMEINDEX 0
		--#SYMBOL SNM_TK_HARDERR

		::= 18


nmTKRingRmvHardErr	TRAP-TYPE
		ENTERPRISE  mib2
		VARIABLES  {  tpSvrName, tpSvcName, tpAlertTime,
			      tpSlotNum }

		DESCRIPTION
			"The token ring adapter in the specified slot
			 removed itself from the token ring."
                --#TYPE ""
		--#SUMMARY "Adapter in slot %u removed itself from "
		--#SUMMARY "	token ring"
		--#ARGUMENTS { 3 }
		--#SEVERITY INFORMATIONAL
		--#TIMEINDEX 0
		--#SYMBOL SNM_TK_RMVHARDERR

		::= 19


nmTKRingRmvMacFrame	TRAP-TYPE
		ENTERPRISE  mib2
		VARIABLES  {  tpSvrName, tpSvcName, tpAlertTime,
			      tpSlotNum }

		DESCRIPTION
			"Removing the MAC frame from the token ring
			 adapter in the specified slot caused it to
			 remove itself from the Token Ring."
                --#TYPE ""
		--#SUMMARY "Remove MAC frame caused adapter in slot"
		--#SUMMARY "	%u to remove itself from token ring"
		--#ARGUMENTS { 3 }
		--#SEVERITY INFORMATIONAL
		--#TIMEINDEX 0
		--#SYMBOL SNM_TK_RMVMACFRM

		::= 20


nmLnkDropsHigh	TRAP-TYPE
		ENTERPRISE  mib2
		VARIABLES  {  tpSvrName, tpSvcName, tpAlertTime,
			      tpLnkDropsThres, tpSlotNum, tpLineNum,
			      tpFRcvd }

		DESCRIPTION
			"The percentage of frames dropped with respect to
			 the total frames received, over the previous 15
			 minutes, exceeded the threshold value."
                --#TYPE ""
		--#SUMMARY "Drops exceeded %lu percent; slot %u line %u"
		--#SUMMARY "	frcvd %lu"
		--#ARGUMENTS { 3, 4, 5, 6 }
		--#SEVERITY INFORMATIONAL
		--#TIMEINDEX 0
		--#SYMBOL SNM_LNKDROPS_HIGH

		::= 21


nmLnkReTXHigh	TRAP-TYPE
		ENTERPRISE  mib2
		VARIABLES  {  tpSvrName, tpSvcName, tpAlertTime,
			      tpLnkReXtThres, tpSlotNum, tpLineNum,
			      tpFXmtd }

		DESCRIPTION
			"The percentage of frames retransmitted with 
			 respect to the total frames transmitted, over
			 the previous 15 minutes, exceeded the threshold
			 value."
                --#TYPE ""
		--#SUMMARY "Retransmits exceeded %lu percent; slot %u"
		--#SUMMARY "	line %u fxmtd %lu"
		--#ARGUMENTS { 3, 4, 5, 6 }
		--#SEVERITY INFORMATIONAL
		--#TIMEINDEX 0
		--#SYMBOL SNM_LNKREXMITS_HIGH

		::= 22


-- Back-Up Service Traps

bsSysBkUpFailed	TRAP-TYPE
		ENTERPRISE  mib2
		VARIABLES  {  tpSvrName, tpSvcName, tpAlertTime,
			      tpErrorCode }

		DESCRIPTION
			"The system back-up on the specified system failed
			 with the given error code."
                --#TYPE ""
		--#SUMMARY "System backup failed: error %u"
		--#ARGUMENTS { 3 }
		--#SEVERITY INFORMATIONAL
		--#TIMEINDEX 0
		--#SYMBOL BS_SYS_BKUP_FAILED

		::= 23


bsIncBkUpAborted	TRAP-TYPE
		ENTERPRISE  mib2
		VARIABLES  {  tpSvrName, tpSvcName, tpAlertTime }

		DESCRIPTION
			"The incremental back-up on the specified system
			 was aborted."
                --#TYPE ""
		--#SUMMARY "Incremental backup aborted: complete"
		--#SUMMARY "	system backup has not been done"
		--#ARGUMENTS { }
		--#SEVERITY INFORMATIONAL
		--#TIMEINDEX 0
		--#SYMBOL BS_INC_BKUP_ABORTED

		::= 24


bsIncBkUpFailed	TRAP-TYPE
		ENTERPRISE  mib2
		VARIABLES  {  tpSvrName, tpSvcName, tpAlertTime,
			      tpErrorCode }

		DESCRIPTION
			"The incremental back-up on the specified system failed
			 with the given error code."
                --#TYPE ""
		--#SUMMARY "Incremental backup failed: error %u"
		--#ARGUMENTS { 3 }
		--#SEVERITY INFORMATIONAL
		--#TIMEINDEX 0
		--#SYMBOL BS_INC_BKUP_FAILED

		::= 25


bsSvcBkUpFailed	TRAP-TYPE
		ENTERPRISE  mib2
		VARIABLES  {  tpSvrName, tpSvcName, tpAlertTime,
			      tpErrorCode }

		DESCRIPTION
			"The service back-up on the specified system failed
			 with the given error code."
                --#TYPE ""
		--#SUMMARY "Service backup failed: error %u"
		--#ARGUMENTS { 3 }
		--#SEVERITY INFORMATIONAL
		--#TIMEINDEX 0
		--#SYMBOL BS_SVC_BKUP_FAILED

		::= 26


--  Print Service Traps


psFormUnavail	TRAP-TYPE
		ENTERPRISE  mib2
		VARIABLES  {  tpSvrName, tpSvcName, tpAlertTime,
			      tpJobId, tpPaperFormat }

		DESCRIPTION
			"The specified job requested a paper format which
			 was not available."
                --#TYPE ""
		--#SUMMARY "Job %d: paper format %s not available"
		--#ARGUMENTS { 3, 4 }
		--#SEVERITY INFORMATIONAL
		--#TIMEINDEX 0
		--#SYMBOL BPS_NPSM_NOFORM

		::= 27


psUserNoAuth	TRAP-TYPE
		ENTERPRISE  mib2
		VARIABLES  {  tpSvrName, tpSvcName, tpAlertTime,
			      tpUserName, tpRefSvcName }

		DESCRIPTION
			"The specified user is not authorized to connect
			 to the specified printer."
                --#TYPE ""
		--#SUMMARY "%s not authorized to connect to %s"
		--#ARGUMENTS { 3, 4 }
		--#SEVERITY INFORMATIONAL
		--#TIMEINDEX 0
		--#SYMBOL BPS_NPSM_NOAUTH

		::= 28


psBadDest	TRAP-TYPE
		ENTERPRISE  mib2
		VARIABLES  {  tpSvrName, tpSvcName, tpAlertTime,
			      tpRefSvcName }

		DESCRIPTION
			"The specified destination cannot be started."
                --#TYPE ""
		--#SUMMARY "Destination %s cannot be started"
		--#ARGUMENTS { 3 }
		--#SEVERITY INFORMATIONAL
		--#TIMEINDEX 0
		--#SYMBOL BPS_NPSM_BADDEST

		::= 29


psJobReject	TRAP-TYPE
		ENTERPRISE  mib2
		VARIABLES  {  tpSvrName, tpSvcName, tpAlertTime,
			      tpJobId, tpRefSvcName, tpUserName }

		DESCRIPTION
			"The specified job was rejected on the specific
			 print service by the given user."
                --#TYPE ""
		--#SUMMARY "Job %d rejected on %s by %s"
		--#ARGUMENTS { 3, 4, 5 }
		--#SEVERITY INFORMATIONAL
		--#TIMEINDEX 0
		--#SYMBOL BPS_NQSM_JOBREJ

		::= 30


psQueueFull	TRAP-TYPE
		ENTERPRISE  mib2
		VARIABLES  {  tpSvrName, tpSvcName, tpAlertTime,
			      tpRefSvcName, tpJobTotal }

		DESCRIPTION
			"The specified print queue has reached its'
			 capacity."
                --#TYPE ""
		--#SUMMARY "The queue %s has reached capacity of %d jobs"
		--#ARGUMENTS { 3, 4 }
		--#SEVERITY INFORMATIONAL
		--#TIMEINDEX 0
		--#SYMBOL BPS_NQSM_FULL

		::= 31


psOffline	TRAP-TYPE
		ENTERPRISE  mib2
		VARIABLES  {  tpSvrName, tpSvcName, tpAlertTime,
			      tpRefSvcName }

		DESCRIPTION
			"The specified entity has gone offline."
                --#TYPE ""
		--#SUMMARY "Entity %s offline"
		--#ARGUMENTS { 3 }
		--#SEVERITY INFORMATIONAL
		--#TIMEINDEX 0
		--#SYMBOL BPS_NQSM_OFFLINE

		::= 32


psPapError	TRAP-TYPE
		ENTERPRISE  mib2
		VARIABLES  {  tpSvrName, tpSvcName, tpAlertTime,
			      tpErrorCode, tpConnId }

		DESCRIPTION
			"The specified PAP error occurred on the given
			 connection ID."
                --#TYPE ""
		--#SUMMARY "PAP error %u connection ID %d"
		--#ARGUMENTS { 3, 4 }
		--#SEVERITY INFORMATIONAL
		--#TIMEINDEX 0
		--#SYMBOL PPS_PAP_ERR

		::= 33


psAtalkErr	TRAP-TYPE
		ENTERPRISE  mib2
		VARIABLES  {  tpSvrName, tpSvcName, tpAlertTime }


		DESCRIPTION
			"A fatal AppleTalk error occurred in the PostScript
			 print service."
                --#TYPE ""
		--#SUMMARY "Fatal AppleTalk error"
		--#ARGUMENTS { }
		--#SEVERITY INFORMATIONAL
		--#TIMEINDEX 0
		--#SYMBOL PPS_PAP_ATALK_ERR

		::= 34


psPsPrinterErr	TRAP-TYPE
		ENTERPRISE  mib2
		VARIABLES  {  tpSvrName, tpSvcName, tpAlertTime }


		DESCRIPTION
			"A printer error was detected on the PostScript
			 print service."
                --#TYPE ""
		--#SUMMARY "Printer error detected"
		--#ARGUMENTS { }
		--#SEVERITY INFORMATIONAL
		--#TIMEINDEX 0
		--#SYMBOL PPS_PRINTER_ERR

		::= 35


--  Server Service Traps

ssSvcNoStart	TRAP-TYPE
		ENTERPRISE  mib2
		VARIABLES  {  tpSvrName, tpSvcName, tpAlertTime,
			      tpRefSvcName, tpErrorCode }


		DESCRIPTION
			"The specified service was unable to be started
			 by Server Service.  The error code is provided."
                --#TYPE ""
		--#SUMMARY "Unable to start %s; error %d"
		--#ARGUMENTS { 3, 4 }
		--#SEVERITY INFORMATIONAL
		--#TIMEINDEX 0
		--#SYMBOL SS_UNABLE_START

		::= 36


ssNoReconnVS	TRAP-TYPE
		ENTERPRISE  mib2
		VARIABLES  {  tpSvrName, tpSvcName, tpAlertTime,
			      tpErrorCode }


		DESCRIPTION
			"Server Service failed to reconnect to VINES Security
			 Service.  The error code is provided."
                --#TYPE ""
		--#SUMMARY "Failed to reconnect to VS: error %d"
		--#ARGUMENTS { 3 }
		--#SEVERITY INFORMATIONAL
		--#TIMEINDEX 0
		--#SYMBOL SS_RECONN_VS

		::= 37


ssNoReconnST	TRAP-TYPE
		ENTERPRISE  mib2
		VARIABLES  {  tpSvrName, tpSvcName, tpAlertTime,
			      tpErrorCode }


		DESCRIPTION
			"Server Service failed to reconnect to StreetTalk
			 Service.  The error code is provided."
                --#TYPE ""
		--#SUMMARY "Failed to reconnect to ST: error %d"
		--#ARGUMENTS { 3 }
		--#SEVERITY INFORMATIONAL
		--#TIMEINDEX 0
		--#SYMBOL SS_RECONN_ST

		::= 38


ssSvcCrashed	TRAP-TYPE
		ENTERPRISE  mib2
		VARIABLES  {  tpSvrName, tpSvcName, tpAlertTime,
			      tpRefSvcName }


		DESCRIPTION
			"The specified service crashed."
                --#TYPE ""
		--#SUMMARY "Service '%s' crashed"
		--#ARGUMENTS { 3 }
		--#SEVERITY INFORMATIONAL
		--#TIMEINDEX 0
		--#SYMBOL SS_SVC_CRASHED

		::= 39


ssSvcRecrashed	TRAP-TYPE
		ENTERPRISE  mib2
		VARIABLES  {  tpSvrName, tpSvcName, tpAlertTime,
			      tpRefSvcName }


		DESCRIPTION
			"The specified service recrashed on a restart
			 attempt."
                --#TYPE ""
		--#SUMMARY "%s crashing too fast; not restarting"
		--#ARGUMENTS { 3 }
		--#SEVERITY INFORMATIONAL
		--#TIMEINDEX 0
		--#SYMBOL SS_SVC_RECRASHED

		::= 40


ssBadSvcDB	TRAP-TYPE
		ENTERPRISE  mib2
		VARIABLES  {  tpSvrName, tpSvcName, tpAlertTime }
	

		DESCRIPTION
			"The services database is corrupted.  Server
			 Service is halting."
                --#TYPE ""
		--#SUMMARY "SS halting...services database file"
		--#SUMMARY "	corrupted"
		--#ARGUMENTS { }
		--#SEVERITY INFORMATIONAL
		--#TIMEINDEX 0
		--#SYMBOL SS_BADSVC_DB

		::= 41


ssPowerFail	TRAP-TYPE
		ENTERPRISE  mib2
		VARIABLES  {  tpSvrName, tpSvcName, tpAlertTime }
	

		DESCRIPTION
			"The power has failed.  Server
			 Service is going down."
                --#TYPE ""
		--#SUMMARY "SS going down...powerfail"
		--#ARGUMENTS { }
		--#SEVERITY INFORMATIONAL
		--#TIMEINDEX 0
		--#SYMBOL SS_POWER_FAIL

		::= 42


ssDying		TRAP-TYPE
		ENTERPRISE  mib2
		VARIABLES  {  tpSvrName, tpSvcName, tpAlertTime,
			      tpErrorCode }
	

		DESCRIPTION
			"Server Service died with the given error.
			 All services will be killed."
                --#TYPE ""
		--#SUMMARY "SS died...%d killing all services"
		--#ARGUMENTS { 3 }
		--#SEVERITY INFORMATIONAL
		--#TIMEINDEX 0
		--#SYMBOL SS_DYING

		::= 43


ssPanicDBWrite	TRAP-TYPE
		ENTERPRISE  mib2
		VARIABLES  {  tpSvrName, tpSvcName, tpAlertTime }
	

		DESCRIPTION
			"Server Service failed to write to the services
			 database file."
                --#TYPE ""
		--#SUMMARY "Failed to write to services database file"
		--#ARGUMENTS { }
		--#SEVERITY INFORMATIONAL
		--#TIMEINDEX 0
		--#SYMBOL SS_PANIC_DBWRITE

		::= 44


ssPanicWait	TRAP-TYPE
		ENTERPRISE  mib2
		VARIABLES  {  tpSvrName, tpSvcName, tpAlertTime }
	

		DESCRIPTION
			"Server Service failed to wait on child process death."
                --#TYPE ""
		--#SUMMARY "Failed to wait() on death of child"
		--#ARGUMENTS { }
		--#SEVERITY INFORMATIONAL
		--#TIMEINDEX 0
		--#SYMBOL SS_PANIC_WAIT

		::= 45


ssPanicUlimit	TRAP-TYPE
		ENTERPRISE  mib2
		VARIABLES  {  tpSvrName, tpSvcName, tpAlertTime }
	

		DESCRIPTION
			"Server Service unable to set limit."
                --#TYPE ""
		--#SUMMARY "Failed to set limit: ulimit() returned -1"
		--#ARGUMENTS { }
		--#SEVERITY INFORMATIONAL
		--#TIMEINDEX 0
		--#SYMBOL SS_PANIC_ULIMIT

		::= 46


ssNoMemory	TRAP-TYPE
		ENTERPRISE  mib2
		VARIABLES  {  tpSvrName, tpSvcName, tpAlertTime }
	

		DESCRIPTION
			"Server Service unable to allocate memory."
                --#TYPE ""
		--#SUMMARY "No memory"
		--#ARGUMENTS { }
		--#SEVERITY INFORMATIONAL
		--#TIMEINDEX 0
		--#SYMBOL SS_NOMEM

		::= 47


ssTimeSet	TRAP-TYPE
		ENTERPRISE  mib2
		VARIABLES  {  tpSvrName, tpSvcName, tpAlertTime }
	

		DESCRIPTION
			"Server Service set the Network Time."
                --#TYPE ""
		--#SUMMARY "Network Time is being set by me"
		--#ARGUMENTS { }
		--#SEVERITY INFORMATIONAL
		--#TIMEINDEX 0
		--#SYMBOL SS_TIME_SET

		::= 48


-- Mail Service Traps

msMBoxFull	TRAP-TYPE
		ENTERPRISE  mib2
		VARIABLES  {  tpSvrName, tpSvcName, tpAlertTime,
			      tpUserName, tpMailSender }
	

		DESCRIPTION
			"The specified user's mailbox is full.  The mail
			 service is unable to deliver mail from the 
			 second user name."
                --#TYPE ""
		--#SUMMARY "Mailbox for user %s is full, unable to"
		--#SUMMARY "	deliver mail from %s"
		--#ARGUMENTS { 3, 4 }
		--#SEVERITY INFORMATIONAL
		--#TIMEINDEX 0
		--#SYMBOL MS_MBOX_FULL

		::= 49


msDiskFull	TRAP-TYPE
		ENTERPRISE  mib2
		VARIABLES  {  tpSvrName, tpSvcName, tpAlertTime,
			      tpDiskSpaceLeft }
	
		DESCRIPTION
			"The Mail service disk is running out of space;
			 only the specified number of kilobytes are left."
                --#TYPE ""
		--#SUMMARY "VINES Mail Service disk has only %luK"
		--#SUMMARY "	bytes remaining."
		--#ARGUMENTS { 3 }
		--#SEVERITY INFORMATIONAL
		--#TIMEINDEX 0
		--#SYMBOL MS_DISK_FULL

		::= 50


msPanic		TRAP-TYPE
		ENTERPRISE  mib2
		VARIABLES  {  tpSvrName, tpSvcName, tpAlertTime,
			      tpErrorCode }
	
		DESCRIPTION
			"The Mail service failed with the given error code."
                --#TYPE ""
		--#SUMMARY "VINES Mail Service failed: %u."
		--#ARGUMENTS { 3 }
		--#SEVERITY INFORMATIONAL
		--#TIMEINDEX 0
		--#SYMBOL MS_PANIC

		::= 51


msCompressFail	TRAP-TYPE
		ENTERPRISE  mib2
		VARIABLES  {  tpSvrName, tpSvcName, tpAlertTime,
			      tpMailMessageId }
	
		DESCRIPTION
			"Message Compression failed on the given message."
                --#TYPE ""
		--#SUMMARY "Message compression failed, Id: %s."
		--#ARGUMENTS { 3 }
		--#SEVERITY INFORMATIONAL
		--#TIMEINDEX 0
		--#SYMBOL MS_COMPRESS_FAIL

		::= 52


msDecompressFail	TRAP-TYPE
		ENTERPRISE  mib2
		VARIABLES  {  tpSvrName, tpSvcName, tpAlertTime,
			      tpMailMessageId }
	
		DESCRIPTION
			"Message Decompression failed on the given message."
                --#TYPE ""
		--#SUMMARY "Message decompression failed, Id: %s."
		--#ARGUMENTS { 3 }
		--#SEVERITY INFORMATIONAL
		--#TIMEINDEX 0
		--#SYMBOL MS_DECOMPRESS_FAIL

		::= 53


msMasquerade	TRAP-TYPE
		ENTERPRISE  mib2
		VARIABLES  {  tpSvrName, tpSvcName, tpAlertTime,
			      tpMailSender, tpUserName }
	
		DESCRIPTION
			"The specified user is sending mail masquerading as
			 the second user name."
                --#TYPE ""
		--#SUMMARY "User %s sending mial using alias %s."
		--#ARGUMENTS { 3, 4 }
		--#SEVERITY INFORMATIONAL
		--#TIMEINDEX 0
		--#SYMBOL MS_MASQUERADE

		::= 54


msMTAPanic	TRAP-TYPE
		ENTERPRISE  mib2
		VARIABLES  {  tpSvrName, tpSvcName, tpAlertTime }
	
		DESCRIPTION
			"The mail message transport system has crashed."
                --#TYPE ""
		--#SUMMARY "VINES Mail message transport system has"
		--#SUMMARY "	crashed."
		--#ARGUMENTS { }
		--#SEVERITY INFORMATIONAL
		--#TIMEINDEX 0
		--#SYMBOL MS_MTA_PANIC

		::= 55


msBMSPanic	TRAP-TYPE
		ENTERPRISE  mib2
		VARIABLES  {  tpSvrName, tpSvcName, tpAlertTime }
	
		DESCRIPTION
			"The mail message store system has crashed."
                --#TYPE ""
		--#SUMMARY "VINES Mail message store system has"
		--#SUMMARY "	crashed."
		--#ARGUMENTS { }
		--#SEVERITY INFORMATIONAL
		--#TIMEINDEX 0
		--#SYMBOL MS_BMS_PANIC

		::= 56


-- VINES Security Service Traps

vsNoReachST	TRAP-TYPE
		ENTERPRISE  mib2
		VARIABLES  {  tpSvrName, tpSvcName, tpAlertTime }
	
		DESCRIPTION
			"The VINES Security Service cannot access the local
			 StreetTalk Service."
                --#TYPE ""
		--#SUMMARY "Cannot access local StreetTalk"
		--#ARGUMENTS { }
		--#SEVERITY INFORMATIONAL
		--#TIMEINDEX 0
		--#SYMBOL VS_CANTREACH_ST

		::= 57


vsBadLoginPhysLoc	TRAP-TYPE
		ENTERPRISE  mib2
		VARIABLES  {  tpSvrName, tpSvcName, tpAlertTime,
			      tpPortId, tpUserName }
	
		DESCRIPTION
			"A failed login occurred due to an invalid
			 physical location.  The attempt was from the
			 given port and using the given user name."
                --#TYPE ""
		--#SUMMARY "Failed login; port %s\n, user=%s,"
		--#SUMMARY "	invalid physical location"
		--#ARGUMENTS { 3, 4 }
		--#SEVERITY INFORMATIONAL
		--#TIMEINDEX 0
		--#SYMBOL VS_BADLOGIN_PHYLOC

		::= 58

 
vsBadLoginDialin	TRAP-TYPE
		ENTERPRISE  mib2
		VARIABLES  {  tpSvrName, tpSvcName, tpAlertTime,
			      tpPortId, tpUserName }
	
		DESCRIPTION
			"A failed login occurred due to a breach of
			 dial-in security.  The attempt was from the
			 given port and using the given user name."
                --#TYPE ""
		--#SUMMARY "Failed login; port %s\n, user=%s,"
		--#SUMMARY "	dialin security"
		--#ARGUMENTS { 3, 4 }
		--#SEVERITY INFORMATIONAL
		--#TIMEINDEX 0
		--#SYMBOL VS_BADLOGIN_DIALIN

		::= 59


vsBadLoginTime	TRAP-TYPE
		ENTERPRISE  mib2
		VARIABLES  {  tpSvrName, tpSvcName, tpAlertTime,
			      tpUserName }
	
		DESCRIPTION
			"A failed login occurred for the given user name
			 due to attempt to login outside of login-time
			 restrictions."
                --#TYPE ""
		--#SUMMARY "Failed login; user=%s, time restrictions"
		--#ARGUMENTS { 3 }
		--#SEVERITY INFORMATIONAL
		--#TIMEINDEX 0
		--#SYMBOL VS_BADLOGIN_TIME

		::= 60


vsMaxBadLogins	TRAP-TYPE
		ENTERPRISE  mib2
		VARIABLES  {  tpSvrName, tpSvcName, tpAlertTime,
			      tpPortId, tpUserName }
	
		DESCRIPTION
			"A failed login occurred from the given port for
			 the given user name due to exceeding the maximum
			 allowed password attempts."
                --#TYPE ""
		--#SUMMARY "Failed login from %s\n, user=%s,"
		--#SUMMARY "	max password attempts"
		--#ARGUMENTS { 3, 4 }
		--#SEVERITY INFORMATIONAL
		--#TIMEINDEX 0
		--#SYMBOL VS_MAXBADLOGINS

		::= 61


vsSDBInconsist	TRAP-TYPE
		ENTERPRISE  mib2
		VARIABLES  {  tpSvrName, tpSvcName, tpAlertTime }
	
		DESCRIPTION
			"The nonce stamp did not match with that
			 in the session database file."
                --#TYPE ""
		--#SUMMARY "Nonce stamp mismatch: session data base"
		--#SUMMARY "	file inconsistent"
		--#ARGUMENTS { }
		--#SEVERITY INFORMATIONAL
		--#TIMEINDEX 0
		--#SYMBOL VS_SDB_INCONSISTENT

		::= 62


vsNoSessAvail	TRAP-TYPE
		ENTERPRISE  mib2
		VARIABLES  {  tpSvrName, tpSvcName, tpAlertTime }
	
		DESCRIPTION
			"A login session was denied as the allowed no.
			 of sessions had been reached."
                --#TYPE ""
		--#SUMMARY "Login session denied; number of sessions "
		--#SUMMARY "	has reached user limit"
		--#ARGUMENTS { }
		--#SEVERITY INFORMATIONAL
		--#TIMEINDEX 0
		--#SYMBOL VS_NOSESS_AVAIL

		::= 63


vsSvrSvrPwd	TRAP-TYPE
		ENTERPRISE  mib2
		VARIABLES  {  tpSvrName, tpSvcName, tpAlertTime,
			      tpRefSvrName }
	
		DESCRIPTION
			"A secure link was requested to the specified
			 server and was not established due to a bad
			 password."
                --#TYPE ""
		--#SUMMARY "Setting link to new neighbor %s as SECURE;"
		--#SUMMARY "	bad password"
		--#ARGUMENTS { 3 }
		--#SEVERITY INFORMATIONAL
		--#TIMEINDEX 0
		--#SYMBOL VS_SVR_SVR_PWD

		::= 64


vsNoSTLogin	TRAP-TYPE
		ENTERPRISE  mib2
		VARIABLES  {  tpSvrName, tpSvcName, tpAlertTime,
			      tpErrorCode }
	
		DESCRIPTION
			"The VINES Security Service could not login to StreetTalk,
			 with the given error code, and hence is exiting."
                --#TYPE ""
		--#SUMMARY "Cannot log into StreetTalk.  Err is %d."
		--#SUMMARY "	  Exiting..."
		--#ARGUMENTS { 3 }
		--#SEVERITY INFORMATIONAL
		--#TIMEINDEX 0
		--#SYMBOL VS_CANT_STLOGIN

		::= 65


vsNoSpace	TRAP-TYPE
		ENTERPRISE  mib2
		VARIABLES  {  tpSvrName, tpSvcName, tpAlertTime }
	
		DESCRIPTION
			"The VINES Security Service could not compress the
			 sessions file as the disk is full."
                --#TYPE ""
		--#SUMMARY "No space left on disk; cannot compress"
		--#SUMMARY "	  sessions file"
		--#ARGUMENTS { }
		--#SEVERITY INFORMATIONAL
		--#TIMEINDEX 0
		--#SYMBOL VS_NO_SPACE

		::= 66


vsLinkDown	TRAP-TYPE
		ENTERPRISE  mib2
		VARIABLES  {  tpSvrName, tpSvcName, tpAlertTime,
			      tpSvrNetId }
	
		DESCRIPTION
			"The point-to-point link to the specified server
			 has been severed."
                --#TYPE ""
		--#SUMMARY "Point-to-point link to server %lu severed"
		--#ARGUMENTS { 3 }
		--#SEVERITY INFORMATIONAL
		--#TIMEINDEX 0
		--#SYMBOL VS_LINK_DOWN

		::= 67


vsPCDialTerm	TRAP-TYPE
		ENTERPRISE  mib2
		VARIABLES  {  tpSvrName, tpSvcName, tpAlertTime,
			      tpUserName, tpSvrNetId, tpSubNetId,
			      tpSlotNum, tpLineNum }
	
		DESCRIPTION
			"A PC Dial-In session has been severed on the
			 indicated slot and line number."
                --#TYPE ""
		--#SUMMARY "PC dial-in severed: usr %s svr %lu snid %u slot %u line %u "
		--#ARGUMENTS { 3, 4, 5, 6, 7 }
		--#SEVERITY INFORMATIONAL
		--#TIMEINDEX 0
		--#SYMBOL VS_PCDIALLINK_DOWN

		::= 68


vsPCDialInit	TRAP-TYPE
		ENTERPRISE  mib2
		VARIABLES  {  tpSvrName, tpSvcName, tpAlertTime,
			      tpUserName, tpSvrNetId, tpSubNetId,
			      tpSlotNum, tpLineNum }
	
		DESCRIPTION
			"A PC Dial-In session has been established on the
			 indicated slot and line number."
                --#TYPE ""
		--#SUMMARY "PC dial-in established: usr %s svr %lu snid %u slot %u line %u "
		--#ARGUMENTS { 3, 4, 5, 6, 7 }
		--#SEVERITY INFORMATIONAL
		--#TIMEINDEX 0
		--#SYMBOL VS_PCDIALLINK_UP

		::= 69


--  AFP Traps


afpAtalkDown	TRAP-TYPE
		ENTERPRISE  mib2
		VARIABLES  {  tpSvrName, tpSvcName, tpAlertTime  }
	
		DESCRIPTION
			"An AppleTalk stack error was detected."
                --#TYPE ""
		--#SUMMARY "AppleTalk stack error detected"
		--#ARGUMENTS { }
		--#SEVERITY INFORMATIONAL
		--#TIMEINDEX 0
		--#SYMBOL AFP_ATALK_DOWN

		::= 70


afpSessDiscon	TRAP-TYPE
		ENTERPRISE  mib2
		VARIABLES  {  tpSvrName, tpSvcName, tpAlertTime,
			      tpUserName  }
	
		DESCRIPTION
			"A Session disconnect was detected."
                --#TYPE ""
		--#SUMMARY "Session disconnect detected for %s"
		--#ARGUMENTS { 3 }
		--#SEVERITY INFORMATIONAL
		--#TIMEINDEX 0
		--#SYMBOL AFP_SESS_DISCONNECT

		::= 71



-- STDA Traps


daGCoreDump	TRAP-TYPE
		ENTERPRISE  mib2
		VARIABLES  {  tpSvrName, tpSvcName, tpAlertTime,
			      tpRtnName  }
	
		DESCRIPTION
			"STDA getnames going down unexpectedly."
                --#TYPE ""
		--#SUMMARY "DA (getnames) going down unexpectedly.(%s)"
		--#ARGUMENTS { 3 }
		--#SEVERITY INFORMATIONAL
		--#TIMEINDEX 0
		--#SYMBOL DAG_CORING_OUT

		::= 72


daSCoreDump	TRAP-TYPE
		ENTERPRISE  mib2
		VARIABLES  {  tpSvrName, tpSvcName, tpAlertTime,
			      tpRtnName  }
	
		DESCRIPTION
			"STDA service going down unexpectedly."
                --#TYPE ""
		--#SUMMARY "DA (service) going down unexpectedly.(%s)"
		--#ARGUMENTS { 3 }
		--#SEVERITY INFORMATIONAL
		--#TIMEINDEX 0
		--#SYMBOL DAS_CORING_OUT

		::= 73



-- StreetTalk Traps


stCoreDump	TRAP-TYPE
		ENTERPRISE  mib2
		VARIABLES  {  tpSvrName, tpSvcName, tpAlertTime,
			      tpErrorCode  }
	
		DESCRIPTION
			"StreetTalk service going down unexpectedly with
			 the given error code."
                --#TYPE ""
		--#SUMMARY "StreetTalk going down unexpectedly.(%u)"
		--#ARGUMENTS { 3 }
		--#SEVERITY INFORMATIONAL
		--#TIMEINDEX 0
		--#SYMBOL ST_CORING_OUT

		::= 74


st162Errs	TRAP-TYPE
		ENTERPRISE  mib2
		VARIABLES  {  tpSvrName, tpSvcName, tpAlertTime,
			      tp162erravg, tp162errThresHigh,
			      tp162errTotal  }
	
		DESCRIPTION
			"The current 15 minute average of 162 (network
			 timeout) errors has exceeded the set threshold." 
                --#TYPE ""
		--#SUMMARY "15 minute 162 threshold exceeded.(%u/%u)."
		--#SUMMARY "	Current Total - %u"
		--#ARGUMENTS { 3, 4, 5 }
		--#SEVERITY INFORMATIONAL
		--#TIMEINDEX 0
		--#SYMBOL ST_162_ERRS

		::= 75


stAddedGrp	TRAP-TYPE
		ENTERPRISE  mib2
		VARIABLES  {  tpSvrName, tpSvcName, tpAlertTime,
			      tpGrpName, tpRefSvrName  }
	
		DESCRIPTION
			"The specified group has been added on the
			 given server." 
                --#TYPE ""
		--#SUMMARY "Group '%s' added to server '%s'"
		--#ARGUMENTS { 3, 4 }
		--#SEVERITY INFORMATIONAL
		--#TIMEINDEX 0
		--#SYMBOL ST_ADDED_GRP

		::= 76


stDeletedGrp	TRAP-TYPE
		ENTERPRISE  mib2
		VARIABLES  {  tpSvrName, tpSvcName, tpAlertTime,
			      tpGrpName, tpRefSvrName  }
	
		DESCRIPTION
			"The specified group has been deleted on the
			 given server." 
                --#TYPE ""
		--#SUMMARY "Group '%s' deleted from server '%s'"
		--#ARGUMENTS { 3, 4 }
		--#SEVERITY INFORMATIONAL
		--#TIMEINDEX 0
		--#SYMBOL ST_DELETED_GRP

		::= 77


stRebuild	TRAP-TYPE
		ENTERPRISE  mib2
		VARIABLES  {  tpSvrName, tpSvcName, tpAlertTime,
			      tpGrpName  }
	
		DESCRIPTION
			"A data inconsistency was found in the specified
			 group. A rebuild will be attempted." 
                --#TYPE ""
		--#SUMMARY "Data consistency error in group '%s'."
		--#SUMMARY "	Attempting a rebuild."
		--#ARGUMENTS { 3 }
		--#SEVERITY INFORMATIONAL
		--#TIMEINDEX 0
		--#SYMBOL ST_REBUILD

		::= 78


stGrpLimit	TRAP-TYPE
		ENTERPRISE  mib2
		VARIABLES  {  tpSvrName, tpSvcName, tpAlertTime,
			      tpNumGrps, tpGrpLimit  }
	
		DESCRIPTION
			"The number of groups on the server has exceeded
			 the threshold percentage value of the maximum
			 allowed." 
                --#TYPE ""
		--#SUMMARY "Number of Groups on server exceeded %u"
		--#SUMMARY "	percent of maximum (%u)."
		--#ARGUMENTS { 3, 4 }
		--#SEVERITY INFORMATIONAL
		--#TIMEINDEX 0
		--#SYMBOL ST_GRP_LIMIT

		::= 79


stSerialNum	TRAP-TYPE
		ENTERPRISE  mib2
		VARIABLES  {  tpSvrName, tpSvcName, tpAlertTime,
			      tpOldSerNum, tpNewSerNum  }
	
		DESCRIPTION
			"The server serial number has been changed from
			 the given old value to the given new value."
                --#TYPE ""
		--#SUMMARY "Server serial number has changed to %lu"
		--#SUMMARY "	from %lu"
		--#ARGUMENTS { 3, 4 }
		--#SEVERITY INFORMATIONAL
		--#TIMEINDEX 0
		--#SYMBOL ST_SERIAL_NUM

		::= 80


stDupGrp	TRAP-TYPE
		ENTERPRISE  mib2
		VARIABLES  {  tpSvrName, tpSvcName, tpAlertTime,
			      tpGrpName, tpSvrNetId  }
	
		DESCRIPTION
			"A duplicate of the specified group also exists
			 on the given server."
                --#TYPE ""
		--#SUMMARY "Group '%s' exists on this server and on"
		--#SUMMARY "	server #%u"
		--#ARGUMENTS { 3, 4 }
		--#SEVERITY INFORMATIONAL
		--#TIMEINDEX 0
		--#SYMBOL ST_DUP_GROUP

		::= 81









END
