Nortel-Magellan-Passport-IpxMIB
DEFINITIONS ::= BEGIN



IMPORTS

      OBJECT-TYPE
   FROM RFC-1212

      passportMIBs
   FROM Nortel-Magellan-Passport-UsefulDefinitionsMIB

      Counter32,
      PhysAddress,
      DisplayString,
      StorageType,
      RowStatus,
      Gauge32,
      Integer32,
      Unsigned32
   FROM Nortel-Magellan-Passport-StandardTextualConventionsMIB

      AsciiString,
      DashedHexString,
      NonReplicated,
      Hex,
      AsciiStringIndex
   FROM Nortel-Magellan-Passport-TextualConventionsMIB

      vrIndex,
      vrPpIndex,
      vrPp,
      vr
   FROM Nortel-Magellan-Passport-VirtualRouterMIB;




-- LAST-UPDATED   "9902010000Z"
-- ORGANIZATION   "Nortel"
-- CONTACT-INFO   "
--         Nortel Magellan Network Management
--         
--         Postal: P.O. Box 5080, Station F 
--                 Ottawa, Ontario 
--                 Canada  K2C 3T1
--         
--         Email:  nm_plm@nt.com"
-- DESCRIPTION
--    "The module describing the Nortel Magellan Passport
--     Ipx Enterprise MIB."

ipxMIB OBJECT IDENTIFIER ::= { passportMIBs 28 }










-- Vr/<string> PP/<string> IpxP
-- The IPX protocol specific information relating to this ProtocolPort 
-- instance. 

vrPpIpxP OBJECT IDENTIFIER ::= { vrPp 6 }



vrPpIpxPRowStatusTable OBJECT-TYPE
   SYNTAX     SEQUENCE OF VrPpIpxPRowStatusEntry
   ACCESS     not-accessible
   STATUS     mandatory
   DESCRIPTION
     "This entry controls the addition and deletion of 
      vrPpIpxP components."
::= { vrPpIpxP 1 }

vrPpIpxPRowStatusEntry OBJECT-TYPE
   SYNTAX     VrPpIpxPRowStatusEntry
   ACCESS     not-accessible
   STATUS     mandatory
   DESCRIPTION
     "A single entry in the table represents a single 
      vrPpIpxP component."
   INDEX {
      vrIndex,
      vrPpIndex,
      vrPpIpxPIndex }
::= { vrPpIpxPRowStatusTable 1 }

VrPpIpxPRowStatusEntry ::= SEQUENCE {
   vrPpIpxPRowStatus
      RowStatus,
   vrPpIpxPComponentName
      DisplayString,
   vrPpIpxPStorageType
      StorageType,
   vrPpIpxPIndex
      INTEGER }

vrPpIpxPRowStatus OBJECT-TYPE
   SYNTAX     RowStatus 
   ACCESS     read-write
   STATUS     mandatory
   DESCRIPTION
     "This variable is used as the basis for SNMP naming of
      vrPpIpxP components.
      These components can be added and deleted."
::= { vrPpIpxPRowStatusEntry 1 }

vrPpIpxPComponentName OBJECT-TYPE
   SYNTAX     DisplayString 
   ACCESS     read-only
   STATUS     mandatory
   DESCRIPTION
     "This variable provides the component's string name for
      use with the ASCII Console Interface"
::= { vrPpIpxPRowStatusEntry 2 }

vrPpIpxPStorageType OBJECT-TYPE
   SYNTAX     StorageType 
   ACCESS     read-only
   STATUS     mandatory
   DESCRIPTION
     "This variable represents the storage type value for the
      vrPpIpxP tables."
::= { vrPpIpxPRowStatusEntry 4 }

vrPpIpxPIndex OBJECT-TYPE
   SYNTAX     INTEGER  {
                 link(1),
                 ethernet(2),
                 novell(3),
                 sap(4),
                 snap(5),
                 vns(6),
                 tunnel(7) }
   ACCESS     not-accessible
   STATUS     mandatory
   DESCRIPTION
     "This variable represents the index for the vrPpIpxP tables."
::= { vrPpIpxPRowStatusEntry 10 }

vrPpIpxPAdminControlTable OBJECT-TYPE
   SYNTAX     SEQUENCE OF VrPpIpxPAdminControlEntry
   ACCESS     not-accessible
   STATUS     mandatory
   DESCRIPTION
     "This group includes the Administrative Control attribute. This 
      attribute defines the current administrative state of this component."
::= { vrPpIpxP 100 }

vrPpIpxPAdminControlEntry OBJECT-TYPE
   SYNTAX     VrPpIpxPAdminControlEntry
   ACCESS     not-accessible
   STATUS     mandatory
   DESCRIPTION
     "An entry in the vrPpIpxPAdminControlTable."
   INDEX {
      vrIndex,
      vrPpIndex,
      vrPpIpxPIndex }
::= { vrPpIpxPAdminControlTable 1 }

VrPpIpxPAdminControlEntry ::= SEQUENCE {
   vrPpIpxPSnmpAdminStatus
      INTEGER }

vrPpIpxPSnmpAdminStatus OBJECT-TYPE
   SYNTAX     INTEGER  {
                 up(1),
                 down(2),
                 testing(3) }
   ACCESS     read-write
   STATUS     mandatory
   DESCRIPTION
     "The desired state of the interface. The up state indicates the 
      interface is operational and packet forwarding is allowed. The down 
      state indicates the interface is not operational and packet forwarding 
      is unavailable. The testing state indicates that no operational 
      packets can be passed."
   DEFVAL     { up }
::= { vrPpIpxPAdminControlEntry 1 }

vrPpIpxPProvTable OBJECT-TYPE
   SYNTAX     SEQUENCE OF VrPpIpxPProvEntry
   ACCESS     not-accessible
   STATUS     mandatory
   DESCRIPTION
     "The Provisionable group for the IpxPort component."
::= { vrPpIpxP 101 }

vrPpIpxPProvEntry OBJECT-TYPE
   SYNTAX     VrPpIpxPProvEntry
   ACCESS     not-accessible
   STATUS     mandatory
   DESCRIPTION
     "An entry in the vrPpIpxPProvTable."
   INDEX {
      vrIndex,
      vrPpIndex,
      vrPpIpxPIndex }
::= { vrPpIpxPProvTable 1 }

VrPpIpxPProvEntry ::= SEQUENCE {
   vrPpIpxPNetworkNumberProv
      DashedHexString,
   vrPpIpxPDefaultType
      INTEGER,
   vrPpIpxPBroadcastInhibit
      INTEGER }

vrPpIpxPNetworkNumberProv OBJECT-TYPE
   SYNTAX     DashedHexString (SIZE (0..4))
   ACCESS     read-write
   STATUS     mandatory
   DESCRIPTION
     "The Ipx network number of the network directly connected to this port."
::= { vrPpIpxPProvEntry 1 }

vrPpIpxPDefaultType OBJECT-TYPE
   SYNTAX     INTEGER  {
                 other(1),
                 broadcast(2),
                 ppp(3),
                 wanRip(4),
                 unnumberedRip(5) }
   ACCESS     read-write
   STATUS     mandatory
   DESCRIPTION
     "This attribute indicates which protocol is to run on a protocol port. 
      In the case of a lan media it is to be set to broadcast.
      In the case of WAN media the following choices are to be exercised:
      For running Pre-IPXWAN RIP set value to other.
      For running numbered RIP set value to wanRip.
      For running un-numbered RIP set value to unnumberedRip. 
      Setting this value to ppp will signify unnumbered Rip running on a ppp 
      port."
::= { vrPpIpxPProvEntry 2 }

vrPpIpxPBroadcastInhibit OBJECT-TYPE
   SYNTAX     INTEGER  {
                 disabled(0),
                 enabled(1) }
   ACCESS     read-write
   STATUS     mandatory
   DESCRIPTION
     "If this attribute is set, all outgoing periodic and triggered updates for RIP 
      and SAP will be inhibited for the port. However the port will still accept 
      incoming RIP and SAP packets on the port. This may be useful for ports 
      with only a bank of servers on its network in order to limit the routing 
      traffic, assuming that servers don't require routing information or other 
      server information."
   DEFVAL     { disabled }
::= { vrPpIpxPProvEntry 3 }

vrPpIpxPSresProvTable OBJECT-TYPE
   SYNTAX     SEQUENCE OF VrPpIpxPSresProvEntry
   ACCESS     not-accessible
   STATUS     mandatory
   DESCRIPTION
     "This group contains the provisioned attributes for 
      SourceRouteEndStation support."
::= { vrPpIpxP 102 }

vrPpIpxPSresProvEntry OBJECT-TYPE
   SYNTAX     VrPpIpxPSresProvEntry
   ACCESS     not-accessible
   STATUS     mandatory
   DESCRIPTION
     "An entry in the vrPpIpxPSresProvTable."
   INDEX {
      vrIndex,
      vrPpIndex,
      vrPpIpxPIndex }
::= { vrPpIpxPSresProvTable 1 }

VrPpIpxPSresProvEntry ::= SEQUENCE {
   vrPpIpxPSourceRouteEndStationSupport
      INTEGER }

vrPpIpxPSourceRouteEndStationSupport OBJECT-TYPE
   SYNTAX     INTEGER  {
                 enable(1),
                 disable(2) }
   ACCESS     read-write
   STATUS     mandatory
   DESCRIPTION
     "This attribute is used to enable or disable support for 
      SourceRouteEndStation (Sres). If set to enable, Sres will be supported 
      on this protocol on this ProtocolPort (Pp). If set to disable, it will not be 
      supported. An Sres component must be provisioned under the 
      VirtualRouter if this attribute is set to enable. If this attribute is set to 
      enable and this Pp has its linkToMedia attribute set, it must be linked to 
      a LanApplication (La) that has its Framer interfaceName linked to a 
      Fddi or TokenRing component."
   DEFVAL     { disable }
::= { vrPpIpxPSresProvEntry 1 }

vrPpIpxPStateTable OBJECT-TYPE
   SYNTAX     SEQUENCE OF VrPpIpxPStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { vrPpIpxP 103 }

vrPpIpxPStateEntry OBJECT-TYPE
   SYNTAX     VrPpIpxPStateEntry
   ACCESS     not-accessible
   STATUS     mandatory
   DESCRIPTION
     "An entry in the vrPpIpxPStateTable."
   INDEX {
      vrIndex,
      vrPpIndex,
      vrPpIpxPIndex }
::= { vrPpIpxPStateTable 1 }

VrPpIpxPStateEntry ::= SEQUENCE {
   vrPpIpxPAdminState
      INTEGER,
   vrPpIpxPOperationalState
      INTEGER,
   vrPpIpxPUsageState
      INTEGER }

vrPpIpxPAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { vrPpIpxPStateEntry 1 }

vrPpIpxPOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { vrPpIpxPStateEntry 2 }

vrPpIpxPUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { vrPpIpxPStateEntry 3 }

vrPpIpxPOperStatusTable OBJECT-TYPE
   SYNTAX     SEQUENCE OF VrPpIpxPOperStatusEntry
   ACCESS     not-accessible
   STATUS     mandatory
   DESCRIPTION
     "This group includes the Operational Status attribute. This attribute 
      defines the current operational state of this component."
::= { vrPpIpxP 104 }

vrPpIpxPOperStatusEntry OBJECT-TYPE
   SYNTAX     VrPpIpxPOperStatusEntry
   ACCESS     not-accessible
   STATUS     mandatory
   DESCRIPTION
     "An entry in the vrPpIpxPOperStatusTable."
   INDEX {
      vrIndex,
      vrPpIndex,
      vrPpIpxPIndex }
::= { vrPpIpxPOperStatusTable 1 }

VrPpIpxPOperStatusEntry ::= SEQUENCE {
   vrPpIpxPSnmpOperStatus
      INTEGER }

vrPpIpxPSnmpOperStatus OBJECT-TYPE
   SYNTAX     INTEGER  {
                 up(1),
                 down(2),
                 testing(3) }
   ACCESS     read-only
   STATUS     mandatory
   DESCRIPTION
     "The current state of the interface. The up state indicates the 
      interface is operational and capable of forwarding packets. The 
      down state indicates the interface is not operational, thus unable to 
      forward packets. testing state indicates that no operational packets 
      can be passed."
   DEFVAL     { up }
::= { vrPpIpxPOperStatusEntry 1 }

vrPpIpxPOperTable OBJECT-TYPE
   SYNTAX     SEQUENCE OF VrPpIpxPOperEntry
   ACCESS     not-accessible
   STATUS     mandatory
   DESCRIPTION
     "The IpxPort Operational Attributes."
::= { vrPpIpxP 105 }

vrPpIpxPOperEntry OBJECT-TYPE
   SYNTAX     VrPpIpxPOperEntry
   ACCESS     not-accessible
   STATUS     mandatory
   DESCRIPTION
     "An entry in the vrPpIpxPOperTable."
   INDEX {
      vrIndex,
      vrPpIndex,
      vrPpIpxPIndex }
::= { vrPpIpxPOperTable 1 }

VrPpIpxPOperEntry ::= SEQUENCE {
   vrPpIpxPType
      INTEGER,
   vrPpIpxPEncapsulation
      INTEGER,
   vrPpIpxPNetworkNumber
      DashedHexString,
   vrPpIpxPNode
      DashedHexString }

vrPpIpxPType OBJECT-TYPE
   SYNTAX     INTEGER  {
                 other(1),
                 broadcast(2),
                 ppp(3),
                 wanRip(4),
                 unnumberedRip(5) }
   ACCESS     read-only
   STATUS     mandatory
   DESCRIPTION
     "The type of the circuit. This would differ from the provisioned type 
      when a different routing protocol is negotiated with the peer."
::= { vrPpIpxPOperEntry 1 }

vrPpIpxPEncapsulation OBJECT-TYPE
   SYNTAX     INTEGER  {
                 link(1),
                 ethernet(2),
                 novell(3),
                 sap(4),
                 snap(5),
                 vns(6),
                 tunnel(7) }
   ACCESS     read-only
   STATUS     mandatory
   DESCRIPTION
     "Packet encapsulation type that the router has determined to use on the 
      port. There are seven encapsulation types used to identify IPX datagram 
      as listed below.
      
      1. link: IPX encapsulation type for PPP, ATM MPE, and X25DTE 
      media types.
      
      2. ethernet: IPX encapsulation type for Ethernet and FrDte media 
      types.
      
      3. novell: IPX encapsulation type for Ethernet and FrDte media 
      types.
      
      4. sap: IPX encapsulation type for FDDI, Token Ring, Ethernet 
      and FrDte media types.
      
      5. snap: IPX encapsulation type for FDDI, Token Ring, Ethernet, 
      and FrDte media types.
      
      6. vns: IPX encapsulation type for VNS media type.
      
      7. tunnel: IPX encapsulation type for Tunnel media type."
::= { vrPpIpxPOperEntry 2 }

vrPpIpxPNetworkNumber OBJECT-TYPE
   SYNTAX     DashedHexString (SIZE (0..4))
   ACCESS     read-only
   STATUS     mandatory
   DESCRIPTION
     "The Ipx network number from the provisioned networkNumberProv 
      value."
::= { vrPpIpxPOperEntry 3 }

vrPpIpxPNode OBJECT-TYPE
   SYNTAX     DashedHexString (SIZE (1..6))
   ACCESS     read-only
   STATUS     mandatory
   DESCRIPTION
     "The Ipx node address of this IpxPort."
::= { vrPpIpxPOperEntry 4 }

vrPpIpxPStatsTable OBJECT-TYPE
   SYNTAX     SEQUENCE OF VrPpIpxPStatsEntry
   ACCESS     not-accessible
   STATUS     mandatory
   DESCRIPTION
     "The IpxPort Statistics group."
::= { vrPpIpxP 106 }

vrPpIpxPStatsEntry OBJECT-TYPE
   SYNTAX     VrPpIpxPStatsEntry
   ACCESS     not-accessible
   STATUS     mandatory
   DESCRIPTION
     "An entry in the vrPpIpxPStatsTable."
   INDEX {
      vrIndex,
      vrPpIndex,
      vrPpIpxPIndex }
::= { vrPpIpxPStatsTable 1 }

VrPpIpxPStatsEntry ::= SEQUENCE {
   vrPpIpxPStateChanges
      Counter32,
   vrPpIpxPInReceives
      Counter32,
   vrPpIpxPForwarded
      Counter32 }

vrPpIpxPStateChanges OBJECT-TYPE
   SYNTAX     Counter32 
   ACCESS     read-only
   STATUS     mandatory
   DESCRIPTION
     "Number of times the port has changed state. This counter wraps around 
      to zero after reaching the maximum value of 4294967295."
::= { vrPpIpxPStatsEntry 1 }

vrPpIpxPInReceives OBJECT-TYPE
   SYNTAX     Counter32 
   ACCESS     read-only
   STATUS     mandatory
   DESCRIPTION
     "Total number of packets received. This counter wraps around to zero 
      after reaching the maximum value of 4294967295."
::= { vrPpIpxPStatsEntry 2 }

vrPpIpxPForwarded OBJECT-TYPE
   SYNTAX     Counter32 
   ACCESS     read-only
   STATUS     mandatory
   DESCRIPTION
     "Number of packets forwarded. This counter wraps around to zero after 
      reaching the maximum value of 4294967295."
::= { vrPpIpxPStatsEntry 3 }


-- Vr/<string> PP/<string> IpxP RipP
-- The RIP specific information pertaining to this IpxPort component. 

vrPpIpxPRipP OBJECT IDENTIFIER ::= { vrPpIpxP 2 }



vrPpIpxPRipPRowStatusTable OBJECT-TYPE
   SYNTAX     SEQUENCE OF VrPpIpxPRipPRowStatusEntry
   ACCESS     not-accessible
   STATUS     mandatory
   DESCRIPTION
     "This entry controls the addition and deletion of 
      vrPpIpxPRipP components."
::= { vrPpIpxPRipP 1 }

vrPpIpxPRipPRowStatusEntry OBJECT-TYPE
   SYNTAX     VrPpIpxPRipPRowStatusEntry
   ACCESS     not-accessible
   STATUS     mandatory
   DESCRIPTION
     "A single entry in the table represents a single 
      vrPpIpxPRipP component."
   INDEX {
      vrIndex,
      vrPpIndex,
      vrPpIpxPIndex,
      vrPpIpxPRipPIndex }
::= { vrPpIpxPRipPRowStatusTable 1 }

VrPpIpxPRipPRowStatusEntry ::= SEQUENCE {
   vrPpIpxPRipPRowStatus
      RowStatus,
   vrPpIpxPRipPComponentName
      DisplayString,
   vrPpIpxPRipPStorageType
      StorageType,
   vrPpIpxPRipPIndex
      NonReplicated }

vrPpIpxPRipPRowStatus OBJECT-TYPE
   SYNTAX     RowStatus 
   ACCESS     read-only
   STATUS     mandatory
   DESCRIPTION
     "This variable is used as the basis for SNMP naming of
      vrPpIpxPRipP components.
      These components cannot be added nor deleted."
::= { vrPpIpxPRipPRowStatusEntry 1 }

vrPpIpxPRipPComponentName OBJECT-TYPE
   SYNTAX     DisplayString 
   ACCESS     read-only
   STATUS     mandatory
   DESCRIPTION
     "This variable provides the component's string name for
      use with the ASCII Console Interface"
::= { vrPpIpxPRipPRowStatusEntry 2 }

vrPpIpxPRipPStorageType OBJECT-TYPE
   SYNTAX     StorageType 
   ACCESS     read-only
   STATUS     mandatory
   DESCRIPTION
     "This variable represents the storage type value for the
      vrPpIpxPRipP tables."
::= { vrPpIpxPRipPRowStatusEntry 4 }

vrPpIpxPRipPIndex OBJECT-TYPE
   SYNTAX     NonReplicated 
   ACCESS     not-accessible
   STATUS     mandatory
   DESCRIPTION
     "This variable represents the index for the vrPpIpxPRipP tables."
::= { vrPpIpxPRipPRowStatusEntry 10 }

vrPpIpxPRipPStatsTable OBJECT-TYPE
   SYNTAX     SEQUENCE OF VrPpIpxPRipPStatsEntry
   ACCESS     not-accessible
   STATUS     mandatory
   DESCRIPTION
     "RIP specific statistics for this IpxPort."
::= { vrPpIpxPRipP 10 }

vrPpIpxPRipPStatsEntry OBJECT-TYPE
   SYNTAX     VrPpIpxPRipPStatsEntry
   ACCESS     not-accessible
   STATUS     mandatory
   DESCRIPTION
     "An entry in the vrPpIpxPRipPStatsTable."
   INDEX {
      vrIndex,
      vrPpIndex,
      vrPpIpxPIndex,
      vrPpIpxPRipPIndex }
::= { vrPpIpxPRipPStatsTable 1 }

VrPpIpxPRipPStatsEntry ::= SEQUENCE {
   vrPpIpxPRipPInPackets
      Counter32,
   vrPpIpxPRipPInRequests
      Counter32,
   vrPpIpxPRipPInResponses
      Counter32,
   vrPpIpxPRipPOutPackets
      Counter32,
   vrPpIpxPRipPOutRequests
      Counter32,
   vrPpIpxPRipPOutResponses
      Counter32,
   vrPpIpxPRipPIncorrectPackets
      Counter32 }

vrPpIpxPRipPInPackets OBJECT-TYPE
   SYNTAX     Counter32 
   ACCESS     read-only
   STATUS     mandatory
   DESCRIPTION
     "The number of RIP packets received on this IpxPort. This counter wraps 
      around to zero after reaching the maximum value of 4294967295."
::= { vrPpIpxPRipPStatsEntry 1 }

vrPpIpxPRipPInRequests OBJECT-TYPE
   SYNTAX     Counter32 
   ACCESS     read-only
   STATUS     mandatory
   DESCRIPTION
     "The number of RIP request packets received on this IpxPort. This 
      counter wraps around to zero after reaching the maximum value of 
      4294967295."
::= { vrPpIpxPRipPStatsEntry 2 }

vrPpIpxPRipPInResponses OBJECT-TYPE
   SYNTAX     Counter32 
   ACCESS     read-only
   STATUS     mandatory
   DESCRIPTION
     "The number of RIP response packets received on this IpxPort. This 
      counter wraps around to zero after reaching the maximum value of 
      4294967295."
::= { vrPpIpxPRipPStatsEntry 3 }

vrPpIpxPRipPOutPackets OBJECT-TYPE
   SYNTAX     Counter32 
   ACCESS     read-only
   STATUS     mandatory
   DESCRIPTION
     "The number of RIP packets sent out on this IpxPort. This counter wraps 
      around to zero after reaching the maximum value of 4294967295."
::= { vrPpIpxPRipPStatsEntry 4 }

vrPpIpxPRipPOutRequests OBJECT-TYPE
   SYNTAX     Counter32 
   ACCESS     read-only
   STATUS     mandatory
   DESCRIPTION
     "The number of RIP request packets sent out on this IpxPort. This 
      counter wraps around to zero after reaching the maximum value of 
      4294967295."
::= { vrPpIpxPRipPStatsEntry 5 }

vrPpIpxPRipPOutResponses OBJECT-TYPE
   SYNTAX     Counter32 
   ACCESS     read-only
   STATUS     mandatory
   DESCRIPTION
     "The number of RIP response packets sent out on this IpxPort. This 
      includes RIP periodic update packets. This counter wraps around to zero 
      after reaching the maximum value of 4294967295."
::= { vrPpIpxPRipPStatsEntry 6 }

vrPpIpxPRipPIncorrectPackets OBJECT-TYPE
   SYNTAX     Counter32 
   ACCESS     read-only
   STATUS     mandatory
   DESCRIPTION
     "Number of times that an incorrectly formatted RIP packet was received 
      on this IpxPort. This counter wraps around to zero after reaching the 
      maximum value of 4294967295."
::= { vrPpIpxPRipPStatsEntry 7 }


-- Vr/<string> PP/<string> IpxP SapP
-- The SAP specific information pertaining to this IpxPort component.

vrPpIpxPSapP OBJECT IDENTIFIER ::= { vrPpIpxP 3 }



vrPpIpxPSapPRowStatusTable OBJECT-TYPE
   SYNTAX     SEQUENCE OF VrPpIpxPSapPRowStatusEntry
   ACCESS     not-accessible
   STATUS     mandatory
   DESCRIPTION
     "This entry controls the addition and deletion of 
      vrPpIpxPSapP components."
::= { vrPpIpxPSapP 1 }

vrPpIpxPSapPRowStatusEntry OBJECT-TYPE
   SYNTAX     VrPpIpxPSapPRowStatusEntry
   ACCESS     not-accessible
   STATUS     mandatory
   DESCRIPTION
     "A single entry in the table represents a single 
      vrPpIpxPSapP component."
   INDEX {
      vrIndex,
      vrPpIndex,
      vrPpIpxPIndex,
      vrPpIpxPSapPIndex }
::= { vrPpIpxPSapPRowStatusTable 1 }

VrPpIpxPSapPRowStatusEntry ::= SEQUENCE {
   vrPpIpxPSapPRowStatus
      RowStatus,
   vrPpIpxPSapPComponentName
      DisplayString,
   vrPpIpxPSapPStorageType
      StorageType,
   vrPpIpxPSapPIndex
      NonReplicated }

vrPpIpxPSapPRowStatus OBJECT-TYPE
   SYNTAX     RowStatus 
   ACCESS     read-only
   STATUS     mandatory
   DESCRIPTION
     "This variable is used as the basis for SNMP naming of
      vrPpIpxPSapP components.
      These components cannot be added nor deleted."
::= { vrPpIpxPSapPRowStatusEntry 1 }

vrPpIpxPSapPComponentName OBJECT-TYPE
   SYNTAX     DisplayString 
   ACCESS     read-only
   STATUS     mandatory
   DESCRIPTION
     "This variable provides the component's string name for
      use with the ASCII Console Interface"
::= { vrPpIpxPSapPRowStatusEntry 2 }

vrPpIpxPSapPStorageType OBJECT-TYPE
   SYNTAX     StorageType 
   ACCESS     read-only
   STATUS     mandatory
   DESCRIPTION
     "This variable represents the storage type value for the
      vrPpIpxPSapP tables."
::= { vrPpIpxPSapPRowStatusEntry 4 }

vrPpIpxPSapPIndex OBJECT-TYPE
   SYNTAX     NonReplicated 
   ACCESS     not-accessible
   STATUS     mandatory
   DESCRIPTION
     "This variable represents the index for the vrPpIpxPSapP tables."
::= { vrPpIpxPSapPRowStatusEntry 10 }

vrPpIpxPSapPStatsTable OBJECT-TYPE
   SYNTAX     SEQUENCE OF VrPpIpxPSapPStatsEntry
   ACCESS     not-accessible
   STATUS     mandatory
   DESCRIPTION
     "SAP specific statistics for this IpxPort."
::= { vrPpIpxPSapP 10 }

vrPpIpxPSapPStatsEntry OBJECT-TYPE
   SYNTAX     VrPpIpxPSapPStatsEntry
   ACCESS     not-accessible
   STATUS     mandatory
   DESCRIPTION
     "An entry in the vrPpIpxPSapPStatsTable."
   INDEX {
      vrIndex,
      vrPpIndex,
      vrPpIpxPIndex,
      vrPpIpxPSapPIndex }
::= { vrPpIpxPSapPStatsTable 1 }

VrPpIpxPSapPStatsEntry ::= SEQUENCE {
   vrPpIpxPSapPInPackets
      Counter32,
   vrPpIpxPSapPInRequests
      Counter32,
   vrPpIpxPSapPInResponses
      Counter32,
   vrPpIpxPSapPOutPackets
      Counter32,
   vrPpIpxPSapPOutRequests
      Counter32,
   vrPpIpxPSapPOutResponses
      Counter32,
   vrPpIpxPSapPIncorrectPackets
      Counter32 }

vrPpIpxPSapPInPackets OBJECT-TYPE
   SYNTAX     Counter32 
   ACCESS     read-only
   STATUS     mandatory
   DESCRIPTION
     "The total number of SAP packets received on this IpxPort. Includes SAP 
      requests and responses. This counter wraps around to zero after reaching 
      the maximum value of 4294967295."
::= { vrPpIpxPSapPStatsEntry 1 }

vrPpIpxPSapPInRequests OBJECT-TYPE
   SYNTAX     Counter32 
   ACCESS     read-only
   STATUS     mandatory
   DESCRIPTION
     "The number of SAP Request packets received on this IpxPort. This 
      counter wraps around to zero after reaching the maximum value of 
      4294967295."
::= { vrPpIpxPSapPStatsEntry 2 }

vrPpIpxPSapPInResponses OBJECT-TYPE
   SYNTAX     Counter32 
   ACCESS     read-only
   STATUS     mandatory
   DESCRIPTION
     "The number of SAP response packets received on this IpxPort. This 
      counter wraps around to zero after reaching the maximum value of 
      4294967295."
::= { vrPpIpxPSapPStatsEntry 3 }

vrPpIpxPSapPOutPackets OBJECT-TYPE
   SYNTAX     Counter32 
   ACCESS     read-only
   STATUS     mandatory
   DESCRIPTION
     "The total number of SAP packets sent out this IpxPort. This counter 
      wraps around to zero after reaching the maximum value of 4294967295."
::= { vrPpIpxPSapPStatsEntry 4 }

vrPpIpxPSapPOutRequests OBJECT-TYPE
   SYNTAX     Counter32 
   ACCESS     read-only
   STATUS     mandatory
   DESCRIPTION
     "The number of SAP request packets sent out on this IpxPort. This 
      counter wraps around to zero after reaching the maximum value of 
      4294967295."
::= { vrPpIpxPSapPStatsEntry 5 }

vrPpIpxPSapPOutResponses OBJECT-TYPE
   SYNTAX     Counter32 
   ACCESS     read-only
   STATUS     mandatory
   DESCRIPTION
     "The number of SAP response packets sent out this IpxPort. This 
      includes periodic SAP update packets. This counter wraps around to 
      zero after reaching the maximum value of 4294967295."
::= { vrPpIpxPSapPStatsEntry 6 }

vrPpIpxPSapPIncorrectPackets OBJECT-TYPE
   SYNTAX     Counter32 
   ACCESS     read-only
   STATUS     mandatory
   DESCRIPTION
     "Number of times an incorrectly formatted SAP packet was received on 
      this IpxPort. This counter wraps around to zero after reaching the 
      maximum value of 4294967295."
::= { vrPpIpxPSapPStatsEntry 7 }

-- 
-- *** THIS SUBTREE CURRENTLY NOT IMPLEMENTED ***
-- 

-- Vr/<string> PP/<string> IpxP IWP
-- This component contains information for this IpxPort that are specific to 
-- the IPXWAN protocol. 

vrPpIpxPIWP OBJECT IDENTIFIER ::= { vrPpIpxP 4 }



vrPpIpxPIWPRowStatusTable OBJECT-TYPE
   SYNTAX     SEQUENCE OF VrPpIpxPIWPRowStatusEntry
   ACCESS     not-accessible
   STATUS     mandatory
   DESCRIPTION
     "*** THIS TABLE CURRENTLY NOT IMPLEMENTED ***

      This entry controls the addition and deletion of 
      vrPpIpxPIWP components."
::= { vrPpIpxPIWP 1 }

vrPpIpxPIWPRowStatusEntry OBJECT-TYPE
   SYNTAX     VrPpIpxPIWPRowStatusEntry
   ACCESS     not-accessible
   STATUS     mandatory
   DESCRIPTION
     "A single entry in the table represents a single 
      vrPpIpxPIWP component."
   INDEX {
      vrIndex,
      vrPpIndex,
      vrPpIpxPIndex,
      vrPpIpxPIWPRemoteStationIdentifierIndex }
::= { vrPpIpxPIWPRowStatusTable 1 }

VrPpIpxPIWPRowStatusEntry ::= SEQUENCE {
   vrPpIpxPIWPRowStatus
      RowStatus,
   vrPpIpxPIWPComponentName
      DisplayString,
   vrPpIpxPIWPStorageType
      StorageType,
   vrPpIpxPIWPRemoteStationIdentifierIndex
      DashedHexString }

vrPpIpxPIWPRowStatus OBJECT-TYPE
   SYNTAX     RowStatus 
   ACCESS     read-only
   STATUS     mandatory
   DESCRIPTION
     "This variable is used as the basis for SNMP naming of
      vrPpIpxPIWP components.
      These components cannot be added nor deleted."
::= { vrPpIpxPIWPRowStatusEntry 1 }

vrPpIpxPIWPComponentName OBJECT-TYPE
   SYNTAX     DisplayString 
   ACCESS     read-only
   STATUS     mandatory
   DESCRIPTION
     "This variable provides the component's string name for
      use with the ASCII Console Interface"
::= { vrPpIpxPIWPRowStatusEntry 2 }

vrPpIpxPIWPStorageType OBJECT-TYPE
   SYNTAX     StorageType 
   ACCESS     read-only
   STATUS     mandatory
   DESCRIPTION
     "This variable represents the storage type value for the
      vrPpIpxPIWP tables."
::= { vrPpIpxPIWPRowStatusEntry 4 }

vrPpIpxPIWPRemoteStationIdentifierIndex OBJECT-TYPE
   SYNTAX     DashedHexString (SIZE (1..8))
   ACCESS     not-accessible
   STATUS     mandatory
   DESCRIPTION
     "This variable represents the index for the vrPpIpxPIWP tables."
::= { vrPpIpxPIWPRowStatusEntry 10 }

vrPpIpxPIWPOperTable OBJECT-TYPE
   SYNTAX     SEQUENCE OF VrPpIpxPIWPOperEntry
   ACCESS     not-accessible
   STATUS     mandatory
   DESCRIPTION
     "*** THIS TABLE CURRENTLY NOT IMPLEMENTED ***

      This group contains operational attributes that are specific for the 
      IPXWAN protocol."
::= { vrPpIpxPIWP 10 }

vrPpIpxPIWPOperEntry OBJECT-TYPE
   SYNTAX     VrPpIpxPIWPOperEntry
   ACCESS     not-accessible
   STATUS     mandatory
   DESCRIPTION
     "An entry in the vrPpIpxPIWPOperTable."
   INDEX {
      vrIndex,
      vrPpIndex,
      vrPpIpxPIndex,
      vrPpIpxPIWPRemoteStationIdentifierIndex }
::= { vrPpIpxPIWPOperTable 1 }

VrPpIpxPIWPOperEntry ::= SEQUENCE {
   vrPpIpxPIWPNeighbourRouterName
      AsciiString,
   vrPpIpxPIWPNeighbourInternalNetworkNumber
      DashedHexString,
   vrPpIpxPIWPInitFails
      Counter32 }

vrPpIpxPIWPNeighbourRouterName OBJECT-TYPE
   SYNTAX     AsciiString (SIZE (0..48))
   ACCESS     read-only
   STATUS     mandatory
   DESCRIPTION
     "The name of the neighboring router on a WAN circuit."
::= { vrPpIpxPIWPOperEntry 1 }

vrPpIpxPIWPNeighbourInternalNetworkNumber OBJECT-TYPE
   SYNTAX     DashedHexString (SIZE (1..4))
   ACCESS     read-only
   STATUS     mandatory
   DESCRIPTION
     "The internal network number of the neighboring router on a WAN 
      circuit."
::= { vrPpIpxPIWPOperEntry 2 }

vrPpIpxPIWPInitFails OBJECT-TYPE
   SYNTAX     Counter32 
   ACCESS     read-only
   STATUS     mandatory
   DESCRIPTION
     "The number of times initialization has failed on this circuit. This counter 
      wraps around to zero after reaching the maximum value of 4294967295"
::= { vrPpIpxPIWPOperEntry 3 }


-- Vr/<string> Pp/<string> IpxP NetSentryPort
-- This component contains the NetSentry attributes that specify the names 
-- of the NetSentry filters which will be applied to IPX packets as 
-- incoming and outgoing filters.

vrPpIpxPNetSentryP OBJECT IDENTIFIER ::= { vrPpIpxP 5 }



vrPpIpxPNetSentryPRowStatusTable OBJECT-TYPE
   SYNTAX     SEQUENCE OF VrPpIpxPNetSentryPRowStatusEntry
   ACCESS     not-accessible
   STATUS     mandatory
   DESCRIPTION
     "This entry controls the addition and deletion of 
      vrPpIpxPNetSentryP components."
::= { vrPpIpxPNetSentryP 1 }

vrPpIpxPNetSentryPRowStatusEntry OBJECT-TYPE
   SYNTAX     VrPpIpxPNetSentryPRowStatusEntry
   ACCESS     not-accessible
   STATUS     mandatory
   DESCRIPTION
     "A single entry in the table represents a single 
      vrPpIpxPNetSentryP component."
   INDEX {
      vrIndex,
      vrPpIndex,
      vrPpIpxPIndex,
      vrPpIpxPNetSentryPIndex }
::= { vrPpIpxPNetSentryPRowStatusTable 1 }

VrPpIpxPNetSentryPRowStatusEntry ::= SEQUENCE {
   vrPpIpxPNetSentryPRowStatus
      RowStatus,
   vrPpIpxPNetSentryPComponentName
      DisplayString,
   vrPpIpxPNetSentryPStorageType
      StorageType,
   vrPpIpxPNetSentryPIndex
      NonReplicated }

vrPpIpxPNetSentryPRowStatus OBJECT-TYPE
   SYNTAX     RowStatus 
   ACCESS     read-write
   STATUS     mandatory
   DESCRIPTION
     "This variable is used as the basis for SNMP naming of
      vrPpIpxPNetSentryP components.
      These components can be added and deleted."
::= { vrPpIpxPNetSentryPRowStatusEntry 1 }

vrPpIpxPNetSentryPComponentName OBJECT-TYPE
   SYNTAX     DisplayString 
   ACCESS     read-only
   STATUS     mandatory
   DESCRIPTION
     "This variable provides the component's string name for
      use with the ASCII Console Interface"
::= { vrPpIpxPNetSentryPRowStatusEntry 2 }

vrPpIpxPNetSentryPStorageType OBJECT-TYPE
   SYNTAX     StorageType 
   ACCESS     read-only
   STATUS     mandatory
   DESCRIPTION
     "This variable represents the storage type value for the
      vrPpIpxPNetSentryP tables."
::= { vrPpIpxPNetSentryPRowStatusEntry 4 }

vrPpIpxPNetSentryPIndex OBJECT-TYPE
   SYNTAX     NonReplicated 
   ACCESS     not-accessible
   STATUS     mandatory
   DESCRIPTION
     "This variable represents the index for the vrPpIpxPNetSentryP tables."
::= { vrPpIpxPNetSentryPRowStatusEntry 10 }

vrPpIpxPNetSentryPProvTable OBJECT-TYPE
   SYNTAX     SEQUENCE OF VrPpIpxPNetSentryPProvEntry
   ACCESS     not-accessible
   STATUS     mandatory
   DESCRIPTION
     "This group contains the NetSentry attributes that specify the names of 
      the NetSentry filters which will be applied to IPX packets as incoming 
      and outgoing filters."
::= { vrPpIpxPNetSentryP 10 }

vrPpIpxPNetSentryPProvEntry OBJECT-TYPE
   SYNTAX     VrPpIpxPNetSentryPProvEntry
   ACCESS     not-accessible
   STATUS     mandatory
   DESCRIPTION
     "An entry in the vrPpIpxPNetSentryPProvTable."
   INDEX {
      vrIndex,
      vrPpIndex,
      vrPpIpxPIndex,
      vrPpIpxPNetSentryPIndex }
::= { vrPpIpxPNetSentryPProvTable 1 }

VrPpIpxPNetSentryPProvEntry ::= SEQUENCE {
   vrPpIpxPNetSentryPInComingFilter
      AsciiString,
   vrPpIpxPNetSentryPOutGoingFilter
      AsciiString }

vrPpIpxPNetSentryPInComingFilter OBJECT-TYPE
   SYNTAX     AsciiString (SIZE (0..32))
   ACCESS     read-write
   STATUS     mandatory
   DESCRIPTION
     "This attribute specifies the name of the NetSentry filter applied to 
      incoming IPX packets on this port."
::= { vrPpIpxPNetSentryPProvEntry 1 }

vrPpIpxPNetSentryPOutGoingFilter OBJECT-TYPE
   SYNTAX     AsciiString (SIZE (0..32))
   ACCESS     read-write
   STATUS     mandatory
   DESCRIPTION
     "The name of the filter applied to outgoing IPX packets on this port."
::= { vrPpIpxPNetSentryPProvEntry 2 }


-- Vr/<string> Ipx
-- This component provides for routing of Novell IPX packets in Novell's 
-- NetWare environment.

vrIpx OBJECT IDENTIFIER ::= { vr 7 }



vrIpxRowStatusTable OBJECT-TYPE
   SYNTAX     SEQUENCE OF VrIpxRowStatusEntry
   ACCESS     not-accessible
   STATUS     mandatory
   DESCRIPTION
     "This entry controls the addition and deletion of 
      vrIpx components."
::= { vrIpx 1 }

vrIpxRowStatusEntry OBJECT-TYPE
   SYNTAX     VrIpxRowStatusEntry
   ACCESS     not-accessible
   STATUS     mandatory
   DESCRIPTION
     "A single entry in the table represents a single 
      vrIpx component."
   INDEX {
      vrIndex,
      vrIpxIndex }
::= { vrIpxRowStatusTable 1 }

VrIpxRowStatusEntry ::= SEQUENCE {
   vrIpxRowStatus
      RowStatus,
   vrIpxComponentName
      DisplayString,
   vrIpxStorageType
      StorageType,
   vrIpxIndex
      NonReplicated }

vrIpxRowStatus OBJECT-TYPE
   SYNTAX     RowStatus 
   ACCESS     read-write
   STATUS     mandatory
   DESCRIPTION
     "This variable is used as the basis for SNMP naming of
      vrIpx components.
      These components can be added and deleted."
::= { vrIpxRowStatusEntry 1 }

vrIpxComponentName OBJECT-TYPE
   SYNTAX     DisplayString 
   ACCESS     read-only
   STATUS     mandatory
   DESCRIPTION
     "This variable provides the component's string name for
      use with the ASCII Console Interface"
::= { vrIpxRowStatusEntry 2 }

vrIpxStorageType OBJECT-TYPE
   SYNTAX     StorageType 
   ACCESS     read-only
   STATUS     mandatory
   DESCRIPTION
     "This variable represents the storage type value for the
      vrIpx tables."
::= { vrIpxRowStatusEntry 4 }

vrIpxIndex OBJECT-TYPE
   SYNTAX     NonReplicated 
   ACCESS     not-accessible
   STATUS     mandatory
   DESCRIPTION
     "This variable represents the index for the vrIpx tables."
::= { vrIpxRowStatusEntry 10 }

vrIpxAdminControlTable OBJECT-TYPE
   SYNTAX     SEQUENCE OF VrIpxAdminControlEntry
   ACCESS     not-accessible
   STATUS     mandatory
   DESCRIPTION
     "This group includes the Administrative Control attribute. This 
      attribute defines the current administrative state of this component."
::= { vrIpx 100 }

vrIpxAdminControlEntry OBJECT-TYPE
   SYNTAX     VrIpxAdminControlEntry
   ACCESS     not-accessible
   STATUS     mandatory
   DESCRIPTION
     "An entry in the vrIpxAdminControlTable."
   INDEX {
      vrIndex,
      vrIpxIndex }
::= { vrIpxAdminControlTable 1 }

VrIpxAdminControlEntry ::= SEQUENCE {
   vrIpxSnmpAdminStatus
      INTEGER }

vrIpxSnmpAdminStatus OBJECT-TYPE
   SYNTAX     INTEGER  {
                 up(1),
                 down(2),
                 testing(3) }
   ACCESS     read-write
   STATUS     mandatory
   DESCRIPTION
     "The desired state of the interface. The up state indicates the 
      interface is operational and packet forwarding is allowed. The down 
      state indicates the interface is not operational and packet forwarding 
      is unavailable. The testing state indicates that no operational 
      packets can be passed."
   DEFVAL     { up }
::= { vrIpxAdminControlEntry 1 }

vrIpxProvTable OBJECT-TYPE
   SYNTAX     SEQUENCE OF VrIpxProvEntry
   ACCESS     not-accessible
   STATUS     mandatory
   DESCRIPTION
     "IPX system provisionable attributes."
::= { vrIpx 101 }

vrIpxProvEntry OBJECT-TYPE
   SYNTAX     VrIpxProvEntry
   ACCESS     not-accessible
   STATUS     mandatory
   DESCRIPTION
     "An entry in the vrIpxProvTable."
   INDEX {
      vrIndex,
      vrIpxIndex }
::= { vrIpxProvTable 1 }

VrIpxProvEntry ::= SEQUENCE {
   vrIpxNetworkNumber
      DashedHexString,
   vrIpxMaxPathSplits
      Unsigned32,
   vrIpxMaxHops
      Unsigned32,
   vrIpxRipUpdateInterval
      Unsigned32,
   vrIpxSapUpdateInterval
      Unsigned32,
   vrIpxControlDelay
      Unsigned32,
   vrIpxUpdateDelay
      Unsigned32,
   vrIpxRipAgeMultiplier
      Unsigned32,
   vrIpxSapAgeMultiplier
      Unsigned32,
   vrIpxDamping
      INTEGER,
   vrIpxRipMaxDampedGeneralRequests
      Unsigned32,
   vrIpxRipMaxDampedSpecificRequests
      Unsigned32,
   vrIpxSapMaxDampedGeneralRequests
      Unsigned32,
   vrIpxSapMaxDampedSpecificRequests
      Unsigned32,
   vrIpxInitialGeneralRequests
      INTEGER,
   vrIpxHoldDownInterval
      Unsigned32 }

vrIpxNetworkNumber OBJECT-TYPE
   SYNTAX     DashedHexString (SIZE (1..4))
   ACCESS     read-write
   STATUS     mandatory
   DESCRIPTION
     "This attribute indicates the internal network number portion of the IPX 
      address. This network number must be unique within the internetwork 
      and is necessary to determine master/slave relationships during 
      IPXWAN negotiations."
::= { vrIpxProvEntry 1 }

vrIpxMaxPathSplits OBJECT-TYPE
   SYNTAX     Unsigned32 (1..4)
   ACCESS     read-write
   STATUS     mandatory
   DESCRIPTION
     "This attribute indicates the maximum number of paths with equal 
      routing metric value which this instance of IPX may split between when 
      forwarding packets."
   DEFVAL     { 1 }
::= { vrIpxProvEntry 2 }

vrIpxMaxHops OBJECT-TYPE
   SYNTAX     Unsigned32 (1..64)
   ACCESS     read-write
   STATUS     mandatory
   DESCRIPTION
     "This attribute indicates the maximum number of hops a packet may take."
   DEFVAL     { 16 }
::= { vrIpxProvEntry 3 }

vrIpxRipUpdateInterval OBJECT-TYPE
   SYNTAX     Unsigned32 (1..255)
   ACCESS     read-write
   STATUS     mandatory
   DESCRIPTION
     "The RIP periodic update interval, in seconds."
   DEFVAL     { 60 }
::= { vrIpxProvEntry 4 }

vrIpxSapUpdateInterval OBJECT-TYPE
   SYNTAX     Unsigned32 (1..255)
   ACCESS     read-write
   STATUS     mandatory
   DESCRIPTION
     "The SAP periodic update interval, in seconds."
   DEFVAL     { 60 }
::= { vrIpxProvEntry 5 }

vrIpxControlDelay OBJECT-TYPE
   SYNTAX     Unsigned32 (1..30)
   ACCESS     read-write
   STATUS     mandatory
   DESCRIPTION
     "The delay, in microsecs, between receiving a request from a client and 
      sending a response. This router is significantly faster than some Ipx 
      clients. If a problem is being experienced between a router and an Ipx 
      client, it might be resolved by changing the controlDelay."
   DEFVAL     { 1 }
::= { vrIpxProvEntry 6 }

vrIpxUpdateDelay OBJECT-TYPE
   SYNTAX     Unsigned32 (55..500)
   ACCESS     read-write
   STATUS     mandatory
   DESCRIPTION
     "The delay, in milliseconds, between sending consecutive (RIP and/or 
      SAP) packets. 55 milliseconds is the minimum specified in the Ipx 
      Router Specification."
   DEFVAL     { 55 }
::= { vrIpxProvEntry 7 }

vrIpxRipAgeMultiplier OBJECT-TYPE
   SYNTAX     Unsigned32 (1..10)
   ACCESS     read-write
   STATUS     mandatory
   DESCRIPTION
     "After this many Rip Update intervals unrefreshed Rip information is 
      considered expired."
   DEFVAL     { 3 }
::= { vrIpxProvEntry 8 }

vrIpxSapAgeMultiplier OBJECT-TYPE
   SYNTAX     Unsigned32 (1..10)
   ACCESS     read-write
   STATUS     mandatory
   DESCRIPTION
     "After this many SAP Update intervals unrefreshed SAP information is 
      considered expired."
   DEFVAL     { 3 }
::= { vrIpxProvEntry 9 }

vrIpxDamping OBJECT-TYPE
   SYNTAX     INTEGER  {
                 disabled(0),
                 enabled(1) }
   ACCESS     read-write
   STATUS     mandatory
   DESCRIPTION
     "This attribute specifies whether damping is applied. Damping refers to 
      the damping of incoming RIP and SAP requests.  It handles cases where 
      a rogue client or server is making an extraodinary number of requests. 
      With damping set to disabled, the switch will reply to all requests with 
      no check for rogue nodes.With damping set to enabled, the switch will 
      not reply to a request if the same node made more than the allowable 
      number of requests within 10 seconds. The maximum number of 
      requests to damp at is specified by the following provisionable 
      attributes: ripMaxDampedGeneralRequest, 
      ripMaxDampedSpecificRequests, sapMaxDampedGeneralRequests, 
      sapMaxDampedSpecificRequests."
   DEFVAL     { enabled }
::= { vrIpxProvEntry 10 }

vrIpxRipMaxDampedGeneralRequests OBJECT-TYPE
   SYNTAX     Unsigned32 (1..100)
   ACCESS     read-write
   STATUS     mandatory
   DESCRIPTION
     "This attribute is only used when the attribute damping is enabled. It is 
      used to limit the average rate at which the switch responds to general 
      RIP requests. If more than this number are received within a ten second 
      interval, the first ripMaxDampedGeneralRequests are responded to and 
      the remainder are ignored."
   DEFVAL     { 1 }
::= { vrIpxProvEntry 11 }

vrIpxRipMaxDampedSpecificRequests OBJECT-TYPE
   SYNTAX     Unsigned32 (1..100)
   ACCESS     read-write
   STATUS     mandatory
   DESCRIPTION
     "This attribute is only used when the attribute damping is enabled. It is 
      used to limit the average rate at which the switch responds to specific 
      RIP requests. If more than this number are received within a ten second 
      interval, the first ripMaxDampedSpecificRequests are responded to and 
      the remainder are ignored."
   DEFVAL     { 4 }
::= { vrIpxProvEntry 12 }

vrIpxSapMaxDampedGeneralRequests OBJECT-TYPE
   SYNTAX     Unsigned32 (1..100)
   ACCESS     read-write
   STATUS     mandatory
   DESCRIPTION
     "This attribute is only used when the attribute damping is enabled. It is 
      used to limit the average rate at which the switch responds to general 
      SAP requests. If more than this number are received within a ten second 
      interval, the first sapMaxDampedGeneralRequests are responded to and 
      the remainder are ignored."
   DEFVAL     { 1 }
::= { vrIpxProvEntry 13 }

vrIpxSapMaxDampedSpecificRequests OBJECT-TYPE
   SYNTAX     Unsigned32 (1..100)
   ACCESS     read-write
   STATUS     mandatory
   DESCRIPTION
     "This attribute is only used when the attribute damping is enabled. It is 
      used to limit the average rate at which the switch responds to specific 
      SAP requests. If more than this number are received within a ten second 
      interval, the first sapMaxDampedSpecificRequests are responded to and 
      the remainder are ignored."
   DEFVAL     { 4 }
::= { vrIpxProvEntry 14 }

vrIpxInitialGeneralRequests OBJECT-TYPE
   SYNTAX     INTEGER  {
                 disabled(0),
                 enabled(1) }
   ACCESS     read-write
   STATUS     mandatory
   DESCRIPTION
     "This attribute specifies whether  the RIP and SAP general requests are 
      sent out a port when the port first comes up.  If this attribute is enabled 
      the initial requests will be made; whereas if the attribute is disabled the 
      initial requests will not be made.  This attribute may be disabled in order 
      to avoid the traffic resulting within the network from these initial 
      requests and the ensuing responses.  With the initial request disabled, 
      the switch will learn about other network segments off of the IPX ports 
      via the periodic broadcasts which are received on those port."
   DEFVAL     { enabled }
::= { vrIpxProvEntry 15 }

vrIpxHoldDownInterval OBJECT-TYPE
   SYNTAX     Unsigned32 (0..255)
   ACCESS     read-write
   STATUS     mandatory
   DESCRIPTION
     "This attribute specifies an interval, after a network is removed from the 
      route table, during which other incoming route updates for the same 
      network will be ignored. The use of this interval prevents the slow 
      convergence which results when switches that receive late network down 
      broadcasts advertise false routes."
   DEFVAL     { 10 }
::= { vrIpxProvEntry 16 }

vrIpxStateTable OBJECT-TYPE
   SYNTAX     SEQUENCE OF VrIpxStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { vrIpx 103 }

vrIpxStateEntry OBJECT-TYPE
   SYNTAX     VrIpxStateEntry
   ACCESS     not-accessible
   STATUS     mandatory
   DESCRIPTION
     "An entry in the vrIpxStateTable."
   INDEX {
      vrIndex,
      vrIpxIndex }
::= { vrIpxStateTable 1 }

VrIpxStateEntry ::= SEQUENCE {
   vrIpxAdminState
      INTEGER,
   vrIpxOperationalState
      INTEGER,
   vrIpxUsageState
      INTEGER }

vrIpxAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { vrIpxStateEntry 1 }

vrIpxOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { vrIpxStateEntry 2 }

vrIpxUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { vrIpxStateEntry 3 }

vrIpxOperStatusTable OBJECT-TYPE
   SYNTAX     SEQUENCE OF VrIpxOperStatusEntry
   ACCESS     not-accessible
   STATUS     mandatory
   DESCRIPTION
     "This group includes the Operational Status attribute. This attribute 
      defines the current operational state of this component."
::= { vrIpx 104 }

vrIpxOperStatusEntry OBJECT-TYPE
   SYNTAX     VrIpxOperStatusEntry
   ACCESS     not-accessible
   STATUS     mandatory
   DESCRIPTION
     "An entry in the vrIpxOperStatusTable."
   INDEX {
      vrIndex,
      vrIpxIndex }
::= { vrIpxOperStatusTable 1 }

VrIpxOperStatusEntry ::= SEQUENCE {
   vrIpxSnmpOperStatus
      INTEGER }

vrIpxSnmpOperStatus OBJECT-TYPE
   SYNTAX     INTEGER  {
                 up(1),
                 down(2),
                 testing(3) }
   ACCESS     read-only
   STATUS     mandatory
   DESCRIPTION
     "The current state of the interface. The up state indicates the 
      interface is operational and capable of forwarding packets. The 
      down state indicates the interface is not operational, thus unable to 
      forward packets. testing state indicates that no operational packets 
      can be passed."
   DEFVAL     { up }
::= { vrIpxOperStatusEntry 1 }

vrIpxOperTable OBJECT-TYPE
   SYNTAX     SEQUENCE OF VrIpxOperEntry
   ACCESS     not-accessible
   STATUS     mandatory
   DESCRIPTION
     "This group contains IPX related operational attributes."
::= { vrIpx 105 }

vrIpxOperEntry OBJECT-TYPE
   SYNTAX     VrIpxOperEntry
   ACCESS     not-accessible
   STATUS     mandatory
   DESCRIPTION
     "An entry in the vrIpxOperTable."
   INDEX {
      vrIndex,
      vrIpxIndex }
::= { vrIpxOperTable 1 }

VrIpxOperEntry ::= SEQUENCE {
   vrIpxProtocolPortCount
      Unsigned32,
   vrIpxDestinationCount
      Unsigned32,
   vrIpxServicesCount
      Unsigned32 }

vrIpxProtocolPortCount OBJECT-TYPE
   SYNTAX     Unsigned32 (0..255)
   ACCESS     read-only
   STATUS     mandatory
   DESCRIPTION
     "The number of portsknown to this instance of Ipx."
   DEFVAL     { 0 }
::= { vrIpxOperEntry 1 }

vrIpxDestinationCount OBJECT-TYPE
   SYNTAX     Unsigned32 (0..65535)
   ACCESS     read-only
   STATUS     mandatory
   DESCRIPTION
     "The number of currently reachable destinations known to Ipx."
   DEFVAL     { 65535 }
::= { vrIpxOperEntry 2 }

vrIpxServicesCount OBJECT-TYPE
   SYNTAX     Unsigned32 (0..65535)
   ACCESS     read-only
   STATUS     mandatory
   DESCRIPTION
     "The number of Services known to Ipx."
   DEFVAL     { 65535 }
::= { vrIpxOperEntry 3 }

vrIpxStatsTable OBJECT-TYPE
   SYNTAX     SEQUENCE OF VrIpxStatsEntry
   ACCESS     not-accessible
   STATUS     mandatory
   DESCRIPTION
     "This group contains IPX related statistics on the CP."
::= { vrIpx 107 }

vrIpxStatsEntry OBJECT-TYPE
   SYNTAX     VrIpxStatsEntry
   ACCESS     not-accessible
   STATUS     mandatory
   DESCRIPTION
     "An entry in the vrIpxStatsTable."
   INDEX {
      vrIndex,
      vrIpxIndex }
::= { vrIpxStatsTable 1 }

VrIpxStatsEntry ::= SEQUENCE {
   vrIpxInReceives
      Counter32,
   vrIpxInHeaderErrors
      Counter32,
   vrIpxInUnknownSocket
      Counter32,
   vrIpxInDiscards
      Counter32,
   vrIpxInBadChecksums
      Counter32,
   vrIpxInDelivers
      Counter32,
   vrIpxNoRoutes
      Counter32,
   vrIpxOutRequests
      Counter32,
   vrIpxOutMalformedRequests
      Counter32,
   vrIpxOutDiscards
      Counter32,
   vrIpxOutPackets
      Counter32,
   vrIpxInTooManyHops
      Counter32,
   vrIpxInFiltered
      Counter32,
   vrIpxInNetBIOS
      Counter32,
   vrIpxForwarded
      Counter32,
   vrIpxOutFiltered
      Counter32 }

vrIpxInReceives OBJECT-TYPE
   SYNTAX     Counter32 
   ACCESS     read-only
   STATUS     mandatory
   DESCRIPTION
     "This attribute counts the total number of IPX packets received, including 
      those received in error. This counter wraps around to zero after reaching 
      the maximum value of 4294967295."
::= { vrIpxStatsEntry 1 }

vrIpxInHeaderErrors OBJECT-TYPE
   SYNTAX     Counter32 
   ACCESS     read-only
   STATUS     mandatory
   DESCRIPTION
     "The number of IPX packets discarded due to errors in their headers, 
      including any IPX packet with a size less than the minimum of 30 bytes. 
      This counter wraps around to zero after reaching the maximum value of 
      4294967295."
::= { vrIpxStatsEntry 2 }

vrIpxInUnknownSocket OBJECT-TYPE
   SYNTAX     Counter32 
   ACCESS     read-only
   STATUS     mandatory
   DESCRIPTION
     "The number of IPX packets discarded because the destination socket 
      was not open. This counter wraps around to zero after reaching the 
      maximum value of 4294967295."
::= { vrIpxStatsEntry 3 }

vrIpxInDiscards OBJECT-TYPE
   SYNTAX     Counter32 
   ACCESS     read-only
   STATUS     mandatory
   DESCRIPTION
     "Number of packets received but discarded due to reasons other than 
      those accounted for by inHeaderErrors and inUnknownSocket. This 
      counter wraps around to zero after reaching the maximum value of 
      4294967295."
::= { vrIpxStatsEntry 4 }

vrIpxInBadChecksums OBJECT-TYPE
   SYNTAX     Counter32 
   ACCESS     read-only
   STATUS     mandatory
   DESCRIPTION
     "Number of packets received with incorrect checksums. This counter 
      wraps around to zero after reaching the maximum value of 4294967295."
::= { vrIpxStatsEntry 5 }

vrIpxInDelivers OBJECT-TYPE
   SYNTAX     Counter32 
   ACCESS     read-only
   STATUS     mandatory
   DESCRIPTION
     "Number of IPX packets delivered locally, including packets from local 
      applications. This counter wraps around to zero after reaching the 
      maximum value of 4294967295."
::= { vrIpxStatsEntry 6 }

vrIpxNoRoutes OBJECT-TYPE
   SYNTAX     Counter32 
   ACCESS     read-only
   STATUS     mandatory
   DESCRIPTION
     "Number of times no route to a destination was found. This counter 
      wraps around to zero after reaching the maximum value of 4294967295."
::= { vrIpxStatsEntry 7 }

vrIpxOutRequests OBJECT-TYPE
   SYNTAX     Counter32 
   ACCESS     read-only
   STATUS     mandatory
   DESCRIPTION
     "The number of IPX packets supplied locally for transmission, not 
      including any packets counted in the forwarded attribute. This counter 
      wraps around to zero after reaching the maximum value of 4294967295."
::= { vrIpxStatsEntry 8 }

vrIpxOutMalformedRequests OBJECT-TYPE
   SYNTAX     Counter32 
   ACCESS     read-only
   STATUS     mandatory
   DESCRIPTION
     "Number of outgoing packets supplied locally that contained errors in 
      their structure. This counter wraps around to zero after reaching the 
      maximum value of 4294967295."
::= { vrIpxStatsEntry 9 }

vrIpxOutDiscards OBJECT-TYPE
   SYNTAX     Counter32 
   ACCESS     read-only
   STATUS     mandatory
   DESCRIPTION
     "The number of outgoing IPX packets discarded due to reasons other 
      than those accounted for in outMalformedRequests or outFiltered. This 
      counter wraps around to zero after reaching the maximum value of 
      4294967295."
::= { vrIpxStatsEntry 10 }

vrIpxOutPackets OBJECT-TYPE
   SYNTAX     Counter32 
   ACCESS     read-only
   STATUS     mandatory
   DESCRIPTION
     "The total number of IPX packets transmitted. This counter wraps around 
      to zero after reaching the maximum value of 4294967295."
::= { vrIpxStatsEntry 11 }

vrIpxInTooManyHops OBJECT-TYPE
   SYNTAX     Counter32 
   ACCESS     read-only
   STATUS     mandatory
   DESCRIPTION
     "Number of packets discarded due to exceeding the maxHops value. This 
      counter wraps around to zero after reaching the maximum value of 
      4294967295."
::= { vrIpxStatsEntry 12 }

vrIpxInFiltered OBJECT-TYPE
   SYNTAX     Counter32 
   ACCESS     read-only
   STATUS     mandatory
   DESCRIPTION
     "The number of incoming IPX packets discarded due to filtering. This 
      counter wraps around to zero after reaching the maximum value of 
      4294967295."
::= { vrIpxStatsEntry 13 }

vrIpxInNetBIOS OBJECT-TYPE
   SYNTAX     Counter32 
   ACCESS     read-only
   STATUS     mandatory
   DESCRIPTION
     "The number of NetBIOS packets received. This counter wraps around to 
      zero after reaching the maximum value of 4294967295."
::= { vrIpxStatsEntry 14 }

vrIpxForwarded OBJECT-TYPE
   SYNTAX     Counter32 
   ACCESS     read-only
   STATUS     mandatory
   DESCRIPTION
     "The number of IPX packets forwarded. This counter wraps around to 
      zero after reaching the maximum value of 4294967295."
::= { vrIpxStatsEntry 15 }

vrIpxOutFiltered OBJECT-TYPE
   SYNTAX     Counter32 
   ACCESS     read-only
   STATUS     mandatory
   DESCRIPTION
     "The number of outgoing packets discarded due to filtering. This also 
      includes the number of forwarded packets filtered. This counter wraps 
      around to zero after reaching the maximum value of 4294967295."
::= { vrIpxStatsEntry 16 }


-- Vr/<string> Ipx Rip
-- The Routing Information Protocol (RIP) exchanges IPX route 
-- information that is used to maintain the routing table. Routing 
-- information is added to the route table for all known networks whose 
-- hops count is equal to or less than the value provisioned for maxHops, 
-- and is propagated for networks less than maxHops away.

vrIpxRip OBJECT IDENTIFIER ::= { vrIpx 2 }



vrIpxRipRowStatusTable OBJECT-TYPE
   SYNTAX     SEQUENCE OF VrIpxRipRowStatusEntry
   ACCESS     not-accessible
   STATUS     mandatory
   DESCRIPTION
     "This entry controls the addition and deletion of 
      vrIpxRip components."
::= { vrIpxRip 1 }

vrIpxRipRowStatusEntry OBJECT-TYPE
   SYNTAX     VrIpxRipRowStatusEntry
   ACCESS     not-accessible
   STATUS     mandatory
   DESCRIPTION
     "A single entry in the table represents a single 
      vrIpxRip component."
   INDEX {
      vrIndex,
      vrIpxIndex,
      vrIpxRipIndex }
::= { vrIpxRipRowStatusTable 1 }

VrIpxRipRowStatusEntry ::= SEQUENCE {
   vrIpxRipRowStatus
      RowStatus,
   vrIpxRipComponentName
      DisplayString,
   vrIpxRipStorageType
      StorageType,
   vrIpxRipIndex
      NonReplicated }

vrIpxRipRowStatus OBJECT-TYPE
   SYNTAX     RowStatus 
   ACCESS     read-only
   STATUS     mandatory
   DESCRIPTION
     "This variable is used as the basis for SNMP naming of
      vrIpxRip components.
      These components cannot be added nor deleted."
::= { vrIpxRipRowStatusEntry 1 }

vrIpxRipComponentName OBJECT-TYPE
   SYNTAX     DisplayString 
   ACCESS     read-only
   STATUS     mandatory
   DESCRIPTION
     "This variable provides the component's string name for
      use with the ASCII Console Interface"
::= { vrIpxRipRowStatusEntry 2 }

vrIpxRipStorageType OBJECT-TYPE
   SYNTAX     StorageType 
   ACCESS     read-only
   STATUS     mandatory
   DESCRIPTION
     "This variable represents the storage type value for the
      vrIpxRip tables."
::= { vrIpxRipRowStatusEntry 4 }

vrIpxRipIndex OBJECT-TYPE
   SYNTAX     NonReplicated 
   ACCESS     not-accessible
   STATUS     mandatory
   DESCRIPTION
     "This variable represents the index for the vrIpxRip tables."
::= { vrIpxRipRowStatusEntry 10 }

vrIpxRipStatsTable OBJECT-TYPE
   SYNTAX     SEQUENCE OF VrIpxRipStatsEntry
   ACCESS     not-accessible
   STATUS     mandatory
   DESCRIPTION
     "IPX statistics related to the RIP protocol."
::= { vrIpxRip 10 }

vrIpxRipStatsEntry OBJECT-TYPE
   SYNTAX     VrIpxRipStatsEntry
   ACCESS     not-accessible
   STATUS     mandatory
   DESCRIPTION
     "An entry in the vrIpxRipStatsTable."
   INDEX {
      vrIndex,
      vrIpxIndex,
      vrIpxRipIndex }
::= { vrIpxRipStatsTable 1 }

VrIpxRipStatsEntry ::= SEQUENCE {
   vrIpxRipRipIn
      Counter32,
   vrIpxRipRipOut
      Counter32,
   vrIpxRipRipIncorrectPackets
      Counter32 }

vrIpxRipRipIn OBJECT-TYPE
   SYNTAX     Counter32 
   ACCESS     read-only
   STATUS     mandatory
   DESCRIPTION
     "This attribute counts the total number of IPX RIP packets received. This 
      counter wraps around to zero after reaching the maximum value of 
      4294967295."
::= { vrIpxRipStatsEntry 1 }

vrIpxRipRipOut OBJECT-TYPE
   SYNTAX     Counter32 
   ACCESS     read-only
   STATUS     mandatory
   DESCRIPTION
     "This attribute counts the total number of RIP packets locally generated 
      and sent out. This counter wraps around to zero after reaching the 
      maximum value of 4294967295."
::= { vrIpxRipStatsEntry 2 }

vrIpxRipRipIncorrectPackets OBJECT-TYPE
   SYNTAX     Counter32 
   ACCESS     read-only
   STATUS     mandatory
   DESCRIPTION
     "This attribute counts the number of times an incorrectly formatted RIP 
      packet was received. This counter wraps around to zero after reaching 
      the maximum value of 4294967295."
::= { vrIpxRipStatsEntry 3 }


-- Vr/<string> Ipx Rip RipFilter
-- RIP filters remove the specified service advertisements from RIP packets 
-- passing through this IPX router instance thereby filtering knowledge of 
-- those network routes. This is done by telling the router to ignore certain 
-- advertised networks present in incoming RIP packet tuples and/or omit 
-- certain networks from outgoing RIP packet advertisements. The 
-- networks are indicated by the attributes hops, ticks, networkNumber, 
-- node and port. For a given filter, networks matching all the attributes of 
-- that filter are filtered or passed depending on the disposition of the filter. 
-- RIP filters are applied as input or output filters via the RipApplyEntry 
-- component.

vrIpxRipRFltr OBJECT IDENTIFIER ::= { vrIpxRip 2 }



vrIpxRipRFltrRowStatusTable OBJECT-TYPE
   SYNTAX     SEQUENCE OF VrIpxRipRFltrRowStatusEntry
   ACCESS     not-accessible
   STATUS     mandatory
   DESCRIPTION
     "This entry controls the addition and deletion of 
      vrIpxRipRFltr components."
::= { vrIpxRipRFltr 1 }

vrIpxRipRFltrRowStatusEntry OBJECT-TYPE
   SYNTAX     VrIpxRipRFltrRowStatusEntry
   ACCESS     not-accessible
   STATUS     mandatory
   DESCRIPTION
     "A single entry in the table represents a single 
      vrIpxRipRFltr component."
   INDEX {
      vrIndex,
      vrIpxIndex,
      vrIpxRipIndex,
      vrIpxRipRFltrIdentifierIndex }
::= { vrIpxRipRFltrRowStatusTable 1 }

VrIpxRipRFltrRowStatusEntry ::= SEQUENCE {
   vrIpxRipRFltrRowStatus
      RowStatus,
   vrIpxRipRFltrComponentName
      DisplayString,
   vrIpxRipRFltrStorageType
      StorageType,
   vrIpxRipRFltrIdentifierIndex
      Integer32 }

vrIpxRipRFltrRowStatus OBJECT-TYPE
   SYNTAX     RowStatus 
   ACCESS     read-write
   STATUS     mandatory
   DESCRIPTION
     "This variable is used as the basis for SNMP naming of
      vrIpxRipRFltr components.
      These components can be added and deleted."
::= { vrIpxRipRFltrRowStatusEntry 1 }

vrIpxRipRFltrComponentName OBJECT-TYPE
   SYNTAX     DisplayString 
   ACCESS     read-only
   STATUS     mandatory
   DESCRIPTION
     "This variable provides the component's string name for
      use with the ASCII Console Interface"
::= { vrIpxRipRFltrRowStatusEntry 2 }

vrIpxRipRFltrStorageType OBJECT-TYPE
   SYNTAX     StorageType 
   ACCESS     read-only
   STATUS     mandatory
   DESCRIPTION
     "This variable represents the storage type value for the
      vrIpxRipRFltr tables."
::= { vrIpxRipRFltrRowStatusEntry 4 }

vrIpxRipRFltrIdentifierIndex OBJECT-TYPE
   SYNTAX     Integer32 (1..268435455)
   ACCESS     not-accessible
   STATUS     mandatory
   DESCRIPTION
     "This variable represents the index for the vrIpxRipRFltr tables."
::= { vrIpxRipRFltrRowStatusEntry 10 }

vrIpxRipRFltrProvTable OBJECT-TYPE
   SYNTAX     SEQUENCE OF VrIpxRipRFltrProvEntry
   ACCESS     not-accessible
   STATUS     mandatory
   DESCRIPTION
     "This is the provisionable attribute group for RipFilter."
::= { vrIpxRipRFltr 10 }

vrIpxRipRFltrProvEntry OBJECT-TYPE
   SYNTAX     VrIpxRipRFltrProvEntry
   ACCESS     not-accessible
   STATUS     mandatory
   DESCRIPTION
     "An entry in the vrIpxRipRFltrProvTable."
   INDEX {
      vrIndex,
      vrIpxIndex,
      vrIpxRipIndex,
      vrIpxRipRFltrIdentifierIndex }
::= { vrIpxRipRFltrProvTable 1 }

VrIpxRipRFltrProvEntry ::= SEQUENCE {
   vrIpxRipRFltrHops
      AsciiString,
   vrIpxRipRFltrTicks
      AsciiString,
   vrIpxRipRFltrNetworkNumber
      AsciiString,
   vrIpxRipRFltrNode
      AsciiString,
   vrIpxRipRFltrPort
      AsciiString,
   vrIpxRipRFltrDisposition
      INTEGER }

vrIpxRipRFltrHops OBJECT-TYPE
   SYNTAX     AsciiString (SIZE (0..4))
   ACCESS     read-write
   STATUS     mandatory
   DESCRIPTION
     "This attribute specifies the distance in terms of number of hops. 
      Networks in RIP packets which are the specified distance away from the 
      switch are filtered or passed depending on the disposition of the filter. A 
      hops value preceded by an equality operator(=), less than operator(<) or 
      greater than operator(>) should be interpreted as matching all RIP 
      packet tuples which are an equal, smaller or greater distance, 
      respectively, away from the switch than the hops value specified. For a 
      given filter, only networks matching all the specified attributes of that 
      filter are filtered or passed depending on the disposition of the filter. The 
      number of hops is specified as a decimal number between 0 and 999."
::= { vrIpxRipRFltrProvEntry 1 }

vrIpxRipRFltrTicks OBJECT-TYPE
   SYNTAX     AsciiString (SIZE (0..4))
   ACCESS     read-write
   STATUS     mandatory
   DESCRIPTION
     "This attribute specifies the distance in terms of delay in ticks. A tick is 1/
      18 of a second. Networks in RIP packets which are the specified 
      distance away from the switch are filtered or passed depending on the 
      disposition of the filter. A ticks value preceded by a equality operator(=), 
      less than operator(<) or greater than operator(>) should be interpreted as 
      matching all RIP packet tuples which are an equal, greater or lower 
      delay, respectively, away from the switch than the ticks value specified. 
      For a given filter, only networks matching all the specified attributes of 
      that filter are filtered or passed depending on the disposition of the filter. 
      The ticks value is specified as a decimal number between 0 and 999."
::= { vrIpxRipRFltrProvEntry 2 }

vrIpxRipRFltrNetworkNumber OBJECT-TYPE
   SYNTAX     AsciiString (SIZE (0..12))
   ACCESS     read-write
   STATUS     mandatory
   DESCRIPTION
     "This attribute specifies the network number of matching networks in RIP 
      packets to be filtered or passed depending on the disposition of the filter. 
      The network number can be entered either as a dashed hex string or a 
      string of hex digits entered in pairs of hex digits up to a maximum 
      length of 8 digits; in addition to hex digits, use of the character '?' to 
      indicate wildcarding is allowed. (For example a valid network number 
      would be ff-ff-ff-?? or ffffff??). Wildcard characters may be used only in 
      pairs to replace a pair of hex digits. Filters with a network number 
      preceded by a caret (^) should be interpreted as matching all RIP packet 
      tuples except for the tuples with this network number. For a given filter, 
      only networks matching all the specified attributes of that filter are 
      filtered or passed depending on the disposition of the filter."
::= { vrIpxRipRFltrProvEntry 3 }

vrIpxRipRFltrNode OBJECT-TYPE
   SYNTAX     AsciiString (SIZE (0..18))
   ACCESS     read-write
   STATUS     mandatory
   DESCRIPTION
     "This attribute specifies the node portion in the source IPX address (that 
      is, the MAC address or circuit ID) of received RIP packets for which the 
      contained network tuples should be filtered or passed depending on the 
      disposition of the filter. This attribute is only valid for filters applied to a 
      port in the input direction and will be ignored if the filter is applied in 
      the output direction.The node number can be entered either as a dashed 
      hex string or a string of hex digits entered in pairs of hex digits up to a 
      maximum length of 12 digits; in addition to hex digits, use of the 
      character '?' to indicate wildcarding is allowed. (For example a valid 
      node number would be 00-20-??-??-??-?? or 0020???????? ). Wildcard 
      characters may be used only in pairs to replace a pair of hex digits. A 
      node number preceded by a caret (^) should be interpreted as matching 
      all RIP packets' network tuples except for the RIP packets with this 
      source node address. For a given filter, only networks matching all the 
      specified attributes of that filter are filtered or passed depending on the 
      disposition of the filter."
::= { vrIpxRipRFltrProvEntry 4 }

vrIpxRipRFltrPort OBJECT-TYPE
   SYNTAX     AsciiString (SIZE (0..18))
   ACCESS     read-write
   STATUS     mandatory
   DESCRIPTION
     "This attribute specifies the name of a protocol port whereby networks 
      learned over this port are to be filtered or passed depending on the 
      disposition of the filter. This attribute is only valid for filters applied to a 
      port in the output direction and will be ignored if the filter is applied in 
      the input direction. This attribute is entered as an ascii string and must 
      correspond to a name of a provisioned protocol port. A port name 
      preceded by a caret (^) should be interpreted as matching all RIP packet 
      tuples except for those learned on this port. For a given filter, only 
      networks matching all the specified attributes of that filter are filtered or 
      passed depending on the disposition of the filter."
::= { vrIpxRipRFltrProvEntry 5 }

vrIpxRipRFltrDisposition OBJECT-TYPE
   SYNTAX     INTEGER  {
                 pass(1),
                 filter(2) }
   ACCESS     read-write
   STATUS     mandatory
   DESCRIPTION
     "This attribute indicates a reversal of the filter pattern match. If the value 
      is pass, then matching filters will cause the RIP packet tuple to be 
      passed. If the value is filter, then matching filters will cause the RIP 
      packet tuple to be filtered."
   DEFVAL     { filter }
::= { vrIpxRipRFltrProvEntry 6 }

vrIpxRipRFltrOperTable OBJECT-TYPE
   SYNTAX     SEQUENCE OF VrIpxRipRFltrOperEntry
   ACCESS     not-accessible
   STATUS     mandatory
   DESCRIPTION
     "This is the operational attribute group for IpxRipFilter."
::= { vrIpxRipRFltr 11 }

vrIpxRipRFltrOperEntry OBJECT-TYPE
   SYNTAX     VrIpxRipRFltrOperEntry
   ACCESS     not-accessible
   STATUS     mandatory
   DESCRIPTION
     "An entry in the vrIpxRipRFltrOperTable."
   INDEX {
      vrIndex,
      vrIpxIndex,
      vrIpxRipIndex,
      vrIpxRipRFltrIdentifierIndex }
::= { vrIpxRipRFltrOperTable 1 }

VrIpxRipRFltrOperEntry ::= SEQUENCE {
   vrIpxRipRFltrNumberOfApplyEntries
      Gauge32 }

vrIpxRipRFltrNumberOfApplyEntries OBJECT-TYPE
   SYNTAX     Gauge32 (0..4294967295)
   ACCESS     read-only
   STATUS     mandatory
   DESCRIPTION
     "This attribute indicates the number of times this filter is referenced by a 
      RipApplyEntry. If zero, this filter is not applied on any ports."
   DEFVAL     { 0 }
::= { vrIpxRipRFltrOperEntry 1 }


-- Vr/<string> Ipx Rip RipFilter RipApplyEntry/<protocol port name, 
-- filter ID>
-- This component contains a list of RIP filters that have been applied to 
-- each IPX port and information pertaining to each application of such 
-- RIP filters. Filters should be applied to ports such that the most specific 
-- filter has the lowest identifier while the least specific filter has the 
-- highest identifier. It should be kept in mind that the filter with the lowest 
-- filter identifier that matches will decide based on its disposition whether 
-- the network tuple is passed or filtered.

vrIpxRipRipApp OBJECT IDENTIFIER ::= { vrIpxRip 3 }



vrIpxRipRipAppRowStatusTable OBJECT-TYPE
   SYNTAX     SEQUENCE OF VrIpxRipRipAppRowStatusEntry
   ACCESS     not-accessible
   STATUS     mandatory
   DESCRIPTION
     "This entry controls the addition and deletion of 
      vrIpxRipRipApp components."
::= { vrIpxRipRipApp 1 }

vrIpxRipRipAppRowStatusEntry OBJECT-TYPE
   SYNTAX     VrIpxRipRipAppRowStatusEntry
   ACCESS     not-accessible
   STATUS     mandatory
   DESCRIPTION
     "A single entry in the table represents a single 
      vrIpxRipRipApp component."
   INDEX {
      vrIndex,
      vrIpxIndex,
      vrIpxRipIndex,
      vrIpxRipRipAppProtocolPortNameIndex,
      vrIpxRipRipAppFilterIdentifierIndex }
::= { vrIpxRipRipAppRowStatusTable 1 }

VrIpxRipRipAppRowStatusEntry ::= SEQUENCE {
   vrIpxRipRipAppRowStatus
      RowStatus,
   vrIpxRipRipAppComponentName
      DisplayString,
   vrIpxRipRipAppStorageType
      StorageType,
   vrIpxRipRipAppProtocolPortNameIndex
      AsciiStringIndex,
   vrIpxRipRipAppFilterIdentifierIndex
      Integer32 }

vrIpxRipRipAppRowStatus OBJECT-TYPE
   SYNTAX     RowStatus 
   ACCESS     read-write
   STATUS     mandatory
   DESCRIPTION
     "This variable is used as the basis for SNMP naming of
      vrIpxRipRipApp components.
      These components can be added and deleted."
::= { vrIpxRipRipAppRowStatusEntry 1 }

vrIpxRipRipAppComponentName OBJECT-TYPE
   SYNTAX     DisplayString 
   ACCESS     read-only
   STATUS     mandatory
   DESCRIPTION
     "This variable provides the component's string name for
      use with the ASCII Console Interface"
::= { vrIpxRipRipAppRowStatusEntry 2 }

vrIpxRipRipAppStorageType OBJECT-TYPE
   SYNTAX     StorageType 
   ACCESS     read-only
   STATUS     mandatory
   DESCRIPTION
     "This variable represents the storage type value for the
      vrIpxRipRipApp tables."
::= { vrIpxRipRipAppRowStatusEntry 4 }

vrIpxRipRipAppProtocolPortNameIndex OBJECT-TYPE
   SYNTAX     AsciiStringIndex (SIZE (1..20))
   ACCESS     not-accessible
   STATUS     mandatory
   DESCRIPTION
     "This variable represents an index for the vrIpxRipRipApp tables."
::= { vrIpxRipRipAppRowStatusEntry 10 }

vrIpxRipRipAppFilterIdentifierIndex OBJECT-TYPE
   SYNTAX     Integer32 (1..268435455)
   ACCESS     not-accessible
   STATUS     mandatory
   DESCRIPTION
     "This variable represents an index for the vrIpxRipRipApp tables."
::= { vrIpxRipRipAppRowStatusEntry 11 }

vrIpxRipRipAppProvTable OBJECT-TYPE
   SYNTAX     SEQUENCE OF VrIpxRipRipAppProvEntry
   ACCESS     not-accessible
   STATUS     mandatory
   DESCRIPTION
     "This is the RipApplyEntry provisionable group of attributes."
::= { vrIpxRipRipApp 10 }

vrIpxRipRipAppProvEntry OBJECT-TYPE
   SYNTAX     VrIpxRipRipAppProvEntry
   ACCESS     not-accessible
   STATUS     mandatory
   DESCRIPTION
     "An entry in the vrIpxRipRipAppProvTable."
   INDEX {
      vrIndex,
      vrIpxIndex,
      vrIpxRipIndex,
      vrIpxRipRipAppProtocolPortNameIndex,
      vrIpxRipRipAppFilterIdentifierIndex }
::= { vrIpxRipRipAppProvTable 1 }

VrIpxRipRipAppProvEntry ::= SEQUENCE {
   vrIpxRipRipAppDirection
      INTEGER }

vrIpxRipRipAppDirection OBJECT-TYPE
   SYNTAX     INTEGER  {
                 none(0),
                 output(1),
                 input(2) }
   ACCESS     read-write
   STATUS     mandatory
   DESCRIPTION
     "This attribute specifies whether this RIP filter is applied as an input filter 
      or an output filter. If set to none, this indicates that the filter, though 
      applied to the port, is not currently active in either direction."
   DEFVAL     { none }
::= { vrIpxRipRipAppProvEntry 1 }


-- Vr/<string> Ipx Sap
-- The Service Advertising Protocol (SAP) exchanges information on the 
-- network about available network services (for example file services or 
-- print services). Service information is kept for services residing on 
-- networks which are known to the router via the routing table (RIP 
-- protocol). That is, services will be added to the services table only if a 
-- route to them has been previously discovered via RIP and entered in the 
-- route table.

vrIpxSap OBJECT IDENTIFIER ::= { vrIpx 3 }



vrIpxSapRowStatusTable OBJECT-TYPE
   SYNTAX     SEQUENCE OF VrIpxSapRowStatusEntry
   ACCESS     not-accessible
   STATUS     mandatory
   DESCRIPTION
     "This entry controls the addition and deletion of 
      vrIpxSap components."
::= { vrIpxSap 1 }

vrIpxSapRowStatusEntry OBJECT-TYPE
   SYNTAX     VrIpxSapRowStatusEntry
   ACCESS     not-accessible
   STATUS     mandatory
   DESCRIPTION
     "A single entry in the table represents a single 
      vrIpxSap component."
   INDEX {
      vrIndex,
      vrIpxIndex,
      vrIpxSapIndex }
::= { vrIpxSapRowStatusTable 1 }

VrIpxSapRowStatusEntry ::= SEQUENCE {
   vrIpxSapRowStatus
      RowStatus,
   vrIpxSapComponentName
      DisplayString,
   vrIpxSapStorageType
      StorageType,
   vrIpxSapIndex
      NonReplicated }

vrIpxSapRowStatus OBJECT-TYPE
   SYNTAX     RowStatus 
   ACCESS     read-only
   STATUS     mandatory
   DESCRIPTION
     "This variable is used as the basis for SNMP naming of
      vrIpxSap components.
      These components cannot be added nor deleted."
::= { vrIpxSapRowStatusEntry 1 }

vrIpxSapComponentName OBJECT-TYPE
   SYNTAX     DisplayString 
   ACCESS     read-only
   STATUS     mandatory
   DESCRIPTION
     "This variable provides the component's string name for
      use with the ASCII Console Interface"
::= { vrIpxSapRowStatusEntry 2 }

vrIpxSapStorageType OBJECT-TYPE
   SYNTAX     StorageType 
   ACCESS     read-only
   STATUS     mandatory
   DESCRIPTION
     "This variable represents the storage type value for the
      vrIpxSap tables."
::= { vrIpxSapRowStatusEntry 4 }

vrIpxSapIndex OBJECT-TYPE
   SYNTAX     NonReplicated 
   ACCESS     not-accessible
   STATUS     mandatory
   DESCRIPTION
     "This variable represents the index for the vrIpxSap tables."
::= { vrIpxSapRowStatusEntry 10 }

vrIpxSapStatsTable OBJECT-TYPE
   SYNTAX     SEQUENCE OF VrIpxSapStatsEntry
   ACCESS     not-accessible
   STATUS     mandatory
   DESCRIPTION
     "IPX statistics specific to the SAP protocol."
::= { vrIpxSap 10 }

vrIpxSapStatsEntry OBJECT-TYPE
   SYNTAX     VrIpxSapStatsEntry
   ACCESS     not-accessible
   STATUS     mandatory
   DESCRIPTION
     "An entry in the vrIpxSapStatsTable."
   INDEX {
      vrIndex,
      vrIpxIndex,
      vrIpxSapIndex }
::= { vrIpxSapStatsTable 1 }

VrIpxSapStatsEntry ::= SEQUENCE {
   vrIpxSapSapIn
      Counter32,
   vrIpxSapSapOut
      Counter32,
   vrIpxSapSapIncorrectPackets
      Counter32 }

vrIpxSapSapIn OBJECT-TYPE
   SYNTAX     Counter32 
   ACCESS     read-only
   STATUS     mandatory
   DESCRIPTION
     "The total number of SAP packets received. This counter wraps around to 
      zero after reaching the maximum value of 4294967295."
::= { vrIpxSapStatsEntry 1 }

vrIpxSapSapOut OBJECT-TYPE
   SYNTAX     Counter32 
   ACCESS     read-only
   STATUS     mandatory
   DESCRIPTION
     "The total number of SAP packets locally generated and sent out. This 
      counter wraps around to zero after reaching the maximum value of 
      4294967295."
::= { vrIpxSapStatsEntry 2 }

vrIpxSapSapIncorrectPackets OBJECT-TYPE
   SYNTAX     Counter32 
   ACCESS     read-only
   STATUS     mandatory
   DESCRIPTION
     "The number of times an incorrectly formatted SAP packet was received. 
      This counter wraps around to zero after reaching the maximum value of 
      4294967295."
::= { vrIpxSapStatsEntry 3 }


-- Vr/<string> Ipx Sap Sfltr
-- SAP filters remove the specified service advertisements from SAP 
-- packets passing through this IPX router instance thereby filtering 
-- knowledge of those services. This is done by telling the router to ignore 
-- certain advertised services present in incoming SAP packet tuples and/or 
-- omit certain services from outgoing SAP packet advertisements. The 
-- services are indicated by the attributes type, name, networkNumber, and 
-- node. For a given filter, services matching all the attributes of that filter 
-- are filtered. SAP filters are applied as input or output filters via the 
-- IpxSapApplyEntry component.

vrIpxSapSFltr OBJECT IDENTIFIER ::= { vrIpxSap 2 }



vrIpxSapSFltrRowStatusTable OBJECT-TYPE
   SYNTAX     SEQUENCE OF VrIpxSapSFltrRowStatusEntry
   ACCESS     not-accessible
   STATUS     mandatory
   DESCRIPTION
     "This entry controls the addition and deletion of 
      vrIpxSapSFltr components."
::= { vrIpxSapSFltr 1 }

vrIpxSapSFltrRowStatusEntry OBJECT-TYPE
   SYNTAX     VrIpxSapSFltrRowStatusEntry
   ACCESS     not-accessible
   STATUS     mandatory
   DESCRIPTION
     "A single entry in the table represents a single 
      vrIpxSapSFltr component."
   INDEX {
      vrIndex,
      vrIpxIndex,
      vrIpxSapIndex,
      vrIpxSapSFltrIdentifierIndex }
::= { vrIpxSapSFltrRowStatusTable 1 }

VrIpxSapSFltrRowStatusEntry ::= SEQUENCE {
   vrIpxSapSFltrRowStatus
      RowStatus,
   vrIpxSapSFltrComponentName
      DisplayString,
   vrIpxSapSFltrStorageType
      StorageType,
   vrIpxSapSFltrIdentifierIndex
      Integer32 }

vrIpxSapSFltrRowStatus OBJECT-TYPE
   SYNTAX     RowStatus 
   ACCESS     read-write
   STATUS     mandatory
   DESCRIPTION
     "This variable is used as the basis for SNMP naming of
      vrIpxSapSFltr components.
      These components can be added and deleted."
::= { vrIpxSapSFltrRowStatusEntry 1 }

vrIpxSapSFltrComponentName OBJECT-TYPE
   SYNTAX     DisplayString 
   ACCESS     read-only
   STATUS     mandatory
   DESCRIPTION
     "This variable provides the component's string name for
      use with the ASCII Console Interface"
::= { vrIpxSapSFltrRowStatusEntry 2 }

vrIpxSapSFltrStorageType OBJECT-TYPE
   SYNTAX     StorageType 
   ACCESS     read-only
   STATUS     mandatory
   DESCRIPTION
     "This variable represents the storage type value for the
      vrIpxSapSFltr tables."
::= { vrIpxSapSFltrRowStatusEntry 4 }

vrIpxSapSFltrIdentifierIndex OBJECT-TYPE
   SYNTAX     Integer32 (1..268435455)
   ACCESS     not-accessible
   STATUS     mandatory
   DESCRIPTION
     "This variable represents the index for the vrIpxSapSFltr tables."
::= { vrIpxSapSFltrRowStatusEntry 10 }

vrIpxSapSFltrProvTable OBJECT-TYPE
   SYNTAX     SEQUENCE OF VrIpxSapSFltrProvEntry
   ACCESS     not-accessible
   STATUS     mandatory
   DESCRIPTION
     "The provisionable attribute group for SapFilter."
::= { vrIpxSapSFltr 10 }

vrIpxSapSFltrProvEntry OBJECT-TYPE
   SYNTAX     VrIpxSapSFltrProvEntry
   ACCESS     not-accessible
   STATUS     mandatory
   DESCRIPTION
     "An entry in the vrIpxSapSFltrProvTable."
   INDEX {
      vrIndex,
      vrIpxIndex,
      vrIpxSapIndex,
      vrIpxSapSFltrIdentifierIndex }
::= { vrIpxSapSFltrProvTable 1 }

VrIpxSapSFltrProvEntry ::= SEQUENCE {
   vrIpxSapSFltrType
      AsciiString,
   vrIpxSapSFltrName
      AsciiString,
   vrIpxSapSFltrNetworkNumber
      AsciiString,
   vrIpxSapSFltrNode
      AsciiString,
   vrIpxSapSFltrDisposition
      INTEGER }

vrIpxSapSFltrType OBJECT-TYPE
   SYNTAX     AsciiString (SIZE (0..6))
   ACCESS     read-write
   STATUS     mandatory
   DESCRIPTION
     "This attribute specifies the Novell Service type of the services to be 
      filtered from the SAP packets. The type can be entered either as a 
      dashed hex string or a string of hex digits entered in pairs of hex digits 
      up to a maximum length of 4 digits. (For example a valid type would be 
      ff-ff or ffff). A type preceded by a caret(^) should be interpreted as 
      filtering all SAP packets except for those with this type."
::= { vrIpxSapSFltrProvEntry 1 }

vrIpxSapSFltrName OBJECT-TYPE
   SYNTAX     AsciiString (SIZE (0..48))
   ACCESS     read-write
   STATUS     mandatory
   DESCRIPTION
     "This attribute specifies the readable name of the service to be filtered 
      from SAP packets. The name can be 47 characters or less. This does not 
      include the caret (^) character which precedes the name. A name 
      preceded by a caret (^) should be interpreted as filtering all SAP packets 
      except for the ones with this name."
::= { vrIpxSapSFltrProvEntry 2 }

vrIpxSapSFltrNetworkNumber OBJECT-TYPE
   SYNTAX     AsciiString (SIZE (0..12))
   ACCESS     read-write
   STATUS     mandatory
   DESCRIPTION
     "This attribute specifies the network number of the service to be filtered 
      from SAP packets. The network number can be entered either as a 
      dashed hex string or a string of hex digits entered in pairs of hex digits 
      up to a maximum length of 8 digits. (For example a valid network 
      number would be ff-ff-ff-ff or ffffffff). A network number preceded by a 
      caret (^) should be interpreted as filtering all SAP packets except for the 
      ones with this network number."
::= { vrIpxSapSFltrProvEntry 3 }

vrIpxSapSFltrNode OBJECT-TYPE
   SYNTAX     AsciiString (SIZE (0..18))
   ACCESS     read-write
   STATUS     mandatory
   DESCRIPTION
     "This attribute specifies the node portion of the IPX address of the service 
      to be filtered from SAP packets. The node number can be entered either 
      as a dashed hex string or a string of hex digits entered in pairs of hex 
      digits up to a maximum length of 12 digits.. (For example a valid node 
      number would be ff-ff-ff-ff-ff-ff or ffffffffffff). A node number preceded 
      by a caret (^) should be interpreted as filtering all SAP packets except 
      for the ones with this node number."
::= { vrIpxSapSFltrProvEntry 4 }

vrIpxSapSFltrDisposition OBJECT-TYPE
   SYNTAX     INTEGER  {
                 pass(1),
                 filter(2) }
   ACCESS     read-write
   STATUS     mandatory
   DESCRIPTION
     "Indicates a reversal of the filter pattern match."
   DEFVAL     { filter }
::= { vrIpxSapSFltrProvEntry 5 }

vrIpxSapSFltrOperTable OBJECT-TYPE
   SYNTAX     SEQUENCE OF VrIpxSapSFltrOperEntry
   ACCESS     not-accessible
   STATUS     mandatory
   DESCRIPTION
     "The operational attribute group for IpxSapFilter."
::= { vrIpxSapSFltr 11 }

vrIpxSapSFltrOperEntry OBJECT-TYPE
   SYNTAX     VrIpxSapSFltrOperEntry
   ACCESS     not-accessible
   STATUS     mandatory
   DESCRIPTION
     "An entry in the vrIpxSapSFltrOperTable."
   INDEX {
      vrIndex,
      vrIpxIndex,
      vrIpxSapIndex,
      vrIpxSapSFltrIdentifierIndex }
::= { vrIpxSapSFltrOperTable 1 }

VrIpxSapSFltrOperEntry ::= SEQUENCE {
   vrIpxSapSFltrNumberOfApplyEntries
      Gauge32 }

vrIpxSapSFltrNumberOfApplyEntries OBJECT-TYPE
   SYNTAX     Gauge32 (0..4294967295)
   ACCESS     read-only
   STATUS     mandatory
   DESCRIPTION
     "The number of times this filter appears in IpxSapApplyEntry. If zero, this 
      filter is not applied on any ports."
   DEFVAL     { 0 }
::= { vrIpxSapSFltrOperEntry 1 }


-- Vr/<string> Ipx Sap SapApp
-- This component contains a list of SAP filters that have been applied to 
-- each IPX port and information pertaining to each application of such 
-- SAP filters.

vrIpxSapSapApp OBJECT IDENTIFIER ::= { vrIpxSap 3 }



vrIpxSapSapAppRowStatusTable OBJECT-TYPE
   SYNTAX     SEQUENCE OF VrIpxSapSapAppRowStatusEntry
   ACCESS     not-accessible
   STATUS     mandatory
   DESCRIPTION
     "This entry controls the addition and deletion of 
      vrIpxSapSapApp components."
::= { vrIpxSapSapApp 1 }

vrIpxSapSapAppRowStatusEntry OBJECT-TYPE
   SYNTAX     VrIpxSapSapAppRowStatusEntry
   ACCESS     not-accessible
   STATUS     mandatory
   DESCRIPTION
     "A single entry in the table represents a single 
      vrIpxSapSapApp component."
   INDEX {
      vrIndex,
      vrIpxIndex,
      vrIpxSapIndex,
      vrIpxSapSapAppProtocolPortNameIndex,
      vrIpxSapSapAppFilterIdentifierIndex }
::= { vrIpxSapSapAppRowStatusTable 1 }

VrIpxSapSapAppRowStatusEntry ::= SEQUENCE {
   vrIpxSapSapAppRowStatus
      RowStatus,
   vrIpxSapSapAppComponentName
      DisplayString,
   vrIpxSapSapAppStorageType
      StorageType,
   vrIpxSapSapAppProtocolPortNameIndex
      AsciiStringIndex,
   vrIpxSapSapAppFilterIdentifierIndex
      Integer32 }

vrIpxSapSapAppRowStatus OBJECT-TYPE
   SYNTAX     RowStatus 
   ACCESS     read-write
   STATUS     mandatory
   DESCRIPTION
     "This variable is used as the basis for SNMP naming of
      vrIpxSapSapApp components.
      These components can be added and deleted."
::= { vrIpxSapSapAppRowStatusEntry 1 }

vrIpxSapSapAppComponentName OBJECT-TYPE
   SYNTAX     DisplayString 
   ACCESS     read-only
   STATUS     mandatory
   DESCRIPTION
     "This variable provides the component's string name for
      use with the ASCII Console Interface"
::= { vrIpxSapSapAppRowStatusEntry 2 }

vrIpxSapSapAppStorageType OBJECT-TYPE
   SYNTAX     StorageType 
   ACCESS     read-only
   STATUS     mandatory
   DESCRIPTION
     "This variable represents the storage type value for the
      vrIpxSapSapApp tables."
::= { vrIpxSapSapAppRowStatusEntry 4 }

vrIpxSapSapAppProtocolPortNameIndex OBJECT-TYPE
   SYNTAX     AsciiStringIndex (SIZE (1..20))
   ACCESS     not-accessible
   STATUS     mandatory
   DESCRIPTION
     "This variable represents an index for the vrIpxSapSapApp tables."
::= { vrIpxSapSapAppRowStatusEntry 10 }

vrIpxSapSapAppFilterIdentifierIndex OBJECT-TYPE
   SYNTAX     Integer32 (1..268435455)
   ACCESS     not-accessible
   STATUS     mandatory
   DESCRIPTION
     "This variable represents an index for the vrIpxSapSapApp tables."
::= { vrIpxSapSapAppRowStatusEntry 11 }

vrIpxSapSapAppProvTable OBJECT-TYPE
   SYNTAX     SEQUENCE OF VrIpxSapSapAppProvEntry
   ACCESS     not-accessible
   STATUS     mandatory
   DESCRIPTION
     "The IpxSapApplyEntry provisionable group of attributes."
::= { vrIpxSapSapApp 10 }

vrIpxSapSapAppProvEntry OBJECT-TYPE
   SYNTAX     VrIpxSapSapAppProvEntry
   ACCESS     not-accessible
   STATUS     mandatory
   DESCRIPTION
     "An entry in the vrIpxSapSapAppProvTable."
   INDEX {
      vrIndex,
      vrIpxIndex,
      vrIpxSapIndex,
      vrIpxSapSapAppProtocolPortNameIndex,
      vrIpxSapSapAppFilterIdentifierIndex }
::= { vrIpxSapSapAppProvTable 1 }

VrIpxSapSapAppProvEntry ::= SEQUENCE {
   vrIpxSapSapAppDirection
      INTEGER }

vrIpxSapSapAppDirection OBJECT-TYPE
   SYNTAX     INTEGER  {
                 none(0),
                 output(1),
                 input(2) }
   ACCESS     read-write
   STATUS     mandatory
   DESCRIPTION
     "Indicates whether this SAP filter is applied as an input filter or an output 
      filter."
   DEFVAL     { none }
::= { vrIpxSapSapAppProvEntry 1 }

-- 
-- *** THIS SUBTREE CURRENTLY NOT IMPLEMENTED ***
-- 

-- Vr/<string> Ipx Fwd
-- The forwarding component represents an entry of the forwarding table. 
-- It contains forwarding information about all known destinations with 
-- each entry in the forwarding table being information pertaining to a 
-- unique IPX destination network number. 

vrIpxFwd OBJECT IDENTIFIER ::= { vrIpx 4 }



vrIpxFwdRowStatusTable OBJECT-TYPE
   SYNTAX     SEQUENCE OF VrIpxFwdRowStatusEntry
   ACCESS     not-accessible
   STATUS     mandatory
   DESCRIPTION
     "*** THIS TABLE CURRENTLY NOT IMPLEMENTED ***

      This entry controls the addition and deletion of 
      vrIpxFwd components."
::= { vrIpxFwd 1 }

vrIpxFwdRowStatusEntry OBJECT-TYPE
   SYNTAX     VrIpxFwdRowStatusEntry
   ACCESS     not-accessible
   STATUS     mandatory
   DESCRIPTION
     "A single entry in the table represents a single 
      vrIpxFwd component."
   INDEX {
      vrIndex,
      vrIpxIndex,
      vrIpxFwdNetworkNumberIndex }
::= { vrIpxFwdRowStatusTable 1 }

VrIpxFwdRowStatusEntry ::= SEQUENCE {
   vrIpxFwdRowStatus
      RowStatus,
   vrIpxFwdComponentName
      DisplayString,
   vrIpxFwdStorageType
      StorageType,
   vrIpxFwdNetworkNumberIndex
      DashedHexString }

vrIpxFwdRowStatus OBJECT-TYPE
   SYNTAX     RowStatus 
   ACCESS     read-only
   STATUS     mandatory
   DESCRIPTION
     "This variable is used as the basis for SNMP naming of
      vrIpxFwd components.
      These components cannot be added nor deleted."
::= { vrIpxFwdRowStatusEntry 1 }

vrIpxFwdComponentName OBJECT-TYPE
   SYNTAX     DisplayString 
   ACCESS     read-only
   STATUS     mandatory
   DESCRIPTION
     "This variable provides the component's string name for
      use with the ASCII Console Interface"
::= { vrIpxFwdRowStatusEntry 2 }

vrIpxFwdStorageType OBJECT-TYPE
   SYNTAX     StorageType 
   ACCESS     read-only
   STATUS     mandatory
   DESCRIPTION
     "This variable represents the storage type value for the
      vrIpxFwd tables."
::= { vrIpxFwdRowStatusEntry 4 }

vrIpxFwdNetworkNumberIndex OBJECT-TYPE
   SYNTAX     DashedHexString (SIZE (1..4))
   ACCESS     not-accessible
   STATUS     mandatory
   DESCRIPTION
     "This variable represents the index for the vrIpxFwd tables."
::= { vrIpxFwdRowStatusEntry 10 }

vrIpxFwdOperTable OBJECT-TYPE
   SYNTAX     SEQUENCE OF VrIpxFwdOperEntry
   ACCESS     not-accessible
   STATUS     mandatory
   DESCRIPTION
     "*** THIS TABLE CURRENTLY NOT IMPLEMENTED ***

      IpxForwarding operational attributes."
::= { vrIpxFwd 10 }

vrIpxFwdOperEntry OBJECT-TYPE
   SYNTAX     VrIpxFwdOperEntry
   ACCESS     not-accessible
   STATUS     mandatory
   DESCRIPTION
     "An entry in the vrIpxFwdOperTable."
   INDEX {
      vrIndex,
      vrIpxIndex,
      vrIpxFwdNetworkNumberIndex }
::= { vrIpxFwdOperTable 1 }

VrIpxFwdOperEntry ::= SEQUENCE {
   vrIpxFwdProtocol
      INTEGER,
   vrIpxFwdTicks
      Unsigned32,
   vrIpxFwdHopCount
      Gauge32,
   vrIpxFwdProtocolPortId
      AsciiString,
   vrIpxFwdNextHopPhysAddress
      PhysAddress,
   vrIpxFwdNextHopNetworkNumber
      DashedHexString }

vrIpxFwdProtocol OBJECT-TYPE
   SYNTAX     INTEGER  {
                 other(1),
                 local(2),
                 rip(3),
                 nlsp(4),
                 static(5) }
   ACCESS     read-only
   STATUS     mandatory
   DESCRIPTION
     "The routing protocol from which knowledge of this destination was 
      obtained."
::= { vrIpxFwdOperEntry 1 }

vrIpxFwdTicks OBJECT-TYPE
   SYNTAX     Unsigned32 (0..4294967295)
   ACCESS     read-only
   STATUS     mandatory
   DESCRIPTION
     "The delay, in ticks, to reach this destination."
::= { vrIpxFwdOperEntry 2 }

vrIpxFwdHopCount OBJECT-TYPE
   SYNTAX     Gauge32 (1..64)
   ACCESS     read-only
   STATUS     mandatory
   DESCRIPTION
     "The number of hops required to reach this destination."
::= { vrIpxFwdOperEntry 3 }

vrIpxFwdProtocolPortId OBJECT-TYPE
   SYNTAX     AsciiString (SIZE (1..20))
   ACCESS     read-only
   STATUS     mandatory
   DESCRIPTION
     "The unique identifier of the ProtocolPort used to reach the next hop."
::= { vrIpxFwdOperEntry 4 }

vrIpxFwdNextHopPhysAddress OBJECT-TYPE
   SYNTAX     PhysAddress (SIZE (1..6))
   ACCESS     read-only
   STATUS     mandatory
   DESCRIPTION
     "The physical address of the next hop"
::= { vrIpxFwdOperEntry 5 }

vrIpxFwdNextHopNetworkNumber OBJECT-TYPE
   SYNTAX     DashedHexString (SIZE (1..4))
   ACCESS     read-only
   STATUS     mandatory
   DESCRIPTION
     "The IPX network number of the next hop."
::= { vrIpxFwdOperEntry 6 }

-- 
-- *** THIS SUBTREE CURRENTLY NOT IMPLEMENTED ***
-- 

-- Vr/<string> Ipx Srvc
-- This is the top level component of the IPX services table, which is a list 
-- of the Novell services known to this IPX router instance.

vrIpxSrvc OBJECT IDENTIFIER ::= { vrIpx 5 }



vrIpxSrvcRowStatusTable OBJECT-TYPE
   SYNTAX     SEQUENCE OF VrIpxSrvcRowStatusEntry
   ACCESS     not-accessible
   STATUS     mandatory
   DESCRIPTION
     "*** THIS TABLE CURRENTLY NOT IMPLEMENTED ***

      This entry controls the addition and deletion of 
      vrIpxSrvc components."
::= { vrIpxSrvc 1 }

vrIpxSrvcRowStatusEntry OBJECT-TYPE
   SYNTAX     VrIpxSrvcRowStatusEntry
   ACCESS     not-accessible
   STATUS     mandatory
   DESCRIPTION
     "A single entry in the table represents a single 
      vrIpxSrvc component."
   INDEX {
      vrIndex,
      vrIpxIndex,
      vrIpxSrvcNetworkNumberIndex,
      vrIpxSrvcNodeIndex,
      vrIpxSrvcTypeIndex,
      vrIpxSrvcNameIndex }
::= { vrIpxSrvcRowStatusTable 1 }

VrIpxSrvcRowStatusEntry ::= SEQUENCE {
   vrIpxSrvcRowStatus
      RowStatus,
   vrIpxSrvcComponentName
      DisplayString,
   vrIpxSrvcStorageType
      StorageType,
   vrIpxSrvcNetworkNumberIndex
      DashedHexString,
   vrIpxSrvcNodeIndex
      DashedHexString,
   vrIpxSrvcTypeIndex
      Integer32,
   vrIpxSrvcNameIndex
      AsciiStringIndex }

vrIpxSrvcRowStatus OBJECT-TYPE
   SYNTAX     RowStatus 
   ACCESS     read-only
   STATUS     mandatory
   DESCRIPTION
     "This variable is used as the basis for SNMP naming of
      vrIpxSrvc components.
      These components cannot be added nor deleted."
::= { vrIpxSrvcRowStatusEntry 1 }

vrIpxSrvcComponentName OBJECT-TYPE
   SYNTAX     DisplayString 
   ACCESS     read-only
   STATUS     mandatory
   DESCRIPTION
     "This variable provides the component's string name for
      use with the ASCII Console Interface"
::= { vrIpxSrvcRowStatusEntry 2 }

vrIpxSrvcStorageType OBJECT-TYPE
   SYNTAX     StorageType 
   ACCESS     read-only
   STATUS     mandatory
   DESCRIPTION
     "This variable represents the storage type value for the
      vrIpxSrvc tables."
::= { vrIpxSrvcRowStatusEntry 4 }

vrIpxSrvcNetworkNumberIndex OBJECT-TYPE
   SYNTAX     DashedHexString (SIZE (1..4))
   ACCESS     not-accessible
   STATUS     mandatory
   DESCRIPTION
     "This variable represents an index for the vrIpxSrvc tables."
::= { vrIpxSrvcRowStatusEntry 10 }

vrIpxSrvcNodeIndex OBJECT-TYPE
   SYNTAX     DashedHexString (SIZE (1..6))
   ACCESS     not-accessible
   STATUS     mandatory
   DESCRIPTION
     "This variable represents an index for the vrIpxSrvc tables."
::= { vrIpxSrvcRowStatusEntry 11 }

vrIpxSrvcTypeIndex OBJECT-TYPE
   SYNTAX     Integer32 (0..65535)
   ACCESS     not-accessible
   STATUS     mandatory
   DESCRIPTION
     "This variable represents an index for the vrIpxSrvc tables."
::= { vrIpxSrvcRowStatusEntry 12 }

vrIpxSrvcNameIndex OBJECT-TYPE
   SYNTAX     AsciiStringIndex (SIZE (1..48))
   ACCESS     not-accessible
   STATUS     mandatory
   DESCRIPTION
     "This variable represents an index for the vrIpxSrvc tables."
::= { vrIpxSrvcRowStatusEntry 13 }

vrIpxSrvcOperTable OBJECT-TYPE
   SYNTAX     SEQUENCE OF VrIpxSrvcOperEntry
   ACCESS     not-accessible
   STATUS     mandatory
   DESCRIPTION
     "*** THIS TABLE CURRENTLY NOT IMPLEMENTED ***

      The Ipx Services Operational group."
::= { vrIpxSrvc 10 }

vrIpxSrvcOperEntry OBJECT-TYPE
   SYNTAX     VrIpxSrvcOperEntry
   ACCESS     not-accessible
   STATUS     mandatory
   DESCRIPTION
     "An entry in the vrIpxSrvcOperTable."
   INDEX {
      vrIndex,
      vrIpxIndex,
      vrIpxSrvcNetworkNumberIndex,
      vrIpxSrvcNodeIndex,
      vrIpxSrvcTypeIndex,
      vrIpxSrvcNameIndex }
::= { vrIpxSrvcOperTable 1 }

VrIpxSrvcOperEntry ::= SEQUENCE {
   vrIpxSrvcSocket
      Hex,
   vrIpxSrvcProtocol
      INTEGER,
   vrIpxSrvcHopCount
      Gauge32 }

vrIpxSrvcSocket OBJECT-TYPE
   SYNTAX     Hex (0..65535)
   ACCESS     read-only
   STATUS     mandatory
   DESCRIPTION
     "Socket at which the service is available"
::= { vrIpxSrvcOperEntry 1 }

vrIpxSrvcProtocol OBJECT-TYPE
   SYNTAX     INTEGER  {
                 other(1),
                 local(2),
                 nlsp(4),
                 static(5),
                 sap(6) }
   ACCESS     read-only
   STATUS     mandatory
   DESCRIPTION
     "The protocol from which knowledge of this service was obtained."
::= { vrIpxSrvcOperEntry 2 }

vrIpxSrvcHopCount OBJECT-TYPE
   SYNTAX     Gauge32 (0..64)
   ACCESS     read-only
   STATUS     mandatory
   DESCRIPTION
     "Number of hops to the service."
::= { vrIpxSrvcOperEntry 3 }

-- 
-- *** THIS SUBTREE CURRENTLY NOT IMPLEMENTED ***
-- 

-- Vr/<string> Ipx Adj
-- This component provides adjacent node information available 
-- on a per ProtocolPort basis. This information is retrieved from, 
-- but formatted and displayed differently than, the information 
-- in the route table. It is useful for network configuration 
-- debugging.

vrIpxAdj OBJECT IDENTIFIER ::= { vrIpx 6 }



vrIpxAdjRowStatusTable OBJECT-TYPE
   SYNTAX     SEQUENCE OF VrIpxAdjRowStatusEntry
   ACCESS     not-accessible
   STATUS     mandatory
   DESCRIPTION
     "*** THIS TABLE CURRENTLY NOT IMPLEMENTED ***

      This entry controls the addition and deletion of 
      vrIpxAdj components."
::= { vrIpxAdj 1 }

vrIpxAdjRowStatusEntry OBJECT-TYPE
   SYNTAX     VrIpxAdjRowStatusEntry
   ACCESS     not-accessible
   STATUS     mandatory
   DESCRIPTION
     "A single entry in the table represents a single 
      vrIpxAdj component."
   INDEX {
      vrIndex,
      vrIpxIndex,
      vrIpxAdjProtocolPortIdentifierIndex,
      vrIpxAdjNetworkNumberIndex }
::= { vrIpxAdjRowStatusTable 1 }

VrIpxAdjRowStatusEntry ::= SEQUENCE {
   vrIpxAdjRowStatus
      RowStatus,
   vrIpxAdjComponentName
      DisplayString,
   vrIpxAdjStorageType
      StorageType,
   vrIpxAdjProtocolPortIdentifierIndex
      AsciiStringIndex,
   vrIpxAdjNetworkNumberIndex
      DashedHexString }

vrIpxAdjRowStatus OBJECT-TYPE
   SYNTAX     RowStatus 
   ACCESS     read-only
   STATUS     mandatory
   DESCRIPTION
     "This variable is used as the basis for SNMP naming of
      vrIpxAdj components.
      These components cannot be added nor deleted."
::= { vrIpxAdjRowStatusEntry 1 }

vrIpxAdjComponentName OBJECT-TYPE
   SYNTAX     DisplayString 
   ACCESS     read-only
   STATUS     mandatory
   DESCRIPTION
     "This variable provides the component's string name for
      use with the ASCII Console Interface"
::= { vrIpxAdjRowStatusEntry 2 }

vrIpxAdjStorageType OBJECT-TYPE
   SYNTAX     StorageType 
   ACCESS     read-only
   STATUS     mandatory
   DESCRIPTION
     "This variable represents the storage type value for the
      vrIpxAdj tables."
::= { vrIpxAdjRowStatusEntry 4 }

vrIpxAdjProtocolPortIdentifierIndex OBJECT-TYPE
   SYNTAX     AsciiStringIndex (SIZE (1..20))
   ACCESS     not-accessible
   STATUS     mandatory
   DESCRIPTION
     "This variable represents an index for the vrIpxAdj tables."
::= { vrIpxAdjRowStatusEntry 10 }

vrIpxAdjNetworkNumberIndex OBJECT-TYPE
   SYNTAX     DashedHexString (SIZE (1..4))
   ACCESS     not-accessible
   STATUS     mandatory
   DESCRIPTION
     "This variable represents an index for the vrIpxAdj tables."
::= { vrIpxAdjRowStatusEntry 11 }

vrIpxAdjOperTable OBJECT-TYPE
   SYNTAX     SEQUENCE OF VrIpxAdjOperEntry
   ACCESS     not-accessible
   STATUS     mandatory
   DESCRIPTION
     "*** THIS TABLE CURRENTLY NOT IMPLEMENTED ***

      The Adjacencies operational group."
::= { vrIpxAdj 10 }

vrIpxAdjOperEntry OBJECT-TYPE
   SYNTAX     VrIpxAdjOperEntry
   ACCESS     not-accessible
   STATUS     mandatory
   DESCRIPTION
     "An entry in the vrIpxAdjOperTable."
   INDEX {
      vrIndex,
      vrIpxIndex,
      vrIpxAdjProtocolPortIdentifierIndex,
      vrIpxAdjNetworkNumberIndex }
::= { vrIpxAdjOperTable 1 }

VrIpxAdjOperEntry ::= SEQUENCE {
   vrIpxAdjPhysAddress
      PhysAddress,
   vrIpxAdjAdjacencyState
      INTEGER }

vrIpxAdjPhysAddress OBJECT-TYPE
   SYNTAX     PhysAddress (SIZE (1..6))
   ACCESS     read-only
   STATUS     mandatory
   DESCRIPTION
     "The physical address of the adjacent router."
::= { vrIpxAdjOperEntry 1 }

vrIpxAdjAdjacencyState OBJECT-TYPE
   SYNTAX     INTEGER  {
                 initializing(1),
                 up(2),
                 failed(3),
                 down(4) }
   ACCESS     read-only
   STATUS     mandatory
   DESCRIPTION
     "The state of the connection to the adjacent router."
::= { vrIpxAdjOperEntry 2 }


-- Vr/<string> Ipx NetSentry
-- NetSentry filters, defined in and compiled by NetSentry can be applied 
-- to IPX packets. IPX packets can be filtered on source and destination 
-- network and node combinations. 

vrIpxNs OBJECT IDENTIFIER ::= { vrIpx 7 }



vrIpxNsRowStatusTable OBJECT-TYPE
   SYNTAX     SEQUENCE OF VrIpxNsRowStatusEntry
   ACCESS     not-accessible
   STATUS     mandatory
   DESCRIPTION
     "This entry controls the addition and deletion of 
      vrIpxNs components."
::= { vrIpxNs 1 }

vrIpxNsRowStatusEntry OBJECT-TYPE
   SYNTAX     VrIpxNsRowStatusEntry
   ACCESS     not-accessible
   STATUS     mandatory
   DESCRIPTION
     "A single entry in the table represents a single 
      vrIpxNs component."
   INDEX {
      vrIndex,
      vrIpxIndex,
      vrIpxNsIndex }
::= { vrIpxNsRowStatusTable 1 }

VrIpxNsRowStatusEntry ::= SEQUENCE {
   vrIpxNsRowStatus
      RowStatus,
   vrIpxNsComponentName
      DisplayString,
   vrIpxNsStorageType
      StorageType,
   vrIpxNsIndex
      NonReplicated }

vrIpxNsRowStatus OBJECT-TYPE
   SYNTAX     RowStatus 
   ACCESS     read-write
   STATUS     mandatory
   DESCRIPTION
     "This variable is used as the basis for SNMP naming of
      vrIpxNs components.
      These components can be added and deleted."
::= { vrIpxNsRowStatusEntry 1 }

vrIpxNsComponentName OBJECT-TYPE
   SYNTAX     DisplayString 
   ACCESS     read-only
   STATUS     mandatory
   DESCRIPTION
     "This variable provides the component's string name for
      use with the ASCII Console Interface"
::= { vrIpxNsRowStatusEntry 2 }

vrIpxNsStorageType OBJECT-TYPE
   SYNTAX     StorageType 
   ACCESS     read-only
   STATUS     mandatory
   DESCRIPTION
     "This variable represents the storage type value for the
      vrIpxNs tables."
::= { vrIpxNsRowStatusEntry 4 }

vrIpxNsIndex OBJECT-TYPE
   SYNTAX     NonReplicated 
   ACCESS     not-accessible
   STATUS     mandatory
   DESCRIPTION
     "This variable represents the index for the vrIpxNs tables."
::= { vrIpxNsRowStatusEntry 10 }

vrIpxNsProvTable OBJECT-TYPE
   SYNTAX     SEQUENCE OF VrIpxNsProvEntry
   ACCESS     not-accessible
   STATUS     mandatory
   DESCRIPTION
     "The provisionable attribute group for the IpxNetSentry component."
::= { vrIpxNs 10 }

vrIpxNsProvEntry OBJECT-TYPE
   SYNTAX     VrIpxNsProvEntry
   ACCESS     not-accessible
   STATUS     mandatory
   DESCRIPTION
     "An entry in the vrIpxNsProvTable."
   INDEX {
      vrIndex,
      vrIpxIndex,
      vrIpxNsIndex }
::= { vrIpxNsProvTable 1 }

VrIpxNsProvEntry ::= SEQUENCE {
   vrIpxNsFirstFilter
      AsciiString,
   vrIpxNsLastFilter
      AsciiString,
   vrIpxNsLocalInFilter
      AsciiString,
   vrIpxNsLocalOutFilter
      AsciiString }

vrIpxNsFirstFilter OBJECT-TYPE
   SYNTAX     AsciiString (SIZE (0..32))
   ACCESS     read-write
   STATUS     mandatory
   DESCRIPTION
     "First NetSentry filter for Ipx. If specified this filter is applied before any 
      other NetSentry filters applicable to the packet."
::= { vrIpxNsProvEntry 1 }

vrIpxNsLastFilter OBJECT-TYPE
   SYNTAX     AsciiString (SIZE (0..32))
   ACCESS     read-write
   STATUS     mandatory
   DESCRIPTION
     "Last filter for Ipx. If specified this filter is applied after all other 
      NetSentry filters applicable to the packet."
::= { vrIpxNsProvEntry 2 }

vrIpxNsLocalInFilter OBJECT-TYPE
   SYNTAX     AsciiString (SIZE (0..32))
   ACCESS     read-write
   STATUS     mandatory
   DESCRIPTION
     "The filter name of the NetSentry filter to be applied at the Local In filter 
      point."
::= { vrIpxNsProvEntry 3 }

vrIpxNsLocalOutFilter OBJECT-TYPE
   SYNTAX     AsciiString (SIZE (0..32))
   ACCESS     read-write
   STATUS     mandatory
   DESCRIPTION
     "The filter name of the NetSentry filter to be applied at the Local Out 
      filter point."
::= { vrIpxNsProvEntry 4 }


-- Vr/<string> Ipx NetSentry NetSentryApplyList
-- This component contains a list of NetSentry filters that have been 
-- applied to IPX packets and information pertaining to each application of 
-- such NetSentry filters.

vrIpxNsNetSentryApp OBJECT IDENTIFIER ::= { vrIpxNs 2 }



vrIpxNsNetSentryAppRowStatusTable OBJECT-TYPE
   SYNTAX     SEQUENCE OF VrIpxNsNetSentryAppRowStatusEntry
   ACCESS     not-accessible
   STATUS     mandatory
   DESCRIPTION
     "This entry controls the addition and deletion of 
      vrIpxNsNetSentryApp components."
::= { vrIpxNsNetSentryApp 1 }

vrIpxNsNetSentryAppRowStatusEntry OBJECT-TYPE
   SYNTAX     VrIpxNsNetSentryAppRowStatusEntry
   ACCESS     not-accessible
   STATUS     mandatory
   DESCRIPTION
     "A single entry in the table represents a single 
      vrIpxNsNetSentryApp component."
   INDEX {
      vrIndex,
      vrIpxIndex,
      vrIpxNsIndex,
      vrIpxNsNetSentryAppEntryIndex }
::= { vrIpxNsNetSentryAppRowStatusTable 1 }

VrIpxNsNetSentryAppRowStatusEntry ::= SEQUENCE {
   vrIpxNsNetSentryAppRowStatus
      RowStatus,
   vrIpxNsNetSentryAppComponentName
      DisplayString,
   vrIpxNsNetSentryAppStorageType
      StorageType,
   vrIpxNsNetSentryAppEntryIndex
      Integer32 }

vrIpxNsNetSentryAppRowStatus OBJECT-TYPE
   SYNTAX     RowStatus 
   ACCESS     read-write
   STATUS     mandatory
   DESCRIPTION
     "This variable is used as the basis for SNMP naming of
      vrIpxNsNetSentryApp components.
      These components can be added and deleted."
::= { vrIpxNsNetSentryAppRowStatusEntry 1 }

vrIpxNsNetSentryAppComponentName OBJECT-TYPE
   SYNTAX     DisplayString 
   ACCESS     read-only
   STATUS     mandatory
   DESCRIPTION
     "This variable provides the component's string name for
      use with the ASCII Console Interface"
::= { vrIpxNsNetSentryAppRowStatusEntry 2 }

vrIpxNsNetSentryAppStorageType OBJECT-TYPE
   SYNTAX     StorageType 
   ACCESS     read-only
   STATUS     mandatory
   DESCRIPTION
     "This variable represents the storage type value for the
      vrIpxNsNetSentryApp tables."
::= { vrIpxNsNetSentryAppRowStatusEntry 4 }

vrIpxNsNetSentryAppEntryIndex OBJECT-TYPE
   SYNTAX     Integer32 (1..268435455)
   ACCESS     not-accessible
   STATUS     mandatory
   DESCRIPTION
     "This variable represents the index for the vrIpxNsNetSentryApp tables."
::= { vrIpxNsNetSentryAppRowStatusEntry 10 }

vrIpxNsNetSentryAppProvTable OBJECT-TYPE
   SYNTAX     SEQUENCE OF VrIpxNsNetSentryAppProvEntry
   ACCESS     not-accessible
   STATUS     mandatory
   DESCRIPTION
     "The Provisionable group for the IpxNetSentryApplyList."
::= { vrIpxNsNetSentryApp 10 }

vrIpxNsNetSentryAppProvEntry OBJECT-TYPE
   SYNTAX     VrIpxNsNetSentryAppProvEntry
   ACCESS     not-accessible
   STATUS     mandatory
   DESCRIPTION
     "An entry in the vrIpxNsNetSentryAppProvTable."
   INDEX {
      vrIndex,
      vrIpxIndex,
      vrIpxNsIndex,
      vrIpxNsNetSentryAppEntryIndex }
::= { vrIpxNsNetSentryAppProvTable 1 }

VrIpxNsNetSentryAppProvEntry ::= SEQUENCE {
   vrIpxNsNetSentryAppFilter
      AsciiString,
   vrIpxNsNetSentryAppNetworkNumber1
      AsciiString,
   vrIpxNsNetSentryAppNode1
      AsciiString,
   vrIpxNsNetSentryAppDirection
      INTEGER,
   vrIpxNsNetSentryAppNetworkNumber2
      AsciiString,
   vrIpxNsNetSentryAppNode2
      AsciiString }

vrIpxNsNetSentryAppFilter OBJECT-TYPE
   SYNTAX     AsciiString (SIZE (0..32))
   ACCESS     read-write
   STATUS     mandatory
   DESCRIPTION
     "The name of the filter to be applied to packets matching the conditions 
      in this entry of the IpxNetSentryApplyList."
::= { vrIpxNsNetSentryAppProvEntry 1 }

vrIpxNsNetSentryAppNetworkNumber1 OBJECT-TYPE
   SYNTAX     AsciiString (SIZE (1..11))
   ACCESS     read-write
   STATUS     mandatory
   DESCRIPTION
     "The first IPX network Number used to compare. This network number 
      can be entered either as a dashed hex string or a string of hex digits. (For 
      example a valid network number would be ff-ff-ff-ff or ffffffff). In 
      addition a value of * will be accepted as a wildcard for all networks."
::= { vrIpxNsNetSentryAppProvEntry 2 }

vrIpxNsNetSentryAppNode1 OBJECT-TYPE
   SYNTAX     AsciiString (SIZE (1..17))
   ACCESS     read-write
   STATUS     mandatory
   DESCRIPTION
     "This attribute is the first IPX node address used to compare. This node 
      number can be entered either as a dashed hex string or a string of hex 
      digits. (For example a valid node number would be ff-ff-ff-ff-ff-ff or 
      ffffffffffff). In addition a value of * will be accepted as a wildcard for all 
      nodes."
::= { vrIpxNsNetSentryAppProvEntry 3 }

vrIpxNsNetSentryAppDirection OBJECT-TYPE
   SYNTAX     INTEGER  {
                 to(1),
                 from(2),
                 tofrom(3) }
   ACCESS     read-write
   STATUS     mandatory
   DESCRIPTION
     "Indicates the direction a packet must be moving between the first and 
      second apply list entries in order for the entries to match. First 'to' 
      second, first 'from' second, or first 'tofrom' second (either direction)."
::= { vrIpxNsNetSentryAppProvEntry 4 }

vrIpxNsNetSentryAppNetworkNumber2 OBJECT-TYPE
   SYNTAX     AsciiString (SIZE (1..11))
   ACCESS     read-write
   STATUS     mandatory
   DESCRIPTION
     "The second IPX network Number used to compare. This network 
      number can be entered either as a dashed hex string or a string of hex 
      digits. (For example a valid network number would be ff-ff-ff-ff or 
      ffffffff). In addition a value of * will be accepted as a wildcard for all 
      networks."
::= { vrIpxNsNetSentryAppProvEntry 5 }

vrIpxNsNetSentryAppNode2 OBJECT-TYPE
   SYNTAX     AsciiString (SIZE (1..17))
   ACCESS     read-write
   STATUS     mandatory
   DESCRIPTION
     "This attribute is the second IPX node address used to compared. This 
      node can be entered either as a dashed hex string or a string of hex 
      digits. (For example a valid network number would be ff-ff-ff-ff-ff-ff or 
      ffffffffffff). In addition a value of * will be accepted as a wildcard for all 
      nodes."
::= { vrIpxNsNetSentryAppProvEntry 6 }




-- 
-- Version and Compliance statements
-- 



-- Object-Group Statement:
-- A list of all current accessible leaf objects.

-- OBJECTS { vrIpxSapSFltrStorageType,
--           vrPpIpxPNode,
--           vrPpIpxPNetSentryPComponentName,
--           vrIpxOutRequests,
--           vrPpIpxPNetSentryPOutGoingFilter,
--           vrPpIpxPRipPInRequests,
--           vrIpxInReceives,
--           vrIpxServicesCount,
--           vrIpxAdjAdjacencyState,
--           vrPpIpxPSapPInRequests,
--           vrIpxHoldDownInterval,
--           vrPpIpxPIWPStorageType,
--           vrIpxSapSFltrRowStatus,
--           vrIpxFwdNextHopNetworkNumber,
--           vrPpIpxPRipPIncorrectPackets,
--           vrPpIpxPComponentName,
--           vrPpIpxPForwarded,
--           vrIpxAdminState,
--           vrIpxSnmpOperStatus,
--           vrIpxNsNetSentryAppComponentName,
--           vrPpIpxPRipPRowStatus,
--           vrIpxRipRipAppDirection,
--           vrIpxRipRFltrNode,
--           vrIpxSrvcSocket,
--           vrIpxNsStorageType,
--           vrIpxSapSapAppDirection,
--           vrIpxNsNetSentryAppFilter,
--           vrPpIpxPSapPOutResponses,
--           vrIpxRipRipOut,
--           vrIpxSapSFltrDisposition,
--           vrIpxStorageType,
--           vrIpxFwdComponentName,
--           vrIpxNoRoutes,
--           vrIpxFwdNextHopPhysAddress,
--           vrIpxRipRFltrComponentName,
--           vrPpIpxPRipPOutPackets,
--           vrIpxRipUpdateInterval,
--           vrIpxInTooManyHops,
--           vrPpIpxPInReceives,
--           vrIpxSapSFltrComponentName,
--           vrIpxNsRowStatus,
--           vrIpxSapStorageType,
--           vrIpxMaxHops,
--           vrIpxRipMaxDampedSpecificRequests,
--           vrIpxRipRowStatus,
--           vrPpIpxPIWPComponentName,
--           vrPpIpxPType,
--           vrIpxSapMaxDampedSpecificRequests,
--           vrPpIpxPNetSentryPStorageType,
--           vrPpIpxPSnmpOperStatus,
--           vrIpxSrvcComponentName,
--           vrIpxRowStatus,
--           vrIpxSnmpAdminStatus,
--           vrIpxSapSapOut,
--           vrIpxInBadChecksums,
--           vrPpIpxPSapPComponentName,
--           vrIpxFwdHopCount,
--           vrPpIpxPSapPOutRequests,
--           vrPpIpxPSapPInResponses,
--           vrIpxSapSFltrNetworkNumber,
--           vrIpxOutFiltered,
--           vrIpxUsageState,
--           vrIpxSapRowStatus,
--           vrIpxNsNetSentryAppStorageType,
--           vrPpIpxPBroadcastInhibit,
--           vrIpxInFiltered,
--           vrIpxNsComponentName,
--           vrIpxDamping,
--           vrIpxOutPackets,
--           vrPpIpxPNetSentryPRowStatus,
--           vrPpIpxPRipPInPackets,
--           vrIpxNsNetSentryAppNetworkNumber2,
--           vrIpxSapSapIncorrectPackets,
--           vrIpxRipRFltrHops,
--           vrIpxInDelivers,
--           vrPpIpxPAdminState,
--           vrIpxRipComponentName,
--           vrIpxSapSapIn,
--           vrIpxFwdProtocol,
--           vrIpxFwdStorageType,
--           vrIpxInHeaderErrors,
--           vrIpxSrvcStorageType,
--           vrPpIpxPRowStatus,
--           vrIpxRipRipIncorrectPackets,
--           vrPpIpxPSnmpAdminStatus,
--           vrIpxOutDiscards,
--           vrPpIpxPNetworkNumberProv,
--           vrIpxRipRipAppComponentName,
--           vrIpxNsNetSentryAppDirection,
--           vrIpxAdjComponentName,
--           vrIpxRipRipIn,
--           vrIpxNsNetSentryAppNetworkNumber1,
--           vrPpIpxPDefaultType,
--           vrPpIpxPSapPStorageType,
--           vrPpIpxPUsageState,
--           vrIpxDestinationCount,
--           vrIpxSrvcProtocol,
--           vrIpxSapSFltrNode,
--           vrIpxRipMaxDampedGeneralRequests,
--           vrIpxNsLocalOutFilter,
--           vrIpxRipRFltrStorageType,
--           vrIpxNetworkNumber,
--           vrPpIpxPSapPIncorrectPackets,
--           vrIpxSapSFltrName,
--           vrIpxSrvcHopCount,
--           vrIpxRipRFltrRowStatus,
--           vrPpIpxPSapPRowStatus,
--           vrPpIpxPRipPOutResponses,
--           vrIpxRipRFltrDisposition,
--           vrPpIpxPOperationalState,
--           vrIpxRipRipAppStorageType,
--           vrIpxAdjStorageType,
--           vrIpxNsNetSentryAppRowStatus,
--           vrIpxMaxPathSplits,
--           vrPpIpxPIWPRowStatus,
--           vrPpIpxPSourceRouteEndStationSupport,
--           vrIpxSapSapAppStorageType,
--           vrIpxSrvcRowStatus,
--           vrPpIpxPRipPComponentName,
--           vrIpxInDiscards,
--           vrIpxNsFirstFilter,
--           vrIpxControlDelay,
--           vrIpxRipRFltrPort,
--           vrIpxAdjRowStatus,
--           vrIpxRipStorageType,
--           vrPpIpxPSapPOutPackets,
--           vrIpxSapUpdateInterval,
--           vrIpxFwdTicks,
--           vrPpIpxPIWPNeighbourRouterName,
--           vrPpIpxPStateChanges,
--           vrIpxNsNetSentryAppNode2,
--           vrIpxAdjPhysAddress,
--           vrIpxSapSFltrNumberOfApplyEntries,
--           vrPpIpxPNetworkNumber,
--           vrIpxFwdRowStatus,
--           vrIpxRipRipAppRowStatus,
--           vrPpIpxPStorageType,
--           vrPpIpxPNetSentryPInComingFilter,
--           vrIpxOutMalformedRequests,
--           vrIpxRipRFltrTicks,
--           vrPpIpxPRipPOutRequests,
--           vrIpxInitialGeneralRequests,
--           vrIpxNsLocalInFilter,
--           vrIpxRipRFltrNumberOfApplyEntries,
--           vrPpIpxPEncapsulation,
--           vrPpIpxPRipPInResponses,
--           vrIpxSapSapAppRowStatus,
--           vrIpxRipAgeMultiplier,
--           vrIpxProtocolPortCount,
--           vrIpxFwdProtocolPortId,
--           vrIpxSapSFltrType,
--           vrIpxSapMaxDampedGeneralRequests,
--           vrIpxComponentName,
--           vrIpxNsLastFilter,
--           vrIpxForwarded,
--           vrPpIpxPIWPInitFails,
--           vrIpxRipRFltrNetworkNumber,
--           vrIpxUpdateDelay,
--           vrIpxNsNetSentryAppNode1,
--           vrIpxOperationalState,
--           vrPpIpxPSapPInPackets,
--           vrIpxInNetBIOS,
--           vrIpxInUnknownSocket,
--           vrIpxSapComponentName,
--           vrIpxSapSapAppComponentName,
--           vrPpIpxPIWPNeighbourInternalNetworkNumber,
--           vrIpxSapAgeMultiplier,
--           vrPpIpxPRipPStorageType }
-- STATUS  mandatory
-- DESCRIPTION
--   "A list of all current accessible leaf objects."

ipxGroup OBJECT IDENTIFIER ::= { ipxMIB 1 }
ipxGroupBE OBJECT IDENTIFIER ::= { ipxGroup 5 }
ipxGroupBE01 OBJECT IDENTIFIER ::= { ipxGroupBE 2 }
ipxGroupBE01A OBJECT IDENTIFIER ::= { ipxGroupBE01 2 }



-- Agent-Capabilities Statement:

-- PRODUCT-RELEASE "Passport Release 7.0 Ipx."
-- STATUS          mandatory
-- DESCRIPTION     "Ipx MIB: MIB Version BE01A,
--                  Software Version BG00S4C."
-- SUPPORTS        Nortel-Magellan-Passport-IpxMIB
--    INCLUDES     { ipxGroupBE01A }

ipxCapabilities OBJECT IDENTIFIER ::= { ipxMIB 3 }
ipxCapabilitiesBE OBJECT IDENTIFIER ::= { ipxCapabilities 5 }
ipxCapabilitiesBE01 OBJECT IDENTIFIER ::= { ipxCapabilitiesBE 2 }
ipxCapabilitiesBE01A OBJECT IDENTIFIER ::= { ipxCapabilitiesBE01 2 }





END
