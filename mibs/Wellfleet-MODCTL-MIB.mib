Wellfleet-MODCTL-MIB DEFINITIONS ::= BEGIN



    IMPORTS

      Gauge
        FROM RFC1155-SMI
      OBJECT-TYPE
        FROM RFC-1212
      wfModCtlGroup
        FROM Wellfleet-COMMON-MIB;

    wfModCtlBase OBJECT IDENTIFIER ::={ wfModCtlGroup 1 }

    wfModCtlPrimarySlot OBJECT-TYPE
        SYNTAX  INTEGER(0..12)
        ACCESS  read-only
        STATUS  mandatory
        DESCRIPTION
                "The slot number of the CPR slot acting as the
                 primary MCD"
        DEFVAL   { 0 }
        ::= { wfModCtlBase 1 }

    wfModCtlState OBJECT-TYPE
        SYNTAX  INTEGER {
                    up(1),
                    down(2),
                    init(3),
                    config(4),
                    notpresent(20)
                }
        ACCESS  read-only
        STATUS  mandatory
        DESCRIPTION
                "The current state of the Module Control Driver"
        DEFVAL  { notpresent }
        ::= { wfModCtlBase 2 }

    wfModCtlActiveMask OBJECT-TYPE
        SYNTAX   Gauge
        ACCESS   read-only
        STATUS   mandatory
        DESCRIPTION
                "Bit mask indicating which slots are operational"
        DEFVAL  { 0 }
        ::= { wfModCtlBase 3 }

    wfModCtlCfgSlotDisableMask OBJECT-TYPE
        SYNTAX   Gauge
        ACCESS   read-write
        STATUS   mandatory
        DESCRIPTION
                "Bit mask indicating which slots are prevented from
                 entering the active state."
        DEFVAL   { 0 }
        ::= { wfModCtlBase 4 }

    wfModCtlCfgHeartbeatPeriod OBJECT-TYPE
        SYNTAX   INTEGER(0..65535)
        ACCESS   read-write
        STATUS   mandatory
        DESCRIPTION
                "The timer period, in seconds, which defines how often
                 heartbeat messages are sent to active Co-processors."
        DEFVAL  { 3 }
        ::= { wfModCtlBase 5 }

    wfModCtlCfgHeartbeatDisableMask OBJECT-TYPE
        SYNTAX   Gauge
        ACCESS   read-write
        STATUS   mandatory
        DESCRIPTION
                 "Bit mask indicating which slots participate in 
                  heartbeat checks from the primary SSP."
        DEFVAL   { 0 }
        ::= { wfModCtlBase 6 }

    wfModCtlCfgBoflFailPeriod OBJECT-TYPE
        SYNTAX   INTEGER(0..65535)
        ACCESS   read-write
        STATUS   mandatory
        DESCRIPTION
                "The timer period, in seconds, which defines how long
                 to wait following a Bofl failure before taking more
                 drastic action to establish a valid DPI path."
        DEFVAL { 30 }
        ::= { wfModCtlBase 7 }

    wfModCtlCfgBoflDisableMask OBJECT-TYPE
        SYNTAX   Gauge
        ACCESS   read-write
        STATUS   mandatory
        DESCRIPTION
                "Bit mask indicating which L3 slots participate in
                 BOFL checks for a valid DPI path from the primary SSP."
        DEFVAL   { 0 }
        ::= { wfModCtlBase 8 }

    wfModCtlCfgRspImageType OBJECT-TYPE
        SYNTAX   INTEGER {
                     normal(1),
                     trace(2)
                 }
        ACCESS   read-write
        STATUS   mandatory
        DESCRIPTION
                "Type of image to be loaded on the RSP by the IFP driver."
        DEFVAL  { normal }
        ::=  { wfModCtlBase 9 }

    wfModCtlDbgMsgLevel OBJECT-TYPE
        SYNTAX   INTEGER {
                     all(2031616),
                     debug(65536),
                     info(131072),
                     warning(262144),
                     fault(524288),
                     trace(1048576)
                }
        ACCESS   read-write
        STATUS   mandatory
        DESCRIPTION
                "MCD log messages level
                 To control certain level of log messages
                              MCD_DBG_MSG_ALL         0x001f0000 - 2031616
                              MCD_DBG_MSG_DEBUG       0x00010000 -   65536
                              MCD_DBG_MSG_INFO        0x00020000 -  131072
                              MCD_DBG_MSG_WARNING     0x00040000 -  262144
                              MCD_DBG_MSG_FAULT       0x00080000 -  524288
                              MCD_DBG_MSG_TRACE       0x00100000 - 1048576"
        DEFVAL  { all }
        ::= { wfModCtlBase 10 }

    wfModCtlScdLogMask  OBJECT-TYPE
        SYNTAX    INTEGER
        ACCESS    read-write
        STATUS    mandatory
        DESCRIPTION
                "The log mask is a bit mask used by the SCD to enable
                 various log levels.
                       SCD_LOG_MASK_NONE           0x00000000
                       SCD_LOG_MASK_INST           0x00000001
                       SCD_LOG_MASK_DCI            0x00000002
                       SCD_LOG_MASK_R4             0x00000004
                       SCD_LOG_MASK_DBG_DISPLAY    0x00000008
                       SCD_LOG_MASK_SCI            0x00000010
                       SCD_LOG_MASK_STATS          0x00000020"
        DEFVAL  { 0 }
        ::= { wfModCtlBase 11 }

    wfModCtlScdDbgMask  OBJECT-TYPE
        SYNTAX    INTEGER (0..65535)
        ACCESS    read-write
        STATUS    mandatory
        DESCRIPTION
                "The debug log mask is used to control the SCD ability
                 to execute and log debug specific functions"
        DEFVAL   { 0 }
        ::= { wfModCtlBase 12 }

    END  -- Wellfleet-MCD-MIB
