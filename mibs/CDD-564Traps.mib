--
-- CDD-564Traps.my
-- MIB generated by MG-SOFT Visual MIB Builder Version 2.1 Build 199
-- Friday, November 19, 2004 at 11:34:35
--

	CDD-564Traps DEFINITIONS ::= BEGIN

		IMPORTS 
			cdd564UnitAlarm, cdd564RxMonitorIndex, cdd564RxAlarm, cdd564LNBMonitorIndex, cdd564LNBAlarm, 
			cdd564			
				FROM CDD-564			
			TRAP-TYPE			
				FROM RFC-1215;
	
	
	
--
-- Trap definitions
--
	
		cdd564UnitAlarmTrap TRAP-TYPE
			ENTERPRISE cdd564
			VARIABLES { cdd564UnitAlarm }
			DESCRIPTION
				"Trap for unit alarms."
			::=  6247251
			
		cdd564RxAlarmTrap TRAP-TYPE
			ENTERPRISE cdd564
			VARIABLES { cdd564RxMonitorIndex, cdd564RxAlarm }
			DESCRIPTION
				"Trap for Rx alarms."
			::=  6247252
			
		cdd564LNBAlarmTrap TRAP-TYPE
			ENTERPRISE cdd564
			VARIABLES { cdd564LNBMonitorIndex, cdd564LNBAlarm }
			DESCRIPTION
				"Trap for LNB alarms."
			::=  6247253
			
	
	END

--
-- CDD-564Traps.my
--
