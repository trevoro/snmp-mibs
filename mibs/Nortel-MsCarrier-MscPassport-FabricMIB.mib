Nortel-MsCarrier-MscPassport-FabricMIB
DEFINITIONS ::= BEGIN



IMPORTS

      OBJECT-TYPE
   FROM RFC-1212

      mscPassportMIBs
   FROM Nortel-MsCarrier-MscPassport-UsefulDefinitionsMIB

      Counter32,
      DisplayString,
      StorageType,
      RowStatus,
      Gauge32,
      Integer32,
      Unsigned32
   FROM Nortel-MsCarrier-MscPassport-StandardTextualConventionsMIB

      AsciiString,
      NonReplicated,
      FixedPoint1
   FROM Nortel-MsCarrier-MscPassport-TextualConventionsMIB

      mscShelfCard,
      mscShelfIndex,
      mscShelf,
      mscShelfCardIndex
   FROM Nortel-MsCarrier-MscPassport-BaseShelfMIB;




-- LAST-UPDATED   "9909010000Z"
-- ORGANIZATION   "Nortel Networks"
-- CONTACT-INFO   "
--         Nortel Carrier Data Network Management
--         
--         Postal:       P.O. Box 3511, Station C 
--                       Ottawa, Ontario 
--                       Canada  K1Y 4H7
--         
--         via the WEB:  http://www.nortelnetworks.com  
--                       select 'Contact Us' from the menu
--          
--         via phone:    1-800-4NORTEL"
-- DESCRIPTION
--    "The module describing the Nortel MsCarrier MscPassport
--     Fabric Enterprise MIB."

fabricMIB OBJECT IDENTIFIER ::= { mscPassportMIBs 145 }










-- Shelf Card/n FabricPort/f
-- This component represents a physical fabric port on a card. A fabric 
-- port is a card's interface to a fabric card; it provides a pathway for 
-- the card to send cells over the fabric card to the other cards in the 
-- module, and to receive cells sent to it over the fabric card by the 
-- other cards in the module.
-- 
-- A card's FabricPort components are created automatically 
-- whenever the card begins acting as an active or standby LP. They 
-- remain in existence as long as the card remains operational. 
-- FabricPort components cannot be added or deleted.

mscShelfCardFabricPort OBJECT IDENTIFIER ::= { mscShelfCard 5 }



mscShelfCardFabricPortRowStatusTable OBJECT-TYPE
   SYNTAX     SEQUENCE OF MscShelfCardFabricPortRowStatusEntry
   ACCESS     not-accessible
   STATUS     mandatory
   DESCRIPTION
     "This entry controls the addition and deletion of 
      mscShelfCardFabricPort components."
::= { mscShelfCardFabricPort 1 }

mscShelfCardFabricPortRowStatusEntry OBJECT-TYPE
   SYNTAX     MscShelfCardFabricPortRowStatusEntry
   ACCESS     not-accessible
   STATUS     mandatory
   DESCRIPTION
     "A single entry in the table represents a single 
      mscShelfCardFabricPort component."
   INDEX {
      mscShelfIndex,
      mscShelfCardIndex,
      mscShelfCardFabricPortIndex }
::= { mscShelfCardFabricPortRowStatusTable 1 }

MscShelfCardFabricPortRowStatusEntry ::= SEQUENCE {
   mscShelfCardFabricPortRowStatus
      RowStatus,
   mscShelfCardFabricPortComponentName
      DisplayString,
   mscShelfCardFabricPortStorageType
      StorageType,
   mscShelfCardFabricPortIndex
      INTEGER }

mscShelfCardFabricPortRowStatus OBJECT-TYPE
   SYNTAX     RowStatus 
   ACCESS     read-only
   STATUS     mandatory
   DESCRIPTION
     "This variable is used as the basis for SNMP naming of
      mscShelfCardFabricPort components.
      These components cannot be added nor deleted."
::= { mscShelfCardFabricPortRowStatusEntry 1 }

mscShelfCardFabricPortComponentName OBJECT-TYPE
   SYNTAX     DisplayString 
   ACCESS     read-only
   STATUS     mandatory
   DESCRIPTION
     "This variable provides the component's string name for
      use with the ASCII Console Interface"
::= { mscShelfCardFabricPortRowStatusEntry 2 }

mscShelfCardFabricPortStorageType OBJECT-TYPE
   SYNTAX     StorageType 
   ACCESS     read-only
   STATUS     mandatory
   DESCRIPTION
     "This variable represents the storage type value for the
      mscShelfCardFabricPort tables."
::= { mscShelfCardFabricPortRowStatusEntry 4 }

mscShelfCardFabricPortIndex OBJECT-TYPE
   SYNTAX     INTEGER  {
                 x(0),
                 y(1) }
   ACCESS     not-accessible
   STATUS     mandatory
   DESCRIPTION
     "This variable represents the index for the mscShelfCardFabricPort tables."
::= { mscShelfCardFabricPortRowStatusEntry 10 }

mscShelfCardFabricPortStateTable OBJECT-TYPE
   SYNTAX     SEQUENCE OF MscShelfCardFabricPortStateEntry
   ACCESS     not-accessible
   STATUS     mandatory
   DESCRIPTION
     "This group contains the three OSI State attributes and the six OSI 
      Status attributes. The descriptions generically indicate what each 
      attribute implies about the component. Note that not all the values 
      and state combinations described here are supported by every 
      component which uses this group. For component-specific 
      information and the valid state combinations, refer to NTP 241-
      7001-150, Passport Operations and Maintenance Guide."
::= { mscShelfCardFabricPort 10 }

mscShelfCardFabricPortStateEntry OBJECT-TYPE
   SYNTAX     MscShelfCardFabricPortStateEntry
   ACCESS     not-accessible
   STATUS     mandatory
   DESCRIPTION
     "An entry in the mscShelfCardFabricPortStateTable."
   INDEX {
      mscShelfIndex,
      mscShelfCardIndex,
      mscShelfCardFabricPortIndex }
::= { mscShelfCardFabricPortStateTable 1 }

MscShelfCardFabricPortStateEntry ::= SEQUENCE {
   mscShelfCardFabricPortAdminState
      INTEGER,
   mscShelfCardFabricPortOperationalState
      INTEGER,
   mscShelfCardFabricPortUsageState
      INTEGER,
   mscShelfCardFabricPortAvailabilityStatus
      OCTET STRING,
   mscShelfCardFabricPortProceduralStatus
      OCTET STRING,
   mscShelfCardFabricPortControlStatus
      OCTET STRING,
   mscShelfCardFabricPortAlarmStatus
      OCTET STRING,
   mscShelfCardFabricPortStandbyStatus
      INTEGER,
   mscShelfCardFabricPortUnknownStatus
      INTEGER }

mscShelfCardFabricPortAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component.
      
      The OSI Status attributes, if supported by the component, may 
      provide more details, qualifying the state of the component."
   DEFVAL     { unlocked }
::= { mscShelfCardFabricPortStateEntry 1 }

mscShelfCardFabricPortOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle.
      
      The OSI Status attributes, if supported by the component, may 
      provide more details, qualifying the state of the component."
   DEFVAL     { disabled }
::= { mscShelfCardFabricPortStateEntry 2 }

mscShelfCardFabricPortUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time.
      
      The OSI Status attributes, if supported by the component, may 
      provide more details, qualifying the state of the component."
   DEFVAL     { idle }
::= { mscShelfCardFabricPortStateEntry 3 }

mscShelfCardFabricPortAvailabilityStatus OBJECT-TYPE
   SYNTAX     OCTET STRING (SIZE (2))
   ACCESS     read-only
   STATUS     mandatory
   DESCRIPTION
     "If supported by the component, this attribute indicates the OSI 
      Availability status of the component. Note that, even though it is 
      defined as a multi-valued set, at most one value is shown to the user.
      
      When no values are in the set, this indicates that either the attribute 
      is not supported or that none of the status conditions described 
      below are present.
      
      The value inTest indicates that the resource is undergoing a test 
      procedure. If adminState is locked or shuttingDown, the normal 
      users are precluded from using the resource and controlStatus is 
      reservedForTest. Tests that do not exclude additional users can be 
      present in any operational or administrative state but the 
      reservedForTest condition should not be present.
      
      The value failed indicates that the component has an internal fault 
      that prevents it from operating. The operationalState is disabled.
      
      The value dependency indicates that the component cannot operate 
      because some other resource on which it depends is unavailable. 
      The operationalState is disabled.
      
      The value powerOff indicates the resource requires power to be 
      applied and it is not powered on. The operationalState is disabled.
      
      The value offLine indicates the resource requires a routine 
      operation (either manual, automatic, or both) to be performed to 
      place it on-line and make it available for use. The operationalState 
      is disabled.
      
      The value offDuty indicates the resource is inactive in accordance 
      with a predetermined time schedule. In the absence of other 
      disabling conditions, the operationalState is enabled or disabled.
      
      The value degraded indicates the service provided by the 
      component is degraded in some way, such as in speed or operating 
      capacity. However, the resource remains available for service. The 
      operationalState is enabled.
      
      The value notInstalled indicates the resource is not present. The 
      operationalState is disabled.
      
      The value logFull is not used.

      Description of bits:
      inTest(0)
      failed(1)
      powerOff(2)
      offLine(3)
      offDuty(4)
      dependency(5)
      degraded(6)
      notInstalled(7)
      logFull(8)"
::= { mscShelfCardFabricPortStateEntry 4 }

mscShelfCardFabricPortProceduralStatus OBJECT-TYPE
   SYNTAX     OCTET STRING (SIZE (1))
   ACCESS     read-only
   STATUS     mandatory
   DESCRIPTION
     "If supported by the component, this attribute indicates the OSI 
      Procedural status of the component. Note that, even though it is 
      defined as a multi-valued set, at most one value is shown to the user.
      
      When no values are in the set, this indicates that either the attribute 
      is not supported or that none of the status conditions described 
      below are present.
      
      The value initializationRequired indicates (for a resource which 
      doesn't initialize autonomously) that initialization is required before 
      it can perform its normal functions, and this procedure has not been 
      initiated. The operationalState is disabled.
      
      The value notInitialized indicates (for a resource which does 
      initialize autonomously) that initialization is required before it can 
      perform its normal functions, and this procedure has not been 
      initiated. The operationalState may be enabled or disabled.
      
      The value initializing indicates that initialization has been initiated 
      but is not yet complete. The operationalState may be enabled or 
      disabled.
      
      The value reporting indicates the resource has completed some 
      processing operation and is notifying the results. The 
      operationalState is enabled.
      
      The value terminating indicates the component is in a termination 
      phase. If the resource doesn't reinitialize autonomously, 
      operationalState is disabled; otherwise it is enabled or disabled.

      Description of bits:
      initializationRequired(0)
      notInitialized(1)
      initializing(2)
      reporting(3)
      terminating(4)"
::= { mscShelfCardFabricPortStateEntry 5 }

mscShelfCardFabricPortControlStatus OBJECT-TYPE
   SYNTAX     OCTET STRING (SIZE (1))
   ACCESS     read-only
   STATUS     mandatory
   DESCRIPTION
     "If supported by the component, this attribute indicates the OSI 
      Control status of the component. Note that, even though it is defined 
      as a multi-valued set, at most one value is shown to the user.
      
      When no values are in the set, this indicates that either the attribute 
      is not supported or that none of the status conditions described 
      below are present.
      
      The value subjectToTest indicates the resource is available but tests 
      may be conducted simultaneously at unpredictable times, which 
      may cause it to exhibit unusual characteristics.
      
      The value partOfServicesLocked indicates that part of the service is 
      restricted from users of a resource. The adminState is unlocked.
      
      The value reservedForTest indicates that the component is 
      administratively unavailable because it is undergoing a test 
      procedure. The adminState is locked.
      
      The value suspended indicates that the service has been 
      administratively suspended.

      Description of bits:
      subjectToTest(0)
      partOfServicesLocked(1)
      reservedForTest(2)
      suspended(3)"
::= { mscShelfCardFabricPortStateEntry 6 }

mscShelfCardFabricPortAlarmStatus OBJECT-TYPE
   SYNTAX     OCTET STRING (SIZE (1))
   ACCESS     read-only
   STATUS     mandatory
   DESCRIPTION
     "If supported by the component, this attribute indicates the OSI 
      Alarm status of the component. Note that, even though it is defined 
      as a multi-valued set, at most one value is shown to the user.
      
      When no values are in the set, this indicates that either the attribute 
      is not supported or that none of the status conditions described 
      below are present.
      
      The value underRepair indicates the component is currently being 
      repaired. The operationalState is enabled or disabled.
      
      The value critical indicates one or more critical alarms are 
      outstanding against the component. Other, less severe, alarms may 
      also be outstanding. The operationalState is enabled or disabled.
      
      The value major indicates one or more major alarms are 
      outstanding against the component. Other, less severe, alarms may 
      also be outstanding. The operationalState is enabled or disabled.
      
      The value minor indicates one or more minor alarms are 
      outstanding against the component. Other, less severe, alarms may 
      also be outstanding. The operationalState is enabled or disabled.
      
      The value alarmOutstanding generically indicates that an alarm of 
      some severity is outstanding against the component.

      Description of bits:
      underRepair(0)
      critical(1)
      major(2)
      minor(3)
      alarmOutstanding(4)"
::= { mscShelfCardFabricPortStateEntry 7 }

mscShelfCardFabricPortStandbyStatus OBJECT-TYPE
   SYNTAX     INTEGER  {
                 hotStandby(0),
                 coldStandby(1),
                 providingService(2),
                 notSet(15) }
   ACCESS     read-only
   STATUS     mandatory
   DESCRIPTION
     "If supported by the component, this attribute indicates the OSI 
      Standby status of the component.
      
      The value notSet indicates that either the attribute is not supported 
      or that none of the status conditions described below are present. 
      Note that this is a non-standard value, used because the original 
      specification indicated this attribute was set-valued and thus, did not 
      provide a value to indicate that none of the other three are 
      applicable.
      
      The value hotStandby indicates that the resource is not providing 
      service but will be immediately able to take over the role of the 
      resource to be backed up, without initialization activity, and 
      containing the same information as the resource to be backed up.
      
      The value coldStandby indicates the resource is a backup for 
      another resource but will not be immediately able to take over the 
      role of the backed up resource and will require some initialization 
      activity.
      
      The value providingService indicates that this component, as a 
      backup resource, is currently backing up another resource."
   DEFVAL     { notSet }
::= { mscShelfCardFabricPortStateEntry 8 }

mscShelfCardFabricPortUnknownStatus OBJECT-TYPE
   SYNTAX     INTEGER  {
                 false(0),
                 true(1) }
   ACCESS     read-only
   STATUS     mandatory
   DESCRIPTION
     "This attribute indicates the OSI Unknown status of the component.
      
      The value false indicates that all of the other OSI State and Status 
      attribute values can be considered accurate.
      
      The value true indicates that the actual state of the component is not 
      known for sure."
   DEFVAL     { false }
::= { mscShelfCardFabricPortStateEntry 9 }

mscShelfCardFabricPortOperTable OBJECT-TYPE
   SYNTAX     SEQUENCE OF MscShelfCardFabricPortOperEntry
   ACCESS     not-accessible
   STATUS     mandatory
   DESCRIPTION
     "This attribute group contains operational attributes of a fabric port. 
      This information outlines what the fabric port is doing and why it is 
      doing it. It is primarily intended for use in diagnosing the cause of a 
      fabric-related problem reported by the module."
::= { mscShelfCardFabricPort 11 }

mscShelfCardFabricPortOperEntry OBJECT-TYPE
   SYNTAX     MscShelfCardFabricPortOperEntry
   ACCESS     not-accessible
   STATUS     mandatory
   DESCRIPTION
     "An entry in the mscShelfCardFabricPortOperTable."
   INDEX {
      mscShelfIndex,
      mscShelfCardIndex,
      mscShelfCardFabricPortIndex }
::= { mscShelfCardFabricPortOperTable 1 }

MscShelfCardFabricPortOperEntry ::= SEQUENCE {
   mscShelfCardFabricPortFailuresInEffect
      OCTET STRING,
   mscShelfCardFabricPortDependenciesInEffect
      OCTET STRING,
   mscShelfCardFabricPortCardsAvailable
      OCTET STRING,
   mscShelfCardFabricPortCardsTxTo
      OCTET STRING }

mscShelfCardFabricPortFailuresInEffect OBJECT-TYPE
   SYNTAX     OCTET STRING (SIZE (1))
   ACCESS     read-only
   STATUS     mandatory
   DESCRIPTION
     "This attribute indicates the failures that prevent the fabric port from 
      using the associated fabric. It may contain any combination of the 
      following values:
      selfTest: The port has failed its self-test.
      hardwareError: An unrecoverable critical error has occurred on the 
      hardware of the processor card which exchanges cells with fabric 
      card. 
      portProtocolError: Errors have occurred which violate the protocol 
      between components of the fabric port in datapath. 
      switchClockError: The fabric card clock is no longer detected by 
      the processor card.
      livelinessError: A non-fatal hardware error has occurred on the 
      component which exchanges cells with the fabric card. Excessive 
      numbers of these errors on the fabric port may be indicating a 
      serious hardware problem.
      dataCorruptionError: Cell payloads or headers are detected as 
      being corrupted at the fabric port level. 
      linkLivelinessError: The link between the fabric port and the fabric 
      card is not indicating liveliness.
      
      Operator action: Run the fabric test to clear these errors.

      Description of bits:
      selfTest(0)
      hardwareError(1)
      portProtocolError(2)
      switchClockError(3)
      livelinessError(4)
      dataCorruptionError(5)
      linkLivelinessError(6)"
::= { mscShelfCardFabricPortOperEntry 1 }

mscShelfCardFabricPortDependenciesInEffect OBJECT-TYPE
   SYNTAX     OCTET STRING (SIZE (1))
   ACCESS     read-only
   STATUS     mandatory
   DESCRIPTION
     "This attribute indicates the non-hardware problems that prevent the 
      fabric port from using the associated fabric. It may be a 
      combination of the following values:
      fabricLocked: The fabric card is locked.
      fabricDisabled: The fabric card is disabled.
      portDisabled: The corresponding card port on the fabric is disabled.

      Description of bits:
      fabricLocked(0)
      fabricDisabled(1)
      portDisabled(2)"
::= { mscShelfCardFabricPortOperEntry 2 }

mscShelfCardFabricPortCardsAvailable OBJECT-TYPE
   SYNTAX     OCTET STRING (SIZE (2))
   ACCESS     read-only
   STATUS     mandatory
   DESCRIPTION
     "This attribute indicates the slot numbers of the cards that the fabric 
      port considers available through the fabric; that is, the cards that 
      have an operational port connected to the fabric. The value of this 
      attribute is determined automatically by the fabric port by 
      monitoring signals generated by each fabric port connected to the 
      fabric card. Normally, every card in the module signals its 
      availability on both fabrics. If a card does not signal its availability 
      on a fabric, then the card is not present or its fabric port has failed. 
      By examining this attribute for both of a card's FabricPort 
      components, it is possible to determine which cards are present in 
      the module and which fabric each can use.
      
      Note: If failuresInEffect has a value of selfTest, signalLoss, 
      synchronizationLoss, or protocolError, the fabric port is unable to 
      monitor the availability of the fabric ports on the fabric. In such 
      cases, cardsAvailable indicates that no fabric port is available on the 
      fabric.

      Description of bits:
      n0(0)
      n1(1)
      n2(2)
      n3(3)
      n4(4)
      n5(5)
      n6(6)
      n7(7)
      n8(8)
      n9(9)
      n10(10)
      n11(11)
      n12(12)
      n13(13)
      n14(14)
      n15(15)"
::= { mscShelfCardFabricPortOperEntry 3 }

mscShelfCardFabricPortCardsTxTo OBJECT-TYPE
   SYNTAX     OCTET STRING (SIZE (2))
   ACCESS     read-only
   STATUS     mandatory
   DESCRIPTION
     "This attribute indicates the slot number of the cards to which the 
      fabric port is currently configured to transmit cells. This 
      configuration is managed automatically, and cannot be changed by 
      the operator. By examining this attribute for both of a card's 
      FabricPort components, it is possible to determine which fabric (if 
      any) the card uses when it needs to transmits cells to a specific card 
      in the module.

      Description of bits:
      n0(0)
      n1(1)
      n2(2)
      n3(3)
      n4(4)
      n5(5)
      n6(6)
      n7(7)
      n8(8)
      n9(9)
      n10(10)
      n11(11)
      n12(12)
      n13(13)
      n14(14)
      n15(15)"
::= { mscShelfCardFabricPortOperEntry 4 }

mscShelfCardFabricPortErrorsTable OBJECT-TYPE
   SYNTAX     SEQUENCE OF MscShelfCardFabricPortErrorsEntry
   ACCESS     not-accessible
   STATUS     mandatory
   DESCRIPTION
     "This attribute group indicates errors that the fabric port has detected 
      since the card was last rebooted. This information is intended for 
      use in detecting and diagnosing fabric-related problems within a 
      module."
::= { mscShelfCardFabricPort 12 }

mscShelfCardFabricPortErrorsEntry OBJECT-TYPE
   SYNTAX     MscShelfCardFabricPortErrorsEntry
   ACCESS     not-accessible
   STATUS     mandatory
   DESCRIPTION
     "An entry in the mscShelfCardFabricPortErrorsTable."
   INDEX {
      mscShelfIndex,
      mscShelfCardIndex,
      mscShelfCardFabricPortIndex }
::= { mscShelfCardFabricPortErrorsTable 1 }

MscShelfCardFabricPortErrorsEntry ::= SEQUENCE {
   mscShelfCardFabricPortSelfTestErrorCode
      Unsigned32,
   mscShelfCardFabricPortLivelinessErrors
      Counter32,
   mscShelfCardFabricPortSwitchClockErrors
      Counter32,
   mscShelfCardFabricPortPortHardwareErrors
      Counter32,
   mscShelfCardFabricPortPortProtocolErrors
      Counter32,
   mscShelfCardFabricPortDataCorruptionErrors
      Counter32,
   mscShelfCardFabricPortLinkLivelinessErrors
      Counter32 }

mscShelfCardFabricPortSelfTestErrorCode OBJECT-TYPE
   SYNTAX     Unsigned32 (0..4294967295)
   ACCESS     read-only
   STATUS     mandatory
   DESCRIPTION
     "This attribute indicates the error code generated by the most recent 
      self-test of the port. Zero indicates that the self-test was successful. 
      A non-zero value indicates that the self-test failed. This information 
      is used by the service technician when a defective card is returned 
      for repair."
::= { mscShelfCardFabricPortErrorsEntry 1 }

mscShelfCardFabricPortLivelinessErrors OBJECT-TYPE
   SYNTAX     Counter32 
   ACCESS     read-only
   STATUS     mandatory
   DESCRIPTION
     "This attribute counts the liveliness errors detected on the port. 
      Liveliness errors are failures to receive yellow cells within a certain 
      period of time. The value wraps to zero when it exceeds the 
      maximum value.
      
      Note: Yellow cells are special types of packets which are generated 
      by the fabric port and detected by the fabric card and the fabric port 
      in order to check the link liveness with the fabric card."
::= { mscShelfCardFabricPortErrorsEntry 7 }

mscShelfCardFabricPortSwitchClockErrors OBJECT-TYPE
   SYNTAX     Counter32 
   ACCESS     read-only
   STATUS     mandatory
   DESCRIPTION
     "This attribute counts the clock errors which have occurred on this 
      port. The value wraps to zero when it exceeds the maximum value."
::= { mscShelfCardFabricPortErrorsEntry 9 }

mscShelfCardFabricPortPortHardwareErrors OBJECT-TYPE
   SYNTAX     Counter32 
   ACCESS     read-only
   STATUS     mandatory
   DESCRIPTION
     "This attribute counts the errors which have occurred on the 
      hardware which exchanges cells with the fabric card. The value 
      wraps to zero when it exceeds the maximum value."
::= { mscShelfCardFabricPortErrorsEntry 18 }

mscShelfCardFabricPortPortProtocolErrors OBJECT-TYPE
   SYNTAX     Counter32 
   ACCESS     read-only
   STATUS     mandatory
   DESCRIPTION
     "This attribute counts the number of errors which affect the protocol 
      between components of the fabric port datapath. The value wraps to 
      zero when it exceeds the maximum value."
::= { mscShelfCardFabricPortErrorsEntry 19 }

mscShelfCardFabricPortDataCorruptionErrors OBJECT-TYPE
   SYNTAX     Counter32 
   ACCESS     read-only
   STATUS     mandatory
   DESCRIPTION
     "This attribute counts the errors which have occurred on the 
      corrupted cell payloads or headers at fabric port level. The value 
      wraps to zero when it exceeds the maximum value."
::= { mscShelfCardFabricPortErrorsEntry 20 }

mscShelfCardFabricPortLinkLivelinessErrors OBJECT-TYPE
   SYNTAX     Counter32 
   ACCESS     read-only
   STATUS     mandatory
   DESCRIPTION
     "This attribute counts the errors which occurred on the link between 
      the fabric port and the fabric card. The value wraps to zero when it 
      exceeds the maximum value."
::= { mscShelfCardFabricPortErrorsEntry 21 }


-- Shelf FabricCard/f
-- This component represents a hardware resource within a module 
-- that cards can use to communicate with each other. Data to be 
-- transferred between cards is broken up into one or more cells by the 
-- sending card, and reassembled by the receiving card.
-- 
-- A module's FabricCard components are created automatically, and 
-- cannot be added or deleted.

mscShelfFabricCard OBJECT IDENTIFIER ::= { mscShelf 5 }



mscShelfFabricCardRowStatusTable OBJECT-TYPE
   SYNTAX     SEQUENCE OF MscShelfFabricCardRowStatusEntry
   ACCESS     not-accessible
   STATUS     mandatory
   DESCRIPTION
     "This entry controls the addition and deletion of 
      mscShelfFabricCard components."
::= { mscShelfFabricCard 1 }

mscShelfFabricCardRowStatusEntry OBJECT-TYPE
   SYNTAX     MscShelfFabricCardRowStatusEntry
   ACCESS     not-accessible
   STATUS     mandatory
   DESCRIPTION
     "A single entry in the table represents a single 
      mscShelfFabricCard component."
   INDEX {
      mscShelfIndex,
      mscShelfFabricCardIndex }
::= { mscShelfFabricCardRowStatusTable 1 }

MscShelfFabricCardRowStatusEntry ::= SEQUENCE {
   mscShelfFabricCardRowStatus
      RowStatus,
   mscShelfFabricCardComponentName
      DisplayString,
   mscShelfFabricCardStorageType
      StorageType,
   mscShelfFabricCardIndex
      INTEGER }

mscShelfFabricCardRowStatus OBJECT-TYPE
   SYNTAX     RowStatus 
   ACCESS     read-only
   STATUS     mandatory
   DESCRIPTION
     "This variable is used as the basis for SNMP naming of
      mscShelfFabricCard components.
      These components cannot be added nor deleted."
::= { mscShelfFabricCardRowStatusEntry 1 }

mscShelfFabricCardComponentName OBJECT-TYPE
   SYNTAX     DisplayString 
   ACCESS     read-only
   STATUS     mandatory
   DESCRIPTION
     "This variable provides the component's string name for
      use with the ASCII Console Interface"
::= { mscShelfFabricCardRowStatusEntry 2 }

mscShelfFabricCardStorageType OBJECT-TYPE
   SYNTAX     StorageType 
   ACCESS     read-only
   STATUS     mandatory
   DESCRIPTION
     "This variable represents the storage type value for the
      mscShelfFabricCard tables."
::= { mscShelfFabricCardRowStatusEntry 4 }

mscShelfFabricCardIndex OBJECT-TYPE
   SYNTAX     INTEGER  {
                 x(0),
                 y(1) }
   ACCESS     not-accessible
   STATUS     mandatory
   DESCRIPTION
     "This variable represents the index for the mscShelfFabricCard tables."
::= { mscShelfFabricCardRowStatusEntry 10 }

mscShelfFabricCardStateTable OBJECT-TYPE
   SYNTAX     SEQUENCE OF MscShelfFabricCardStateEntry
   ACCESS     not-accessible
   STATUS     mandatory
   DESCRIPTION
     "This group contains the three OSI State attributes and the six OSI 
      Status attributes. The descriptions generically indicate what each 
      attribute implies about the component. Note that not all the values 
      and state combinations described here are supported by every 
      component which uses this group. For component-specific 
      information and the valid state combinations, refer to NTP 241-
      7001-150, Passport Operations and Maintenance Guide."
::= { mscShelfFabricCard 10 }

mscShelfFabricCardStateEntry OBJECT-TYPE
   SYNTAX     MscShelfFabricCardStateEntry
   ACCESS     not-accessible
   STATUS     mandatory
   DESCRIPTION
     "An entry in the mscShelfFabricCardStateTable."
   INDEX {
      mscShelfIndex,
      mscShelfFabricCardIndex }
::= { mscShelfFabricCardStateTable 1 }

MscShelfFabricCardStateEntry ::= SEQUENCE {
   mscShelfFabricCardAdminState
      INTEGER,
   mscShelfFabricCardOperationalState
      INTEGER,
   mscShelfFabricCardUsageState
      INTEGER,
   mscShelfFabricCardAvailabilityStatus
      OCTET STRING,
   mscShelfFabricCardProceduralStatus
      OCTET STRING,
   mscShelfFabricCardControlStatus
      OCTET STRING,
   mscShelfFabricCardAlarmStatus
      OCTET STRING,
   mscShelfFabricCardStandbyStatus
      INTEGER,
   mscShelfFabricCardUnknownStatus
      INTEGER }

mscShelfFabricCardAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component.
      
      The OSI Status attributes, if supported by the component, may 
      provide more details, qualifying the state of the component."
   DEFVAL     { unlocked }
::= { mscShelfFabricCardStateEntry 1 }

mscShelfFabricCardOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle.
      
      The OSI Status attributes, if supported by the component, may 
      provide more details, qualifying the state of the component."
   DEFVAL     { disabled }
::= { mscShelfFabricCardStateEntry 2 }

mscShelfFabricCardUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time.
      
      The OSI Status attributes, if supported by the component, may 
      provide more details, qualifying the state of the component."
   DEFVAL     { idle }
::= { mscShelfFabricCardStateEntry 3 }

mscShelfFabricCardAvailabilityStatus OBJECT-TYPE
   SYNTAX     OCTET STRING (SIZE (2))
   ACCESS     read-only
   STATUS     mandatory
   DESCRIPTION
     "If supported by the component, this attribute indicates the OSI 
      Availability status of the component. Note that, even though it is 
      defined as a multi-valued set, at most one value is shown to the user.
      
      When no values are in the set, this indicates that either the attribute 
      is not supported or that none of the status conditions described 
      below are present.
      
      The value inTest indicates that the resource is undergoing a test 
      procedure. If adminState is locked or shuttingDown, the normal 
      users are precluded from using the resource and controlStatus is 
      reservedForTest. Tests that do not exclude additional users can be 
      present in any operational or administrative state but the 
      reservedForTest condition should not be present.
      
      The value failed indicates that the component has an internal fault 
      that prevents it from operating. The operationalState is disabled.
      
      The value dependency indicates that the component cannot operate 
      because some other resource on which it depends is unavailable. 
      The operationalState is disabled.
      
      The value powerOff indicates the resource requires power to be 
      applied and it is not powered on. The operationalState is disabled.
      
      The value offLine indicates the resource requires a routine 
      operation (either manual, automatic, or both) to be performed to 
      place it on-line and make it available for use. The operationalState 
      is disabled.
      
      The value offDuty indicates the resource is inactive in accordance 
      with a predetermined time schedule. In the absence of other 
      disabling conditions, the operationalState is enabled or disabled.
      
      The value degraded indicates the service provided by the 
      component is degraded in some way, such as in speed or operating 
      capacity. However, the resource remains available for service. The 
      operationalState is enabled.
      
      The value notInstalled indicates the resource is not present. The 
      operationalState is disabled.
      
      The value logFull is not used.

      Description of bits:
      inTest(0)
      failed(1)
      powerOff(2)
      offLine(3)
      offDuty(4)
      dependency(5)
      degraded(6)
      notInstalled(7)
      logFull(8)"
::= { mscShelfFabricCardStateEntry 4 }

mscShelfFabricCardProceduralStatus OBJECT-TYPE
   SYNTAX     OCTET STRING (SIZE (1))
   ACCESS     read-only
   STATUS     mandatory
   DESCRIPTION
     "If supported by the component, this attribute indicates the OSI 
      Procedural status of the component. Note that, even though it is 
      defined as a multi-valued set, at most one value is shown to the user.
      
      When no values are in the set, this indicates that either the attribute 
      is not supported or that none of the status conditions described 
      below are present.
      
      The value initializationRequired indicates (for a resource which 
      doesn't initialize autonomously) that initialization is required before 
      it can perform its normal functions, and this procedure has not been 
      initiated. The operationalState is disabled.
      
      The value notInitialized indicates (for a resource which does 
      initialize autonomously) that initialization is required before it can 
      perform its normal functions, and this procedure has not been 
      initiated. The operationalState may be enabled or disabled.
      
      The value initializing indicates that initialization has been initiated 
      but is not yet complete. The operationalState may be enabled or 
      disabled.
      
      The value reporting indicates the resource has completed some 
      processing operation and is notifying the results. The 
      operationalState is enabled.
      
      The value terminating indicates the component is in a termination 
      phase. If the resource doesn't reinitialize autonomously, 
      operationalState is disabled; otherwise it is enabled or disabled.

      Description of bits:
      initializationRequired(0)
      notInitialized(1)
      initializing(2)
      reporting(3)
      terminating(4)"
::= { mscShelfFabricCardStateEntry 5 }

mscShelfFabricCardControlStatus OBJECT-TYPE
   SYNTAX     OCTET STRING (SIZE (1))
   ACCESS     read-only
   STATUS     mandatory
   DESCRIPTION
     "If supported by the component, this attribute indicates the OSI 
      Control status of the component. Note that, even though it is defined 
      as a multi-valued set, at most one value is shown to the user.
      
      When no values are in the set, this indicates that either the attribute 
      is not supported or that none of the status conditions described 
      below are present.
      
      The value subjectToTest indicates the resource is available but tests 
      may be conducted simultaneously at unpredictable times, which 
      may cause it to exhibit unusual characteristics.
      
      The value partOfServicesLocked indicates that part of the service is 
      restricted from users of a resource. The adminState is unlocked.
      
      The value reservedForTest indicates that the component is 
      administratively unavailable because it is undergoing a test 
      procedure. The adminState is locked.
      
      The value suspended indicates that the service has been 
      administratively suspended.

      Description of bits:
      subjectToTest(0)
      partOfServicesLocked(1)
      reservedForTest(2)
      suspended(3)"
::= { mscShelfFabricCardStateEntry 6 }

mscShelfFabricCardAlarmStatus OBJECT-TYPE
   SYNTAX     OCTET STRING (SIZE (1))
   ACCESS     read-only
   STATUS     mandatory
   DESCRIPTION
     "If supported by the component, this attribute indicates the OSI 
      Alarm status of the component. Note that, even though it is defined 
      as a multi-valued set, at most one value is shown to the user.
      
      When no values are in the set, this indicates that either the attribute 
      is not supported or that none of the status conditions described 
      below are present.
      
      The value underRepair indicates the component is currently being 
      repaired. The operationalState is enabled or disabled.
      
      The value critical indicates one or more critical alarms are 
      outstanding against the component. Other, less severe, alarms may 
      also be outstanding. The operationalState is enabled or disabled.
      
      The value major indicates one or more major alarms are 
      outstanding against the component. Other, less severe, alarms may 
      also be outstanding. The operationalState is enabled or disabled.
      
      The value minor indicates one or more minor alarms are 
      outstanding against the component. Other, less severe, alarms may 
      also be outstanding. The operationalState is enabled or disabled.
      
      The value alarmOutstanding generically indicates that an alarm of 
      some severity is outstanding against the component.

      Description of bits:
      underRepair(0)
      critical(1)
      major(2)
      minor(3)
      alarmOutstanding(4)"
::= { mscShelfFabricCardStateEntry 7 }

mscShelfFabricCardStandbyStatus OBJECT-TYPE
   SYNTAX     INTEGER  {
                 hotStandby(0),
                 coldStandby(1),
                 providingService(2),
                 notSet(15) }
   ACCESS     read-only
   STATUS     mandatory
   DESCRIPTION
     "If supported by the component, this attribute indicates the OSI 
      Standby status of the component.
      
      The value notSet indicates that either the attribute is not supported 
      or that none of the status conditions described below are present. 
      Note that this is a non-standard value, used because the original 
      specification indicated this attribute was set-valued and thus, did not 
      provide a value to indicate that none of the other three are 
      applicable.
      
      The value hotStandby indicates that the resource is not providing 
      service but will be immediately able to take over the role of the 
      resource to be backed up, without initialization activity, and 
      containing the same information as the resource to be backed up.
      
      The value coldStandby indicates the resource is a backup for 
      another resource but will not be immediately able to take over the 
      role of the backed up resource and will require some initialization 
      activity.
      
      The value providingService indicates that this component, as a 
      backup resource, is currently backing up another resource."
   DEFVAL     { notSet }
::= { mscShelfFabricCardStateEntry 8 }

mscShelfFabricCardUnknownStatus OBJECT-TYPE
   SYNTAX     INTEGER  {
                 false(0),
                 true(1) }
   ACCESS     read-only
   STATUS     mandatory
   DESCRIPTION
     "This attribute indicates the OSI Unknown status of the component.
      
      The value false indicates that all of the other OSI State and Status 
      attribute values can be considered accurate.
      
      The value true indicates that the actual state of the component is not 
      known for sure."
   DEFVAL     { false }
::= { mscShelfFabricCardStateEntry 9 }

mscShelfFabricCardPropTable OBJECT-TYPE
   SYNTAX     SEQUENCE OF MscShelfFabricCardPropEntry
   ACCESS     not-accessible
   STATUS     mandatory
   DESCRIPTION
     "This attribute group indicates property attributes of a fabric card."
::= { mscShelfFabricCard 11 }

mscShelfFabricCardPropEntry OBJECT-TYPE
   SYNTAX     MscShelfFabricCardPropEntry
   ACCESS     not-accessible
   STATUS     mandatory
   DESCRIPTION
     "An entry in the mscShelfFabricCardPropTable."
   INDEX {
      mscShelfIndex,
      mscShelfFabricCardIndex }
::= { mscShelfFabricCardPropTable 1 }

MscShelfFabricCardPropEntry ::= SEQUENCE {
   mscShelfFabricCardProductCode
      AsciiString,
   mscShelfFabricCardSerialNumber
      AsciiString }

mscShelfFabricCardProductCode OBJECT-TYPE
   SYNTAX     AsciiString (SIZE (0..12))
   ACCESS     read-only
   STATUS     mandatory
   DESCRIPTION
     "This attribute indicates the product code (that is the PEC and 
      revision codes) of the fabric card."
::= { mscShelfFabricCardPropEntry 1 }

mscShelfFabricCardSerialNumber OBJECT-TYPE
   SYNTAX     AsciiString (SIZE (0..16))
   ACCESS     read-only
   STATUS     mandatory
   DESCRIPTION
     "This attribute indicates the serial number of the fabric card."
::= { mscShelfFabricCardPropEntry 2 }

mscShelfFabricCardOperTable OBJECT-TYPE
   SYNTAX     SEQUENCE OF MscShelfFabricCardOperEntry
   ACCESS     not-accessible
   STATUS     mandatory
   DESCRIPTION
     "This attribute group contains operational attributes of a FabricCard 
      component."
::= { mscShelfFabricCard 12 }

mscShelfFabricCardOperEntry OBJECT-TYPE
   SYNTAX     MscShelfFabricCardOperEntry
   ACCESS     not-accessible
   STATUS     mandatory
   DESCRIPTION
     "An entry in the mscShelfFabricCardOperTable."
   INDEX {
      mscShelfIndex,
      mscShelfFabricCardIndex }
::= { mscShelfFabricCardOperTable 1 }

MscShelfFabricCardOperEntry ::= SEQUENCE {
   mscShelfFabricCardFailureCause
      OCTET STRING,
   mscShelfFabricCardUtilization
      Gauge32,
   mscShelfFabricCardOperatingTemperature
      FixedPoint1,
   mscShelfFabricCardSecondaryControlBusStatus
      OCTET STRING,
   mscShelfFabricCardSelfTestResults
      Unsigned32,
   mscShelfFabricCardDependencyInEffect
      OCTET STRING,
   mscShelfFabricCardVoltageAFeedDetected
      INTEGER,
   mscShelfFabricCardVoltageBFeedDetected
      INTEGER,
   mscShelfFabricCardTemperatureThreshold
      FixedPoint1 }

mscShelfFabricCardFailureCause OBJECT-TYPE
   SYNTAX     OCTET STRING (SIZE (1))
   ACCESS     read-only
   STATUS     mandatory
   DESCRIPTION
     "This attribute indicates why the fabric card has failed. This attribute 
      is meaningful when the OSI availabilityStatus attribute is set to 
      failed. Possible values are:
      queueFull: The fabric card buffers are full.
      notInserted: The fabric card is not inserted.
      failedSelfTest: The fabric card has failed its self test.
      internalFailure: The fabric card has internal ASIC failure.
      notResponding: The fabric card is not responding.
      highTemperature: The fabric card is running at high temperature.
      powerProblem: The fabric card has a power problem.
      fabricStateUnknown: The fabric card is inserted, but it is in an 
      unknown state.

      Description of bits:
      queueFull(0)
      notInserted(1)
      failedSelfTest(2)
      internalFailure(3)
      notResponding(4)
      highTemperature(5)
      powerProblem(6)
      fabricStateUnknown(7)"
::= { mscShelfFabricCardOperEntry 1 }

mscShelfFabricCardUtilization OBJECT-TYPE
   SYNTAX     Gauge32 (0..100)
   ACCESS     read-only
   STATUS     mandatory
   DESCRIPTION
     "This attribute indicates an approximation of the current fabric 
      utilization."
::= { mscShelfFabricCardOperEntry 2 }

mscShelfFabricCardOperatingTemperature OBJECT-TYPE
   SYNTAX     FixedPoint1 (1..640)
   ACCESS     read-only
   STATUS     mandatory
   DESCRIPTION
     "This attribute indicates the current fabric operating temperature. 
      When the temperature reaches the value specified by the 
      temperatureThreshold attribute, the fabric card generates an alarm."
::= { mscShelfFabricCardOperEntry 3 }

mscShelfFabricCardSecondaryControlBusStatus OBJECT-TYPE
   SYNTAX     OCTET STRING (SIZE (2))
   ACCESS     read-only
   STATUS     mandatory
   DESCRIPTION
     "This attribute indicates the state of the fabric's Secondary Control 
      Bus (SCB). It may contain any combination of the following values:
      operational - The SCB is operational.
      locked - The SCB is being manually prevented from operating.
      noBus - The bus is down.
      failed - The SCB is disabled due to fault.
      bestEffort - The SCB is ignoring faults to allow a single channel to 
      be operational.
      hardwareFailure - The bus failed due to an HSCX hardware error.
      parityOrCrcError - The bus failed due to a CRC error or a parity 
      error.
      timeOutError - The bus failed due to an SSC message time-out.
      txOrRxError - The bus failed due to Tx or Rx problems.
      pollError - The bus failed an SCB poll.
      testMessageError - The bus failed a fabric card test.

      Description of bits:
      operational(0)
      locked(1)
      noBus(2)
      failed(3)
      bestEffort(4)
      hardwareFailure(5)
      parityOrCrcError(6)
      timeOutError(7)
      txOrRxError(8)
      pollError(9)
      testMessageError(10)"
::= { mscShelfFabricCardOperEntry 4 }

mscShelfFabricCardSelfTestResults OBJECT-TYPE
   SYNTAX     Unsigned32 (0..4294967295)
   ACCESS     read-only
   STATUS     mandatory
   DESCRIPTION
     "This attribute indicates the result of the most recent execution of the 
      fabric card's self-tests, performed either when it initially came up, 
      or during operation. A value of 0 indicates success, and a non-zero 
      value indicates a failure or and absent fabric card."
::= { mscShelfFabricCardOperEntry 5 }

mscShelfFabricCardDependencyInEffect OBJECT-TYPE
   SYNTAX     OCTET STRING (SIZE (1))
   ACCESS     read-only
   STATUS     mandatory
   DESCRIPTION
     "This attribute indicates why the fabric card has failed. This attribute 
      is meaningful when the OSI availabilityStatus attribute is set to 
      depend. Possible values are:
      portDisabled: Card port or fabric port is disabled.
      fabricCardLocked: The fabric card is locked.

      Description of bits:
      portDisabled(0)
      fabricCardLocked(1)"
::= { mscShelfFabricCardOperEntry 6 }

mscShelfFabricCardVoltageAFeedDetected OBJECT-TYPE
   SYNTAX     INTEGER  {
                 no(0),
                 yes(1) }
   ACCESS     read-only
   STATUS     mandatory
   DESCRIPTION
     "This attribute indicates if the fabric card is detecting current on 
      power feed A. If it is not, check that the breaker is not turned off."
::= { mscShelfFabricCardOperEntry 7 }

mscShelfFabricCardVoltageBFeedDetected OBJECT-TYPE
   SYNTAX     INTEGER  {
                 no(0),
                 yes(1) }
   ACCESS     read-only
   STATUS     mandatory
   DESCRIPTION
     "This attribute indicates if the fabric card is detecting current on 
      power feed B. If it is not, check that the breaker is not turned off."
::= { mscShelfFabricCardOperEntry 8 }

mscShelfFabricCardTemperatureThreshold OBJECT-TYPE
   SYNTAX     FixedPoint1 (1..1000)
   ACCESS     read-only
   STATUS     mandatory
   DESCRIPTION
     "This attributes indicates at which temperature the fabric card 
      generates a temperature alarm."
::= { mscShelfFabricCardOperEntry 9 }

mscShelfFabricCardErrorsTable OBJECT-TYPE
   SYNTAX     SEQUENCE OF MscShelfFabricCardErrorsEntry
   ACCESS     not-accessible
   STATUS     mandatory
   DESCRIPTION
     "This attribute group indicates errors that the fabric card has detected 
      since the card was last rebooted. This information is intended for 
      use in detecting and diagnosing the fabric-related problems within a 
      module."
::= { mscShelfFabricCard 13 }

mscShelfFabricCardErrorsEntry OBJECT-TYPE
   SYNTAX     MscShelfFabricCardErrorsEntry
   ACCESS     not-accessible
   STATUS     mandatory
   DESCRIPTION
     "An entry in the mscShelfFabricCardErrorsTable."
   INDEX {
      mscShelfIndex,
      mscShelfFabricCardIndex }
::= { mscShelfFabricCardErrorsTable 1 }

MscShelfFabricCardErrorsEntry ::= SEQUENCE {
   mscShelfFabricCardVoltageErrors
      Counter32,
   mscShelfFabricCardTemperatureErrors
      Counter32 }

mscShelfFabricCardVoltageErrors OBJECT-TYPE
   SYNTAX     Counter32 
   ACCESS     read-only
   STATUS     mandatory
   DESCRIPTION
     "This attribute counts the voltage errors detected on the fabric. The 
      value wraps to zero when it exceeds the maximum value."
::= { mscShelfFabricCardErrorsEntry 1 }

mscShelfFabricCardTemperatureErrors OBJECT-TYPE
   SYNTAX     Counter32 
   ACCESS     read-only
   STATUS     mandatory
   DESCRIPTION
     "This attribute counts the temperature errors encountered on the 
      fabric card. The value wraps to zero when it exceeds the maximum 
      value."
::= { mscShelfFabricCardErrorsEntry 2 }

mscShelfFabricCardBanksTable OBJECT-TYPE
   SYNTAX     SEQUENCE OF MscShelfFabricCardBanksEntry
   ACCESS     not-accessible
   STATUS     mandatory
   DESCRIPTION
     "This group contains the attributes that govern the operation of a 
      fabric card banks. These attributes cannot be changed while the 
      fabric card writable bank is loading."
::= { mscShelfFabricCard 14 }

mscShelfFabricCardBanksEntry OBJECT-TYPE
   SYNTAX     MscShelfFabricCardBanksEntry
   ACCESS     not-accessible
   STATUS     mandatory
   DESCRIPTION
     "An entry in the mscShelfFabricCardBanksTable."
   INDEX {
      mscShelfIndex,
      mscShelfFabricCardIndex }
::= { mscShelfFabricCardBanksTable 1 }

MscShelfFabricCardBanksEntry ::= SEQUENCE {
   mscShelfFabricCardFixedBankVersion
      FixedPoint1,
   mscShelfFabricCardWritableBankVersion
      FixedPoint1,
   mscShelfFabricCardRecommendedVersionToInstall
      AsciiString,
   mscShelfFabricCardActiveBank
      INTEGER,
   mscShelfFabricCardBankOnShelfRestart
      INTEGER,
   mscShelfFabricCardWritableBankStatus
      INTEGER }

mscShelfFabricCardFixedBankVersion OBJECT-TYPE
   SYNTAX     FixedPoint1 (0..999)
   ACCESS     read-only
   STATUS     mandatory
   DESCRIPTION
     "This attribute indicates what the fabric card software version in the 
      fixed bank is. It is zero during start-up. After start-up it is queried 
      from the fabric card."
::= { mscShelfFabricCardBanksEntry 1 }

mscShelfFabricCardWritableBankVersion OBJECT-TYPE
   SYNTAX     FixedPoint1 (0..999)
   ACCESS     read-only
   STATUS     mandatory
   DESCRIPTION
     "This attribute indicates the software version that is loaded on the 
      writable bank. It is zero if there is no version loaded."
::= { mscShelfFabricCardBanksEntry 2 }

mscShelfFabricCardRecommendedVersionToInstall OBJECT-TYPE
   SYNTAX     AsciiString (SIZE (0..49))
   ACCESS     read-only
   STATUS     mandatory
   DESCRIPTION
     "This attribute indicates the recommended fabric application version 
      to install using the Install command. If the current active software is 
      up-to-date, it indicates no version is needed to install."
::= { mscShelfFabricCardBanksEntry 3 }

mscShelfFabricCardActiveBank OBJECT-TYPE
   SYNTAX     INTEGER  {
                 fixed(0),
                 writable(1),
                 unknown(2) }
   ACCESS     read-write
   STATUS     mandatory
   DESCRIPTION
     "This attribute indicates which bank is the currently running. The 
      writable bank can only be made active if it has been installed using 
      the Install command at least once. 
      
      writable: Indicates the writable bank is the active bank.
      fixed: Indicates the fixed bank is the active bank.
      unknown: The software has not yet determined which is the active 
      bank. This normally takes a few seconds when the software is first 
      activated."
::= { mscShelfFabricCardBanksEntry 4 }

mscShelfFabricCardBankOnShelfRestart OBJECT-TYPE
   SYNTAX     INTEGER  {
                 fixed(0),
                 writable(1),
                 unknown(2) }
   ACCESS     read-only
   STATUS     mandatory
   DESCRIPTION
     "This attribute indicates which bank will be running when the shelf 
      is reset or powered-down and then powered-up.
      
      writable: Indicates the writable bank will be the bank on the next 
      power up or reset.
      fixed: Indicates the fixed bank will be the bank on the next power 
      up or reset.
      unknown: The software has not yet determined which is the bank 
      on shelf restart. This normally takes a few seconds when the 
      software is first activated."
::= { mscShelfFabricCardBanksEntry 5 }

mscShelfFabricCardWritableBankStatus OBJECT-TYPE
   SYNTAX     INTEGER  {
                 unknown(0),
                 empty(1),
                 loading(2),
                 loaded(3) }
   ACCESS     read-only
   STATUS     mandatory
   DESCRIPTION
     "This attribute specifies the current status of the writable bank. It is 
      set to unknown until the status is determined by the software. It 
      takes a few seconds at software activation time to determine the 
      status of the writable bank.
      
      unknown: The switch has not yet determined the state of the 
      writable bank. This happens only within the first few seconds the 
      software is activated. 
      empty: No (valid) software is loaded in the writable bank. 
      loading: Software is currently loading into the writable bank.
      loaded: The software has successfully loaded.
      
      An example of a transition sequence for the writable bank status is: 
      unknown -> empty-> loading -> loaded-> loading.
      
      On a failure, the status reverts to the previous status that was 
      successful. For example if the loading fails, the status returns to 
      empty."
::= { mscShelfFabricCardBanksEntry 6 }

mscShelfFabricCardSecondaryControlBusCardBustapsTable OBJECT-TYPE
   SYNTAX     SEQUENCE OF MscShelfFabricCardSecondaryControlBusCardBustapsEntry
   ACCESS     not-accessible
   STATUS     mandatory
   DESCRIPTION
     "Each processor card has a bus tap on both of the system's secondary 
      control buses. This indicates the state of each processor card's bus 
      tap onto the secondary control bus for which clocking is supplied by 
      this fabric card. Possible values are:
      ok - The SCB is operational.
      hardwareFailure - The bus failed due to an HSCX hardware error.
      parityOrCrcErrors - The bus failed due to a CRC error or a parity 
      error.
      timeOutError - The bus failed due to an SSC message time-out.
      txOrRxError - The bus failed due to Tx or Rx problems.
      pollError - The bus failed an SCB poll.
      none - The processor card is not available."
::= { mscShelfFabricCard 443 }

mscShelfFabricCardSecondaryControlBusCardBustapsEntry OBJECT-TYPE
   SYNTAX     MscShelfFabricCardSecondaryControlBusCardBustapsEntry
   ACCESS     not-accessible
   STATUS     mandatory
   DESCRIPTION
     "An entry in the mscShelfFabricCardSecondaryControlBusCardBustapsTable."
   INDEX {
      mscShelfIndex,
      mscShelfFabricCardIndex,
      mscShelfFabricCardSecondaryControlBusCardBustapsIndex }
::= { mscShelfFabricCardSecondaryControlBusCardBustapsTable 1 }

MscShelfFabricCardSecondaryControlBusCardBustapsEntry ::= SEQUENCE {
   mscShelfFabricCardSecondaryControlBusCardBustapsIndex
      Integer32,
   mscShelfFabricCardSecondaryControlBusCardBustapsValue
      INTEGER }

mscShelfFabricCardSecondaryControlBusCardBustapsIndex OBJECT-TYPE
   SYNTAX     Integer32 (0..15)
   ACCESS     not-accessible
   STATUS     mandatory
   DESCRIPTION
     "This variable represents the mscShelfFabricCardSecondaryControlBusCardBustapsTable
      specific index for the mscShelfFabricCardSecondaryControlBusCardBustapsTable."
::= { mscShelfFabricCardSecondaryControlBusCardBustapsEntry 1 }

mscShelfFabricCardSecondaryControlBusCardBustapsValue OBJECT-TYPE
   SYNTAX     INTEGER  {
                 ok(0),
                 hardwareFailure(1),
                 parityOrCrcErrors(2),
                 timeOutError(3),
                 txOrRxError(4),
                 pollError(5),
                 none(6) }
   ACCESS     read-only
   STATUS     mandatory
   DESCRIPTION
     "This variable represents an individual value for the
      mscShelfFabricCardSecondaryControlBusCardBustapsTable."
::= { mscShelfFabricCardSecondaryControlBusCardBustapsEntry 2 }

mscShelfFabricCardSecondaryControlBusFabricBustapsTable OBJECT-TYPE
   SYNTAX     SEQUENCE OF MscShelfFabricCardSecondaryControlBusFabricBustapsEntry
   ACCESS     not-accessible
   STATUS     mandatory
   DESCRIPTION
     "Each fabric card has a bus tap on both of the system's secondary 
      control buses. This indicates the state of each fabric card's bus tap 
      onto the secondary control bus for which clocking is supplied by 
      this fabric card. The enumerated values describe the state of the 
      each bus tap.
      Possible values are:
      ok - The SCB is operational.
      txOrRxError - The bus failed due to Tx or Rx problems.
      pollError - The bus failed an SCB poll.
      testMessageError - The bus failed a fabric card test.
      none - The processor card is not available.
      unknown - The state cannot be determined due to faulty bustap on 
      CP."
::= { mscShelfFabricCard 445 }

mscShelfFabricCardSecondaryControlBusFabricBustapsEntry OBJECT-TYPE
   SYNTAX     MscShelfFabricCardSecondaryControlBusFabricBustapsEntry
   ACCESS     not-accessible
   STATUS     mandatory
   DESCRIPTION
     "An entry in the mscShelfFabricCardSecondaryControlBusFabricBustapsTable."
   INDEX {
      mscShelfIndex,
      mscShelfFabricCardIndex,
      mscShelfFabricCardSecondaryControlBusFabricBustapsIndex }
::= { mscShelfFabricCardSecondaryControlBusFabricBustapsTable 1 }

MscShelfFabricCardSecondaryControlBusFabricBustapsEntry ::= SEQUENCE {
   mscShelfFabricCardSecondaryControlBusFabricBustapsIndex
      INTEGER,
   mscShelfFabricCardSecondaryControlBusFabricBustapsValue
      INTEGER }

mscShelfFabricCardSecondaryControlBusFabricBustapsIndex OBJECT-TYPE
   SYNTAX     INTEGER  {
                 x(0),
                 y(1) }
   ACCESS     not-accessible
   STATUS     mandatory
   DESCRIPTION
     "This variable represents the mscShelfFabricCardSecondaryControlBusFabricBustapsTable
      specific index for the mscShelfFabricCardSecondaryControlBusFabricBustapsTable."
::= { mscShelfFabricCardSecondaryControlBusFabricBustapsEntry 1 }

mscShelfFabricCardSecondaryControlBusFabricBustapsValue OBJECT-TYPE
   SYNTAX     INTEGER  {
                 ok(0),
                 txOrRxError(1),
                 pollError(2),
                 testMessageError(3),
                 none(4),
                 unknown(5) }
   ACCESS     read-only
   STATUS     mandatory
   DESCRIPTION
     "This variable represents an individual value for the
      mscShelfFabricCardSecondaryControlBusFabricBustapsTable."
::= { mscShelfFabricCardSecondaryControlBusFabricBustapsEntry 2 }


-- Shelf FabricCard/b Test
-- This component is used to verify the operation of a fabric card. A 
-- fabric card test may be run as part of a regular maintenance 
-- program, or to diagnose the cause of a fabric-related problem. The 
-- Test component is created automatically, and cannot be added or 
-- deleted.
-- 
-- The fabric card test ensures that the fabric ports on a specific fabric 
-- card are functioning properly at minimal utilization rates. The fabric 
-- card to be tested must be locked while testing is in progress. The 
-- test only involves fabric ports on operational cards (active and 
-- standby LPs). If an operational card becomes non-operational or 
-- fails to respond during the test, it is dropped from the test and is not 
-- allowed to rejoin; however, the results of any tests on its fabric port 
-- up to that point are preserved. The results of the test can help to 
-- determine which portions of the fabric card system are faulty, if any.
-- 
-- A fabric card test comprises several different tests. The tests are 
-- performed in the following order:
-- self test: The fabric card performs its self-test.
-- port test: The fabric port 
-- broadcast test: Each fabric port ensures that it can receive a 
-- broadcast frame over the fabric card from every operational card 
-- (including itself).
-- ping test: Each fabric port ensures that it can receive a low priority 
-- non-broadcast frame over the backplane from every operational 
-- card (including itself).
-- 
-- Once all of the tests have been performed, the ping test is repeated 
-- continuously until the fabric card test is terminated; this repetition 
-- helps to detect transient fabric faults. The fabric test stops 
-- automatically after a specified time interval, or if it detects a self-
-- test failure, a port test failure, or a broadcast test failure.

mscShelfFabricCardTest OBJECT IDENTIFIER ::= { mscShelfFabricCard 2 }



mscShelfFabricCardTestRowStatusTable OBJECT-TYPE
   SYNTAX     SEQUENCE OF MscShelfFabricCardTestRowStatusEntry
   ACCESS     not-accessible
   STATUS     mandatory
   DESCRIPTION
     "This entry controls the addition and deletion of 
      mscShelfFabricCardTest components."
::= { mscShelfFabricCardTest 1 }

mscShelfFabricCardTestRowStatusEntry OBJECT-TYPE
   SYNTAX     MscShelfFabricCardTestRowStatusEntry
   ACCESS     not-accessible
   STATUS     mandatory
   DESCRIPTION
     "A single entry in the table represents a single 
      mscShelfFabricCardTest component."
   INDEX {
      mscShelfIndex,
      mscShelfFabricCardIndex,
      mscShelfFabricCardTestIndex }
::= { mscShelfFabricCardTestRowStatusTable 1 }

MscShelfFabricCardTestRowStatusEntry ::= SEQUENCE {
   mscShelfFabricCardTestRowStatus
      RowStatus,
   mscShelfFabricCardTestComponentName
      DisplayString,
   mscShelfFabricCardTestStorageType
      StorageType,
   mscShelfFabricCardTestIndex
      NonReplicated }

mscShelfFabricCardTestRowStatus OBJECT-TYPE
   SYNTAX     RowStatus 
   ACCESS     read-only
   STATUS     mandatory
   DESCRIPTION
     "This variable is used as the basis for SNMP naming of
      mscShelfFabricCardTest components.
      These components cannot be added nor deleted."
::= { mscShelfFabricCardTestRowStatusEntry 1 }

mscShelfFabricCardTestComponentName OBJECT-TYPE
   SYNTAX     DisplayString 
   ACCESS     read-only
   STATUS     mandatory
   DESCRIPTION
     "This variable provides the component's string name for
      use with the ASCII Console Interface"
::= { mscShelfFabricCardTestRowStatusEntry 2 }

mscShelfFabricCardTestStorageType OBJECT-TYPE
   SYNTAX     StorageType 
   ACCESS     read-only
   STATUS     mandatory
   DESCRIPTION
     "This variable represents the storage type value for the
      mscShelfFabricCardTest tables."
::= { mscShelfFabricCardTestRowStatusEntry 4 }

mscShelfFabricCardTestIndex OBJECT-TYPE
   SYNTAX     NonReplicated 
   ACCESS     not-accessible
   STATUS     mandatory
   DESCRIPTION
     "This variable represents the index for the mscShelfFabricCardTest tables."
::= { mscShelfFabricCardTestRowStatusEntry 10 }

mscShelfFabricCardTestStateTable OBJECT-TYPE
   SYNTAX     SEQUENCE OF MscShelfFabricCardTestStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { mscShelfFabricCardTest 10 }

mscShelfFabricCardTestStateEntry OBJECT-TYPE
   SYNTAX     MscShelfFabricCardTestStateEntry
   ACCESS     not-accessible
   STATUS     mandatory
   DESCRIPTION
     "An entry in the mscShelfFabricCardTestStateTable."
   INDEX {
      mscShelfIndex,
      mscShelfFabricCardIndex,
      mscShelfFabricCardTestIndex }
::= { mscShelfFabricCardTestStateTable 1 }

MscShelfFabricCardTestStateEntry ::= SEQUENCE {
   mscShelfFabricCardTestAdminState
      INTEGER,
   mscShelfFabricCardTestOperationalState
      INTEGER,
   mscShelfFabricCardTestUsageState
      INTEGER }

mscShelfFabricCardTestAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { mscShelfFabricCardTestStateEntry 1 }

mscShelfFabricCardTestOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { mscShelfFabricCardTestStateEntry 2 }

mscShelfFabricCardTestUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { mscShelfFabricCardTestStateEntry 3 }

mscShelfFabricCardTestSetupTable OBJECT-TYPE
   SYNTAX     SEQUENCE OF MscShelfFabricCardTestSetupEntry
   ACCESS     not-accessible
   STATUS     mandatory
   DESCRIPTION
     "This attribute group contains the attributes that govern the operation 
      of a fabric card test. These attributes cannot be changed while the 
      fabric card test is running."
::= { mscShelfFabricCardTest 11 }

mscShelfFabricCardTestSetupEntry OBJECT-TYPE
   SYNTAX     MscShelfFabricCardTestSetupEntry
   ACCESS     not-accessible
   STATUS     mandatory
   DESCRIPTION
     "An entry in the mscShelfFabricCardTestSetupTable."
   INDEX {
      mscShelfIndex,
      mscShelfFabricCardIndex,
      mscShelfFabricCardTestIndex }
::= { mscShelfFabricCardTestSetupTable 1 }

MscShelfFabricCardTestSetupEntry ::= SEQUENCE {
   mscShelfFabricCardTestDuration
      Unsigned32 }

mscShelfFabricCardTestDuration OBJECT-TYPE
   SYNTAX     Unsigned32 (1..43200)
   ACCESS     read-write
   STATUS     mandatory
   DESCRIPTION
     "This attribute specifies the maximum length of time that the fabric 
      card test is allowed to run. The maximum allowed value permits the 
      fabric card test to be run for up to 30 days."
   DEFVAL     { 2 }
::= { mscShelfFabricCardTestSetupEntry 1 }

mscShelfFabricCardTestResultsTable OBJECT-TYPE
   SYNTAX     SEQUENCE OF MscShelfFabricCardTestResultsEntry
   ACCESS     not-accessible
   STATUS     mandatory
   DESCRIPTION
     "This attribute group contains the results of the fabric card test that is 
      currently running; if no fabric card test is running, the attribute 
      group contains the results of the most recently completed fabric 
      card test. The attributes of the Results group are reset to their initial 
      values whenever a fabric card test is started or any attribute in the 
      Setup group is set."
::= { mscShelfFabricCardTest 12 }

mscShelfFabricCardTestResultsEntry OBJECT-TYPE
   SYNTAX     MscShelfFabricCardTestResultsEntry
   ACCESS     not-accessible
   STATUS     mandatory
   DESCRIPTION
     "An entry in the mscShelfFabricCardTestResultsTable."
   INDEX {
      mscShelfIndex,
      mscShelfFabricCardIndex,
      mscShelfFabricCardTestIndex }
::= { mscShelfFabricCardTestResultsTable 1 }

MscShelfFabricCardTestResultsEntry ::= SEQUENCE {
   mscShelfFabricCardTestElapsedTime
      Unsigned32,
   mscShelfFabricCardTestTimeRemaining
      Unsigned32,
   mscShelfFabricCardTestCauseOfTermination
      INTEGER,
   mscShelfFabricCardTestTestsDone
      OCTET STRING,
   mscShelfFabricCardTestFabricSelfTestResults
      INTEGER }

mscShelfFabricCardTestElapsedTime OBJECT-TYPE
   SYNTAX     Unsigned32 (0..43200)
   ACCESS     read-only
   STATUS     mandatory
   DESCRIPTION
     "This attribute indicates the length of time that the fabric card test 
      has been running."
::= { mscShelfFabricCardTestResultsEntry 1 }

mscShelfFabricCardTestTimeRemaining OBJECT-TYPE
   SYNTAX     Unsigned32 (0..43200)
   ACCESS     read-only
   STATUS     mandatory
   DESCRIPTION
     "This attribute indicates the maximum length of time that the fabric 
      card test runs before stopping."
::= { mscShelfFabricCardTestResultsEntry 2 }

mscShelfFabricCardTestCauseOfTermination OBJECT-TYPE
   SYNTAX     INTEGER  {
                 neverStarted(0),
                 testRunning(1),
                 testTimeExpired(2),
                 stoppedByOperator(3),
                 portTestFailure(4),
                 fabricSelfTestFailure(5),
                 broadcastFailure(6) }
   ACCESS     read-only
   STATUS     mandatory
   DESCRIPTION
     "This attribute indicates the reason the fabric card test ended. It 
      contains one of the following values:
      neverStarted: The fabric card test has not been started.
      testRunning: The fabric card test is currently running.
      testTimeExpired: The fabric card test ran for the specified duration.
      stoppedByOperator: A stop command was issued.
      portTestFailure: A failure was detected during the port test.
      fabricSelfTestFailure: A failure was detected during the fabric 
      card self-test.
      broadcastFailure: A failure was detected during the broadcast test."
::= { mscShelfFabricCardTestResultsEntry 3 }

mscShelfFabricCardTestTestsDone OBJECT-TYPE
   SYNTAX     OCTET STRING (SIZE (1))
   ACCESS     read-only
   STATUS     mandatory
   DESCRIPTION
     "This attribute indicates the tests that have been performed during 
      the fabric card test. It contains zero or more of the following values:
      selfTest: The fabric card self-test has been performed.
      portTest: The port test has been performed.
      broadcastTest: The broadcast test has been performed.
      pingTest: At least one ping test has been performed.

      Description of bits:
      selfTest(0)
      portTest(1)
      broadcastTest(2)
      pingTest(3)"
::= { mscShelfFabricCardTestResultsEntry 4 }

mscShelfFabricCardTestFabricSelfTestResults OBJECT-TYPE
   SYNTAX     INTEGER  {
                 failed(0),
                 ok(1),
                 noTest(2) }
   ACCESS     read-only
   STATUS     mandatory
   DESCRIPTION
     "This attribute indicates the results of the fabric's self test. The fabric 
      test terminates automatically if a failure is detected.
      ok: The fabric self test is passed.
      failed: The fabric self test is failed.
      noTest: The default value indicates no self test is performed."
::= { mscShelfFabricCardTestResultsEntry 5 }

mscShelfFabricCardTestPortTestResultsTable OBJECT-TYPE
   SYNTAX     SEQUENCE OF MscShelfFabricCardTestPortTestResultsEntry
   ACCESS     not-accessible
   STATUS     mandatory
   DESCRIPTION
     "This attribute indicates the results of the fabric port, indexed by the 
      slot number of the card containing the fabric port tested. Each entry 
      contains one of the following values.
      +: the port passed its test
      X: the port failed its test
      .: the port was not tested
      The fabric card test terminates automatically if a failure is detected."
::= { mscShelfFabricCardTest 468 }

mscShelfFabricCardTestPortTestResultsEntry OBJECT-TYPE
   SYNTAX     MscShelfFabricCardTestPortTestResultsEntry
   ACCESS     not-accessible
   STATUS     mandatory
   DESCRIPTION
     "An entry in the mscShelfFabricCardTestPortTestResultsTable."
   INDEX {
      mscShelfIndex,
      mscShelfFabricCardIndex,
      mscShelfFabricCardTestIndex,
      mscShelfFabricCardTestPortTestResultsIndex }
::= { mscShelfFabricCardTestPortTestResultsTable 1 }

MscShelfFabricCardTestPortTestResultsEntry ::= SEQUENCE {
   mscShelfFabricCardTestPortTestResultsIndex
      Integer32,
   mscShelfFabricCardTestPortTestResultsValue
      INTEGER }

mscShelfFabricCardTestPortTestResultsIndex OBJECT-TYPE
   SYNTAX     Integer32 (0..15)
   ACCESS     not-accessible
   STATUS     mandatory
   DESCRIPTION
     "This variable represents the mscShelfFabricCardTestPortTestResultsTable
      specific index for the mscShelfFabricCardTestPortTestResultsTable."
::= { mscShelfFabricCardTestPortTestResultsEntry 1 }

mscShelfFabricCardTestPortTestResultsValue OBJECT-TYPE
   SYNTAX     INTEGER  {
                 x(0),
                 n1(1),
                 n2(2) }
   ACCESS     read-only
   STATUS     mandatory
   DESCRIPTION
     "This variable represents an individual value for the
      mscShelfFabricCardTestPortTestResultsTable."
::= { mscShelfFabricCardTestPortTestResultsEntry 2 }

mscShelfFabricCardTestBroadcastTestResultsTable OBJECT-TYPE
   SYNTAX     SEQUENCE OF MscShelfFabricCardTestBroadcastTestResultsEntry
   ACCESS     not-accessible
   STATUS     mandatory
   DESCRIPTION
     "This attribute indicates the results of the broadcast test, indexed by 
      the slot numbers of the cards containing the fabric port tested. Each 
      entry contains one of the following values.
      +: a broadcast message was successfully sent from the transmitting 
      fabric port to the receiving fabric port 
      X: a broadcast message was not successfully sent from the 
      transmitting fabric port to the receiving fabric port
      .: the associated pair of fabric ports was not tested 
      The fabric card test terminates automatically if a failure is detected."
::= { mscShelfFabricCardTest 469 }

mscShelfFabricCardTestBroadcastTestResultsEntry OBJECT-TYPE
   SYNTAX     MscShelfFabricCardTestBroadcastTestResultsEntry
   ACCESS     not-accessible
   STATUS     mandatory
   DESCRIPTION
     "An entry in the mscShelfFabricCardTestBroadcastTestResultsTable."
   INDEX {
      mscShelfIndex,
      mscShelfFabricCardIndex,
      mscShelfFabricCardTestIndex,
      mscShelfFabricCardTestBroadcastTestResultsTxCardIndex,
      mscShelfFabricCardTestBroadcastTestResultsRxCardIndex }
::= { mscShelfFabricCardTestBroadcastTestResultsTable 1 }

MscShelfFabricCardTestBroadcastTestResultsEntry ::= SEQUENCE {
   mscShelfFabricCardTestBroadcastTestResultsTxCardIndex
      Integer32,
   mscShelfFabricCardTestBroadcastTestResultsRxCardIndex
      Integer32,
   mscShelfFabricCardTestBroadcastTestResultsValue
      INTEGER }

mscShelfFabricCardTestBroadcastTestResultsTxCardIndex OBJECT-TYPE
   SYNTAX     Integer32 (0..15)
   ACCESS     not-accessible
   STATUS     mandatory
   DESCRIPTION
     "This variable represents the next to last index for the 
      mscShelfFabricCardTestBroadcastTestResultsTable."
::= { mscShelfFabricCardTestBroadcastTestResultsEntry 1 }

mscShelfFabricCardTestBroadcastTestResultsRxCardIndex OBJECT-TYPE
   SYNTAX     Integer32 (0..15)
   ACCESS     not-accessible
   STATUS     mandatory
   DESCRIPTION
     "This variable represents the final index for the 
      mscShelfFabricCardTestBroadcastTestResultsTable."
::= { mscShelfFabricCardTestBroadcastTestResultsEntry 2 }

mscShelfFabricCardTestBroadcastTestResultsValue OBJECT-TYPE
   SYNTAX     INTEGER  {
                 x(0),
                 n1(1),
                 n2(2) }
   ACCESS     read-only
   STATUS     mandatory
   DESCRIPTION
     "This variable represents an individual value for the
      mscShelfFabricCardTestBroadcastTestResultsTable."
::= { mscShelfFabricCardTestBroadcastTestResultsEntry 3 }

mscShelfFabricCardTestPingTestsTable OBJECT-TYPE
   SYNTAX     SEQUENCE OF MscShelfFabricCardTestPingTestsEntry
   ACCESS     not-accessible
   STATUS     mandatory
   DESCRIPTION
     "This attribute indicates the number of ping tests performed, indexed 
      by the slot numbers of the cards containing the fabric ports 
      involved. Each test attempts to transmit a single low-priority frame 
      from the transmitting fabric port to the receiving fabric port."
::= { mscShelfFabricCardTest 470 }

mscShelfFabricCardTestPingTestsEntry OBJECT-TYPE
   SYNTAX     MscShelfFabricCardTestPingTestsEntry
   ACCESS     not-accessible
   STATUS     mandatory
   DESCRIPTION
     "An entry in the mscShelfFabricCardTestPingTestsTable."
   INDEX {
      mscShelfIndex,
      mscShelfFabricCardIndex,
      mscShelfFabricCardTestIndex,
      mscShelfFabricCardTestPingTestsTxCardIndex,
      mscShelfFabricCardTestPingTestsRxCardIndex }
::= { mscShelfFabricCardTestPingTestsTable 1 }

MscShelfFabricCardTestPingTestsEntry ::= SEQUENCE {
   mscShelfFabricCardTestPingTestsTxCardIndex
      Integer32,
   mscShelfFabricCardTestPingTestsRxCardIndex
      Integer32,
   mscShelfFabricCardTestPingTestsValue
      Unsigned32 }

mscShelfFabricCardTestPingTestsTxCardIndex OBJECT-TYPE
   SYNTAX     Integer32 (0..15)
   ACCESS     not-accessible
   STATUS     mandatory
   DESCRIPTION
     "This variable represents the next to last index for the 
      mscShelfFabricCardTestPingTestsTable."
::= { mscShelfFabricCardTestPingTestsEntry 1 }

mscShelfFabricCardTestPingTestsRxCardIndex OBJECT-TYPE
   SYNTAX     Integer32 (0..15)
   ACCESS     not-accessible
   STATUS     mandatory
   DESCRIPTION
     "This variable represents the final index for the 
      mscShelfFabricCardTestPingTestsTable."
::= { mscShelfFabricCardTestPingTestsEntry 2 }

mscShelfFabricCardTestPingTestsValue OBJECT-TYPE
   SYNTAX     Unsigned32 (0..4294967295)
   ACCESS     read-only
   STATUS     mandatory
   DESCRIPTION
     "This variable represents an individual value for the
      mscShelfFabricCardTestPingTestsTable."
::= { mscShelfFabricCardTestPingTestsEntry 3 }

mscShelfFabricCardTestPingFailuresTable OBJECT-TYPE
   SYNTAX     SEQUENCE OF MscShelfFabricCardTestPingFailuresEntry
   ACCESS     not-accessible
   STATUS     mandatory
   DESCRIPTION
     "This attribute indicates the number of ping test failures detected, 
      indexed by the slot numbers of the cards containing the fabric ports 
      involved. Each failure represents a single low-priority frame that 
      was not successfully transmitted from the transmitting fabric port to 
      the receiving fabric port. The fabric card test does not terminate 
      automatically if a failure is detected."
::= { mscShelfFabricCardTest 471 }

mscShelfFabricCardTestPingFailuresEntry OBJECT-TYPE
   SYNTAX     MscShelfFabricCardTestPingFailuresEntry
   ACCESS     not-accessible
   STATUS     mandatory
   DESCRIPTION
     "An entry in the mscShelfFabricCardTestPingFailuresTable."
   INDEX {
      mscShelfIndex,
      mscShelfFabricCardIndex,
      mscShelfFabricCardTestIndex,
      mscShelfFabricCardTestPingFailuresTxCardIndex,
      mscShelfFabricCardTestPingFailuresRxCardIndex }
::= { mscShelfFabricCardTestPingFailuresTable 1 }

MscShelfFabricCardTestPingFailuresEntry ::= SEQUENCE {
   mscShelfFabricCardTestPingFailuresTxCardIndex
      Integer32,
   mscShelfFabricCardTestPingFailuresRxCardIndex
      Integer32,
   mscShelfFabricCardTestPingFailuresValue
      Unsigned32 }

mscShelfFabricCardTestPingFailuresTxCardIndex OBJECT-TYPE
   SYNTAX     Integer32 (0..15)
   ACCESS     not-accessible
   STATUS     mandatory
   DESCRIPTION
     "This variable represents the next to last index for the 
      mscShelfFabricCardTestPingFailuresTable."
::= { mscShelfFabricCardTestPingFailuresEntry 1 }

mscShelfFabricCardTestPingFailuresRxCardIndex OBJECT-TYPE
   SYNTAX     Integer32 (0..15)
   ACCESS     not-accessible
   STATUS     mandatory
   DESCRIPTION
     "This variable represents the final index for the 
      mscShelfFabricCardTestPingFailuresTable."
::= { mscShelfFabricCardTestPingFailuresEntry 2 }

mscShelfFabricCardTestPingFailuresValue OBJECT-TYPE
   SYNTAX     Unsigned32 (0..4294967295)
   ACCESS     read-only
   STATUS     mandatory
   DESCRIPTION
     "This variable represents an individual value for the
      mscShelfFabricCardTestPingFailuresTable."
::= { mscShelfFabricCardTestPingFailuresEntry 3 }


-- Shelf FabricCard/f cardPort/n
-- This component represents a physical port on a fabric card. A card 
-- port is the interface to the cards; it provides a pathway for the fabric 
-- card to send cells to the processor cards in the module and to 
-- receive cells sent to it from the processor cards.
-- 
-- A fabric card's CardPort components are created automatically, can 
-- not be added or deleted.

mscShelfFabricCardCardPort OBJECT IDENTIFIER ::= { mscShelfFabricCard 3 }



mscShelfFabricCardCardPortRowStatusTable OBJECT-TYPE
   SYNTAX     SEQUENCE OF MscShelfFabricCardCardPortRowStatusEntry
   ACCESS     not-accessible
   STATUS     mandatory
   DESCRIPTION
     "This entry controls the addition and deletion of 
      mscShelfFabricCardCardPort components."
::= { mscShelfFabricCardCardPort 1 }

mscShelfFabricCardCardPortRowStatusEntry OBJECT-TYPE
   SYNTAX     MscShelfFabricCardCardPortRowStatusEntry
   ACCESS     not-accessible
   STATUS     mandatory
   DESCRIPTION
     "A single entry in the table represents a single 
      mscShelfFabricCardCardPort component."
   INDEX {
      mscShelfIndex,
      mscShelfFabricCardIndex,
      mscShelfFabricCardCardPortIndex }
::= { mscShelfFabricCardCardPortRowStatusTable 1 }

MscShelfFabricCardCardPortRowStatusEntry ::= SEQUENCE {
   mscShelfFabricCardCardPortRowStatus
      RowStatus,
   mscShelfFabricCardCardPortComponentName
      DisplayString,
   mscShelfFabricCardCardPortStorageType
      StorageType,
   mscShelfFabricCardCardPortIndex
      Integer32 }

mscShelfFabricCardCardPortRowStatus OBJECT-TYPE
   SYNTAX     RowStatus 
   ACCESS     read-only
   STATUS     mandatory
   DESCRIPTION
     "This variable is used as the basis for SNMP naming of
      mscShelfFabricCardCardPort components.
      These components cannot be added nor deleted."
::= { mscShelfFabricCardCardPortRowStatusEntry 1 }

mscShelfFabricCardCardPortComponentName OBJECT-TYPE
   SYNTAX     DisplayString 
   ACCESS     read-only
   STATUS     mandatory
   DESCRIPTION
     "This variable provides the component's string name for
      use with the ASCII Console Interface"
::= { mscShelfFabricCardCardPortRowStatusEntry 2 }

mscShelfFabricCardCardPortStorageType OBJECT-TYPE
   SYNTAX     StorageType 
   ACCESS     read-only
   STATUS     mandatory
   DESCRIPTION
     "This variable represents the storage type value for the
      mscShelfFabricCardCardPort tables."
::= { mscShelfFabricCardCardPortRowStatusEntry 4 }

mscShelfFabricCardCardPortIndex OBJECT-TYPE
   SYNTAX     Integer32 (0..15)
   ACCESS     not-accessible
   STATUS     mandatory
   DESCRIPTION
     "This variable represents the index for the mscShelfFabricCardCardPort tables."
::= { mscShelfFabricCardCardPortRowStatusEntry 10 }

mscShelfFabricCardCardPortStateTable OBJECT-TYPE
   SYNTAX     SEQUENCE OF MscShelfFabricCardCardPortStateEntry
   ACCESS     not-accessible
   STATUS     mandatory
   DESCRIPTION
     "This group contains the three OSI State attributes and the six OSI 
      Status attributes. The descriptions generically indicate what each 
      attribute implies about the component. Note that not all the values 
      and state combinations described here are supported by every 
      component which uses this group. For component-specific 
      information and the valid state combinations, refer to NTP 241-
      7001-150, Passport Operations and Maintenance Guide."
::= { mscShelfFabricCardCardPort 10 }

mscShelfFabricCardCardPortStateEntry OBJECT-TYPE
   SYNTAX     MscShelfFabricCardCardPortStateEntry
   ACCESS     not-accessible
   STATUS     mandatory
   DESCRIPTION
     "An entry in the mscShelfFabricCardCardPortStateTable."
   INDEX {
      mscShelfIndex,
      mscShelfFabricCardIndex,
      mscShelfFabricCardCardPortIndex }
::= { mscShelfFabricCardCardPortStateTable 1 }

MscShelfFabricCardCardPortStateEntry ::= SEQUENCE {
   mscShelfFabricCardCardPortAdminState
      INTEGER,
   mscShelfFabricCardCardPortOperationalState
      INTEGER,
   mscShelfFabricCardCardPortUsageState
      INTEGER,
   mscShelfFabricCardCardPortAvailabilityStatus
      OCTET STRING,
   mscShelfFabricCardCardPortProceduralStatus
      OCTET STRING,
   mscShelfFabricCardCardPortControlStatus
      OCTET STRING,
   mscShelfFabricCardCardPortAlarmStatus
      OCTET STRING,
   mscShelfFabricCardCardPortStandbyStatus
      INTEGER,
   mscShelfFabricCardCardPortUnknownStatus
      INTEGER }

mscShelfFabricCardCardPortAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component.
      
      The OSI Status attributes, if supported by the component, may 
      provide more details, qualifying the state of the component."
   DEFVAL     { unlocked }
::= { mscShelfFabricCardCardPortStateEntry 1 }

mscShelfFabricCardCardPortOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle.
      
      The OSI Status attributes, if supported by the component, may 
      provide more details, qualifying the state of the component."
   DEFVAL     { disabled }
::= { mscShelfFabricCardCardPortStateEntry 2 }

mscShelfFabricCardCardPortUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time.
      
      The OSI Status attributes, if supported by the component, may 
      provide more details, qualifying the state of the component."
   DEFVAL     { idle }
::= { mscShelfFabricCardCardPortStateEntry 3 }

mscShelfFabricCardCardPortAvailabilityStatus OBJECT-TYPE
   SYNTAX     OCTET STRING (SIZE (2))
   ACCESS     read-only
   STATUS     mandatory
   DESCRIPTION
     "If supported by the component, this attribute indicates the OSI 
      Availability status of the component. Note that, even though it is 
      defined as a multi-valued set, at most one value is shown to the user.
      
      When no values are in the set, this indicates that either the attribute 
      is not supported or that none of the status conditions described 
      below are present.
      
      The value inTest indicates that the resource is undergoing a test 
      procedure. If adminState is locked or shuttingDown, the normal 
      users are precluded from using the resource and controlStatus is 
      reservedForTest. Tests that do not exclude additional users can be 
      present in any operational or administrative state but the 
      reservedForTest condition should not be present.
      
      The value failed indicates that the component has an internal fault 
      that prevents it from operating. The operationalState is disabled.
      
      The value dependency indicates that the component cannot operate 
      because some other resource on which it depends is unavailable. 
      The operationalState is disabled.
      
      The value powerOff indicates the resource requires power to be 
      applied and it is not powered on. The operationalState is disabled.
      
      The value offLine indicates the resource requires a routine 
      operation (either manual, automatic, or both) to be performed to 
      place it on-line and make it available for use. The operationalState 
      is disabled.
      
      The value offDuty indicates the resource is inactive in accordance 
      with a predetermined time schedule. In the absence of other 
      disabling conditions, the operationalState is enabled or disabled.
      
      The value degraded indicates the service provided by the 
      component is degraded in some way, such as in speed or operating 
      capacity. However, the resource remains available for service. The 
      operationalState is enabled.
      
      The value notInstalled indicates the resource is not present. The 
      operationalState is disabled.
      
      The value logFull is not used.

      Description of bits:
      inTest(0)
      failed(1)
      powerOff(2)
      offLine(3)
      offDuty(4)
      dependency(5)
      degraded(6)
      notInstalled(7)
      logFull(8)"
::= { mscShelfFabricCardCardPortStateEntry 4 }

mscShelfFabricCardCardPortProceduralStatus OBJECT-TYPE
   SYNTAX     OCTET STRING (SIZE (1))
   ACCESS     read-only
   STATUS     mandatory
   DESCRIPTION
     "If supported by the component, this attribute indicates the OSI 
      Procedural status of the component. Note that, even though it is 
      defined as a multi-valued set, at most one value is shown to the user.
      
      When no values are in the set, this indicates that either the attribute 
      is not supported or that none of the status conditions described 
      below are present.
      
      The value initializationRequired indicates (for a resource which 
      doesn't initialize autonomously) that initialization is required before 
      it can perform its normal functions, and this procedure has not been 
      initiated. The operationalState is disabled.
      
      The value notInitialized indicates (for a resource which does 
      initialize autonomously) that initialization is required before it can 
      perform its normal functions, and this procedure has not been 
      initiated. The operationalState may be enabled or disabled.
      
      The value initializing indicates that initialization has been initiated 
      but is not yet complete. The operationalState may be enabled or 
      disabled.
      
      The value reporting indicates the resource has completed some 
      processing operation and is notifying the results. The 
      operationalState is enabled.
      
      The value terminating indicates the component is in a termination 
      phase. If the resource doesn't reinitialize autonomously, 
      operationalState is disabled; otherwise it is enabled or disabled.

      Description of bits:
      initializationRequired(0)
      notInitialized(1)
      initializing(2)
      reporting(3)
      terminating(4)"
::= { mscShelfFabricCardCardPortStateEntry 5 }

mscShelfFabricCardCardPortControlStatus OBJECT-TYPE
   SYNTAX     OCTET STRING (SIZE (1))
   ACCESS     read-only
   STATUS     mandatory
   DESCRIPTION
     "If supported by the component, this attribute indicates the OSI 
      Control status of the component. Note that, even though it is defined 
      as a multi-valued set, at most one value is shown to the user.
      
      When no values are in the set, this indicates that either the attribute 
      is not supported or that none of the status conditions described 
      below are present.
      
      The value subjectToTest indicates the resource is available but tests 
      may be conducted simultaneously at unpredictable times, which 
      may cause it to exhibit unusual characteristics.
      
      The value partOfServicesLocked indicates that part of the service is 
      restricted from users of a resource. The adminState is unlocked.
      
      The value reservedForTest indicates that the component is 
      administratively unavailable because it is undergoing a test 
      procedure. The adminState is locked.
      
      The value suspended indicates that the service has been 
      administratively suspended.

      Description of bits:
      subjectToTest(0)
      partOfServicesLocked(1)
      reservedForTest(2)
      suspended(3)"
::= { mscShelfFabricCardCardPortStateEntry 6 }

mscShelfFabricCardCardPortAlarmStatus OBJECT-TYPE
   SYNTAX     OCTET STRING (SIZE (1))
   ACCESS     read-only
   STATUS     mandatory
   DESCRIPTION
     "If supported by the component, this attribute indicates the OSI 
      Alarm status of the component. Note that, even though it is defined 
      as a multi-valued set, at most one value is shown to the user.
      
      When no values are in the set, this indicates that either the attribute 
      is not supported or that none of the status conditions described 
      below are present.
      
      The value underRepair indicates the component is currently being 
      repaired. The operationalState is enabled or disabled.
      
      The value critical indicates one or more critical alarms are 
      outstanding against the component. Other, less severe, alarms may 
      also be outstanding. The operationalState is enabled or disabled.
      
      The value major indicates one or more major alarms are 
      outstanding against the component. Other, less severe, alarms may 
      also be outstanding. The operationalState is enabled or disabled.
      
      The value minor indicates one or more minor alarms are 
      outstanding against the component. Other, less severe, alarms may 
      also be outstanding. The operationalState is enabled or disabled.
      
      The value alarmOutstanding generically indicates that an alarm of 
      some severity is outstanding against the component.

      Description of bits:
      underRepair(0)
      critical(1)
      major(2)
      minor(3)
      alarmOutstanding(4)"
::= { mscShelfFabricCardCardPortStateEntry 7 }

mscShelfFabricCardCardPortStandbyStatus OBJECT-TYPE
   SYNTAX     INTEGER  {
                 hotStandby(0),
                 coldStandby(1),
                 providingService(2),
                 notSet(15) }
   ACCESS     read-only
   STATUS     mandatory
   DESCRIPTION
     "If supported by the component, this attribute indicates the OSI 
      Standby status of the component.
      
      The value notSet indicates that either the attribute is not supported 
      or that none of the status conditions described below are present. 
      Note that this is a non-standard value, used because the original 
      specification indicated this attribute was set-valued and thus, did not 
      provide a value to indicate that none of the other three are 
      applicable.
      
      The value hotStandby indicates that the resource is not providing 
      service but will be immediately able to take over the role of the 
      resource to be backed up, without initialization activity, and 
      containing the same information as the resource to be backed up.
      
      The value coldStandby indicates the resource is a backup for 
      another resource but will not be immediately able to take over the 
      role of the backed up resource and will require some initialization 
      activity.
      
      The value providingService indicates that this component, as a 
      backup resource, is currently backing up another resource."
   DEFVAL     { notSet }
::= { mscShelfFabricCardCardPortStateEntry 8 }

mscShelfFabricCardCardPortUnknownStatus OBJECT-TYPE
   SYNTAX     INTEGER  {
                 false(0),
                 true(1) }
   ACCESS     read-only
   STATUS     mandatory
   DESCRIPTION
     "This attribute indicates the OSI Unknown status of the component.
      
      The value false indicates that all of the other OSI State and Status 
      attribute values can be considered accurate.
      
      The value true indicates that the actual state of the component is not 
      known for sure."
   DEFVAL     { false }
::= { mscShelfFabricCardCardPortStateEntry 9 }

mscShelfFabricCardCardPortOperTable OBJECT-TYPE
   SYNTAX     SEQUENCE OF MscShelfFabricCardCardPortOperEntry
   ACCESS     not-accessible
   STATUS     mandatory
   DESCRIPTION
     "This attribute group contains operational attributes of a card port. 
      This information outlines what the card port is doing and why it is 
      doing it and is primarily intended for use in diagnosing the cause of 
      a port-related problem reported by the module."
::= { mscShelfFabricCardCardPort 11 }

mscShelfFabricCardCardPortOperEntry OBJECT-TYPE
   SYNTAX     MscShelfFabricCardCardPortOperEntry
   ACCESS     not-accessible
   STATUS     mandatory
   DESCRIPTION
     "An entry in the mscShelfFabricCardCardPortOperTable."
   INDEX {
      mscShelfIndex,
      mscShelfFabricCardIndex,
      mscShelfFabricCardCardPortIndex }
::= { mscShelfFabricCardCardPortOperTable 1 }

MscShelfFabricCardCardPortOperEntry ::= SEQUENCE {
   mscShelfFabricCardCardPortFailuresInEffect
      OCTET STRING,
   mscShelfFabricCardCardPortDependenciesInEffect
      OCTET STRING }

mscShelfFabricCardCardPortFailuresInEffect OBJECT-TYPE
   SYNTAX     OCTET STRING (SIZE (1))
   ACCESS     read-only
   STATUS     mandatory
   DESCRIPTION
     "This attribute indicates the hardware problems that prevent the 
      CardPort from using the fabric. It may contain any combination of 
      the following values.
      selfTest: The port has failed its self-test.
      crcError: The port has detected too many CRC errors.
      signalLoss: The serial link receiver is not receiving a signal. 
      That is, the electrical connection to the far end transmitter is not 
      valid.
      flowControlViolation: An unacceptable number of flow control 
      violation errors have occurred.
      synchronizationLoss: The serial link's phase or alignment is lost. 
      Therefore, the port's synchronization is lost.
      queueFull: The output queue is full.
      syncLoss: The card port has lost synchronization with the fabric 
      port.

      Description of bits:
      selfTest(0)
      crcError(1)
      signalLoss(2)
      flowControlViolation(3)
      synchronizationLoss(4)
      queueFull(5)
      syncLoss(6)"
::= { mscShelfFabricCardCardPortOperEntry 1 }

mscShelfFabricCardCardPortDependenciesInEffect OBJECT-TYPE
   SYNTAX     OCTET STRING (SIZE (1))
   ACCESS     read-only
   STATUS     mandatory
   DESCRIPTION
     "This attribute indicates the non-hardware problems that prevent the 
      port from using the associated fabric. It may contain the following 
      values:
      fabricLocked - The fabric card is locked.
      fabricDisabled - The fabric card is disabled.
      portDisabled - The corresponding fabric port is disabled.
      cardNotInserted - The corresponding processor card is not inserted.

      Description of bits:
      fabricLocked(0)
      fabricDisabled(1)
      portDisabled(2)
      cardNotInserted(3)"
::= { mscShelfFabricCardCardPortOperEntry 2 }

mscShelfFabricCardCardPortCardPortErrorsTable OBJECT-TYPE
   SYNTAX     SEQUENCE OF MscShelfFabricCardCardPortCardPortErrorsEntry
   ACCESS     not-accessible
   STATUS     mandatory
   DESCRIPTION
     "This attribute group indicates errors that the card port has detected 
      since the fabric card was last rebooted. This information is intended 
      for use in detecting and diagnosing port-related problems within a 
      module."
::= { mscShelfFabricCardCardPort 12 }

mscShelfFabricCardCardPortCardPortErrorsEntry OBJECT-TYPE
   SYNTAX     MscShelfFabricCardCardPortCardPortErrorsEntry
   ACCESS     not-accessible
   STATUS     mandatory
   DESCRIPTION
     "An entry in the mscShelfFabricCardCardPortCardPortErrorsTable."
   INDEX {
      mscShelfIndex,
      mscShelfFabricCardIndex,
      mscShelfFabricCardCardPortIndex }
::= { mscShelfFabricCardCardPortCardPortErrorsTable 1 }

MscShelfFabricCardCardPortCardPortErrorsEntry ::= SEQUENCE {
   mscShelfFabricCardCardPortSelfTestErrorCode
      Unsigned32,
   mscShelfFabricCardCardPortDataOrAddressCrcErrors
      Counter32,
   mscShelfFabricCardCardPortFlowControlViolationErrors
      Counter32,
   mscShelfFabricCardCardPortLivelinessErrors
      Counter32,
   mscShelfFabricCardCardPortLossOfSignalOrSyncErrors
      Counter32 }

mscShelfFabricCardCardPortSelfTestErrorCode OBJECT-TYPE
   SYNTAX     Unsigned32 (0..4294967295)
   ACCESS     read-only
   STATUS     mandatory
   DESCRIPTION
     "This attribute indicates the error code generated by the most recent 
      self-test of the port."
::= { mscShelfFabricCardCardPortCardPortErrorsEntry 1 }

mscShelfFabricCardCardPortDataOrAddressCrcErrors OBJECT-TYPE
   SYNTAX     Counter32 
   ACCESS     read-only
   STATUS     mandatory
   DESCRIPTION
     "This attribute indicates the packet data or address CRC errors 
      encountered on the port. The value wraps to zero when it exceeds 
      the maximum value."
::= { mscShelfFabricCardCardPortCardPortErrorsEntry 2 }

mscShelfFabricCardCardPortFlowControlViolationErrors OBJECT-TYPE
   SYNTAX     Counter32 
   ACCESS     read-only
   STATUS     mandatory
   DESCRIPTION
     "This attribute counts the flow control violations (that is 'threshold 
      exceeded errors') detected on the port. The value wraps to zero 
      when it exceeds the maximum value."
::= { mscShelfFabricCardCardPortCardPortErrorsEntry 3 }

mscShelfFabricCardCardPortLivelinessErrors OBJECT-TYPE
   SYNTAX     Counter32 
   ACCESS     read-only
   STATUS     mandatory
   DESCRIPTION
     "This attribute counts the liveliness errors detected on the card port. 
      Liveliness errors are failures to receive yellow cells within a certain 
      period of time. The value wraps to zero when it exceeds the 
      maximum value.
      
      Note: Yellow cells are special types of packets which are generated 
      by the fabric port and detected by the fabric card and the fabric port 
      in order to check the link liveness with the fabric card."
::= { mscShelfFabricCardCardPortCardPortErrorsEntry 4 }

mscShelfFabricCardCardPortLossOfSignalOrSyncErrors OBJECT-TYPE
   SYNTAX     Counter32 
   ACCESS     read-only
   STATUS     mandatory
   DESCRIPTION
     "This attribute counts the loss of signal or loss of synchronization 
      errors on the port that caused the port to fail. The value wraps to 
      zero when it exceeds the maximum value."
::= { mscShelfFabricCardCardPortCardPortErrorsEntry 5 }




-- 
-- Version and Compliance statements
-- 



-- Object-Group Statement:
-- A list of all current accessible leaf objects.

-- OBJECTS { mscShelfFabricCardAdminState,
--           mscShelfFabricCardCardPortProceduralStatus,
--           mscShelfCardFabricPortComponentName,
--           mscShelfFabricCardTestFabricSelfTestResults,
--           mscShelfFabricCardCardPortRowStatus,
--           mscShelfFabricCardTestBroadcastTestResultsValue,
--           mscShelfFabricCardOperatingTemperature,
--           mscShelfFabricCardRowStatus,
--           mscShelfFabricCardUtilization,
--           mscShelfCardFabricPortDependenciesInEffect,
--           mscShelfFabricCardProceduralStatus,
--           mscShelfFabricCardCardPortLivelinessErrors,
--           mscShelfFabricCardCardPortControlStatus,
--           mscShelfCardFabricPortOperationalState,
--           mscShelfFabricCardCardPortDependenciesInEffect,
--           mscShelfCardFabricPortLinkLivelinessErrors,
--           mscShelfCardFabricPortCardsAvailable,
--           mscShelfFabricCardTestStorageType,
--           mscShelfFabricCardCardPortUsageState,
--           mscShelfFabricCardFixedBankVersion,
--           mscShelfFabricCardUsageState,
--           mscShelfFabricCardTestAdminState,
--           mscShelfFabricCardTestTestsDone,
--           mscShelfFabricCardVoltageErrors,
--           mscShelfFabricCardComponentName,
--           mscShelfFabricCardCardPortOperationalState,
--           mscShelfFabricCardRecommendedVersionToInstall,
--           mscShelfFabricCardTestPingTestsValue,
--           mscShelfFabricCardTestRowStatus,
--           mscShelfFabricCardFailureCause,
--           mscShelfFabricCardSecondaryControlBusStatus,
--           mscShelfFabricCardCardPortAvailabilityStatus,
--           mscShelfCardFabricPortAvailabilityStatus,
--           mscShelfFabricCardTemperatureErrors,
--           mscShelfFabricCardTestCauseOfTermination,
--           mscShelfFabricCardWritableBankStatus,
--           mscShelfFabricCardOperationalState,
--           mscShelfCardFabricPortDataCorruptionErrors,
--           mscShelfFabricCardSerialNumber,
--           mscShelfFabricCardTestTimeRemaining,
--           mscShelfFabricCardTestPingFailuresValue,
--           mscShelfFabricCardSelfTestResults,
--           mscShelfCardFabricPortAlarmStatus,
--           mscShelfFabricCardTemperatureThreshold,
--           mscShelfCardFabricPortSwitchClockErrors,
--           mscShelfFabricCardVoltageBFeedDetected,
--           mscShelfFabricCardTestPortTestResultsValue,
--           mscShelfCardFabricPortPortProtocolErrors,
--           mscShelfCardFabricPortStandbyStatus,
--           mscShelfFabricCardDependencyInEffect,
--           mscShelfFabricCardSecondaryControlBusFabricBustapsValue,
--           mscShelfFabricCardTestElapsedTime,
--           mscShelfFabricCardCardPortComponentName,
--           mscShelfCardFabricPortStorageType,
--           mscShelfCardFabricPortCardsTxTo,
--           mscShelfFabricCardCardPortFlowControlViolationErrors,
--           mscShelfFabricCardCardPortAlarmStatus,
--           mscShelfFabricCardCardPortFailuresInEffect,
--           mscShelfCardFabricPortUnknownStatus,
--           mscShelfFabricCardAvailabilityStatus,
--           mscShelfCardFabricPortSelfTestErrorCode,
--           mscShelfFabricCardCardPortStandbyStatus,
--           mscShelfFabricCardActiveBank,
--           mscShelfFabricCardTestDuration,
--           mscShelfFabricCardSecondaryControlBusCardBustapsValue,
--           mscShelfFabricCardAlarmStatus,
--           mscShelfFabricCardTestUsageState,
--           mscShelfCardFabricPortControlStatus,
--           mscShelfCardFabricPortAdminState,
--           mscShelfFabricCardUnknownStatus,
--           mscShelfFabricCardStandbyStatus,
--           mscShelfFabricCardCardPortDataOrAddressCrcErrors,
--           mscShelfFabricCardTestComponentName,
--           mscShelfFabricCardStorageType,
--           mscShelfFabricCardProductCode,
--           mscShelfCardFabricPortRowStatus,
--           mscShelfFabricCardVoltageAFeedDetected,
--           mscShelfFabricCardBankOnShelfRestart,
--           mscShelfCardFabricPortPortHardwareErrors,
--           mscShelfCardFabricPortProceduralStatus,
--           mscShelfFabricCardTestOperationalState,
--           mscShelfCardFabricPortFailuresInEffect,
--           mscShelfFabricCardCardPortAdminState,
--           mscShelfFabricCardCardPortLossOfSignalOrSyncErrors,
--           mscShelfFabricCardCardPortStorageType,
--           mscShelfFabricCardWritableBankVersion,
--           mscShelfFabricCardCardPortUnknownStatus,
--           mscShelfFabricCardCardPortSelfTestErrorCode,
--           mscShelfCardFabricPortUsageState,
--           mscShelfCardFabricPortLivelinessErrors,
--           mscShelfFabricCardControlStatus }
-- STATUS  mandatory
-- DESCRIPTION
--   "A list of all current accessible leaf objects."

fabricGroup OBJECT IDENTIFIER ::= { fabricMIB 1 }
fabricGroupCA OBJECT IDENTIFIER ::= { fabricGroup 1 }
fabricGroupCA02 OBJECT IDENTIFIER ::= { fabricGroupCA 3 }
fabricGroupCA02A OBJECT IDENTIFIER ::= { fabricGroupCA02 2 }



-- Agent-Capabilities Statement:

-- PRODUCT-RELEASE "MscPassport Release 1.2 Fabric."
-- STATUS          mandatory
-- DESCRIPTION     "Carrier Passport Fabric MIB: MIB Version CA02A,
--                  Software Version CA02S9C."
-- SUPPORTS        Nortel-MsCarrier-MscPassport-FabricMIB
--    INCLUDES     { fabricGroupCA02A }

fabricCapabilities OBJECT IDENTIFIER ::= { fabricMIB 3 }
fabricCapabilitiesCA OBJECT IDENTIFIER ::= { fabricCapabilities 1 }
fabricCapabilitiesCA02 OBJECT IDENTIFIER ::= { fabricCapabilitiesCA 3 }
fabricCapabilitiesCA02A OBJECT IDENTIFIER ::= { fabricCapabilitiesCA02 2 }





END
