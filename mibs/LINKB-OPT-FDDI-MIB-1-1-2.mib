--  LinkBuilder 3GH Optional FDDI MIB for SMT 7
        --  Version 1.1.2
        --  Apr 27, 1994
 
        --  3Com Corporation
        --  5400 Bayfront Plaza
        --  Santa Clara, CA 95052-8145
        --  (408) 764-5000

        LINKB-OPT-FDDI-MIB-1-1-2 DEFINITIONS ::= BEGIN

        IMPORTS
	    enterprises, Counter    FROM RFC1155-SMI
            OBJECT-TYPE             FROM RFC-1212
            TRAP-TYPE               FROM RFC-1215
--            lb3gh                   FROM LB3GH-1-0-7
            FddiTimeNano,
            FddiSMTStationIdType,
            fddimibSMTStationId,
            fddimibSMTCFState,
            fddimibSMTPeerWrapFlag,
            fddimibMACSMTAddress,
            fddimibMACDaFlag,
            fddimibMACUnaDaFlag,
            fddimibMACFrameErrorFlag,
            fddimibMACFrameCts,
            fddimibMACErrorCts,
            fddimibMACLostCts,
            fddimibMACFrameErrorRatio,
            fddimibMACNotCopiedCts,
            fddimibMACCopiedCts,
            fddimibMACNotCopiedRatio,
            fddimibMACNotCopiedFlag,
            fddimibMACUpstreamNbr,
            fddimibMACOldUpstreamNbr,
            fddimibMACDownstreamNbr,
            fddimibMACOldDownstreamNbr,
            fddimibMACCurrentPath,
            fddimibMACAvailablePaths,
            fddimibMACRequestedPaths,
            fddimibPORTLerCutoff,
            fddimibPORTLerAlarm,
            fddimibPORTLerEstimate,
            fddimibPORTLemRejectCts,
            fddimibPORTLemCts,
            fddimibPORTLerFlag,
            fddimibPORTMyType,
            fddimibPORTConnectState,
            fddimibPORTNeighborType,
            fddimibPORTPCWithhold,
            fddimibPORTAvailablePaths,
            fddimibPORTCurrentPath,
            fddimibPORTRequestedPaths   FROM DRAFT-FDDI-MIB-VER-3-2;

	a3Com			OBJECT IDENTIFIER ::= { enterprises 43 }
	lb3gh			OBJECT IDENTIFIER ::= { a3Com 7 }
        lb3ghOptFddi    OBJECT IDENTIFIER ::= { lb3gh 2 }

        -- groups

        lbOptSMT        OBJECT IDENTIFIER ::= { lb3ghOptFddi 1 }
        lbOptMAC        OBJECT IDENTIFIER ::= { lb3ghOptFddi 2 }
        lbOptPATH       OBJECT IDENTIFIER ::= { lb3ghOptFddi 3 }
        lbOptPORT       OBJECT IDENTIFIER ::= { lb3ghOptFddi 4 }

        -- the lbOptSMT group

        -- the lbOptSMTTable

        lbOptSMTTable OBJECT-TYPE
            SYNTAX  SEQUENCE OF LbOptSMTEntry
            ACCESS  not-accessible
            STATUS  mandatory
            DESCRIPTION
                    "A list of optional SMT entries.  The number of entries
                    shall not exceed the value of snmpFddiSMTNumber."
            ::= { lbOptSMT 1 }

        lbOptSMTEntry OBJECT-TYPE
            SYNTAX  LbOptSMTEntry
            ACCESS  not-accessible
            STATUS  mandatory
            DESCRIPTION
                    "An optional SMT entry containing information common to
                    a given optional SMT."
            INDEX   { lbOptSMTIndex }
            ::= { lbOptSMTTable 1 }

        LbOptSMTEntry ::=
            SEQUENCE {
                lbOptSMTIndex
                    INTEGER,
                lbOptSMTManufacturerOUI
                    OCTET STRING,
                lbOptSMTManufacturerData
                    OCTET STRING,
                lbOptSMTHoldState
                    INTEGER,
                lbOptSMTSetCount
                    INTEGER,
                lbOptSMTLastSetStationId
                    FddiSMTStationIdType
            }

        lbOptSMTIndex OBJECT-TYPE
            SYNTAX  INTEGER (1..65535)
            ACCESS  read-only
            STATUS  mandatory
            DESCRIPTION
                    "A unique value for each SMT.  Its value ranges
                    between 1 and the value of snmpFddiSMTNumber.  The
                    value for each SMT must remain constant at least
                    from one re-initialization of the entity's network
                    management system to the next re-initialization."
            ::= { lbOptSMTEntry 1 }

        lbOptSMTManufacturerOUI OBJECT-TYPE
            SYNTAX  OCTET STRING (SIZE (3))
            ACCESS  read-only
            STATUS  mandatory
            DESCRIPTION
                    "The three octets of manufacturer data which make
                    up the manufacturerOUI component."
            REFERENCE
                    "ANSI { fddiSMT 16 }"
            ::= { lbOptSMTEntry 2 }

        lbOptSMTManufacturerData OBJECT-TYPE
            SYNTAX  OCTET STRING (SIZE (29))
            ACCESS  read-only
            STATUS  mandatory
            DESCRIPTION
                    "The 29 octets of manufacturer data which make up the
                    manufacturerData component."
            REFERENCE
                    "ANSI { fddiSMT 16 }"
            ::= { lbOptSMTEntry 3 }

        lbOptSMTHoldState OBJECT-TYPE
            SYNTAX  INTEGER {
                        not-implemented(1),     -- holding not implemented
                        not-holding(2),
                        holding-prm(3),         -- holding on primary
                        holding-sec(4)          -- holding on secondary
                    }
            ACCESS  read-only
            STATUS  mandatory
            DESCRIPTION
                    "This variable indicates the current state of the
                    Hold function. The value 'not-holding' is the
                    default and initial value.  The value must be set
                    to 'not-holding' as part of Active_Actions and
                    when the conditions causing 'holding-prm' or
                    'holding-sec' are no longer true. The value
                    'holding-prm' must be set when the condition
                    (notTR_Flag & not RE_Flag & (PC_LS=QLS | LEM_Fail
                    | TNE>NS_Max | (not LS_Flag & TPC > T_Out))) is
                    satisfied in state PC8:ACTIVE for the A Port. The
                    value 'holding-sec' must be set when the condition
                    (notTR_Flag & not RE_Flag & (PC_LS=QLS | LEM_Fail
                    | TNE>NS_Max | (not LS_Flag & TPC > T_Out))) is
                    satisfied in state PC8:ACTIVE for the B Port."
            REFERENCE
                    "ANSI { fddiSMT 43 }"
            ::= { lbOptSMTEntry 4 }

        lbOptSMTSetCount OBJECT-TYPE
            SYNTAX  INTEGER
            ACCESS  read-only
            STATUS  mandatory
            DESCRIPTION
                    "This variable is composed of a count incremented
                    in response to a Set operation on the MIB, and the
                    time of the change, however only the count is
                    reported here (refer to ANSI SMT 8.4.1)."
            REFERENCE
                    "ANSI { fddiSMT 53 }"
            ::= { lbOptSMTEntry 5 }

        lbOptSMTLastSetStationId OBJECT-TYPE
            SYNTAX  FddiSMTStationIdType
            ACCESS  read-only
            STATUS  mandatory
            DESCRIPTION
                    "The Station ID of the station that effected the last
                    change in the FDDI MIB."
            REFERENCE
                    "ANSI { fddiSMT 54 }"
            ::= { lbOptSMTEntry 6 }

        -- the lbOptMAC group

        -- the lbOptMACBridgeFunctionTable

        lbOptMACBridgeFunctionTable OBJECT-TYPE
            SYNTAX  SEQUENCE OF LbOptMACBridgeFunctionEntry
            ACCESS  not-accessible
            STATUS  mandatory
            DESCRIPTION
                    "A list of MAC bridge function entries."
            ::= { lbOptMAC 1 }

        lbOptMACBridgeFunctionEntry OBJECT-TYPE
            SYNTAX  LbOptMACBridgeFunctionEntry
            ACCESS  not-accessible
            STATUS  mandatory
            DESCRIPTION
                    "Bridge function information for a given MAC 
                    within a given SMT."
            INDEX   { lbOptMACBridgeFunctionSMTIndex, 
                    lbOptMACBridgeFunctionMACIndex }
            ::= { lbOptMACBridgeFunctionTable 1 }

        LbOptMACBridgeFunctionEntry ::=
            SEQUENCE {
                lbOptMACBridgeFunctionSMTIndex
                    INTEGER,
                lbOptMACBridgeFunctionMACIndex
                    INTEGER,
                lbOptMACBridgeFunctions
                    INTEGER
            }

        lbOptMACBridgeFunctionSMTIndex OBJECT-TYPE
            SYNTAX  INTEGER (1..65535)
            ACCESS  read-only
            STATUS  mandatory
            DESCRIPTION
                    "A unique value for each SMT.  Its value ranges
                    between 1 and the value of snmpFddiSMTNumber.  The
                    value for each SMT must remain constant at least
                    from one re-initialization of the entity's network
                    management system to the next re-initialization."
            ::= { lbOptMACBridgeFunctionEntry 1 }

        lbOptMACBridgeFunctionMACIndex OBJECT-TYPE
            SYNTAX  INTEGER (1..65535)
            ACCESS  read-only
            STATUS  mandatory
            DESCRIPTION
                    "Index variable for uniquely identifying the MAC
                    object instances."
            REFERENCE
                    "ANSI { fddiMAC 34 }"
            ::= { lbOptMACBridgeFunctionEntry 2 }

        lbOptMACBridgeFunctions OBJECT-TYPE
            SYNTAX  INTEGER (-1..7)
            ACCESS  read-only
            STATUS  mandatory
            DESCRIPTION
                    "Indicates the MAC's optional bridging functions.

                    The Value -1 is used to indicate that bridging is
                    not supported by this MAC.

                    The value is a sum.  This value initially takes
                    the value zero, then for each function present, 2
                    raised to a power is added to the sum.  The powers
                    are according to the following table:

                    Function    Power
                        tb      0 -- Transparent bridging active
                        sr      1 -- Src routing active
                        srt     2 -- Src routing transparent active
                    "
            REFERENCE
                    "ANSI { fddiMAC 12 }"
            ::= { lbOptMACBridgeFunctionEntry 3 }

        -- the lbOptMACTPriTable

        lbOptMACTPriTable OBJECT-TYPE
            SYNTAX  SEQUENCE OF LbOptMACTPriEntry
            ACCESS  not-accessible
            STATUS  mandatory
            DESCRIPTION
                    "A list of MAC T-Pri entries."
            ::= { lbOptMAC 2 }

        lbOptMACTPriEntry OBJECT-TYPE
            SYNTAX  LbOptMACTPriEntry
            ACCESS  not-accessible
            STATUS  mandatory
            DESCRIPTION
                    "A collection of T-Pri information for a given MAC within
                    a given SMT."
            INDEX   { lbOptMACTPriSMTIndex, lbOptMACTPriMACIndex }
            ::= { lbOptMACTPriTable 1 }

        LbOptMACTPriEntry ::=
            SEQUENCE {
                lbOptMACTPriSMTIndex
                    INTEGER,
                lbOptMACTPriMACIndex
                    INTEGER,
                lbOptMACTPri0
                    FddiTimeNano,
                lbOptMACTPri1
                    FddiTimeNano,
                lbOptMACTPri2
                    FddiTimeNano,
                lbOptMACTPri3
                    FddiTimeNano,
                lbOptMACTPri4
                    FddiTimeNano,
                lbOptMACTPri5
                    FddiTimeNano,
                lbOptMACTPri6
                    FddiTimeNano
            }

        lbOptMACTPriSMTIndex OBJECT-TYPE
            SYNTAX  INTEGER (1..65535)
            ACCESS  read-only
            STATUS  mandatory
            DESCRIPTION
                    "A unique value for each SMT.  Its value ranges
                    between 1 and the value of snmpFddiSMTNumber.  The
                    value for each SMT must remain constant at least
                    from one re-initialization of the entity's network
                    management system to the next re-initialization."
            ::= { lbOptMACTPriEntry 1 }

        lbOptMACTPriMACIndex OBJECT-TYPE
            SYNTAX  INTEGER (1..65535)
            ACCESS  read-only
            STATUS  mandatory
            DESCRIPTION
                    "Index variable for uniquely identifying the MAC
                    object instances."
            REFERENCE
                    "ANSI { fddiMAC 34 }"
            ::= { lbOptMACTPriEntry 2 }

        lbOptMACTPri0 OBJECT-TYPE
            SYNTAX  FddiTimeNano
            ACCESS  read-only
            STATUS  mandatory
            DESCRIPTION
                    "This attribute is an unsigned twos-complement T_pri
                    threshold as described in the MAC standard converted
                    to non-twos-complement form and reported in 1 ns units."
            REFERENCE
                    "ANSI { fddiMAC 56 }"
            ::= { lbOptMACTPriEntry 3 }

        lbOptMACTPri1 OBJECT-TYPE
            SYNTAX  FddiTimeNano
            ACCESS  read-only
            STATUS  mandatory
            DESCRIPTION
                    "This attribute is an unsigned twos-complement T_pri
                    threshold as described in the MAC standard converted
                    to non-twos-complement form and reported in 1 ns units."
            REFERENCE
                    "ANSI { fddiMAC 57 }"
            ::= { lbOptMACTPriEntry 4 }

        lbOptMACTPri2 OBJECT-TYPE
            SYNTAX  FddiTimeNano
            ACCESS  read-only
            STATUS  mandatory
            DESCRIPTION
                    "This attribute is an unsigned twos-complement T_pri
                    threshold as described in the MAC standard converted
                    to non-twos-complement form and reported in 1 ns units."
            REFERENCE
                    "ANSI { fddiMAC 58 }"
            ::= { lbOptMACTPriEntry 5 }

        lbOptMACTPri3 OBJECT-TYPE
            SYNTAX  FddiTimeNano
            ACCESS  read-only
            STATUS  mandatory
            DESCRIPTION
                    "This attribute is an unsigned twos-complement T_pri
                    threshold as described in the MAC standard converted
                    to non-twos-complement form and reported in 1 ns units."
            REFERENCE
                    "ANSI { fddiMAC 59 }"
            ::= { lbOptMACTPriEntry 6 }

        lbOptMACTPri4 OBJECT-TYPE
            SYNTAX  FddiTimeNano
            ACCESS  read-only
            STATUS  mandatory
            DESCRIPTION
                    "This attribute is an unsigned twos-complement T_pri
                    threshold as described in the MAC standard converted
                    to non-twos-complement form and reported in 1 ns units."
            REFERENCE
                    "ANSI { fddiMAC 60 }"
            ::= { lbOptMACTPriEntry 7 }

        lbOptMACTPri5 OBJECT-TYPE
            SYNTAX  FddiTimeNano
            ACCESS  read-only
            STATUS  mandatory
            DESCRIPTION
                    "This attribute is an unsigned twos-complement T_pri
                    threshold as described in the MAC standard converted
                    to non-twos-complement form and reported in 1 ns units."
            REFERENCE
                    "ANSI { fddiMAC 61 }"
            ::= { lbOptMACTPriEntry 8 }

        lbOptMACTPri6 OBJECT-TYPE
            SYNTAX  FddiTimeNano
            ACCESS  read-only
            STATUS  mandatory
            DESCRIPTION
                    "This attribute is an unsigned twos-complement T_pri
                    threshold as described in the MAC standard converted
                    to non-twos-complement form and reported in 1 ns units."
            REFERENCE
                    "ANSI { fddiMAC 62 }"
            ::= { lbOptMACTPriEntry 9 }

        -- the lbOptPATH group

        -- the lbOptPATHRingTable

        lbOptPATHRingTable OBJECT-TYPE
            SYNTAX  SEQUENCE OF LbOptPATHRingEntry
            ACCESS  not-accessible
            STATUS  mandatory
            DESCRIPTION
                    "A list of PATH ring entries."
            ::= { lbOptPATH 1 }

        lbOptPATHRingEntry OBJECT-TYPE
            SYNTAX  LbOptPATHRingEntry
            ACCESS  not-accessible
            STATUS  mandatory
            DESCRIPTION
                    "Ring latency, trace status, and T-Rmode information for a
                    given PATH within a given SMT."
            INDEX   { lbOptPATHRingSMTIndex, lbOptPATHRingPATHIndex }
            ::= { lbOptPATHRingTable 1 }

        LbOptPATHRingEntry ::=
            SEQUENCE {
                lbOptPATHRingSMTIndex
                    INTEGER,
                lbOptPATHRingPATHIndex
                    INTEGER,
                lbOptPATHRingLatency
                    FddiTimeNano,
                lbOptPATHTraceStatus
                    INTEGER,
                lbOptPATHT-Rmode
                    FddiTimeNano
            }

        lbOptPATHRingSMTIndex OBJECT-TYPE
            SYNTAX  INTEGER (1..65535)
            ACCESS  read-only
            STATUS  mandatory
            DESCRIPTION
                    "A unique value for each SMT.  Its value ranges
                    between 1 and the value of snmpFddiSMTNumber.  The
                    value for each SMT must remain constant at least
                    from one re-initialization of the entity's network
                    management system to the next re-initialization."
            ::= { lbOptPATHRingEntry 1 }

        lbOptPATHRingPATHIndex OBJECT-TYPE
            SYNTAX  INTEGER (1..255)
            ACCESS  read-only
            STATUS  mandatory
            DESCRIPTION
                    "Index variable for uniquely identifying the
                    primary, secondary and local PATH object
                    instances. Local PATH object instances are
                    represented with integer values 3 to 255."
            REFERENCE
                    "ANSI { fddiPATH 11 }"
            ::= { lbOptPATHRingEntry 2 }

        lbOptPATHRingLatency OBJECT-TYPE
            SYNTAX  FddiTimeNano
            ACCESS  read-write
            STATUS  mandatory
            DESCRIPTION
                    "Gives the total accumulated latency of the ring 
                    associated with this path.  May be measured directly
                    by the station or calculated by a management station.
                    Values of this object are reported in 1 ns units."
            REFERENCE
                    "ANSI { fddiPATH 13 }"
            ::= { lbOptPATHRingEntry 3 }

        lbOptPATHTraceStatus OBJECT-TYPE
            SYNTAX  INTEGER (0..15)
            ACCESS  read-only
            STATUS  mandatory
            DESCRIPTION
                    "This attribute indicates the current trace status of
                    the path.

                    The value is a sum which represents all of the trace
                    status information which applies.  This value initially
                    takes the value zero, then for each condition which
                    applies, 2 raised to a power is added to the sum.  the
                    powers are according to the following table:

                    TraceStatus    Power
                  traceinitiated    0
                tracepropragated    1
                 traceterminated    2
                    tracetimeout    3"

            REFERENCE
                    "ANSI { fddiPATH 14 }"
            ::= { lbOptPATHRingEntry 4 }

        lbOptPATHT-Rmode OBJECT-TYPE
            SYNTAX  FddiTimeNano
            ACCESS  read-write
            STATUS  mandatory
            DESCRIPTION
                    "Used by RMT to limit the duration of restricted dialogs
                    on a path.  This object is reported in 1 ns units."
            REFERENCE
                    "ANSI { fddiPATH 19 }"
            ::= { lbOptPATHRingEntry 5 }

        -- the lbOptPATHSbaTable

        lbOptPATHSbaTable OBJECT-TYPE
            SYNTAX  SEQUENCE OF LbOptPATHSbaEntry
            ACCESS  not-accessible
            STATUS  mandatory
            DESCRIPTION
                    "A list of PATH Sba entries."
            ::= { lbOptPATH 2 }

        lbOptPATHSbaEntry OBJECT-TYPE
            SYNTAX  LbOptPATHSbaEntry
            ACCESS  not-accessible
            STATUS  mandatory
            DESCRIPTION
                    "Sba information for a given PATH within a given SMT."
            INDEX   { lbOptPATHSbaSMTIndex, lbOptPATHSbaPATHIndex }
            ::= { lbOptPATHSbaTable 1 }

        LbOptPATHSbaEntry ::=
            SEQUENCE {
                lbOptPATHSbaSMTIndex
                    INTEGER,
                lbOptPATHSbaPATHIndex
                    INTEGER,
                lbOptPATHSbaPayload
                    INTEGER,
                lbOptPATHSbaOverhead
                    INTEGER,
                lbOptPATHSbaAvailable
                    INTEGER
            }

        lbOptPATHSbaSMTIndex OBJECT-TYPE
            SYNTAX  INTEGER (1..65535)
            ACCESS  read-only
            STATUS  mandatory
            DESCRIPTION
                    "A unique value for each SMT.  Its value ranges
                    between 1 and the value of snmpFddiSMTNumber.  The
                    value for each SMT must remain constant at least
                    from one re-initialization of the entity's network
                    management system to the next re-initialization."
            ::= { lbOptPATHSbaEntry 1 }

        lbOptPATHSbaPATHIndex OBJECT-TYPE
            SYNTAX  INTEGER (1..255)
            ACCESS  read-only
            STATUS  mandatory
            DESCRIPTION
                    "Index variable for uniquely identifying the
                    primary, secondary and local PATH object
                    instances. Local PATH object instances are
                    represented with integer values 3 to 255."
            REFERENCE
                    "ANSI { fddiPATH 11 }"
            ::= { lbOptPATHSbaEntry 2 }

        lbOptPATHSbaPayload OBJECT-TYPE
            SYNTAX  INTEGER (0..1562)
            ACCESS  read-write
            STATUS  mandatory
            DESCRIPTION
                    "The payload portion of the Synchronous Bandwidth
                    Allocation for thi path.  This value represents the
                    maximum number of bytes of data allocated for
                    transmission per 125 microseconds."
            REFERENCE
                    "ANSI { fddiPATH 15 }"
            ::= { lbOptPATHSbaEntry 3 }

        lbOptPATHSbaOverhead OBJECT-TYPE
            SYNTAX  INTEGER
            ACCESS  read-write
            STATUS  mandatory
            DESCRIPTION
                    "The overhead portion of the Synchronous Bandwith
                    Allocation for this path.  This value repersents the
                    maximum number of bytes overhead (token capture, frame
                    header, etc.) used pre negotiated Target Token Rotation
                    Time (T_neg)."
            REFERENCE
                    "ANSI { fddiPATH 16 }"
            ::= { lbOptPATHSbaEntry 4 }

        lbOptPATHSbaAvailable OBJECT-TYPE
            SYNTAX  INTEGER (0..12500000)
            ACCESS  read-write
            STATUS  mandatory
            DESCRIPTION
                    "This value is the maximum Synchronous Bandwith available
                    for a path in bytes per second."
            REFERENCE
                    "ANSI { fddiPATH 20 }"
            ::= { lbOptPATHSbaEntry 5 }

        -- the lbOptPORT group

        -- the lbOptPORTTable

        lbOptPORTTable OBJECT-TYPE
            SYNTAX  SEQUENCE OF LbOptPORTEntry
            ACCESS  not-accessible
            STATUS  mandatory
            DESCRIPTION
                    "A list of optional PORT entries."
            ::= { lbOptPORT 1 }

        lbOptPORTEntry OBJECT-TYPE
            SYNTAX  LbOptPORTEntry
            ACCESS  not-accessible
            STATUS  mandatory
            DESCRIPTION
                    "MAC loop time and EB error count information for a 
                    given PORT within a given SMT."
            INDEX   { lbOptPORTSMTIndex, lbOptPORTIndex }
            ::= { lbOptPORTTable 1 }

        LbOptPORTEntry ::=
            SEQUENCE {
                lbOptPORTSMTIndex
                    INTEGER,
                lbOptPORTIndex
                    INTEGER,
                lbOptPORTMACLoopTime
                    FddiTimeNano,
                lbOptPORTEBErrorCt
                    Counter
            }

        lbOptPORTSMTIndex OBJECT-TYPE
            SYNTAX  INTEGER (1..65535)
            ACCESS  read-only
            STATUS  mandatory
            DESCRIPTION
                    "A unique value for each SMT.  Its value ranges
                    between 1 and the value of snmpFddiSMTNumber.  The
                    value for each SMT must remain constant at least
                    from one re-initialization of the entity's network
                    management system to the next re-initialization."
            ::= { lbOptPORTEntry 1 }

        lbOptPORTIndex OBJECT-TYPE
            SYNTAX  INTEGER (1..65535)
            ACCESS  read-only
            STATUS  mandatory
            DESCRIPTION
                    "Index variable for uniquely identifying the PORT
                    object instances."
            REFERENCE
                    "ANSI { fddiPORT 29 }"
            ::= { lbOptPORTEntry 2 }

        lbOptPORTMACLoopTime OBJECT-TYPE
            SYNTAX  FddiTimeNano
            ACCESS  read-write
            STATUS  mandatory
            DESCRIPTION
                    "This attribute controls the value used for T_Next(9)
                    (see 9.4.4.2.3).  This object is reported in 1 ns 
                    units."
            REFERENCE
                    "ANSI { fddiPORT 21 }"
            ::= { lbOptPORTEntry 3 }

        lbOptPORTEBErrorCt OBJECT-TYPE
            SYNTAX  Counter
            ACCESS  read-only
            STATUS  mandatory
            DESCRIPTION
                    "A count that should as closely as possible match the 
                    times an Elasticity Buffer Error has occurred while in
                    active line state."
            REFERENCE
                    "ANSI { fddiPORT 41 }"
            ::= { lbOptPORTEntry 4 }

        -- the lbOptPORTLSTable

        lbOptPORTLSTable OBJECT-TYPE
            SYNTAX  SEQUENCE OF LbOptPORTLSEntry
            ACCESS  not-accessible
            STATUS  mandatory
            DESCRIPTION
                    "A list of optional PORT line state entries."
            ::= { lbOptPORT 2 }

        lbOptPORTLSEntry OBJECT-TYPE
            SYNTAX  LbOptPORTLSEntry
            ACCESS  not-accessible
            STATUS  mandatory
            DESCRIPTION
                    "Maintenance line state and PC line state information
                    for a given PORT within a given SMT."
            INDEX   { lbOptPORTLSSMTIndex, lbOptPORTLSPORTIndex }
            ::= { lbOptPORTLSTable 1 }

        LbOptPORTLSEntry ::=
            SEQUENCE {
                lbOptPORTLSSMTIndex
                    INTEGER,
                lbOptPORTLSPORTIndex
                    INTEGER,
                lbOptPORTMaintLS
                    INTEGER,
                lbOptPORTPCLS
                    INTEGER
            }

        lbOptPORTLSSMTIndex OBJECT-TYPE
            SYNTAX  INTEGER (1..65535)
            ACCESS  read-only
            STATUS  mandatory
            DESCRIPTION
                    "A unique value for each SMT.  Its value ranges
                    between 1 and the value of snmpFddiSMTNumber.  The
                    value for each SMT must remain constant at least
                    from one re-initialization of the entity's network
                    management system to the next re-initialization."
            ::= { lbOptPORTLSEntry 1 }

        lbOptPORTLSPORTIndex OBJECT-TYPE
            SYNTAX  INTEGER (1..65535)
            ACCESS  read-only
            STATUS  mandatory
            DESCRIPTION
                    "Index variable for uniquely identifying the PORT
                    object instances."
            REFERENCE
                    "ANSI { fddiPORT 29 }"
            ::= { lbOptPORTLSEntry 2 }

        lbOptPORTMaintLS OBJECT-TYPE
            SYNTAX  INTEGER {
                        quiet(1),
                        idle(2),
                        master(3),
                        halt(4),
                        receive-active(5),
                        receive-unknown(6),
                        receive-noise(7)
                    }
            ACCESS  read-write
            STATUS  mandatory
            DESCRIPTION
                    "The PORT Maintenance Line State specifies the line state
                    (Maint_LS) to be transmitted when the PCM state machine 
                    for the port is in state PC9 Maint."
            REFERENCE
                    "ANSI { fddiPORT 31 }"
            ::= { lbOptPORTLSEntry 3 }

        lbOptPORTPCLS OBJECT-TYPE
            SYNTAX  INTEGER {
                        quiet(1),
                        idle(2),
                        master(3),
                        halt(4),
                        receive-active(5),
                        receive-unknown(6),
                        receive-noise(7)
                    }
            ACCESS  read-only
            STATUS  mandatory
            DESCRIPTION
                    "This attribute indicates the line state (PC_LS) received
                    by the port."
            REFERENCE
                    "ANSI { fddiPORT 34 }"
            ::= { lbOptPORTLSEntry 4 }

        -- traps

        -- SMT events

        lbOptSMTHoldCondition TRAP-TYPE
            ENTERPRISE  lb3ghOptFddi
            VARIABLES   { fddimibSMTStationId,
                        lbOptSMTHoldState }
            DESCRIPTION
                    "Generated when fddiSMTHoldState (fddimibSMTHoldState)
                    assumes the state holding-prm or holding-sec.  This 
                    notification is a Condition in the Status Report
                    Protocol (see 7.2.7 and 8.3)."
            REFERENCE
                    "ANSI { fddiSMT 71 }"
            ::= 1

        lbOptSMTPeerWrapCondition TRAP-TYPE
            ENTERPRISE  lb3ghOptFddi
            VARIABLES   { fddimibSMTStationId,
                        fddimibSMTCFState,
                        fddimibSMTPeerWrapFlag }
            DESCRIPTION
                    "This condition is active when fddiSMTPeerWrapFlag 
                    (fddimibSMTPeerWrapFlag) is set.  This notification is
                    a Condition in the Status Report Protocol (see 7.2.7 
                    and 8.3)."
            REFERENCE
                    "ANSI { fddiSMT 72 }"
            ::= 2

        -- MAC events

        lbOptMACDuplicateAddressCondition TRAP-TYPE
            ENTERPRISE  lb3ghOptFddi
            VARIABLES   { fddimibSMTStationId,
                        fddimibMACSMTAddress,
                        fddimibMACUpstreamNbr,
                        fddimibMACDaFlag,
                        fddimibMACUnaDaFlag }
            DESCRIPTION
                    "This condition is active when either fddiMACDA-Flag
                    (fddimibMACDaFlag) or fddiMACUNDA-Flag 
                    (fddimibMACUnaDaFlag) is set.  This event is handled
                    as a Condition in the Status Report Protocol (see 7.2.7
                    and 8.3)."
            REFERENCE
                    "ANSI { fddiMAC 140 }"
            ::= 3

        lbOptMACFrameErrorCondition TRAP-TYPE
            ENTERPRISE  lb3ghOptFddi
            VARIABLES   { fddimibSMTStationId,
                        fddimibMACFrameErrorFlag,
                        fddimibMACFrameCts,
                        fddimibMACErrorCts,
                        fddimibMACLostCts,
                        fddimibMACFrameErrorRatio }
            DESCRIPTION
                    "Generated when the fddiMACFrameErrorRatio 
                    (fddimibMACFrameErrorRatio) is greater than or equal
                    to fddiMACFrameErrorThreshold 
                    (fddimibMACFrameErrorThreshold).  This event is handled
                    as a Condition in the Status Report Protocol (see 7.2.7
                    and 8.3)."
            REFERENCE
                    "ANSI { fddiMAC 141 }"
            ::= 4

        lbOptMACNotCopiedCondition TRAP-TYPE
            ENTERPRISE  lb3ghOptFddi
            VARIABLES   { fddimibSMTStationId,
                        fddimibMACNotCopiedCts,
                        fddimibMACCopiedCts,
                        fddimibMACNotCopiedRatio,
                        fddimibMACNotCopiedFlag }
            DESCRIPTION
                    "Generated when the fddiMACNotCopiedRatio 
                    (fddimibMACNotCopiedRatio) is greater than or equal to 
                    the fddiMACNotCopiedThreshold (lbOptMACNotCopiedThreshold).
                    This event is handled as a Condition in the Status Report 
                    Protocol (see 7.2.7 and 8.3)."
            REFERENCE
                    "ANSI { fddiMAC 142 }"
            ::= 5

        lbOptMACNeighborChangeEvent TRAP-TYPE
            ENTERPRISE  lb3ghOptFddi
            VARIABLES   { fddimibSMTStationId,
                        fddimibMACUpstreamNbr,
                        fddimibMACOldUpstreamNbr,
                        fddimibMACDownstreamNbr,
                        fddimibMACOldDownstreamNbr,
                        fddimibMACCurrentPath,
                        fddimibMACSMTAddress }
            DESCRIPTION
                    "Generated when a change in a MAC's upstream neighbor
                    address or downstream neighbor address is detected.
                    (see 7.2.7 and 8.3)."
            REFERENCE
                    "ANSI { fddiMAC 143 }"
            ::= 6

        lbOptMACPathChangeEvent TRAP-TYPE
            ENTERPRISE  lb3ghOptFddi
            VARIABLES   { fddimibSMTStationId,
                        fddimibMACAvailablePaths,
                        fddimibMACCurrentPath,
                        fddimibMACRequestedPaths }
            DESCRIPTION
                    "This event is generated when the value of the 
                    fddiMACCurrentPath (fddimibMACCurrentPath) changes.
                    This event shall be supressed if the value changes
                    from isolated to local or local to isolated (see
                    7.2.7 and 8.3)."
            REFERENCE
                    "ANSI { fddiMAC 144 }"
            ::= 7

        -- PORT events

        lbOptPORTLerCondition TRAP-TYPE
            ENTERPRISE  lb3ghOptFddi
            VARIABLES   { fddimibSMTStationId,
                        fddimibPORTLerCutoff,
                        fddimibPORTLerAlarm,
                        fddimibPORTLerEstimate,
                        fddimibPORTLemRejectCts,
                        fddimibPORTLemCts,
                        fddimibPORTLerFlag }
            DESCRIPTION
                    "This condition becomes active when the value of 
                    fddiPORTLer-Estimate (fddimibPORTLerEstimate)
                    is less than or equal to fddiPORTLer-Alarm
                    (fddimibPORTLerAlarm).  This will be reported
                    with the Status Report Frames (SRF) (see 7.2.7 
                    and 8.3)."
            REFERENCE
                    "ANSI { fddiPORT 80 }"
            ::= 8

        lbOptPORTUndesiredConnAttemptEvent TRAP-TYPE
            ENTERPRISE  lb3ghOptFddi
            VARIABLES   { fddimibSMTStationId,
                        fddimibPORTMyType,
                        fddimibPORTConnectState,
                        fddimibPORTNeighborType,
                        fddimibPORTPCWithhold }
            DESCRIPTION
                    "Generated when an undesired connection attempt has
                    been made (see 5.2.4, 7.2.7, and 8.3)."
            REFERENCE
                    "ANSI { fddiPORT 81 }"
            ::= 9

        lbOptPORTEBErrorCondition TRAP-TYPE
            ENTERPRISE  lb3ghOptFddi
            VARIABLES   { fddimibSMTStationId,
                        lbOptPORTEBErrorCt }
            DESCRIPTION
                    "Generated when the Elasticity Buffer Error-Ct
                    (lbOptPORTEBErrorCt) increments.  This is handled
                    as a condition in the Status Report Protocol.  It
                    is generated when an increment occurs in the 
                    station's sampling period (see 7.2.7 and 8.3)."
            REFERENCE
                    "ANSI { fddiPORT 82 }"
            ::= 10

        lbOptPORTPathChangeEvent TRAP-TYPE
            ENTERPRISE  lb3ghOptFddi
            VARIABLES   { fddimibSMTStationId,
                        fddimibPORTAvailablePaths,
                        fddimibPORTCurrentPath,
                        fddimibPORTRequestedPaths,
                        fddimibPORTMyType,
                        fddimibPORTNeighborType }
            DESCRIPTION
                    "This event is generated when the value of the 
                    fddiPORTCurrentPath (lbOptPORTCurrentPath)
                    changes.  This event shall be surpressed if the
                    value changes from isolated to local or local
                    to isolated (see 7.2.7 and 8.3)."
            REFERENCE
                    "ANSI { fddiPORT 83 }"
            ::= 11

        END
