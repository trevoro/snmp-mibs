-- *****************************************************************
-- CISCO-IETF-DHCP-SERVER-CAPABILITY.my:  Cisco IETF DHCP Server 
-- MIB AGENT-CAPABILITIES
--
-- January 2005, Shobana Sampath
--
-- Copyright (c) 2005 by Cisco Systems, Inc. 
-- All rights reserved. 
-- *****************************************************************

CISCO-IETF-DHCP-SERVER-CAPABILITY DEFINITIONS ::= BEGIN

IMPORTS
        MODULE-IDENTITY
                FROM SNMPv2-SMI
        AGENT-CAPABILITIES
                FROM SNMPv2-CONF
        ciscoAgentCapability
                FROM CISCO-SMI;

ciscoIetfDhcpSrvCapability MODULE-IDENTITY
        LAST-UPDATED    "200505240000Z"
        ORGANIZATION    "Cisco Systems, Inc."
        CONTACT-INFO
                "       Cisco Systems
                        Customer Service

                Postal: 170 W Tasman Drive
                        San Jose, CA  95134
                        USA

                   Tel: +1 800 553-NETS

                E-mail: cs-dhcp-mib@cisco.com"
        DESCRIPTION
           "Agent capabilities for the CISCO-IETF-DHCP-SERVER-MIB."

        REVISION  "200505240000Z"
        DESCRIPTION
           "Initial version of this MIB module."
        ::= { ciscoAgentCapability 439 }

ciscoIetfDhcpServerCapabilityV62R00 AGENT-CAPABILITIES

PRODUCT-RELEASE "Cisco CNS Network Registrar 6.2"
        STATUS          current
        DESCRIPTION     
           "CISCO-IETF-DHCP-SERVER-MIB capabilities for
            Cisco CNS Network Registrar 6.2"

        SUPPORTS    CISCO-IETF-DHCP-SERVER-MIB
        INCLUDES    { cDhcpv4SrvSystemObjects, 
                      cDhcpv4CounterObjects }

        VARIATION   cBootpCountRequests
        ACCESS      not-implemented      
        DESCRIPTION "Not supported."

        VARIATION   cBootpCountInvalids 
        ACCESS      not-implemented      
        DESCRIPTION "Not supported."

        VARIATION   cBootpCountReplies
        ACCESS      not-implemented      
        DESCRIPTION "Not supported."

        VARIATION   cBootpCountDropUnknownClients
        ACCESS      not-implemented      
        DESCRIPTION "Not supported."

        VARIATION   cBootpCountDropNotServingSubnet
        ACCESS      not-implemented      
        DESCRIPTION "Not supported."
        
        VARIATION   cDhcpv4CountInvalids
        ACCESS      not-implemented      
        DESCRIPTION "Not supported."

        VARIATION   cDhcpv4CountDropUnknownClient
        ACCESS      not-implemented      
        DESCRIPTION "Not supported."

        VARIATION   cDhcpv4CountDropNotServingSubnet
        ACCESS      not-implemented      
        DESCRIPTION "Not supported."

::= { ciscoIetfDhcpSrvCapability 1 }

END
