-- file:  d5.mib

-- SYMPLEX PRIVATE MIB EXTENTION FOR DATAMIZER 5 and 6 SERIES  VERSION 05.04

-- MIB Revision History
--         MAT    04/26/99 05.04  Official release of previous (5.03) special.
--         MAT    03/25/99 05.03  Special for Controlware to correct trap
--                                issues (varbinding of Symplex traps.)
--         MAT    09/15/98 05.02  Clean-up of DirectRoute references.
--         MAT    08/13/98 05.01  Enhanced statistics reporting.
--         MAT    10/28/97 05.00  Originally created for 5.00 (from 4.01)

-- Copyright (c) 1996 by Symplex Communications, Inc.
-- All Rights Reserved.
-- Reproduction of this document is authorized on condition 
-- that the foregoing copyright notice is included.

-- Symplex Communications
-- 5 Research Dr.
-- Ann Arbor, MI  48103
-- (313)995-1555

-- Questions or comments should be directed to:
-- support@symplex.com



-- 1. Introduction

-- This memo describes the variables that are implemented for Symplex
-- Communications, Inc.  set of products.  The document relies upon the
-- Structure of Management Information (SMI), RFC1155.  It is presented in
-- a format described in RFC1212, the Concise MIB document; and RFC1215, 
-- Defining Traps for SNMP.
-- 
-- This  document describes the Symplex Management Information Base (MIB)
-- variables.


-- 2. Object Definitions

D5-MIB DEFINITIONS ::= BEGIN

IMPORTS
                    enterprises, IpAddress, Counter
                    FROM RFC1155-SMI
                    OBJECT-TYPE
                    FROM RFC-1212
                                        snmp, sysUpTime, ifIndex, sysDescr, ipAdEntAddr
                                        FROM RFC1213-MIB
                                        TRAP-TYPE
                                        FROM RFC-1215;


-- textual conventions
DisplayString ::= OCTET STRING


symplex             OBJECT IDENTIFIER ::= { enterprises 385 }

products            OBJECT IDENTIFIER ::= { symplex 1 }

--
--
-- Datamizer IV
--
--

datamizerHseries    OBJECT IDENTIFIER ::= { products 1 }

--
--
-- Direct Route Products
--
--

directrouteSeries   OBJECT IDENTIFIER ::= { products 2 }

directroute4Series   OBJECT IDENTIFIER ::= { products 3 }

--
--
-- Datamizer V
--
--

datamizerVseries    OBJECT IDENTIFIER ::= { products 4 }

--
--
--

drcalldata   OBJECT IDENTIFIER ::= { datamizerVseries 1}

--
--  DR Call Data
--

 callDataTrapAddr OBJECT-TYPE
         SYNTAX  IpAddress
         ACCESS  read-only
         STATUS  mandatory
         DESCRIPTION
                 "The IP address of the device to which Call Data traps will be 
                         sent.  Set to 0.0.0.0 to disable Call Data traps."
         ::= { drcalldata 1 }

 callDataTotalActiveCalls OBJECT-TYPE
         SYNTAX  INTEGER
         ACCESS  read-only
         STATUS  mandatory
         DESCRIPTION
                 "The total number of currently active calls."
         ::= { drcalldata 2 }

 callDataActvTable OBJECT-TYPE
         SYNTAX  SEQUENCE OF CallDataActvEntry
         ACCESS  not-accessible
         STATUS  mandatory
         DESCRIPTION
                  "A list of active call entries."
         ::= { drcalldata 3 }

 callDataActvEntry OBJECT-TYPE
         SYNTAX CallDataActvEntry
         ACCESS  not-accessible
         STATUS  mandatory
         DESCRIPTION
                  ""
         INDEX { callDataActvIndex }
 ::= { callDataActvTable 1 }

 CallDataActvEntry ::=
         SEQUENCE {
         callDataActvIndex
                 INTEGER,
         callDataActvReqTime
                 DisplayString,
         callDataActvEstTime
                 DisplayString,
         callDataActvCurrTime
                 DisplayString,
         callDataActvSourceSys
                 DisplayString,
         callDataActvDestSys
                 DisplayString,
         callDataActvPhoneNum
                 DisplayString,
         callDataActvBandwidth
                 INTEGER,
         callDataActvStatus
                 INTEGER
         }

 callDataActvIndex OBJECT-TYPE
         SYNTAX  INTEGER
         ACCESS  read-only
         STATUS  mandatory
         DESCRIPTION
                 "The index of this call event in the callDataTable."
         ::= { callDataActvEntry 1 }

 callDataActvReqTime OBJECT-TYPE
         SYNTAX  DisplayString
         ACCESS  read-only
         STATUS  mandatory
         DESCRIPTION
                 "The time that this call was initiated."
         ::= { callDataActvEntry 2 }

 callDataActvEstTime OBJECT-TYPE
         SYNTAX  DisplayString
         ACCESS  read-only
         STATUS  mandatory
         DESCRIPTION
                 "The time that this call connected to the remote system."
         ::= { callDataActvEntry 3 }

 callDataActvCurrTime OBJECT-TYPE
         SYNTAX  DisplayString
         ACCESS  read-only
         STATUS  mandatory
         DESCRIPTION
                 "This field will return the current timestamp."
         ::= { callDataActvEntry 4 }

 callDataActvSourceSys OBJECT-TYPE
         SYNTAX  DisplayString
         ACCESS  read-only
         STATUS  mandatory
         DESCRIPTION
                 "The System Name of the unit making the call."
         ::= { callDataActvEntry 5 }

 callDataActvDestSys OBJECT-TYPE
         SYNTAX  DisplayString
         ACCESS  read-only
         STATUS  mandatory
         DESCRIPTION
                 "The System Name of the unit being called."
         ::= { callDataActvEntry 6 }

 callDataActvPhoneNum OBJECT-TYPE
         SYNTAX  DisplayString
         ACCESS  read-only
         STATUS  mandatory
         DESCRIPTION
                 "The Phone Number used when the call was placed."
         ::= { callDataActvEntry 7 }

 callDataActvBandwidth OBJECT-TYPE
         SYNTAX  INTEGER
         ACCESS  read-only
         STATUS  mandatory
         DESCRIPTION
                 "The speed in bps used for the connection."
         ::= { callDataActvEntry 8 }

 callDataActvStatus OBJECT-TYPE
         SYNTAX  INTEGER {
         inactive(1),
         requested(2),
         active(3),
         complete(4),
         failed(5)
         }
         ACCESS  read-only
         STATUS  mandatory
         DESCRIPTION
                 "The current status of the call. (call active, call failed,
                 etc.)"
         ::= { callDataActvEntry 9 }

 callDataCompTable OBJECT-TYPE
         SYNTAX  SEQUENCE OF CallDataCompEntry
         ACCESS  not-accessible
         STATUS  mandatory
         DESCRIPTION
                         "A list of completed call entries."
         ::= { drcalldata 4 }

 callDataCompEntry OBJECT-TYPE
         SYNTAX CallDataCompEntry
         ACCESS  not-accessible
         STATUS  mandatory
         DESCRIPTION
                  ""
         INDEX { callDataCompIndex }
 ::= { callDataCompTable 1 }

 CallDataCompEntry ::=
         SEQUENCE {
         callDataCompIndex
                 INTEGER,
         callDataCompReqTime
                 DisplayString,
         callDataCompEstTime
                 DisplayString,
         callDataCompRelTime
                 DisplayString,
         callDataCompSourceSys
                 DisplayString,
         callDataCompDestSys
                 DisplayString,
         callDataCompPhoneNum
                 DisplayString,
         callDataCompBandwidth
                 INTEGER,
         callDataCompStatus
                 INTEGER
         }

 callDataCompIndex OBJECT-TYPE
         SYNTAX  INTEGER
         ACCESS  read-only
         STATUS  mandatory
         DESCRIPTION
                 "The index of this call event in the callDataTable."
         ::= { callDataCompEntry 1 }

 callDataCompReqTime OBJECT-TYPE
         SYNTAX  DisplayString
         ACCESS  read-only
         STATUS  mandatory
         DESCRIPTION
                 "The time that this call was initiated."
         ::= { callDataCompEntry 2 }

 callDataCompEstTime OBJECT-TYPE
         SYNTAX  DisplayString
         ACCESS  read-only
         STATUS  mandatory
         DESCRIPTION
                 "The time that this call connected to the remote system."
         ::= { callDataCompEntry 3 }

 callDataCompRelTime OBJECT-TYPE
         SYNTAX  DisplayString
         ACCESS  read-only
         STATUS  mandatory
         DESCRIPTION
                 "The time that an established call released, or a requested
                 call was marked as failing."
         ::= { callDataCompEntry 4 }

 callDataCompSourceSys OBJECT-TYPE
         SYNTAX  DisplayString
         ACCESS  read-only
         STATUS  mandatory
         DESCRIPTION
                 "The System Name of the unit making the call."
         ::= { callDataCompEntry 5 }

 callDataCompDestSys OBJECT-TYPE
         SYNTAX  DisplayString
         ACCESS  read-only
         STATUS  mandatory
         DESCRIPTION
                 "The System Name of the unit being called."
         ::= { callDataCompEntry 6 }

 callDataCompPhoneNum OBJECT-TYPE
         SYNTAX  DisplayString
         ACCESS  read-only
         STATUS  mandatory
         DESCRIPTION
                 "The Phone Number used when the call was placed."
         ::= { callDataCompEntry 7 }

 callDataCompBandwidth OBJECT-TYPE
         SYNTAX  INTEGER
         ACCESS  read-only
         STATUS  mandatory
         DESCRIPTION
                 "The speed in bps used for the connection."
         ::= { callDataCompEntry 8 }

 callDataCompStatus OBJECT-TYPE
         SYNTAX  INTEGER {
         inactive(1),
         requested(2),
         active(3),
         complete(4),
         failed(5)
         }
         ACCESS  read-only
         STATUS  mandatory
         DESCRIPTION
                 "The current status of the call. (call active, call failed, etc.)"
         ::= { callDataCompEntry 9 }


d5system   OBJECT IDENTIFIER ::= { datamizerVseries 2}

--
--  D5 System Group
--


 drProdType OBJECT-TYPE
         SYNTAX INTEGER {
                datamizer-5(1)
     }
         ACCESS  read-only
         STATUS  mandatory
         DESCRIPTION
                 "The type of product."
         ::= { d5system 1 }

 drSoftVersion OBJECT-TYPE
         SYNTAX  DisplayString
         ACCESS  read-only
         STATUS  mandatory
         DESCRIPTION
                 "The Software version."
         ::= { d5system 2 }


--
--
--

d5stats   OBJECT IDENTIFIER ::= { datamizerVseries 3}

--
--  D5 Statistics Group
--

 d5PortStatsTable OBJECT-TYPE
         SYNTAX  SEQUENCE OF D5PortStatsEntry
         ACCESS  not-accessible
         STATUS  mandatory
         DESCRIPTION
                  "A list of statistics collected for each Datamizer V port."
         ::= { d5stats 1 }

 d5PortStatsEntry OBJECT-TYPE
         SYNTAX D5PortStatsEntry
         ACCESS  not-accessible
         STATUS  mandatory
         DESCRIPTION
                  ""
         INDEX { d5StatsPortIndex }
 ::= { d5PortStatsTable 1 }

 D5PortStatsEntry ::=
         SEQUENCE {
         d5StatsPortIndex
                 INTEGER,
         d5StatsPortPacketsIn
                 Counter,
         d5StatsPortPacketsOut
                 Counter,
         d5StatsPortPPSIn 
                 INTEGER,
         d5StatsPortPPSOut
                 INTEGER,
         d5StatsPortBPSIn
                 INTEGER,
         d5StatsPortBPSOut
                 INTEGER
         }

 d5StatsPortIndex OBJECT-TYPE
         SYNTAX  INTEGER {
         briA(1),
         briB(2),
         briC(3),
         briD(4),
         lanE(5),
         serialHostF(6),
         serialTrunkG(7)
         }
         ACCESS  read-only
         STATUS  mandatory
         DESCRIPTION
                 "The index of this port in the d5StatsTable."
         ::= { d5PortStatsEntry 1 }

 d5StatsPortPacketsIn OBJECT-TYPE
         SYNTAX  Counter
         ACCESS  read-only
         STATUS  mandatory
         DESCRIPTION
                 "Raw count of incoming packets received on this port since power-up."
         ::= { d5PortStatsEntry 2 }

 d5StatsPortPacketsOut OBJECT-TYPE
         SYNTAX  Counter
         ACCESS  read-only
         STATUS  mandatory
         DESCRIPTION
                 "Raw count of outgoing packets transmitted on this port since power-up."
         ::= { d5PortStatsEntry 3 }

 d5StatsPortPPSIn OBJECT-TYPE
         SYNTAX  INTEGER
         ACCESS  read-only
         STATUS  mandatory
         DESCRIPTION
                 "Received packets per second averaged over a configured interval."
         ::= { d5PortStatsEntry 4 }

 d5StatsPortPPSOut OBJECT-TYPE
         SYNTAX  INTEGER
         ACCESS  read-only
         STATUS  mandatory
         DESCRIPTION
                 "Transmitted packets per second averaged over a configured interval."
         ::= { d5PortStatsEntry 5 }

 d5StatsPortBPSIn OBJECT-TYPE
         SYNTAX  INTEGER
         ACCESS  read-only
         STATUS  mandatory
         DESCRIPTION
                 "Received bits per second averaged over a configured interval."
         ::= { d5PortStatsEntry 6 }

 d5StatsPortBPSOut OBJECT-TYPE
         SYNTAX  INTEGER
         ACCESS  read-only
         STATUS  mandatory
         DESCRIPTION
                 "Transmitted bits per second averaged over a configured interval."
         ::= { d5PortStatsEntry 7 }

 d5PortStatsInterval OBJECT-TYPE
         SYNTAX  INTEGER {
         one-minute(1),
         fifteen-minutes(2),
         thirty-minutes(3),
         sixty-minutes(4)
         }
         ACCESS  read-write
         STATUS  mandatory
         DESCRIPTION
                 "The length of time over which the preceding stats are averaged."
         ::= { d5stats 2 }

 d5SystemStatsTable OBJECT-TYPE
         SYNTAX  SEQUENCE OF D5SystemStatsEntry
         ACCESS  not-accessible
         STATUS  mandatory
         DESCRIPTION
                  "A list of events collected for this Datamizer V unit."
         ::= { d5stats 3 }

 d5SystemStatsEntry OBJECT-TYPE
         SYNTAX D5SystemStatsEntry
         ACCESS  not-accessible
         STATUS  mandatory
         DESCRIPTION
                  ""
         INDEX { d5SystemStatsIndex }
 ::= { d5SystemStatsTable 1 }

 D5SystemStatsEntry ::=
         SEQUENCE {
         d5SystemStatsIndex
                 INTEGER,
         d5SystemStatsCount
                 Counter
         }

 d5SystemStatsIndex OBJECT-TYPE
         SYNTAX  INTEGER {
         wanDataErrors(1),
         serialHostDataErrors(2),
         lanDataErrors(3),
         congestionDetection(4)
         }
         ACCESS  read-only
         STATUS  mandatory
         DESCRIPTION
                 "The index of this type of event in the d5SystemStatsTable."
         ::= { d5SystemStatsEntry 1 }

 d5SystemStatsCount OBJECT-TYPE
         SYNTAX  Counter
         ACCESS  read-only
         STATUS  mandatory
         DESCRIPTION
                 "Raw count of events of this type detected since power-up."
         ::= { d5SystemStatsEntry 2 }


-- The standard traps 

 coldStart TRAP-TYPE
     ENTERPRISE  snmp
     VARIABLES   { sysUpTime }
     DESCRIPTION
                 "A coldStart trap signifies that the sending
                 protocol entity is reinitializing itself such
                 that the agent's configuration or the protocol
                 entity implementation may be altered."
     ::= 0

 -- Symplex does not generate warmstart traps

 warmStart TRAP-TYPE
     ENTERPRISE  snmp
     DESCRIPTION
                 "A warmStart trap signifies that the sending
                 protocol entity is reinitializing itself such
                 that neither the agent configuration nor the
                 protocol entity implementation is altered."
     ::= 1

 linkDown TRAP-TYPE
     ENTERPRISE  snmp
     VARIABLES   { ifIndex }
     DESCRIPTION
                 "A linkDown trap signifies that the sending
                 protocol entity recognizes a failure in one of
                 the communication links represented in the
                 agent's configuration."
     ::= 2

 linkUp TRAP-TYPE
     ENTERPRISE  snmp
     VARIABLES   { ifIndex }
     DESCRIPTION
                 "A linkUp trap signifies that the sending
                 protocol entity recognizes that one of the
                 communication links represented in the agent's
                 configuration has come up."
     ::= 3

 authenticationFailure TRAP-TYPE
     ENTERPRISE  snmp
     VARIABLES   { ipAdEntAddr }
     DESCRIPTION
                 "An authenticationFailure trap signifies that
                 the sending protocol entity is the addressee
                 of a protocol message that is not properly
                 authenticated.  While implementations of the
                 SNMP must be capable of generating this trap,
                 they must also be capable of suppressing the
                 emission of such traps via an implementation-
                 specific mechanism."
     ::= 4

 egpNeighborLoss TRAP-TYPE
     ENTERPRISE  snmp
     VARIABLES   { sysUpTime }
     DESCRIPTION
                 "An egpNeighborLoss trap signifies that an EGP
                 neighbor for whom the sending protocol entity
                 was an EGP peer has been marked down and the
                 peer relationship no longer obtains."
     ::= 5

-- Symplex Private Enterprise Traps

 unspecifiedTrap TRAP-TYPE
     ENTERPRISE  symplex
     VARIABLES   { sysDescr }
     DESCRIPTION
                 "An alarm condition has occured within the 
                                 unit.  This trap's text will provide details on the alarm."
     ::= 1

 startDisasterRecovery TRAP-TYPE
     ENTERPRISE  symplex
     VARIABLES   { sysDescr }
     DESCRIPTION
                 "A startDisasterRecovery trap signifies that the normal
                                 external path to a remote site has been lost,
                                 and an ISDN connection to that site will be made."
     ::= 2

 stopDisasterRecovery TRAP-TYPE
     ENTERPRISE  symplex
     VARIABLES   { sysDescr }
     DESCRIPTION
                 "A stopDisasterRecovery trap signifies that the normal
                                 external path to a remote site has been recovered,
                                 any ISDN connections to that site will be terminated."
     ::= 3

 noBChannel TRAP-TYPE
     ENTERPRISE  symplex
     VARIABLES   { sysDescr }
     DESCRIPTION
                 "A noBChannel trap signifies that the desired call
                                 to a remote site using a phone number was unsuccessful, 
                                 this phone number has now been disabled."
     ::= 4

 dailyConnLimit TRAP-TYPE
     ENTERPRISE  symplex
     VARIABLES   { sysDescr }
     DESCRIPTION
                 "A dailyConnLimit trap signifies that the cummulative
                                 connect time for originated calls to a remote site has been
                                 exceeded.  No additional calls can be placed to this
                                 site until the next day; unless the administrator
                                 intervenes."
     ::= 5

 monthlyConnLimit TRAP-TYPE
     ENTERPRISE  symplex
     VARIABLES   { sysDescr }
     DESCRIPTION
                 "A monthlyConnLimit trap signifies that the cummulative
                                 connect time for originated calls to a remote site has been
                                 exceeded.  No additional calls can be placed to this
                                 site until the next month; unless the administrator
                                 intervenes."
     ::= 6

 dataErrorBChannel TRAP-TYPE
     ENTERPRISE  symplex
     VARIABLES   { sysDescr }
     DESCRIPTION
                 "A dataErrorBChannel trap signifies that the data
                                 received on a trunk has been received in error."
     ::= 7

 pppVersion TRAP-TYPE
     ENTERPRISE  symplex
     VARIABLES   { sysDescr }
     DESCRIPTION
                 "A pppVersion trap signifies that the PPP/LCP versions
                                 used by this unit and its peer are incompatible."
     ::= 8

 ipTableFull TRAP-TYPE
     ENTERPRISE  symplex
     VARIABLES   { sysDescr }
     DESCRIPTION
                 "An ipTableFull trap signifies that the IP Address
                                 Table is full and another entry cannot be made at
                                 this time."
     ::= 9

 macTableFull TRAP-TYPE
     ENTERPRISE  symplex
     VARIABLES   { sysDescr }
     DESCRIPTION
                 "A macTableFull trap signifies that the MAC Address
                                 Table is full and another entry cannot be made at
                                 this time."
     ::= 10

 routeTableFull TRAP-TYPE
     ENTERPRISE  symplex
     VARIABLES   { sysDescr }
     DESCRIPTION
                 "A routeTableFull trap signifies that either the IP 
                                 RIP, IPX RIP, or IPX SAP Table is full and another 
                                 entry cannot be made at this time."
     ::= 11

 duplicateItem TRAP-TYPE
     ENTERPRISE  symplex
     VARIABLES   { sysDescr }
     DESCRIPTION
                 "A duplicateItem trap signifies that some protocol
                                 entity (such as an IPX Network) has been discovered
                                 at two sites."
     ::= 12

 noDChannel TRAP-TYPE
     ENTERPRISE  symplex
     VARIABLES   { sysDescr }
     DESCRIPTION
                 "A noDChannel trap signifies that the D channel
                                 connection to the switch for a port cannot be made."
     ::= 13

 lostDedicated TRAP-TYPE
     ENTERPRISE  symplex
     VARIABLES   { sysDescr }
     DESCRIPTION
                 "A lostDedicated trap signifies that the dedicated
                 trunk connection has been lost."
     ::= 14

 compCallData TRAP-TYPE
     ENTERPRISE  symplex
     VARIABLES   { sysDescr }
     DESCRIPTION
                 "A compCallData trap signifies that the Completed
                 Call records need to be retrieved from the unit."
     ::= 15

END
