-- MIB generated by miftomib version 1.0a

INTELCORPORATIONBASEBOARD2-MIB DEFINITIONS ::= BEGIN

-- This component allows full monitoring and a limited control ofSystem 
-- baseboard, processor, memory, chassis and other peripherals.The Groups 
-- in this component are a subset of the Standard System MIF Groups.

IMPORTS
    OBJECT-TYPE
    FROM RFC-1212
    Counter, enterprises
    FROM RFC1155-SMI
    DisplayString
    FROM RFC1213-MIB;

DmiCounter			::= Counter
DmiInteger			::= INTEGER
DmiInteger64X		::= INTEGER (-18446744073709551615..18446744073709551615)
DmiOctetstring		::= OCTET STRING
DmiDisplaystring	::= DisplayString
DmiDateX			::= OCTET STRING (SIZE (28))
DmiComponentIndex	::= INTEGER

intel                   OBJECT IDENTIFIER ::= {enterprises 343}
products                OBJECT IDENTIFIER ::= {intel 2}
server-products         OBJECT IDENTIFIER ::= {products 6}
platforms               OBJECT IDENTIFIER ::= {server-products 2}
basebrd2                OBJECT IDENTIFIER ::= {platforms 2}
dmtfGroups              OBJECT IDENTIFIER ::= {basebrd2 1}

SComponentid ::= SEQUENCE {
	a1Manufacturer                          	DmiDisplaystring,
	a1Product                               	DmiDisplaystring,
	a1Version                               	DmiDisplaystring,
	a1SerialNumber                          	DmiDisplaystring,
	a1Installation                          	DmiDateX,
	a1Verify                                	DmiInteger
}

tComponentid OBJECT-TYPE
	SYNTAX		SEQUENCE OF SComponentid
	ACCESS		not-accessible
	STATUS		mandatory
	DESCRIPTION	"This group defines the attributes common to all components.
This groupis required."
	::= {dmtfGroups 1}

eComponentid OBJECT-TYPE
	SYNTAX		SComponentid
	ACCESS		not-accessible
	STATUS		mandatory
	DESCRIPTION	""
	INDEX		{DmiComponentIndex}
	::= {tComponentid 1}

a1Manufacturer OBJECT-TYPE
	SYNTAX		DmiDisplaystring
	ACCESS		read-only
	STATUS		mandatory
	DESCRIPTION	"Manufacturer of this system."
	::= {eComponentid 1}

a1Product OBJECT-TYPE
	SYNTAX		DmiDisplaystring
	ACCESS		read-only
	STATUS		mandatory
	DESCRIPTION	"Product name for this system."
	::= {eComponentid 2}

a1Version OBJECT-TYPE
	SYNTAX		DmiDisplaystring
	ACCESS		read-only
	STATUS		mandatory
	DESCRIPTION	"Version number of this system."
	::= {eComponentid 3}

a1SerialNumber OBJECT-TYPE
	SYNTAX		DmiDisplaystring
	ACCESS		read-only
	STATUS		mandatory
	DESCRIPTION	"Serial number for this system."
	::= {eComponentid 4}

a1Installation OBJECT-TYPE
	SYNTAX		DmiDateX
	ACCESS		read-only
	STATUS		mandatory
	DESCRIPTION	"The time and date when this component was installed."
	::= {eComponentid 5}

a1Verify OBJECT-TYPE
	SYNTAX		INTEGER {
		vAnErrorOccurredCheckStatusCode         	(0),
		vThisComponentDoesNotExist              	(1),
		vVerificationIsNotSupported             	(2),
		vReserved                               	(3),
		vThisComponentExistsButTheFunctionalityI	(4),
		vThisComponentExistsButTheFunctionality1	(5),
		vThisComponentExistsAndIsNotFunctioningC	(6),
		vThisComponentExistsAndIsFunctioningCorr	(7)
	}
	ACCESS		read-only
	STATUS		mandatory
	DESCRIPTION	"A code that provides a level of verification that the component
is stillinstalled and working."
	::= {eComponentid 6}

SGeneralInformation ::= SEQUENCE {
	a2SystemName                            	DmiDisplaystring,
	a2SystemLocation                        	DmiDisplaystring,
	a2SystemPrimaryUserName                 	DmiDisplaystring,
	a2SystemPrimaryUserPhone                	DmiDisplaystring,
	a2SystemBootupTime                      	DmiDateX,
	a2SystemDateTime                        	DmiDateX
}

tGeneralInformation OBJECT-TYPE
	SYNTAX		SEQUENCE OF SGeneralInformation
	ACCESS		not-accessible
	STATUS		mandatory
	DESCRIPTION	"This group defines general information about this system."
	::= {dmtfGroups 2}

eGeneralInformation OBJECT-TYPE
	SYNTAX		SGeneralInformation
	ACCESS		not-accessible
	STATUS		mandatory
	DESCRIPTION	""
	INDEX		{DmiComponentIndex}
	::= {tGeneralInformation 1}

a2SystemName OBJECT-TYPE
	SYNTAX		DmiDisplaystring
	ACCESS		read-write
	STATUS		mandatory
	DESCRIPTION	"A name to identify this system."
	::= {eGeneralInformation 1}

a2SystemLocation OBJECT-TYPE
	SYNTAX		DmiDisplaystring
	ACCESS		read-write
	STATUS		mandatory
	DESCRIPTION	"The physical location of this system."
	::= {eGeneralInformation 2}

a2SystemPrimaryUserName OBJECT-TYPE
	SYNTAX		DmiDisplaystring
	ACCESS		read-write
	STATUS		mandatory
	DESCRIPTION	"The name of the primary user or owner of this system."
	::= {eGeneralInformation 3}

a2SystemPrimaryUserPhone OBJECT-TYPE
	SYNTAX		DmiDisplaystring
	ACCESS		read-write
	STATUS		mandatory
	DESCRIPTION	"The phone number of the primary user of this system."
	::= {eGeneralInformation 4}

a2SystemBootupTime OBJECT-TYPE
	SYNTAX		DmiDateX
	ACCESS		read-only
	STATUS		mandatory
	DESCRIPTION	"The time at which the system was last booted."
	::= {eGeneralInformation 5}

a2SystemDateTime OBJECT-TYPE
	SYNTAX		DmiDateX
	ACCESS		read-write
	STATUS		mandatory
	DESCRIPTION	"The actual system date and time."
	::= {eGeneralInformation 6}

SSystemBios ::= SEQUENCE {
	a4BiosIndex                             	DmiInteger,
	a4BiosManufacturer                      	DmiDisplaystring,
	a4BiosVersion                           	DmiDisplaystring,
	a4BiosRomSize                           	DmiInteger,
	a4BiosStartingAddress                   	DmiInteger64X,
	a4BiosEndingAddress                     	DmiInteger64X,
	a4BiosLoaderVersion                     	DmiDisplaystring,
	a4BiosReleaseDate                       	DmiDateX,
	a4PrimaryBios                           	DmiInteger
}

tSystemBios OBJECT-TYPE
	SYNTAX		SEQUENCE OF SSystemBios
	ACCESS		not-accessible
	STATUS		mandatory
	DESCRIPTION	"This group defines the attributes for the System BIOS."
	::= {dmtfGroups 4}

eSystemBios OBJECT-TYPE
	SYNTAX		SSystemBios
	ACCESS		not-accessible
	STATUS		mandatory
	DESCRIPTION	""
	INDEX		{DmiComponentIndex, a4BiosIndex}
	::= {tSystemBios 1}

a4BiosIndex OBJECT-TYPE
	SYNTAX		DmiInteger
	ACCESS		read-only
	STATUS		mandatory
	DESCRIPTION	"The index into the system BIOS table."
	::= {eSystemBios 1}

a4BiosManufacturer OBJECT-TYPE
	SYNTAX		DmiDisplaystring
	ACCESS		read-only
	STATUS		mandatory
	DESCRIPTION	"The name of the company that wrote this System BIOS."
	::= {eSystemBios 2}

a4BiosVersion OBJECT-TYPE
	SYNTAX		DmiDisplaystring
	ACCESS		read-only
	STATUS		mandatory
	DESCRIPTION	"The version number or version string of this BIOS."
	::= {eSystemBios 3}

a4BiosRomSize OBJECT-TYPE
	SYNTAX		DmiInteger
	ACCESS		read-only
	STATUS		mandatory
	DESCRIPTION	"The physical size of this BIOS ROM device in kilobytes."
	::= {eSystemBios 4}

a4BiosStartingAddress OBJECT-TYPE
	SYNTAX		DmiInteger64X
	ACCESS		read-only
	STATUS		mandatory
	DESCRIPTION	"The starting physical address for the memory which the BIOS
occupies."
	::= {eSystemBios 5}

a4BiosEndingAddress OBJECT-TYPE
	SYNTAX		DmiInteger64X
	ACCESS		read-only
	STATUS		mandatory
	DESCRIPTION	"The ending physical address for the memory which the BIOS
occupies."
	::= {eSystemBios 6}

a4BiosLoaderVersion OBJECT-TYPE
	SYNTAX		DmiDisplaystring
	ACCESS		read-only
	STATUS		mandatory
	DESCRIPTION	"The BIOS flash loader version number or string."
	::= {eSystemBios 7}

a4BiosReleaseDate OBJECT-TYPE
	SYNTAX		DmiDateX
	ACCESS		read-only
	STATUS		mandatory
	DESCRIPTION	"The BIOS release date."
	::= {eSystemBios 8}

a4PrimaryBios OBJECT-TYPE
	SYNTAX		INTEGER {
		vFalse                                  	(0),
		vTrue                                   	(1)
	}
	ACCESS		read-only
	STATUS		mandatory
	DESCRIPTION	"If true, this is the primary System BIOS."
	::= {eSystemBios 9}

SSystemBiosCharacteristics ::= SEQUENCE {
	a5BiosCharacteristicIndex               	DmiInteger,
	a5BiosNumber                            	DmiInteger,
	a5BiosCharacteristic                    	DmiInteger,
	a5BiosCharacteristicDescription         	DmiDisplaystring
}

tSystemBiosCharacteristics OBJECT-TYPE
	SYNTAX		SEQUENCE OF SSystemBiosCharacteristics
	ACCESS		not-accessible
	STATUS		mandatory
	DESCRIPTION	"This group defines the characteristics of the System BIOS."
	::= {dmtfGroups 5}

eSystemBiosCharacteristics OBJECT-TYPE
	SYNTAX		SSystemBiosCharacteristics
	ACCESS		not-accessible
	STATUS		mandatory
	DESCRIPTION	""
	INDEX		{DmiComponentIndex, a5BiosCharacteristicIndex, a5BiosNumber}
	::= {tSystemBiosCharacteristics 1}

a5BiosCharacteristicIndex OBJECT-TYPE
	SYNTAX		DmiInteger
	ACCESS		read-only
	STATUS		mandatory
	DESCRIPTION	"This is an index into the BIOS Characteristics table."
	::= {eSystemBiosCharacteristics 1}

a5BiosNumber OBJECT-TYPE
	SYNTAX		DmiInteger
	ACCESS		read-only
	STATUS		mandatory
	DESCRIPTION	"The BIOS number, which correlates to the BIOS Index attribute
in theSystem BIOS group."
	::= {eSystemBiosCharacteristics 2}

a5BiosCharacteristic OBJECT-TYPE
	SYNTAX		INTEGER {
		vOther                                  	(1),
		vUnknown                                	(2),
		vUnsupported                            	(3),
		vIsaSupport                             	(4),
		vMcaSupport                             	(5),
		vEisaSupport                            	(6),
		vPciSupport                             	(7),
		vPcmciaSupport                          	(8),
		vPnpSupport                             	(9),
		vApmSupport                             	(10),
		vUpgradeableBios                        	(11),
		vBiosShadowingAllowed                   	(12),
		vVlVesaSupport                          	(13),
		vEscdSupport                            	(14),
		vPc-98                                  	(160)
	}
	ACCESS		read-only
	STATUS		mandatory
	DESCRIPTION	"The different features supported by this version of the BIOS."
	::= {eSystemBiosCharacteristics 3}

a5BiosCharacteristicDescription OBJECT-TYPE
	SYNTAX		DmiDisplaystring
	ACCESS		read-only
	STATUS		mandatory
	DESCRIPTION	"An expanded description of this BIOS Characteristic."
	::= {eSystemBiosCharacteristics 4}

SProcessor ::= SEQUENCE {
	a6ProcessorIndex                        	DmiInteger,
	a6ProcessorType                         	DmiInteger,
	a6ProcessorFamily                       	DmiInteger,
	a6ProcessorVersionInformation           	DmiDisplaystring,
	a6MaximumSpeed                          	DmiInteger,
	a6CurrentSpeed                          	DmiInteger,
	a6ProcessorUpgrade                      	DmiInteger,
	a6FruGroupIndex                         	DmiInteger,
	a6OperationalGroupIndex                 	DmiInteger,
	a6Level1CacheIndex                      	DmiInteger,
	a6Level2CacheIndex                      	DmiInteger,
	a6Level3CacheIndex                      	DmiInteger
}

tProcessor OBJECT-TYPE
	SYNTAX		SEQUENCE OF SProcessor
	ACCESS		not-accessible
	STATUS		mandatory
	DESCRIPTION	"This group defines the attributes for each and every processorin
talled in this system."
	::= {dmtfGroups 6}

eProcessor OBJECT-TYPE
	SYNTAX		SProcessor
	ACCESS		not-accessible
	STATUS		mandatory
	DESCRIPTION	""
	INDEX		{DmiComponentIndex, a6ProcessorIndex}
	::= {tProcessor 1}

a6ProcessorIndex OBJECT-TYPE
	SYNTAX		DmiInteger
	ACCESS		read-only
	STATUS		mandatory
	DESCRIPTION	"An index into the processor table."
	::= {eProcessor 1}

a6ProcessorType OBJECT-TYPE
	SYNTAX		INTEGER {
		vOther                                  	(1),
		vUnknown                                	(2),
		vCentralProcessor                       	(3),
		vMathProcessor                          	(4),
		vDspProcessor                           	(5),
		vVideoProcessor                         	(6)
	}
	ACCESS		read-only
	STATUS		mandatory
	DESCRIPTION	"The type of processor currently in the system."
	::= {eProcessor 2}

a6ProcessorFamily OBJECT-TYPE
	SYNTAX		INTEGER {
		vOther                                  	(1),
		vUnknown                                	(2),
		v8086                                   	(3),
		v80286                                  	(4),
		v80386                                  	(5),
		v80486                                  	(6),
		v8087                                   	(7),
		v80287                                  	(8),
		v80387                                  	(9),
		v80487                                  	(10),
		vPentiumFamily                          	(11),
		vPentiumPro                             	(12),
		vM1Family                               	(18),
		vK5Family                               	(25),
		vPowerPcFamily                          	(32),
		vPowerPc601                             	(33),
		vPowerPc603                             	(34),
		vPowerPc603plus                         	(35),
		vPowerPc604                             	(36),
		vAlphaFamily                            	(48),
		vMipsFamily                             	(64),
		vSparcFamily                            	(80),
		v68040                                  	(96),
		v68xxxFamily                            	(97),
		v68000                                  	(98),
		v68010                                  	(99),
		v68020                                  	(100),
		v68030                                  	(101),
		vHobbitFamily                           	(112),
		vWeitek                                 	(128),
		vPa-riscFamily                          	(144),
		vV30Family                              	(160)
	}
	ACCESS		read-only
	STATUS		mandatory
	DESCRIPTION	"The family of processors to which this processor belongs."
	::= {eProcessor 3}

a6ProcessorVersionInformation OBJECT-TYPE
	SYNTAX		DmiDisplaystring
	ACCESS		read-only
	STATUS		mandatory
	DESCRIPTION	"The version number or string for this processor."
	::= {eProcessor 4}

a6MaximumSpeed OBJECT-TYPE
	SYNTAX		DmiInteger
	ACCESS		read-only
	STATUS		mandatory
	DESCRIPTION	"The maximum speed (in MHz) of this processor."
	::= {eProcessor 5}

a6CurrentSpeed OBJECT-TYPE
	SYNTAX		DmiInteger
	ACCESS		read-only
	STATUS		mandatory
	DESCRIPTION	"The current speed (in MHz) of this processor."
	::= {eProcessor 6}

a6ProcessorUpgrade OBJECT-TYPE
	SYNTAX		INTEGER {
		vOther                                  	(1),
		vUnknown                                	(2),
		vDaughterBoard                          	(3),
		vZifSocket                              	(4),
		vReplacementpiggyBack                   	(5),
		vNone                                   	(6),
		vLifSocket                              	(7)
	}
	ACCESS		read-only
	STATUS		mandatory
	DESCRIPTION	"The method by which this processor can be upgraded, if upgrades
aresupported."
	::= {eProcessor 7}

a6FruGroupIndex OBJECT-TYPE
	SYNTAX		DmiInteger
	ACCESS		read-only
	STATUS		mandatory
	DESCRIPTION	"If this is a Field Replaceable Unit or if it is part of another
FRU, thisprovides an index into the FRU table; 'value = -1' indicates that
the group is not a FRU."
	::= {eProcessor 8}

a6OperationalGroupIndex OBJECT-TYPE
	SYNTAX		DmiInteger
	ACCESS		read-only
	STATUS		mandatory
	DESCRIPTION	"The index into the Operational State Table for this device
if applicable."
	::= {eProcessor 9}

a6Level1CacheIndex OBJECT-TYPE
	SYNTAX		DmiInteger
	ACCESS		read-only
	STATUS		mandatory
	DESCRIPTION	"An index into the System Cache table that identifies the
entrythat describes the L1 cache for this processor. If more than oneprocessor
points to the same cache entry this means they sharethat cache."
	::= {eProcessor 10}

a6Level2CacheIndex OBJECT-TYPE
	SYNTAX		DmiInteger
	ACCESS		read-only
	STATUS		mandatory
	DESCRIPTION	"An index into the System Cache table that identifies the
entrythat describes the L2 cache for this processor If more than oneprocessor
points to the same cache entry this means they sharethat cache."
	::= {eProcessor 11}

a6Level3CacheIndex OBJECT-TYPE
	SYNTAX		DmiInteger
	ACCESS		read-only
	STATUS		mandatory
	DESCRIPTION	"An index into the System Cache table that identifies the
entrythat describes the L3 cache for this processor. If more than oneprocessor
points to the same cache entry this means they sharethat cache."
	::= {eProcessor 12}

SMotherboard ::= SEQUENCE {
	a7NumberOfExpansionSlots                	DmiInteger,
	a7FruGroupIndex                         	DmiInteger,
	a7OperationalGroupIndex                 	DmiInteger
}

tMotherboard OBJECT-TYPE
	SYNTAX		SEQUENCE OF SMotherboard
	ACCESS		not-accessible
	STATUS		mandatory
	DESCRIPTION	"This group defines attributes for the motherboard."
	::= {dmtfGroups 7}

eMotherboard OBJECT-TYPE
	SYNTAX		SMotherboard
	ACCESS		not-accessible
	STATUS		mandatory
	DESCRIPTION	""
	INDEX		{DmiComponentIndex}
	::= {tMotherboard 1}

a7NumberOfExpansionSlots OBJECT-TYPE
	SYNTAX		DmiInteger
	ACCESS		read-only
	STATUS		mandatory
	DESCRIPTION	"The total number of expansion slots which physically exist
on themotherboard whether occupied or not (see System Slots group)."
	::= {eMotherboard 1}

a7FruGroupIndex OBJECT-TYPE
	SYNTAX		DmiInteger
	ACCESS		read-only
	STATUS		mandatory
	DESCRIPTION	"If this is a Field Replaceable Unit or if it is part of another
FRU, thisprovides an index into the FRU table; 'value = -1' indicates that
the group is not a FRU."
	::= {eMotherboard 2}

a7OperationalGroupIndex OBJECT-TYPE
	SYNTAX		DmiInteger
	ACCESS		read-only
	STATUS		mandatory
	DESCRIPTION	"The index into the Operational State Table for this device
if applicable."
	::= {eMotherboard 3}

SSystemCache ::= SEQUENCE {
	a10SystemCacheIndex                     	DmiInteger,
	a10SystemCacheLevel                     	DmiInteger,
	a10SystemCacheSpeed                     	DmiInteger,
	a10SystemCacheSize                      	DmiInteger,
	a10SystemCacheWritePolicy               	DmiInteger,
	a10SystemCacheErrorCorrection           	DmiInteger,
	a10FruGroupIndex                        	DmiInteger,
	a10OperationalGroupIndex                	DmiInteger,
	a10SystemCacheType                      	DmiInteger
}

tSystemCache OBJECT-TYPE
	SYNTAX		SEQUENCE OF SSystemCache
	ACCESS		not-accessible
	STATUS		mandatory
	DESCRIPTION	"This group defines the attributes for different System Caches
installed inthis system."
	::= {dmtfGroups 10}

eSystemCache OBJECT-TYPE
	SYNTAX		SSystemCache
	ACCESS		not-accessible
	STATUS		mandatory
	DESCRIPTION	""
	INDEX		{DmiComponentIndex, a10SystemCacheIndex}
	::= {tSystemCache 1}

a10SystemCacheIndex OBJECT-TYPE
	SYNTAX		DmiInteger
	ACCESS		read-only
	STATUS		mandatory
	DESCRIPTION	"An index into the System Cache table."
	::= {eSystemCache 1}

a10SystemCacheLevel OBJECT-TYPE
	SYNTAX		INTEGER {
		vOther                                  	(1),
		vUnknown                                	(2),
		vPrimary                                	(3),
		vSecondary                              	(4),
		vTertiary                               	(5)
	}
	ACCESS		read-only
	STATUS		mandatory
	DESCRIPTION	"Is this the primary System Cache, or a subsidiary cache?"
	::= {eSystemCache 2}

a10SystemCacheSpeed OBJECT-TYPE
	SYNTAX		DmiInteger
	ACCESS		read-only
	STATUS		mandatory
	DESCRIPTION	"The speed of this System Cache module in nanoseconds."
	::= {eSystemCache 3}

a10SystemCacheSize OBJECT-TYPE
	SYNTAX		DmiInteger
	ACCESS		read-only
	STATUS		mandatory
	DESCRIPTION	"The size of this System Cache module in kilobytes."
	::= {eSystemCache 4}

a10SystemCacheWritePolicy OBJECT-TYPE
	SYNTAX		INTEGER {
		vOther                                  	(1),
		vUnknown                                	(2),
		vWriteBack                              	(3),
		vWriteThrough                           	(4)
	}
	ACCESS		read-only
	STATUS		mandatory
	DESCRIPTION	"Is this a write-back or a write-through cache?"
	::= {eSystemCache 5}

a10SystemCacheErrorCorrection OBJECT-TYPE
	SYNTAX		INTEGER {
		vOther                                  	(1),
		vUnknown                                	(2),
		vNone                                   	(3),
		vParity                                 	(4),
		vSingleBitEcc                           	(5),
		vMultibitEcc                            	(6)
	}
	ACCESS		read-only
	STATUS		mandatory
	DESCRIPTION	"The error correction scheme supported by this cache component."
	::= {eSystemCache 6}

a10FruGroupIndex OBJECT-TYPE
	SYNTAX		DmiInteger
	ACCESS		read-only
	STATUS		mandatory
	DESCRIPTION	"If this is a Field Replaceable Unit or if it is part of another
FRU, thisprovides an index into the FRU table; 'value = -1' indicates that
the group is not a FRU."
	::= {eSystemCache 7}

a10OperationalGroupIndex OBJECT-TYPE
	SYNTAX		DmiInteger
	ACCESS		read-only
	STATUS		mandatory
	DESCRIPTION	"The index into the Operational State Table for this device."
	::= {eSystemCache 8}

a10SystemCacheType OBJECT-TYPE
	SYNTAX		INTEGER {
		vOther                                  	(1),
		vUnknown                                	(2),
		vInstruction                            	(3),
		vData                                   	(4),
		vUnified                                	(5)
	}
	ACCESS		read-only
	STATUS		mandatory
	DESCRIPTION	"This defines the system cache type."
	::= {eSystemCache 9}

SPowerSupply ::= SEQUENCE {
	a17PowerSupplyIndex                     	DmiInteger,
	a17FruGroupIndex                        	DmiInteger,
	a17OperationalGroupIndex                	DmiInteger,
	a17PowerUnitIndex                       	DmiInteger,
	a17PowerSupplyType                      	DmiInteger,
	a17InputVoltageCapabilityDescription    	DmiDisplaystring,
	a17Range1InputVoltageLow                	DmiInteger,
	a17Range1InputVoltageHigh               	DmiInteger,
	a17Range1VoltageProbeIndex              	DmiInteger,
	a17Range1ElectricalCurrentProbeIndex    	DmiInteger,
	a17Range2InputVoltageLow                	DmiInteger,
	a17Range2InputVoltageHigh               	DmiInteger,
	a17Range2VoltageProbeIndex              	DmiInteger,
	a17Range2CurrentProbeIndex              	DmiInteger,
	a17ActiveInputVoltageRange              	DmiInteger,
	a17InputVoltageRangeSwitching           	DmiInteger,
	a17Range1InputFrequencyLow              	DmiInteger,
	a17Range1InputFrequencyHigh             	DmiInteger,
	a17Range2InputFrequencyLow              	DmiInteger,
	a17Range2InputFrequencyHigh             	DmiInteger,
	a17TotalOutputPower                     	DmiInteger
}

tPowerSupply OBJECT-TYPE
	SYNTAX		SEQUENCE OF SPowerSupply
	ACCESS		not-accessible
	STATUS		mandatory
	DESCRIPTION	"This group defines various attributes for power supplies
in this system."
	::= {dmtfGroups 17}

ePowerSupply OBJECT-TYPE
	SYNTAX		SPowerSupply
	ACCESS		not-accessible
	STATUS		mandatory
	DESCRIPTION	""
	INDEX		{DmiComponentIndex, a17PowerSupplyIndex}
	::= {tPowerSupply 1}

a17PowerSupplyIndex OBJECT-TYPE
	SYNTAX		DmiInteger
	ACCESS		read-only
	STATUS		mandatory
	DESCRIPTION	"The index number of the current power supply."
	::= {ePowerSupply 1}

a17FruGroupIndex OBJECT-TYPE
	SYNTAX		DmiInteger
	ACCESS		read-only
	STATUS		mandatory
	DESCRIPTION	"If this is a Field Replaceable Unit or if it is part of another
FRU, thisprovides an index into the FRU table; 'value = -1' indicates that
the group is not a FRU."
	::= {ePowerSupply 2}

a17OperationalGroupIndex OBJECT-TYPE
	SYNTAX		DmiInteger
	ACCESS		read-only
	STATUS		mandatory
	DESCRIPTION	"The index into the Operational State table for this device."
	::= {ePowerSupply 3}

a17PowerUnitIndex OBJECT-TYPE
	SYNTAX		DmiInteger
	ACCESS		read-only
	STATUS		mandatory
	DESCRIPTION	"This is the ID of the Power Unit (logical power supply) to
which thisPower Supply belongs. This value matches up with the Power Unit
Table Indexattribute defined in the Power Unit Globe Table."
	::= {ePowerSupply 4}

a17PowerSupplyType OBJECT-TYPE
	SYNTAX		INTEGER {
		vOther                                  	(1),
		vUnknown                                	(2),
		vLinear                                 	(3),
		vSwitching                              	(4),
		vBattery                                	(5),
		vUps                                    	(6),
		vConverter                              	(7),
		vRegulator                              	(8)
	}
	ACCESS		read-only
	STATUS		mandatory
	DESCRIPTION	"This attribute describes the type of Power Supply, e.g. Linear,
Switching, Battery, etc."
	::= {ePowerSupply 5}

a17InputVoltageCapabilityDescription OBJECT-TYPE
	SYNTAX		DmiDisplaystring
	ACCESS		read-only
	STATUS		mandatory
	DESCRIPTION	"An expanded description of the Input Voltage Capability for
this PowerSupply."
	::= {ePowerSupply 6}

a17Range1InputVoltageLow OBJECT-TYPE
	SYNTAX		DmiInteger
	ACCESS		read-only
	STATUS		mandatory
	DESCRIPTION	"The low voltage of Input Voltage Range 1 for this Power Supply,
inmillivolts. A value of 0x80000000 denotes 'unknown'."
	::= {ePowerSupply 7}

a17Range1InputVoltageHigh OBJECT-TYPE
	SYNTAX		DmiInteger
	ACCESS		read-only
	STATUS		mandatory
	DESCRIPTION	"The high voltage of Input Voltage Range 1 for this Power
Supply, inmillivolts. A value of 0x80000000 denotes 'unknown'."
	::= {ePowerSupply 8}

a17Range1VoltageProbeIndex OBJECT-TYPE
	SYNTAX		DmiInteger
	ACCESS		read-only
	STATUS		mandatory
	DESCRIPTION	"Index into the Voltage Probe table identifying the voltage
probemonitoring this input range. 0 indicates no probe provided."
	::= {ePowerSupply 9}

a17Range1ElectricalCurrentProbeIndex OBJECT-TYPE
	SYNTAX		DmiInteger
	ACCESS		read-only
	STATUS		mandatory
	DESCRIPTION	"Index into the Elelctrical Current Probe table identifying
the Electrical current probe monitoring this input range. 0 indicates no
probe provided."
	::= {ePowerSupply 10}

a17Range2InputVoltageLow OBJECT-TYPE
	SYNTAX		DmiInteger
	ACCESS		read-only
	STATUS		mandatory
	DESCRIPTION	"The low voltage of Input Voltage Range 2 for this Power Supply,
inmillivolts. A value of 0x80000000 denotes 'unknown'."
	::= {ePowerSupply 11}

a17Range2InputVoltageHigh OBJECT-TYPE
	SYNTAX		DmiInteger
	ACCESS		read-only
	STATUS		mandatory
	DESCRIPTION	"The high voltage of Input Voltage Range 2 for this Power
Supply, inmillivolts. A value of 0x80000000 denotes 'unknown'"
	::= {ePowerSupply 12}

a17Range2VoltageProbeIndex OBJECT-TYPE
	SYNTAX		DmiInteger
	ACCESS		read-only
	STATUS		mandatory
	DESCRIPTION	"Index into the Voltage Probe table identifying the voltage
probemonitoring this input range. 0 indicates no probe provided."
	::= {ePowerSupply 13}

a17Range2CurrentProbeIndex OBJECT-TYPE
	SYNTAX		DmiInteger
	ACCESS		read-only
	STATUS		mandatory
	DESCRIPTION	"Index into the Current Probe table identifying the current
probemonitoring this input range. 0 indicates no probe provided."
	::= {ePowerSupply 14}

a17ActiveInputVoltageRange OBJECT-TYPE
	SYNTAX		INTEGER {
		vOther                                  	(1),
		vUnknown                                	(2),
		vRange1                                 	(3),
		vRange2                                 	(4),
		vBoth                                   	(5)
	}
	ACCESS		read-only
	STATUS		mandatory
	DESCRIPTION	"The value of this attribute indicates which input voltage
range of thisPower Supply is currently active."
	::= {ePowerSupply 15}

a17InputVoltageRangeSwitching OBJECT-TYPE
	SYNTAX		INTEGER {
		vOther                                  	(1),
		vUnknown                                	(2),
		vManual                                 	(3),
		vAutoswitch                             	(4),
		vWideRange                              	(5),
		vNotApplicable                          	(6)
	}
	ACCESS		read-only
	STATUS		mandatory
	DESCRIPTION	"This attribute describes the kind of input voltage range
switching that isimplemented in this power supply."
	::= {ePowerSupply 16}

a17Range1InputFrequencyLow OBJECT-TYPE
	SYNTAX		DmiInteger
	ACCESS		read-only
	STATUS		mandatory
	DESCRIPTION	"The frequency at the low end of this power supply's Input
FrequencyRange 1. A value of zero implies DC. A value of 0x80000000 denotes
'unknown'"
	::= {ePowerSupply 17}

a17Range1InputFrequencyHigh OBJECT-TYPE
	SYNTAX		DmiInteger
	ACCESS		read-only
	STATUS		mandatory
	DESCRIPTION	"The frequency at the high end of this power supply's Input
FrequencyRange 1. A value of zero implies DC. A value of 0x80000000 denotes
'unknown'"
	::= {ePowerSupply 18}

a17Range2InputFrequencyLow OBJECT-TYPE
	SYNTAX		DmiInteger
	ACCESS		read-only
	STATUS		mandatory
	DESCRIPTION	"The frequency at the low end of this power supply's Input
FrequencyRange 2. A value of zero implies DC. A value of 0x80000000 denotes
'unknown'"
	::= {ePowerSupply 19}

a17Range2InputFrequencyHigh OBJECT-TYPE
	SYNTAX		DmiInteger
	ACCESS		read-only
	STATUS		mandatory
	DESCRIPTION	"The frequency at the high end of this power supply's Input
FrequencyRange 2. A value of zero implies DC. A value of 0x80000000 denotes
'unknown'"
	::= {ePowerSupply 20}

a17TotalOutputPower OBJECT-TYPE
	SYNTAX		DmiInteger
	ACCESS		read-only
	STATUS		mandatory
	DESCRIPTION	"This attribute value represents the total output power of
this powersupply in milliWatts. 0x80000000 denotes 'unknown'"
	::= {ePowerSupply 21}

SSystemSlots ::= SEQUENCE {
	a19SlotIndex                            	DmiInteger,
	a19SlotType                             	DmiInteger64X,
	a19SlotWidth                            	DmiInteger,
	a19CurrentUsage                         	DmiInteger,
	a19SlotDescription                      	DmiDisplaystring,
	a19SlotCategory                         	DmiInteger,
	a19VirtualSlot                          	DmiInteger,
	a19ResourceUserId                       	DmiInteger
}

tSystemSlots OBJECT-TYPE
	SYNTAX		SEQUENCE OF SSystemSlots
	ACCESS		not-accessible
	STATUS		mandatory
	DESCRIPTION	"This group defines the attributes for the different system
expansion slotssupportedin this system."
	::= {dmtfGroups 19}

eSystemSlots OBJECT-TYPE
	SYNTAX		SSystemSlots
	ACCESS		not-accessible
	STATUS		mandatory
	DESCRIPTION	""
	INDEX		{DmiComponentIndex, a19SlotIndex}
	::= {tSystemSlots 1}

a19SlotIndex OBJECT-TYPE
	SYNTAX		DmiInteger
	ACCESS		read-only
	STATUS		mandatory
	DESCRIPTION	"An index into the system slot table. This is the hardware
ID number foreach expansion slot, whether it is occupied or not (starting
with 1)."
	::= {eSystemSlots 1}

a19SlotType OBJECT-TYPE
	SYNTAX		DmiInteger64X
	ACCESS		read-only
	STATUS		mandatory
	DESCRIPTION	"The bus type supported in this slot. This is a bit field
with the followingdefinitions: Bit 0 (2^0), if set, means it is a long-length
card; if 0, it is a short-length card, Bit 1(2^1), if set, indicates ISA,
Bit 2 (2^2) indicates EISA, Bit 3 (2^3) indicates MCA, Bit 4 (2^4) indicates
PCI, Bit 5 (2^5) indicates VL,Bit 6 (2^6) indicates PCMCIA, Bit (2^7) refers
to NuBus, Bit 8 (2^8) indicates PC-98/C20, Bit 9 (2^9) indicates PC-98/C24,
Bit 10 (2^10) indicates PC-98/E, Bit 11 (2^11) indicates PC-98/Local "
	::= {eSystemSlots 2}

a19SlotWidth OBJECT-TYPE
	SYNTAX		INTEGER {
		vOther                                  	(1),
		vUnknown                                	(2),
		v8BitCard                               	(3),
		v16BitCard                              	(4),
		v32BitCard                              	(5),
		v64BitCard                              	(6),
		v128BitCard                             	(7)
	}
	ACCESS		read-only
	STATUS		mandatory
	DESCRIPTION	"The maximum bus width of cards accepted in this slot."
	::= {eSystemSlots 3}

a19CurrentUsage OBJECT-TYPE
	SYNTAX		INTEGER {
		vOther                                  	(1),
		vUnknown                                	(2),
		vAvailable                              	(3),
		vInUse                                  	(4)
	}
	ACCESS		read-only
	STATUS		mandatory
	DESCRIPTION	"Is this slot is currently in use?"
	::= {eSystemSlots 4}

a19SlotDescription OBJECT-TYPE
	SYNTAX		DmiDisplaystring
	ACCESS		read-only
	STATUS		mandatory
	DESCRIPTION	"The card currently occupying this slot."
	::= {eSystemSlots 5}

a19SlotCategory OBJECT-TYPE
	SYNTAX		INTEGER {
		vOther                                  	(1),
		vUnknown                                	(2),
		vBusConnector                           	(3),
		vPcmciaSlot                             	(4),
		vMotherboard                            	(5)
	}
	ACCESS		read-only
	STATUS		mandatory
	DESCRIPTION	"The word 'slot' is used to refer to bus slots. The last case
(motherboard)refers to situations where a functional element is integrated
onto, say, a motherboardand connects to a bus without a connector. It still
takes up an expansion site on the busbut this is termed a 'virtual slot'
as opposed to a physical slot (see the attribute 'VirtualSlot'). Virtual
slots are in effect permanently occupied expansion sites. This attributeestablis
es which category of physical slot this table entry is defining."
	::= {eSystemSlots 6}

a19VirtualSlot OBJECT-TYPE
	SYNTAX		INTEGER {
		vFalse                                  	(0),
		vTrue                                   	(1),
		vUnknown                                	(2)
	}
	ACCESS		read-only
	STATUS		mandatory
	DESCRIPTION	"This attribute indicates whether this is a 'virtual slot'
or not. A 'virtualslot' is an expansion site that is permanently occupied
because of the level ofintegration of an expandable component. An example
of a virtual slot is an I/O busposition taken up by a LAN controller that
is integrated onto a motherboard. A slot withthe 'Slot Category' of Motherboard
is typically a Virtual Slot."
	::= {eSystemSlots 7}

a19ResourceUserId OBJECT-TYPE
	SYNTAX		DmiInteger
	ACCESS		read-only
	STATUS		mandatory
	DESCRIPTION	"Value used to locate the rows in the System Resources 2 table
forthe resources associated with this slot or expansion site. 0 = 'unspecified'."
	::= {eSystemSlots 8}

SFieldReplaceableUnit ::= SEQUENCE {
	a30FruIndex                             	DmiInteger,
	a30DeviceGroupIndex                     	DmiInteger,
	a30Description                          	DmiDisplaystring,
	a30Manufacturer                         	DmiDisplaystring,
	a30Model                                	DmiDisplaystring,
	a30PartNumber                           	DmiDisplaystring,
	a30FruSerialNumber                      	DmiDisplaystring,
	a30RevisionLevel                        	DmiDisplaystring,
	a30WarrantyStartDate                    	DmiDateX,
	a30WarrantyDuration                     	DmiInteger,
	a30SupportPhoneNumber                   	DmiDisplaystring,
	a30FruInternetUniformResourceLocator    	DmiDisplaystring
}

tFieldReplaceableUnit OBJECT-TYPE
	SYNTAX		SEQUENCE OF SFieldReplaceableUnit
	ACCESS		not-accessible
	STATUS		mandatory
	DESCRIPTION	"A Field Replaceable Unit (FRU), is defined as a hardware
componentwhich is designed to be separately removable for replacement or
repair. For thepurposes of this definition, a motherboard and a fixed hard
disk are FRUs, whereas afixed hard disk platter or a chip fixed in place
on the motherboard are not FRUs sincethey are not designed to be separately
removable. Each instance within the FRU tableshould contain the device group
and instance data for the associated hardwarecomponent."
	::= {dmtfGroups 30}

eFieldReplaceableUnit OBJECT-TYPE
	SYNTAX		SFieldReplaceableUnit
	ACCESS		not-accessible
	STATUS		mandatory
	DESCRIPTION	""
	INDEX		{DmiComponentIndex, a30FruIndex}
	::= {tFieldReplaceableUnit 1}

a30FruIndex OBJECT-TYPE
	SYNTAX		DmiInteger
	ACCESS		read-only
	STATUS		mandatory
	DESCRIPTION	"The index into the Field Replaceable Unit table."
	::= {eFieldReplaceableUnit 1}

a30DeviceGroupIndex OBJECT-TYPE
	SYNTAX		DmiInteger
	ACCESS		read-only
	STATUS		mandatory
	DESCRIPTION	"The group ID of the group referencing this Field Replaceable
Unitinstance."
	::= {eFieldReplaceableUnit 2}

a30Description OBJECT-TYPE
	SYNTAX		DmiDisplaystring
	ACCESS		read-only
	STATUS		mandatory
	DESCRIPTION	"A clear description of this Field Replaceable Unit."
	::= {eFieldReplaceableUnit 3}

a30Manufacturer OBJECT-TYPE
	SYNTAX		DmiDisplaystring
	ACCESS		read-only
	STATUS		mandatory
	DESCRIPTION	"The name of the company manufacturing or providing this FieldRep
aceableUnit."
	::= {eFieldReplaceableUnit 4}

a30Model OBJECT-TYPE
	SYNTAX		DmiDisplaystring
	ACCESS		read-only
	STATUS		mandatory
	DESCRIPTION	"The manufacturer's model number for this Field Replaceable
Unit."
	::= {eFieldReplaceableUnit 5}

a30PartNumber OBJECT-TYPE
	SYNTAX		DmiDisplaystring
	ACCESS		read-only
	STATUS		mandatory
	DESCRIPTION	"A part number by which a replacement part can be ordered
for this FieldReplaceable Unit."
	::= {eFieldReplaceableUnit 6}

a30FruSerialNumber OBJECT-TYPE
	SYNTAX		DmiDisplaystring
	ACCESS		read-only
	STATUS		mandatory
	DESCRIPTION	"The manufacturer's serial number for this Field Replaceable
Unit."
	::= {eFieldReplaceableUnit 7}

a30RevisionLevel OBJECT-TYPE
	SYNTAX		DmiDisplaystring
	ACCESS		read-only
	STATUS		mandatory
	DESCRIPTION	"The revision level of this Field Replaceable Unit."
	::= {eFieldReplaceableUnit 8}

a30WarrantyStartDate OBJECT-TYPE
	SYNTAX		DmiDateX
	ACCESS		read-only
	STATUS		mandatory
	DESCRIPTION	"The start date of the service warranty for this Field Replaceabl
 Unit."
	::= {eFieldReplaceableUnit 9}

a30WarrantyDuration OBJECT-TYPE
	SYNTAX		DmiInteger
	ACCESS		read-only
	STATUS		mandatory
	DESCRIPTION	"The total duration of this Field Replaceable Unit warranty
in months."
	::= {eFieldReplaceableUnit 10}

a30SupportPhoneNumber OBJECT-TYPE
	SYNTAX		DmiDisplaystring
	ACCESS		read-only
	STATUS		mandatory
	DESCRIPTION	"The phone number(s) for support for this Field Replaceable
Unit."
	::= {eFieldReplaceableUnit 11}

a30FruInternetUniformResourceLocator OBJECT-TYPE
	SYNTAX		DmiDisplaystring
	ACCESS		read-only
	STATUS		mandatory
	DESCRIPTION	"The Internet Uniform Resource Locator string that can be
used through a World Wide Web browser to obtain further information about
this FRU"
	::= {eFieldReplaceableUnit 12}

SOperationalState ::= SEQUENCE {
	a31OperationalStateInstanceIndex        	DmiInteger,
	a31DeviceGroupIndex                     	DmiInteger,
	a31OperationalStatus                    	DmiInteger,
	a31UsageState                           	DmiInteger,
	a31AvailabilityStatus                   	DmiInteger,
	a31AdministrativeState                  	DmiInteger,
	a31FatalErrorCount                      	DmiCounter,
	a31MajorErrorCount                      	DmiCounter,
	a31WarningErrorCount                    	DmiCounter,
	a31CurrentErrorStatus                   	DmiInteger
}

tOperationalState OBJECT-TYPE
	SYNTAX		SEQUENCE OF SOperationalState
	ACCESS		not-accessible
	STATUS		mandatory
	DESCRIPTION	"This group provides the operational state, usage, and availabili
y status,and administrative state indicators for specific Device Group instances
"
	::= {dmtfGroups 31}

eOperationalState OBJECT-TYPE
	SYNTAX		SOperationalState
	ACCESS		not-accessible
	STATUS		mandatory
	DESCRIPTION	""
	INDEX		{DmiComponentIndex, a31OperationalStateInstanceIndex}
	::= {tOperationalState 1}

a31OperationalStateInstanceIndex OBJECT-TYPE
	SYNTAX		DmiInteger
	ACCESS		read-only
	STATUS		mandatory
	DESCRIPTION	"The Index into the Operational State table."
	::= {eOperationalState 1}

a31DeviceGroupIndex OBJECT-TYPE
	SYNTAX		DmiInteger
	ACCESS		read-only
	STATUS		mandatory
	DESCRIPTION	"The group ID of the group referencing this instance."
	::= {eOperationalState 2}

a31OperationalStatus OBJECT-TYPE
	SYNTAX		INTEGER {
		vOther                                  	(1),
		vUnknown                                	(2),
		vEnabled                                	(3),
		vDisabled                               	(4),
		vNotApplicable                          	(5)
	}
	ACCESS		read-only
	STATUS		mandatory
	DESCRIPTION	"The operational status of the Device Group instance."
	::= {eOperationalState 3}

a31UsageState OBJECT-TYPE
	SYNTAX		INTEGER {
		vOther                                  	(1),
		vUnknown                                	(2),
		vIdle                                   	(3),
		vActive                                 	(4),
		vBusy                                   	(5),
		vNotApplicable                          	(6)
	}
	ACCESS		read-only
	STATUS		mandatory
	DESCRIPTION	"The usage state of the Device Group instance."
	::= {eOperationalState 4}

a31AvailabilityStatus OBJECT-TYPE
	SYNTAX		INTEGER {
		vOther                                  	(1),
		vUnknown                                	(2),
		vRunning                                	(3),
		vWarning                                	(4),
		vInTest                                 	(5),
		vNotApplicable                          	(6),
		vPowerOff                               	(7),
		vOffLine                                	(8),
		vOffDuty                                	(9),
		vDegraded                               	(10),
		vNotInstalled                           	(11),
		vInstallError                           	(12),
		vPowerSave                              	(13)
	}
	ACCESS		read-only
	STATUS		mandatory
	DESCRIPTION	"The availability status of the Device Group instance."
	::= {eOperationalState 5}

a31AdministrativeState OBJECT-TYPE
	SYNTAX		INTEGER {
		vOther                                  	(1),
		vUnknown                                	(2),
		vLocked                                 	(3),
		vUnlocked                               	(4),
		vNotApplicable                          	(5),
		vShuttingDown                           	(6)
	}
	ACCESS		read-only
	STATUS		mandatory
	DESCRIPTION	"The administrative state of the Device Group instance."
	::= {eOperationalState 6}

a31FatalErrorCount OBJECT-TYPE
	SYNTAX		DmiCounter
	ACCESS		read-only
	STATUS		mandatory
	DESCRIPTION	"The accumulated Fatal or Non-recoverable error count for
this DeviceGroup instance."
	::= {eOperationalState 7}

a31MajorErrorCount OBJECT-TYPE
	SYNTAX		DmiCounter
	ACCESS		read-only
	STATUS		mandatory
	DESCRIPTION	"The accumulated Major or Critical error count for this Device
Groupinstance."
	::= {eOperationalState 8}

a31WarningErrorCount OBJECT-TYPE
	SYNTAX		DmiCounter
	ACCESS		read-only
	STATUS		mandatory
	DESCRIPTION	"The accumulated Warning or Non-Critical error count for this
DeviceGroup instance."
	::= {eOperationalState 9}

a31CurrentErrorStatus OBJECT-TYPE
	SYNTAX		INTEGER {
		vOther                                  	(1),
		vUnknown                                	(2),
		vOk                                     	(3),
		vNon-critical                           	(4),
		vCritical                               	(5),
		vNon-recoverable                        	(6)
	}
	ACCESS		read-only
	STATUS		mandatory
	DESCRIPTION	"This attribute presents the current error status for this
Device Groupinstance. The most critical error status in effect should be
presented. I.e. if a part of theDevice Group instance is 'Critical', while
other status is 'Non-critical' then the status'Critical' should be reported."
	::= {eOperationalState 10}

SPhysicalMemoryArray ::= SEQUENCE {
	a34MemoryArrayTableIndex                	DmiInteger,
	a34MemoryArrayLocation                  	DmiInteger,
	a34MemoryArrayUse                       	DmiInteger,
	a34MaximumMemoryCapacity                	DmiInteger,
	a34NumberOfMemoryDeviceSockets          	DmiInteger,
	a34NumberOfMemoryDeviceSocketsUsed      	DmiInteger,
	a34MemoryErrorCorrection                	DmiInteger,
	a34ArrayErrorType                       	DmiInteger,
	a34LastErrorUpdate                      	DmiInteger,
	a34ErrorOperation                       	DmiInteger,
	a34ErrorDataSize                        	DmiInteger,
	a34ErrorData                            	DmiOctetstring,
	a34VendorSyndrome                       	DmiOctetstring,
	a34ErrorAddress                         	DmiInteger64X,
	a34ErrorResolution                      	DmiInteger,
	a34FruGroupIndex                        	DmiInteger,
	a34OperationalGroupIndex                	DmiInteger
}

tPhysicalMemoryArray OBJECT-TYPE
	SYNTAX		SEQUENCE OF SPhysicalMemoryArray
	ACCESS		not-accessible
	STATUS		mandatory
	DESCRIPTION	"This group represents an array of physical memory as a collectio
 ofone or more Memory Devices associated in sets and partitions."
	::= {dmtfGroups 34}

ePhysicalMemoryArray OBJECT-TYPE
	SYNTAX		SPhysicalMemoryArray
	ACCESS		not-accessible
	STATUS		mandatory
	DESCRIPTION	""
	INDEX		{DmiComponentIndex, a34MemoryArrayTableIndex}
	::= {tPhysicalMemoryArray 1}

a34MemoryArrayTableIndex OBJECT-TYPE
	SYNTAX		DmiInteger
	ACCESS		read-only
	STATUS		mandatory
	DESCRIPTION	"A unique number that identifies this row."
	::= {ePhysicalMemoryArray 1}

a34MemoryArrayLocation OBJECT-TYPE
	SYNTAX		INTEGER {
		vOther                                  	(1),
		vUnknown                                	(2),
		vSystemBoardOrMotherboard               	(3),
		vIsaAdd-onCard                          	(4),
		vEisaAdd-onCard                         	(5),
		vPciAdd-onCard                          	(6),
		vMcaAdd-onCard                          	(7),
		vPcmciaAdd-onCard                       	(8),
		vProprietaryAdd-onCard                  	(9),
		vNubus                                  	(16),
		vPc-98c20Add-onCard                     	(160),
		vPc-98c24Add-onCard                     	(161),
		vPc-98eAdd-onCard                       	(162),
		vPc-98localBusAdd-onCard                	(163),
		vPc-98cardSlotAdd-onCard                	(164)
	}
	ACCESS		read-only
	STATUS		mandatory
	DESCRIPTION	"The physical location of the Memory Array, whether on the
systemboard or an add-on board."
	::= {ePhysicalMemoryArray 2}

a34MemoryArrayUse OBJECT-TYPE
	SYNTAX		INTEGER {
		vOther                                  	(1),
		vUnknown                                	(2),
		vSystemMemory                           	(3),
		vVideoMemory                            	(4),
		vFlashMemory                            	(5),
		vNonVolatileRam                         	(6),
		vCacheMemory                            	(7)
	}
	ACCESS		read-only
	STATUS		mandatory
	DESCRIPTION	"What this Memory Array is used for."
	::= {ePhysicalMemoryArray 3}

a34MaximumMemoryCapacity OBJECT-TYPE
	SYNTAX		DmiInteger
	ACCESS		read-only
	STATUS		mandatory
	DESCRIPTION	"The maximum memory capacity, in kilobytes, on this array.
0x80000000denotes 'unknown'."
	::= {ePhysicalMemoryArray 4}

a34NumberOfMemoryDeviceSockets OBJECT-TYPE
	SYNTAX		DmiInteger
	ACCESS		read-only
	STATUS		mandatory
	DESCRIPTION	"The number of SIMM slots or sockets available for Memory
Devices inthis array. 0x80000000 denotes 'unknown'."
	::= {ePhysicalMemoryArray 5}

a34NumberOfMemoryDeviceSocketsUsed OBJECT-TYPE
	SYNTAX		DmiInteger
	ACCESS		read-only
	STATUS		mandatory
	DESCRIPTION	"The number of SIMM slots or sockets in use for Memory Devices
in thisarray. 0x80000000 denotes 'unknown'."
	::= {ePhysicalMemoryArray 6}

a34MemoryErrorCorrection OBJECT-TYPE
	SYNTAX		INTEGER {
		vOther                                  	(1),
		vUnknown                                	(2),
		vNone                                   	(3),
		vParity                                 	(4),
		vSingleBitEcc                           	(5),
		vMultibitEcc                            	(6),
		vCrc                                    	(7)
	}
	ACCESS		read-only
	STATUS		mandatory
	DESCRIPTION	"The main hardware error correction or detection method supported
bythis Memory Array."
	::= {ePhysicalMemoryArray 7}

a34ArrayErrorType OBJECT-TYPE
	SYNTAX		INTEGER {
		vOther                                  	(1),
		vUnknown                                	(2),
		vOk                                     	(3),
		vBadRead                                	(4),
		vParityError                            	(5),
		vSingle-bitError                        	(6),
		vDouble-bitError                        	(7),
		vMulti-bitError                         	(8),
		vNibbleError                            	(9),
		vChecksumError                          	(10),
		vCrcError                               	(11),
		vCorrectedSingle-bitError               	(12),
		vCorrectedError                         	(13),
		vUncorrectableError                     	(14)
	}
	ACCESS		read-only
	STATUS		mandatory
	DESCRIPTION	"The type of error that is associated with the current status
reported inOperational State for this Memory Array."
	::= {ePhysicalMemoryArray 8}

a34LastErrorUpdate OBJECT-TYPE
	SYNTAX		INTEGER {
		vOther                                  	(1),
		vUnknown                                	(2),
		vNoUpdateSinceLastInstrumentationStart  	(3),
		vUpdatedFromInformationObtainedPriorToIn	(4),
		vUpdatedDuringInstrumentationRun-time   	(5)
	}
	ACCESS		read-only
	STATUS		mandatory
	DESCRIPTION	"System state during which last error status was collected."
	::= {ePhysicalMemoryArray 9}

a34ErrorOperation OBJECT-TYPE
	SYNTAX		INTEGER {
		vOther                                  	(1),
		vUnknown                                	(2),
		vRead                                   	(3),
		vWrite                                  	(4),
		vPartialWrite                           	(5)
	}
	ACCESS		read-only
	STATUS		mandatory
	DESCRIPTION	"The memory access operation that caused the current error."
	::= {ePhysicalMemoryArray 10}

a34ErrorDataSize OBJECT-TYPE
	SYNTAX		DmiInteger
	ACCESS		read-only
	STATUS		mandatory
	DESCRIPTION	"The size of the data transfer that caused the error, in bits.
Zero indicatesno error, 0x80000000 denotes 'unknown'."
	::= {ePhysicalMemoryArray 11}

a34ErrorData OBJECT-TYPE
	SYNTAX		DmiOctetstring
	ACCESS		read-only
	STATUS		mandatory
	DESCRIPTION	"Data captured during the erroneous Memory Array access. The
dataoccupy the first n bytes of the octetstring required to hold 'Error Data
Size' bits of thedata. Data are stored least-significant byte first."
	::= {ePhysicalMemoryArray 12}

a34VendorSyndrome OBJECT-TYPE
	SYNTAX		DmiOctetstring
	ACCESS		read-only
	STATUS		mandatory
	DESCRIPTION	"Vendor-specific syndrome or CRC data associated with the
erroneousaccess."
	::= {ePhysicalMemoryArray 13}

a34ErrorAddress OBJECT-TYPE
	SYNTAX		DmiInteger64X
	ACCESS		read-only
	STATUS		mandatory
	DESCRIPTION	"Physical address of the error based on the addressing of
the bus that theMemory Array is connected to. 0x8000 0000 0000 0000 denotes
'unknown'."
	::= {ePhysicalMemoryArray 14}

a34ErrorResolution OBJECT-TYPE
	SYNTAX		DmiInteger
	ACCESS		read-only
	STATUS		mandatory
	DESCRIPTION	"Range in bytes that the error can be determined to be within,
when anError Address is given. 0x80000000 denotes 'unknown'."
	::= {ePhysicalMemoryArray 15}

a34FruGroupIndex OBJECT-TYPE
	SYNTAX		DmiInteger
	ACCESS		read-only
	STATUS		mandatory
	DESCRIPTION	"If this is a Field Replaceable Unit or if it is part of another
FRU, thisprovides an index into the FRU table; 'value = -1' indicates that
the group is not aFRU."
	::= {ePhysicalMemoryArray 16}

a34OperationalGroupIndex OBJECT-TYPE
	SYNTAX		DmiInteger
	ACCESS		read-only
	STATUS		mandatory
	DESCRIPTION	"The index into the Operational State Table for this Memory
Array. TheOperational State row is used to hold the overall error count and
error status for thisarray."
	::= {ePhysicalMemoryArray 17}

SMemoryArrayMappedAddresses ::= SEQUENCE {
	a35MemoryArrayMappedAddressesTableIndex 	DmiInteger,
	a35MemoryArrayIndex                     	DmiInteger,
	a35MappedRangeStartingAddress           	DmiInteger,
	a35MappedRangeEndingAddress             	DmiInteger,
	a35PartitionId                          	DmiInteger,
	a35PartitionWidth                       	DmiInteger,
	a35OperationalGroupIndex                	DmiInteger
}

tMemoryArrayMappedAddresses OBJECT-TYPE
	SYNTAX		SEQUENCE OF SMemoryArrayMappedAddresses
	ACCESS		not-accessible
	STATUS		mandatory
	DESCRIPTION	"This table presents ranges of physical addresses that are
mapped to agiven Memory Array."
	::= {dmtfGroups 35}

eMemoryArrayMappedAddresses OBJECT-TYPE
	SYNTAX		SMemoryArrayMappedAddresses
	ACCESS		not-accessible
	STATUS		mandatory
	DESCRIPTION	""
	INDEX		{DmiComponentIndex, a35MemoryArrayMappedAddressesTableIndex}
	::= {tMemoryArrayMappedAddresses 1}

a35MemoryArrayMappedAddressesTableIndex OBJECT-TYPE
	SYNTAX		DmiInteger
	ACCESS		read-only
	STATUS		mandatory
	DESCRIPTION	"A unique number that identifies this row."
	::= {eMemoryArrayMappedAddresses 1}

a35MemoryArrayIndex OBJECT-TYPE
	SYNTAX		DmiInteger
	ACCESS		read-only
	STATUS		mandatory
	DESCRIPTION	"The ID of the Memory Array that this address range is mapped
to.Multiple address ranges may be mapped to a Memory Array."
	::= {eMemoryArrayMappedAddresses 2}

a35MappedRangeStartingAddress OBJECT-TYPE
	SYNTAX		DmiInteger
	ACCESS		read-only
	STATUS		mandatory
	DESCRIPTION	"The physical starting address, in kilobytes, of a range of
memorymapped to the specified Memory Array. 0x80000000 denotes 'unknown'."
	::= {eMemoryArrayMappedAddresses 3}

a35MappedRangeEndingAddress OBJECT-TYPE
	SYNTAX		DmiInteger
	ACCESS		read-only
	STATUS		mandatory
	DESCRIPTION	"The physical ending address of the last kilobyte of a range
of addressesmapped to the specified Memory Array. 0x80000000 denotes 'unknown'."
	::= {eMemoryArrayMappedAddresses 4}

a35PartitionId OBJECT-TYPE
	SYNTAX		DmiInteger
	ACCESS		read-only
	STATUS		mandatory
	DESCRIPTION	"Identifies a Memory Partition associated with the Memory
Arrayspecified by Memory Array Table Index. 0x80000000 denotes 'unknown'."
	::= {eMemoryArrayMappedAddresses 5}

a35PartitionWidth OBJECT-TYPE
	SYNTAX		DmiInteger
	ACCESS		read-only
	STATUS		mandatory
	DESCRIPTION	"The number of Memory Devices that form a single row of memory
forthe partition. 0x80000000 denotes 'unknown'."
	::= {eMemoryArrayMappedAddresses 6}

a35OperationalGroupIndex OBJECT-TYPE
	SYNTAX		DmiInteger
	ACCESS		read-only
	STATUS		mandatory
	DESCRIPTION	"The index into the Operational State Table for this Memory
Range.Generally, there will be a 1:1 correspondence between a mapped range
and a partition.In which case, the Operational State will be for the partition
as well. In the case thatthere is more than one mapped range for a partion,
it will be necessary to check theOperational State entries for each range
to determine the overall status of the partition."
	::= {eMemoryArrayMappedAddresses 7}

SMemoryDevice ::= SEQUENCE {
	a36MemoryDeviceTableIndex               	DmiInteger,
	a36MemoryArrayIndex                     	DmiInteger,
	a36DeviceLocator                        	DmiDisplaystring,
	a36BankLocator                          	DmiDisplaystring,
	a36Size                                 	DmiInteger,
	a36FormFactor                           	DmiInteger,
	a36TotalWidth                           	DmiInteger,
	a36DataWidth                            	DmiInteger,
	a36MemoryType                           	DmiInteger,
	a36TypeDetail                           	DmiInteger,
	a36DeviceSet                            	DmiInteger,
	a36DeviceErrorType                      	DmiInteger,
	a36ErrorGranularity                     	DmiInteger,
	a36LastErrorUpdate                      	DmiInteger,
	a36ErrorOperation                       	DmiInteger,
	a36ErrorDataSize                        	DmiInteger,
	a36ErrorData                            	DmiOctetstring,
	a36VendorSyndrome                       	DmiOctetstring,
	a36DeviceErrorAddress                   	DmiInteger,
	a36ArrayErrorAddress                    	DmiInteger,
	a36ErrorResolution                      	DmiInteger,
	a36FruGroupIndex                        	DmiInteger,
	a36OperationalGroupIndex                	DmiInteger
}

tMemoryDevice OBJECT-TYPE
	SYNTAX		SEQUENCE OF SMemoryDevice
	ACCESS		not-accessible
	STATUS		mandatory
	DESCRIPTION	"This group presents information about individual memory devices
in thesystem. A memory device can be a SIMM, a SIPP, or a single chip, or
an entire card -based on the resolution to which a memory error can be determine
 and whether thedevice is replaceable as a unit."
	::= {dmtfGroups 36}

eMemoryDevice OBJECT-TYPE
	SYNTAX		SMemoryDevice
	ACCESS		not-accessible
	STATUS		mandatory
	DESCRIPTION	""
	INDEX		{DmiComponentIndex, a36MemoryDeviceTableIndex}
	::= {tMemoryDevice 1}

a36MemoryDeviceTableIndex OBJECT-TYPE
	SYNTAX		DmiInteger
	ACCESS		read-only
	STATUS		mandatory
	DESCRIPTION	"A unique number that identifies this row."
	::= {eMemoryDevice 1}

a36MemoryArrayIndex OBJECT-TYPE
	SYNTAX		DmiInteger
	ACCESS		read-only
	STATUS		mandatory
	DESCRIPTION	"The ID of the Memory Array that this Memory Device is a part
of."
	::= {eMemoryDevice 2}

a36DeviceLocator OBJECT-TYPE
	SYNTAX		DmiDisplaystring
	ACCESS		read-only
	STATUS		mandatory
	DESCRIPTION	"A string identifying the physically labeled socket or board
positionwhere the memory device is located. Eg. 'SIMM 3' or 'IC12'."
	::= {eMemoryDevice 3}

a36BankLocator OBJECT-TYPE
	SYNTAX		DmiDisplaystring
	ACCESS		read-only
	STATUS		mandatory
	DESCRIPTION	"A string identifying the physically labeled bank where the
memorydevice is located. Eg. 'Bank 0' or 'A'."
	::= {eMemoryDevice 4}

a36Size OBJECT-TYPE
	SYNTAX		DmiInteger
	ACCESS		read-only
	STATUS		mandatory
	DESCRIPTION	"Size of this memory device, in bytes."
	::= {eMemoryDevice 5}

a36FormFactor OBJECT-TYPE
	SYNTAX		INTEGER {
		vOther                                  	(1),
		vUnknown                                	(2),
		vSimm                                   	(3),
		vSip                                    	(4),
		vChip                                   	(5),
		vDip                                    	(6),
		vZip                                    	(7),
		vProprietaryCard                        	(8),
		vDimm                                   	(9),
		vTsop                                   	(10),
		vRowOfChips                             	(11)
	}
	ACCESS		read-only
	STATUS		mandatory
	DESCRIPTION	"Implementation form factor for this memory device."
	::= {eMemoryDevice 6}

a36TotalWidth OBJECT-TYPE
	SYNTAX		DmiInteger
	ACCESS		read-only
	STATUS		mandatory
	DESCRIPTION	"Total width of this memory device, including check or error
correctionbits, in bits. If there are no error correction bits, the value
in this attribute should matchthat specified in Data Width. 0x80000000 denotes
'unknown'."
	::= {eMemoryDevice 7}

a36DataWidth OBJECT-TYPE
	SYNTAX		DmiInteger
	ACCESS		read-only
	STATUS		mandatory
	DESCRIPTION	"Data width of this memory device, in bits. A data width of
0 and a TotalWidth of 8 would indicate that the device is solely being used
to provide eight errorcorrection bits. 0x80000000 denotes 'unknown'."
	::= {eMemoryDevice 8}

a36MemoryType OBJECT-TYPE
	SYNTAX		INTEGER {
		vOther                                  	(1),
		vUnknown                                	(2),
		vDram                                   	(3),
		vEdram                                  	(4),
		vVram                                   	(5),
		vSram                                   	(6),
		vRam                                    	(7),
		vRom                                    	(8),
		vFlash                                  	(9),
		vEeprom                                 	(10),
		vFeprom                                 	(11),
		vEprom                                  	(12)
	}
	ACCESS		read-only
	STATUS		mandatory
	DESCRIPTION	"Type of memory used in this memory device."
	::= {eMemoryDevice 9}

a36TypeDetail OBJECT-TYPE
	SYNTAX		INTEGER {
		vOther                                  	(1),
		vUnknown                                	(2),
		vFastPaged                              	(3),
		vStaticColumn                           	(4),
		vPseudo-static                          	(5),
		vRambus                                 	(6),
		vSynchronous                            	(7),
		vCmos                                   	(8),
		vEdo                                    	(9),
		vWindowDram                             	(10),
		vCacheDram                              	(11),
		vNon-volatile                           	(12)
	}
	ACCESS		read-only
	STATUS		mandatory
	DESCRIPTION	"Additional detail on the device type."
	::= {eMemoryDevice 10}

a36DeviceSet OBJECT-TYPE
	SYNTAX		DmiInteger
	ACCESS		read-only
	STATUS		mandatory
	DESCRIPTION	"This attribute is used to identify when the Memory Device
is one of a setof Memory Devices that must be populated with all devices
of the same type and size, and which set the device belongs to. For example,
when one SIMM belongs to a set offour. 0 indicates the Memory Device isn't
part of a set.  0x80000000 denotes 'unknown'."
	::= {eMemoryDevice 11}

a36DeviceErrorType OBJECT-TYPE
	SYNTAX		INTEGER {
		vOther                                  	(1),
		vUnknown                                	(2),
		vOk                                     	(3),
		vBadRead                                	(4),
		vParityError                            	(5),
		vSingle-bitError                        	(6),
		vDouble-bitError                        	(7),
		vMulti-bitError                         	(8),
		vNibbleError                            	(9),
		vChecksumError                          	(10),
		vCrcError                               	(11),
		vCorrectedSingle-bitError               	(12),
		vCorrectedError                         	(13),
		vUncorrectableError                     	(14)
	}
	ACCESS		read-only
	STATUS		mandatory
	DESCRIPTION	"The type of error that is associated with the current status
reported inOperational State for this Memory Device."
	::= {eMemoryDevice 12}

a36ErrorGranularity OBJECT-TYPE
	SYNTAX		INTEGER {
		vOther                                  	(1),
		vUnknown                                	(2),
		vDeviceLevel                            	(3),
		vMemoryPartitionLevel                   	(4)
	}
	ACCESS		read-only
	STATUS		mandatory
	DESCRIPTION	"Specifies whether the current error's location can be resolved
to thepartition or device level."
	::= {eMemoryDevice 13}

a36LastErrorUpdate OBJECT-TYPE
	SYNTAX		INTEGER {
		vOther                                  	(1),
		vUnknown                                	(2),
		vNoUpdateSinceLastInstrumentationStart  	(3),
		vUpdatedFromInformationObtainedPriorToIn	(4),
		vUpdatedDuringInstrumentationRun-time   	(5)
	}
	ACCESS		read-only
	STATUS		mandatory
	DESCRIPTION	"System state during which the last error update was collected."
	::= {eMemoryDevice 14}

a36ErrorOperation OBJECT-TYPE
	SYNTAX		INTEGER {
		vOther                                  	(1),
		vUnknown                                	(2),
		vRead                                   	(3),
		vWrite                                  	(4),
		vPartialWrite                           	(5)
	}
	ACCESS		read-only
	STATUS		mandatory
	DESCRIPTION	"The memory access operation that caused the current error."
	::= {eMemoryDevice 15}

a36ErrorDataSize OBJECT-TYPE
	SYNTAX		DmiInteger
	ACCESS		read-only
	STATUS		mandatory
	DESCRIPTION	"The size of the data transfer that caused the error,in bits.
Zero indicatesno error, 0x80000000 denotes 'unknown'."
	::= {eMemoryDevice 16}

a36ErrorData OBJECT-TYPE
	SYNTAX		DmiOctetstring
	ACCESS		read-only
	STATUS		mandatory
	DESCRIPTION	"Data captured during the erroneous Memory Array access. The
dataoccupies the first n bytes of the octetstring required to hold 'Error
Data Size' bits of thedata. Data is stored least-significant byte first."
	::= {eMemoryDevice 17}

a36VendorSyndrome OBJECT-TYPE
	SYNTAX		DmiOctetstring
	ACCESS		read-only
	STATUS		mandatory
	DESCRIPTION	"Vendor-specific syndrome or CRC data associated withthe erroneou
access."
	::= {eMemoryDevice 18}

a36DeviceErrorAddress OBJECT-TYPE
	SYNTAX		DmiInteger
	ACCESS		read-only
	STATUS		mandatory
	DESCRIPTION	"Physical address of the error relative to the start of the
device, in bytes.0x80000000 denotes 'unknown'."
	::= {eMemoryDevice 19}

a36ArrayErrorAddress OBJECT-TYPE
	SYNTAX		DmiInteger
	ACCESS		read-only
	STATUS		mandatory
	DESCRIPTION	"Physical address of the kilobyte where the error is located,
relative to thebus for the Memory Array. 0x80000000 denotes 'unknown'."
	::= {eMemoryDevice 20}

a36ErrorResolution OBJECT-TYPE
	SYNTAX		DmiInteger
	ACCESS		read-only
	STATUS		mandatory
	DESCRIPTION	"Range in bytes that the error can be determined to be within,
when anError Address is given. 0x80000000 denotes 'unknown'."
	::= {eMemoryDevice 21}

a36FruGroupIndex OBJECT-TYPE
	SYNTAX		DmiInteger
	ACCESS		read-only
	STATUS		mandatory
	DESCRIPTION	"If this is a Field Replaceable Unit or if it is partof another
FRU, thisprovides an index into the FRU table; 'value = -1' indicates that
the group is not a FRU."
	::= {eMemoryDevice 22}

a36OperationalGroupIndex OBJECT-TYPE
	SYNTAX		DmiInteger
	ACCESS		read-only
	STATUS		mandatory
	DESCRIPTION	"The index into the Operational State Table for this device."
	::= {eMemoryDevice 23}

SMemoryDeviceMappedAddresses ::= SEQUENCE {
	a37MemoryDeviceMappedAddressesTableIndex	DmiInteger,
	a37MemoryDeviceSetId                    	DmiInteger,
	a37Partition                            	DmiInteger,
	a37MappedRangeStartingAddress           	DmiInteger,
	a37MappedRangeEndingAddress             	DmiInteger,
	a37PartitionRowPosition                 	DmiInteger,
	a37InterleavePosition                   	DmiInteger,
	a37DataDepth                            	DmiInteger
}

tMemoryDeviceMappedAddresses OBJECT-TYPE
	SYNTAX		SEQUENCE OF SMemoryDeviceMappedAddresses
	ACCESS		not-accessible
	STATUS		mandatory
	DESCRIPTION	"This table presents ranges of physical addresses that are
mapped to agiven Memory Device Set."
	::= {dmtfGroups 37}

eMemoryDeviceMappedAddresses OBJECT-TYPE
	SYNTAX		SMemoryDeviceMappedAddresses
	ACCESS		not-accessible
	STATUS		mandatory
	DESCRIPTION	""
	INDEX		{DmiComponentIndex, a37MemoryDeviceMappedAddressesTableIndex}
	::= {tMemoryDeviceMappedAddresses 1}

a37MemoryDeviceMappedAddressesTableIndex OBJECT-TYPE
	SYNTAX		DmiInteger
	ACCESS		read-only
	STATUS		mandatory
	DESCRIPTION	"A unique number that identifies this row."
	::= {eMemoryDeviceMappedAddresses 1}

a37MemoryDeviceSetId OBJECT-TYPE
	SYNTAX		DmiInteger
	ACCESS		read-only
	STATUS		mandatory
	DESCRIPTION	"The row in the Memory Device table that this address range
is for. Thismatches with a Memory Device Table Index. There may be multiple
rows in MemoryDevice Mapped addresses for a single Memory Device."
	::= {eMemoryDeviceMappedAddresses 2}

a37Partition OBJECT-TYPE
	SYNTAX		DmiInteger
	ACCESS		read-only
	STATUS		mandatory
	DESCRIPTION	"Identifies the Memory partition in the Memory Array Mapped
Addressestable that this Memory Device is part of. Partition number should
be positive.0x80000000 denotes 'unknown'."
	::= {eMemoryDeviceMappedAddresses 3}

a37MappedRangeStartingAddress OBJECT-TYPE
	SYNTAX		DmiInteger
	ACCESS		read-only
	STATUS		mandatory
	DESCRIPTION	"The physical starting address, in kilobytes, of a range of
memorymapped to the specified Memory Device set. The address is specified
relative to the busthat the device is connected to. 0x80000000 denotes 'unknown'
"
	::= {eMemoryDeviceMappedAddresses 4}

a37MappedRangeEndingAddress OBJECT-TYPE
	SYNTAX		DmiInteger
	ACCESS		read-only
	STATUS		mandatory
	DESCRIPTION	"The physical ending address of the last kilobyte of a range
of addressesmapped to the specified Memory Device. The address is specified
relative to the busthat the device is connected to. 0x80000000 denotes 'unknown'
"
	::= {eMemoryDeviceMappedAddresses 5}

a37PartitionRowPosition OBJECT-TYPE
	SYNTAX		DmiInteger
	ACCESS		read-only
	STATUS		mandatory
	DESCRIPTION	"This specifies the position of the device in a row of the
partition. Forexample, if it takes two 8-bit memory devices to form a 16-bit
row, then a value of '2'in this attribute means the device is the second
device. 0 is an invalid return value.0x80000000 denotes 'unknown'."
	::= {eMemoryDeviceMappedAddresses 6}

a37InterleavePosition OBJECT-TYPE
	SYNTAX		DmiInteger
	ACCESS		read-only
	STATUS		mandatory
	DESCRIPTION	"The position of this device in an interleave. 0 indicates
non-interleaved.1 indicates the first position  2 the second, and so on.
For example, in a 2:1 interleave,a value of '1' would indicate the device
is in the 'even' position, in a 4:1 interleave thiswould be the first of
four possible positions). 0x80000000 denotes 'unknown' or'unsupported'."
	::= {eMemoryDeviceMappedAddresses 7}

a37DataDepth OBJECT-TYPE
	SYNTAX		DmiInteger
	ACCESS		read-only
	STATUS		mandatory
	DESCRIPTION	"The maximum number of consecutive rows accessed from this
device ina single interleaved transfer. For example, if a device transfer
two rows each time it'sread it's Interleaved Data Depth would be 2. If that
device is 2:1 interleaved and inInterleave Position '1' then the rows mapped
to that device would be rows1,2,5,6,9,10,etc. If the device is not part of
an interleave, this value should be 0.0x80000000 denotes 'unknown'."
	::= {eMemoryDeviceMappedAddresses 8}

SSystemHardwareSecurity ::= SEQUENCE {
	a50Power-onPasswordStatus               	DmiInteger,
	a50KeyboardPasswordStatus               	DmiInteger,
	a50AdministratorPasswordStatus          	DmiInteger,
	a50FrontPanelResetStatus                	DmiInteger
}

tSystemHardwareSecurity OBJECT-TYPE
	SYNTAX		SEQUENCE OF SSystemHardwareSecurity
	ACCESS		not-accessible
	STATUS		mandatory
	DESCRIPTION	"This group describes the system-wide hardware security settings."
	::= {dmtfGroups 50}

eSystemHardwareSecurity OBJECT-TYPE
	SYNTAX		SSystemHardwareSecurity
	ACCESS		not-accessible
	STATUS		mandatory
	DESCRIPTION	""
	INDEX		{DmiComponentIndex}
	::= {tSystemHardwareSecurity 1}

a50Power-onPasswordStatus OBJECT-TYPE
	SYNTAX		INTEGER {
		vOther                                  	(1),
		vUnknown                                	(2),
		vDisabled                               	(3),
		vEnabled                                	(4),
		vNotImplemented                         	(5)
	}
	ACCESS		read-only
	STATUS		mandatory
	DESCRIPTION	"The current power-on password setting on the system."
	::= {eSystemHardwareSecurity 1}

a50KeyboardPasswordStatus OBJECT-TYPE
	SYNTAX		INTEGER {
		vOther                                  	(1),
		vUnknown                                	(2),
		vDisabled                               	(3),
		vEnabled                                	(4),
		vNotImplemented                         	(5)
	}
	ACCESS		read-only
	STATUS		mandatory
	DESCRIPTION	"The current keyboard password setting on the system"
	::= {eSystemHardwareSecurity 2}

a50AdministratorPasswordStatus OBJECT-TYPE
	SYNTAX		INTEGER {
		vOther                                  	(1),
		vUnknown                                	(2),
		vDisabled                               	(3),
		vEnabled                                	(4),
		vNotImplemented                         	(5)
	}
	ACCESS		read-only
	STATUS		mandatory
	DESCRIPTION	"The current administrator password setting on the system.
This passwordis required to make hardware configuration changes to the system."
	::= {eSystemHardwareSecurity 3}

a50FrontPanelResetStatus OBJECT-TYPE
	SYNTAX		INTEGER {
		vOther                                  	(1),
		vUnknown                                	(2),
		vDisabled                               	(3),
		vEnabled                                	(4),
		vNotImplemented                         	(5)
	}
	ACCESS		read-write
	STATUS		mandatory
	DESCRIPTION	"The present status of the front panel reset button capability.
If Enabled, the machine can be reset via the front panel reset button. IfDisable
, the reset button, if available, is inoperative."
	::= {eSystemHardwareSecurity 4}

SSystemPowerControls ::= SEQUENCE {
	a52PowerControlRequest                  	DmiInteger,
	a52TimedPower-onAvailable               	DmiInteger,
	a52TimeToNextScheduledPower-on          	DmiInteger
}

tSystemPowerControls OBJECT-TYPE
	SYNTAX		SEQUENCE OF SSystemPowerControls
	ACCESS		not-accessible
	STATUS		mandatory
	DESCRIPTION	"This group defines attributes for controlling the main power
supply tothe system."
	::= {dmtfGroups 52}

eSystemPowerControls OBJECT-TYPE
	SYNTAX		SSystemPowerControls
	ACCESS		not-accessible
	STATUS		mandatory
	DESCRIPTION	""
	INDEX		{DmiComponentIndex}
	::= {tSystemPowerControls 1}

a52PowerControlRequest OBJECT-TYPE
	SYNTAX		INTEGER {
		vOther                                  	(1),
		vUnknown                                	(2),
		vPowerOff                               	(3),
		vPowerOffThenOnAgain                    	(4),
		vEnterStandbyMode                       	(5),
		vEnterSuspendMode                       	(6),
		vEnterHibernationMode                   	(7)
	}
	ACCESS		read-write
	STATUS		mandatory
	DESCRIPTION	"Reading the value of this attribute gives the value of the
last valid power control request that was written into it.  Writing a valid
value into it causes the appropriate power control action to be exeucted
immediately. Writing an invalid or unimplemented value causes no change."
	::= {eSystemPowerControls 1}

a52TimedPower-onAvailable OBJECT-TYPE
	SYNTAX		INTEGER {
		vFalse                                  	(0),
		vTrue                                   	(1),
		vUnknown                                	(2)
	}
	ACCESS		read-only
	STATUS		mandatory
	DESCRIPTION	"Defines whether a timed power-on facility is available."
	::= {eSystemPowerControls 2}

a52TimeToNextScheduledPower-on OBJECT-TYPE
	SYNTAX		DmiInteger
	ACCESS		read-write
	STATUS		mandatory
	DESCRIPTION	"The number of seconds until the next timed power-on is scheduled
tooccur. A value of 0 means that if the system is powered off, no automatic
timed poweron will occur. A value of 0x80000000 denotes 'unknown'."
	::= {eSystemPowerControls 3}

SVoltageProbe ::= SEQUENCE {
	a54VoltageProbeIndex                    	DmiInteger,
	a54VoltageProbeLocation                 	DmiInteger,
	a54VoltageProbeDescription              	DmiDisplaystring,
	a54VoltageStatus                        	DmiInteger,
	a54VoltageProbeVoltageLevel             	DmiInteger,
	a54MonitoredVoltageNominalLevel         	DmiInteger,
	a54MonitoredVoltageNormalMaximum        	DmiInteger,
	a54MonitoredVoltageNormalMinimum        	DmiInteger,
	a54VoltageProbeMaximum                  	DmiInteger,
	a54VoltageProbeMinimum                  	DmiInteger,
	a54VoltageLevelLowerThreshold-Non-critic	DmiInteger,
	a54VoltageLevelUpperThreshold-Non-critic	DmiInteger,
	a54VoltageLevelLowerThreshold-Critical  	DmiInteger,
	a54VoltageLevelUpperThreshold-Critical  	DmiInteger,
	a54VoltageLevelLowerThreshold-Non-recove	DmiInteger,
	a54VoltageLevelUpperThreshold-Non-recove	DmiInteger,
	a54VoltageProbeResolution               	DmiInteger,
	a54VoltageProbeTolerance                	DmiInteger,
	a54VoltageProbeAccuracy                 	DmiInteger,
	a54FruGroupIndex1                       	DmiInteger,
	a54OperationalGroupIndex1               	DmiInteger
}

tVoltageProbe OBJECT-TYPE
	SYNTAX		SEQUENCE OF SVoltageProbe
	ACCESS		not-accessible
	STATUS		mandatory
	DESCRIPTION	"This group defines the attributes for the voltage probes
in this system."
	::= {dmtfGroups 54}

eVoltageProbe OBJECT-TYPE
	SYNTAX		SVoltageProbe
	ACCESS		not-accessible
	STATUS		mandatory
	DESCRIPTION	""
	INDEX		{DmiComponentIndex, a54VoltageProbeIndex}
	::= {tVoltageProbe 1}

a54VoltageProbeIndex OBJECT-TYPE
	SYNTAX		DmiInteger
	ACCESS		read-only
	STATUS		mandatory
	DESCRIPTION	"Index into this voltage probe table."
	::= {eVoltageProbe 1}

a54VoltageProbeLocation OBJECT-TYPE
	SYNTAX		INTEGER {
		vOther                                  	(1),
		vUnknown                                	(2),
		vProcessor                              	(3),
		vDisk                                   	(4),
		vPeripheralBay                          	(5),
		vSystemManagementModule                 	(6),
		vMotherboard                            	(7),
		vMemoryModule                           	(8),
		vProcessorModule                        	(9),
		vPowerUnit                              	(10),
		vAdd-inCard                             	(11)
	}
	ACCESS		read-only
	STATUS		mandatory
	DESCRIPTION	"Identifies the physical location of the voltage probe."
	::= {eVoltageProbe 2}

a54VoltageProbeDescription OBJECT-TYPE
	SYNTAX		DmiDisplaystring
	ACCESS		read-only
	STATUS		mandatory
	DESCRIPTION	"Additional descriptive information about the voltage probe
or probe'slocation."
	::= {eVoltageProbe 3}

a54VoltageStatus OBJECT-TYPE
	SYNTAX		INTEGER {
		vOther                                  	(1),
		vUnknown                                	(2),
		vOk                                     	(3),
		vNon-critical                           	(4),
		vCritical                               	(5),
		vNon-recoverable                        	(6)
	}
	ACCESS		read-only
	STATUS		mandatory
	DESCRIPTION	"Defines the status of the voltage monitored by this voltage
probe."
	::= {eVoltageProbe 4}

a54VoltageProbeVoltageLevel OBJECT-TYPE
	SYNTAX		DmiInteger
	ACCESS		read-only
	STATUS		mandatory
	DESCRIPTION	"The current voltage level of this voltage probe in millivolts.
0x8000000denotes 'unknown'."
	::= {eVoltageProbe 5}

a54MonitoredVoltageNominalLevel OBJECT-TYPE
	SYNTAX		DmiInteger
	ACCESS		read-only
	STATUS		mandatory
	DESCRIPTION	"The nominal voltage level of the voltage monitored by this
probe inmillivolts. 0x80000000 denotes 'unknown'."
	::= {eVoltageProbe 6}

a54MonitoredVoltageNormalMaximum OBJECT-TYPE
	SYNTAX		DmiInteger
	ACCESS		read-only
	STATUS		mandatory
	DESCRIPTION	"The normal maximum voltage level of the voltage monitored
by thisprobe in millivolts. 0x80000000 denotes 'unknown'."
	::= {eVoltageProbe 7}

a54MonitoredVoltageNormalMinimum OBJECT-TYPE
	SYNTAX		DmiInteger
	ACCESS		read-only
	STATUS		mandatory
	DESCRIPTION	"The normal minimum voltage level of the voltage monitored
by thisprobe in millivolts. 0x80000000 denotes 'unknown'."
	::= {eVoltageProbe 8}

a54VoltageProbeMaximum OBJECT-TYPE
	SYNTAX		DmiInteger
	ACCESS		read-only
	STATUS		mandatory
	DESCRIPTION	"The maximum voltage level specified to be readable by this
probe inmillivolts. 0x80000000 denotes 'unknown'."
	::= {eVoltageProbe 9}

a54VoltageProbeMinimum OBJECT-TYPE
	SYNTAX		DmiInteger
	ACCESS		read-only
	STATUS		mandatory
	DESCRIPTION	"The minimum voltage level specified to be readable by this
probe inmillivolts. 0x80000000 denotes 'unknown'."
	::= {eVoltageProbe 10}

a54VoltageLevelLowerThreshold-Non-critic OBJECT-TYPE
	SYNTAX		DmiInteger
	ACCESS		read-write
	STATUS		mandatory
	DESCRIPTION	"The lower non-critical threshold for the voltage level set
by the user, inmillivolts. 0x80000000 denotes 'unknown'."
	::= {eVoltageProbe 11}

a54VoltageLevelUpperThreshold-Non-critic OBJECT-TYPE
	SYNTAX		DmiInteger
	ACCESS		read-write
	STATUS		mandatory
	DESCRIPTION	"The upper non-critical threshold for the voltage probe, in
millivolts.0x80000000 denotes 'unknown'."
	::= {eVoltageProbe 12}

a54VoltageLevelLowerThreshold-Critical OBJECT-TYPE
	SYNTAX		DmiInteger
	ACCESS		read-write
	STATUS		mandatory
	DESCRIPTION	"The lower critical threshold for the voltage probe, in millivolt
.0x80000000 denotes 'unknown'."
	::= {eVoltageProbe 13}

a54VoltageLevelUpperThreshold-Critical OBJECT-TYPE
	SYNTAX		DmiInteger
	ACCESS		read-write
	STATUS		mandatory
	DESCRIPTION	"The upper critical threshold for the voltage probe, in millivolt
.0x80000000 denotes 'unknown'."
	::= {eVoltageProbe 14}

a54VoltageLevelLowerThreshold-Non-recove OBJECT-TYPE
	SYNTAX		DmiInteger
	ACCESS		read-write
	STATUS		mandatory
	DESCRIPTION	"The lower non-recoverable threshold for the voltage probe,
in millivolts.0x80000000 denotes 'unknown'."
	::= {eVoltageProbe 15}

a54VoltageLevelUpperThreshold-Non-recove OBJECT-TYPE
	SYNTAX		DmiInteger
	ACCESS		read-write
	STATUS		mandatory
	DESCRIPTION	"The upper non-recoverable threshold for the voltage probe,
in millivolts.0x80000000 denotes 'unknown'."
	::= {eVoltageProbe 16}

a54VoltageProbeResolution OBJECT-TYPE
	SYNTAX		DmiInteger
	ACCESS		read-write
	STATUS		mandatory
	DESCRIPTION	"The resolution for the reading from this voltage probe, in
tenths ofmillivolts. '0x80000000 denotes 'unknown'."
	::= {eVoltageProbe 17}

a54VoltageProbeTolerance OBJECT-TYPE
	SYNTAX		DmiInteger
	ACCESS		read-write
	STATUS		mandatory
	DESCRIPTION	"The tolerance for the reading from this voltage probe, in
plus/minusmillivolts. 0x80000000 denotes 'unknown'."
	::= {eVoltageProbe 18}

a54VoltageProbeAccuracy OBJECT-TYPE
	SYNTAX		DmiInteger
	ACCESS		read-write
	STATUS		mandatory
	DESCRIPTION	"The accuracy for the reading from this voltage probe, in
plus/minushundredths of a percent. 0x80000000 denotes 'unknown'."
	::= {eVoltageProbe 19}

a54FruGroupIndex OBJECT-TYPE
	SYNTAX		DmiInteger
	ACCESS		read-only
	STATUS		mandatory
	DESCRIPTION	"Index into the FRU table"
	::= {eVoltageProbe 20}

a54OperationalGroupIndex OBJECT-TYPE
	SYNTAX		DmiInteger
	ACCESS		read-only
	STATUS		mandatory
	DESCRIPTION	"Index into the Operational State table"
	::= {eVoltageProbe 21}

STemperatureProbe ::= SEQUENCE {
	a55TemperatureProbeTableIndex           	DmiInteger,
	a55TemperatureProbeLocation             	DmiInteger,
	a55TemperatureProbeDescription          	DmiDisplaystring,
	a55TemperatureStatus                    	DmiInteger,
	a55TemperatureProbeTemperatureReading   	DmiInteger,
	a55MonitoredTemperatureNominalReading   	DmiInteger,
	a55MonitoredTemperatureNormalMaximum    	DmiInteger,
	a55MonitoredTemperatureNormalMinimum    	DmiInteger,
	a55TemperatureProbeMaximum              	DmiInteger,
	a55TemperatureProbeMinimum              	DmiInteger,
	a55TemperatureLowerThreshold-Non-critica	DmiInteger,
	a55TemperatureUpperThreshold-Non-critica	DmiInteger,
	a55TemperatureLowerThreshold-Critical   	DmiInteger,
	a55TemperatureUpperThreshold-Critical   	DmiInteger,
	a55TemperatureLowerThreshold-Non-recover	DmiInteger,
	a55TemperatureUpperThreshold-Non-recover	DmiInteger,
	a55TemperatureProbeResolution           	DmiInteger,
	a55TemperatureProbeTolerance            	DmiInteger,
	a55TemperatureProbeAccuracy             	DmiInteger,
	a55FruGroupIndex                        	DmiInteger,
	a55OperationalGroupIndex                	DmiInteger
}

tTemperatureProbe OBJECT-TYPE
	SYNTAX		SEQUENCE OF STemperatureProbe
	ACCESS		not-accessible
	STATUS		mandatory
	DESCRIPTION	"This group defines the attributes for the temperature probes
in thissystem."
	::= {dmtfGroups 55}

eTemperatureProbe OBJECT-TYPE
	SYNTAX		STemperatureProbe
	ACCESS		not-accessible
	STATUS		mandatory
	DESCRIPTION	""
	INDEX		{DmiComponentIndex, a55TemperatureProbeTableIndex}
	::= {tTemperatureProbe 1}

a55TemperatureProbeTableIndex OBJECT-TYPE
	SYNTAX		DmiInteger
	ACCESS		read-only
	STATUS		mandatory
	DESCRIPTION	"Index into this temperature probe table."
	::= {eTemperatureProbe 1}

a55TemperatureProbeLocation OBJECT-TYPE
	SYNTAX		INTEGER {
		vOther                                  	(1),
		vUnknown                                	(2),
		vProcessor                              	(3),
		vDisk                                   	(4),
		vPeripheralBay                          	(5),
		vSmbMaster                              	(6),
		vMotherboard                            	(7),
		vMemoryModule                           	(8),
		vProcessorModule                        	(9),
		vPowerUnit                              	(10),
		vAdd-inCard                             	(11)
	}
	ACCESS		read-only
	STATUS		mandatory
	DESCRIPTION	"Identifies the physical location of the temperature probe."
	::= {eTemperatureProbe 2}

a55TemperatureProbeDescription OBJECT-TYPE
	SYNTAX		DmiDisplaystring
	ACCESS		read-only
	STATUS		mandatory
	DESCRIPTION	"Additional descriptive information about the temperature
probe orprobe's location."
	::= {eTemperatureProbe 3}

a55TemperatureStatus OBJECT-TYPE
	SYNTAX		INTEGER {
		vOther                                  	(1),
		vUnknown                                	(2),
		vOk                                     	(3),
		vNon-critical                           	(4),
		vCritical                               	(5),
		vNon-recoverable                        	(6)
	}
	ACCESS		read-only
	STATUS		mandatory
	DESCRIPTION	"Defines the status of the temperature monitored by this temperat
reprobe."
	::= {eTemperatureProbe 4}

a55TemperatureProbeTemperatureReading OBJECT-TYPE
	SYNTAX		DmiInteger
	ACCESS		read-only
	STATUS		mandatory
	DESCRIPTION	"The present temperature reading of this temperature probe
in 1/10th degrees C. 0x8000000 denotes 'unknown'."
	::= {eTemperatureProbe 5}

a55MonitoredTemperatureNominalReading OBJECT-TYPE
	SYNTAX		DmiInteger
	ACCESS		read-only
	STATUS		mandatory
	DESCRIPTION	"The nominal temperature reading of the temperature monitoredby
this probe in 1/10th degrees C. 0x80000000 denotes 'unknown'."
	::= {eTemperatureProbe 6}

a55MonitoredTemperatureNormalMaximum OBJECT-TYPE
	SYNTAX		DmiInteger
	ACCESS		read-only
	STATUS		mandatory
	DESCRIPTION	"The normal maximum temperature reading of the temperaturemonitor
d by this probe in 1/10th degrees C. 0x80000000 denotes 'unknown'."
	::= {eTemperatureProbe 7}

a55MonitoredTemperatureNormalMinimum OBJECT-TYPE
	SYNTAX		DmiInteger
	ACCESS		read-only
	STATUS		mandatory
	DESCRIPTION	"The normal minimum temperature reading of the temperaturemonitor
d by this probe in 1/10th degrees C. 0x80000000 denotes 'unknown'."
	::= {eTemperatureProbe 8}

a55TemperatureProbeMaximum OBJECT-TYPE
	SYNTAX		DmiInteger
	ACCESS		read-only
	STATUS		mandatory
	DESCRIPTION	"The maximum temperature reading specified to be readable
bythis probe in 1/10th degrees C. 0x80000000 denotes 'unknown'."
	::= {eTemperatureProbe 9}

a55TemperatureProbeMinimum OBJECT-TYPE
	SYNTAX		DmiInteger
	ACCESS		read-only
	STATUS		mandatory
	DESCRIPTION	"The minimum temperature reading specified to be readable
bythis probe in 1/10th degrees C. 0x80000000 denotes 'unknown'."
	::= {eTemperatureProbe 10}

a55TemperatureLowerThreshold-Non-critica OBJECT-TYPE
	SYNTAX		DmiInteger
	ACCESS		read-write
	STATUS		mandatory
	DESCRIPTION	"The lower non-critical threshold for the temperature reading
setby the user, in 1/10th degrees C. 0x80000000 denotes 'unknown'."
	::= {eTemperatureProbe 11}

a55TemperatureUpperThreshold-Non-critica OBJECT-TYPE
	SYNTAX		DmiInteger
	ACCESS		read-write
	STATUS		mandatory
	DESCRIPTION	"The upper non-critical threshold for the temperature probe,
in 1/10th degrees C. 0x80000000 denotes 'unknown'."
	::= {eTemperatureProbe 12}

a55TemperatureLowerThreshold-Critical OBJECT-TYPE
	SYNTAX		DmiInteger
	ACCESS		read-write
	STATUS		mandatory
	DESCRIPTION	"The lower critical threshold for the temperature probe, in
1/10 degrees C. 0x80000000 denotes 'unknown'."
	::= {eTemperatureProbe 13}

a55TemperatureUpperThreshold-Critical OBJECT-TYPE
	SYNTAX		DmiInteger
	ACCESS		read-write
	STATUS		mandatory
	DESCRIPTION	"The upper critical threshold for the temperature probe, in
/10th degrees C. 0x80000000 denotes 'unknown'."
	::= {eTemperatureProbe 14}

a55TemperatureLowerThreshold-Non-recover OBJECT-TYPE
	SYNTAX		DmiInteger
	ACCESS		read-write
	STATUS		mandatory
	DESCRIPTION	"The lower non-recoverable threshold for the temperature probe,
in 1/10th degrees C. 0x80000000 denotes 'unknown'."
	::= {eTemperatureProbe 15}

a55TemperatureUpperThreshold-Non-recover OBJECT-TYPE
	SYNTAX		DmiInteger
	ACCESS		read-write
	STATUS		mandatory
	DESCRIPTION	"The upper non-recoverable threshold for the temperature probe,
in 1/10th degrees C. 0x80000000 denotes 'unknown'."
	::= {eTemperatureProbe 16}

a55TemperatureProbeResolution OBJECT-TYPE
	SYNTAX		DmiInteger
	ACCESS		read-write
	STATUS		mandatory
	DESCRIPTION	"The resolution for the reading from this temperature probe,
in tenths of 1/10th degrees C. '0x80000000 denotes 'unknown'."
	::= {eTemperatureProbe 17}

a55TemperatureProbeTolerance OBJECT-TYPE
	SYNTAX		DmiInteger
	ACCESS		read-write
	STATUS		mandatory
	DESCRIPTION	"The tolerance for the reading from this temperature probe,
in plus/minus 1/10 degrees C. 0x80000000 denotes 'unknown'."
	::= {eTemperatureProbe 18}

a55TemperatureProbeAccuracy OBJECT-TYPE
	SYNTAX		DmiInteger
	ACCESS		read-write
	STATUS		mandatory
	DESCRIPTION	"The accuracy for the reading from this temperature probe,
in plus/minus hundredths of a percent. 0x80000000 denotes 'unknown' or'unsupport
d'."
	::= {eTemperatureProbe 19}

a55FruGroupIndex OBJECT-TYPE
	SYNTAX		DmiInteger
	ACCESS		read-only
	STATUS		mandatory
	DESCRIPTION	"Index into the FRU table. A value of -1 indicatesthat this
device is not an FRU."
	::= {eTemperatureProbe 20}

a55OperationalGroupIndex OBJECT-TYPE
	SYNTAX		DmiInteger
	ACCESS		read-only
	STATUS		mandatory
	DESCRIPTION	"Index into the Operational State table"
	::= {eTemperatureProbe 21}

SPhysicalContainerGlobalTable ::= SEQUENCE {
	a64ContainerOrChassisType               	DmiInteger,
	a64AssetTag                             	DmiDisplaystring,
	a64ChassisLockPresent                   	DmiInteger,
	a64BootupState                          	DmiInteger,
	a64PowerState                           	DmiInteger,
	a64ThermalState                         	DmiInteger,
	a64FruGroupIndex                        	DmiInteger,
	a64OperationalGroupIndex                	DmiInteger,
	a64ContainerIndex                       	DmiInteger,
	a64ContainerName                        	DmiDisplaystring,
	a64ContainerLocation                    	DmiDisplaystring,
	a64ContainerSecurityStatus              	DmiInteger
}

tPhysicalContainerGlobalTable OBJECT-TYPE
	SYNTAX		SEQUENCE OF SPhysicalContainerGlobalTable
	ACCESS		not-accessible
	STATUS		mandatory
	DESCRIPTION	"This group of attributes describes the fields in a row ofthe
Physical Container Global Table. This table lists all ofthe containers (e.g.
chassis, sub-chassis, etc.) included withinthe component whose structure
is being described"
	::= {dmtfGroups 64}

ePhysicalContainerGlobalTable OBJECT-TYPE
	SYNTAX		SPhysicalContainerGlobalTable
	ACCESS		not-accessible
	STATUS		mandatory
	DESCRIPTION	""
	INDEX		{DmiComponentIndex, a64ContainerIndex}
	::= {tPhysicalContainerGlobalTable 1}

a64ContainerOrChassisType OBJECT-TYPE
	SYNTAX		INTEGER {
		vOther                                  	(1),
		vUnknown                                	(2),
		vDesktop                                	(3),
		vLowProfileDesktop                      	(4),
		vPizzaBox                               	(5),
		vMiniTower                              	(6),
		vTower                                  	(7),
		vPortable                               	(8),
		vLaptop                                 	(9),
		vNotebook                               	(10),
		vHandHeld                               	(11),
		vDockingStation                         	(12),
		vAllInOne                               	(13),
		vSubNotebook                            	(14),
		vSpace-saving                           	(15),
		vLunchBox                               	(16),
		vMainSystemChassis                      	(17),
		vExpansionChassis                       	(18),
		vSubchassis                             	(19),
		vBusExpansionChassis                    	(20),
		vPeripheralChassis                      	(21),
		vRaidChassis                            	(22),
		vRackMountChassis                       	(23)
	}
	ACCESS		read-only
	STATUS		mandatory
	DESCRIPTION	"The type of container or chassis."
	::= {ePhysicalContainerGlobalTable 1}

a64AssetTag OBJECT-TYPE
	SYNTAX		DmiDisplaystring
	ACCESS		read-write
	STATUS		mandatory
	DESCRIPTION	"The Container asset tag string.This asset tag string is writeabl
by the system administrator."
	::= {ePhysicalContainerGlobalTable 2}

a64ChassisLockPresent OBJECT-TYPE
	SYNTAX		INTEGER {
		vFalse                                  	(0),
		vTrue                                   	(1)
	}
	ACCESS		read-only
	STATUS		mandatory
	DESCRIPTION	"If true, a chassis lock is present on the Container."
	::= {ePhysicalContainerGlobalTable 3}

a64BootupState OBJECT-TYPE
	SYNTAX		INTEGER {
		vOther                                  	(1),
		vUnknown                                	(2),
		vOk                                     	(3),
		vWarning                                	(4),
		vCritical                               	(5),
		vNon-recoverable1                       	(6)
	}
	ACCESS		read-only
	STATUS		mandatory
	DESCRIPTION	"The current state of this system when it booted."
	::= {ePhysicalContainerGlobalTable 4}

a64PowerState OBJECT-TYPE
	SYNTAX		INTEGER {
		vOther                                  	(1),
		vUnknown                                	(2),
		vOk                                     	(3),
		vWarning                                	(4),
		vCritical                               	(5),
		vNon-recoverable                        	(6)
	}
	ACCESS		read-only
	STATUS		mandatory
	DESCRIPTION	"The current state of the power supply for this system."
	::= {ePhysicalContainerGlobalTable 5}

a64ThermalState OBJECT-TYPE
	SYNTAX		INTEGER {
		vOther                                  	(1),
		vUnknown                                	(2),
		vOk                                     	(3),
		vWarning                                	(4),
		vCritical                               	(5),
		vNon-recoverable                        	(6)
	}
	ACCESS		read-only
	STATUS		mandatory
	DESCRIPTION	"The current thermal state of this Container."
	::= {ePhysicalContainerGlobalTable 6}

a64FruGroupIndex OBJECT-TYPE
	SYNTAX		DmiInteger
	ACCESS		read-only
	STATUS		mandatory
	DESCRIPTION	"If this is a Field Replaceable Unit or if it is part of another
FRU, this provides an index into the FRU table; 'value = -1' indicates that
the group is not a FRU."
	::= {ePhysicalContainerGlobalTable 7}

a64OperationalGroupIndex OBJECT-TYPE
	SYNTAX		DmiInteger
	ACCESS		read-only
	STATUS		mandatory
	DESCRIPTION	"The index into the Operational State table for this deviceif
applicable."
	::= {ePhysicalContainerGlobalTable 8}

a64ContainerIndex OBJECT-TYPE
	SYNTAX		DmiInteger
	ACCESS		read-only
	STATUS		mandatory
	DESCRIPTION	"A unique index for the Physical Container in Physical Container
Global Table."
	::= {ePhysicalContainerGlobalTable 9}

a64ContainerName OBJECT-TYPE
	SYNTAX		DmiDisplaystring
	ACCESS		read-write
	STATUS		mandatory
	DESCRIPTION	"This is any 64-octet long name that the user orsystem administra
or wishes to give this specific physical container."
	::= {ePhysicalContainerGlobalTable 10}

a64ContainerLocation OBJECT-TYPE
	SYNTAX		DmiDisplaystring
	ACCESS		read-write
	STATUS		mandatory
	DESCRIPTION	"This attribute is a string name for the location of thecontainer
 This attribute is Read-Write and may be set to any  appropriate value by
the user. The string may be 128 octets long."
	::= {ePhysicalContainerGlobalTable 11}

a64ContainerSecurityStatus OBJECT-TYPE
	SYNTAX		INTEGER {
		vOther                                  	(1),
		vUnknown                                	(2),
		vNoSecurityBreachDetected               	(3),
		vContainerSecurityBreachAttempted       	(4),
		vContainerSecurityBreached              	(5)
	}
	ACCESS		read-only
	STATUS		mandatory
	DESCRIPTION	"This attribute describes whether the Container is physically
 secure or not. This includes the state of the door lock, or the boot devices
or  the keyboard or mouse."
	::= {ePhysicalContainerGlobalTable 12}

SOperatingSystem ::= SEQUENCE {
	a66OperatingSystemIndex                 	DmiInteger,
	a66OperatingSystemName                  	DmiDisplaystring,
	a66OperatingSystemVersion               	DmiDisplaystring,
	a66PrimaryOperatingSystem               	DmiInteger,
	a66OperatingSystemBootDeviceStorageType 	DmiInteger,
	a66OperatingSystemBootDeviceIndex       	DmiInteger,
	a66OperatingSystemBootPartitionIndex    	DmiInteger,
	a66OperatingSystemDescription           	DmiDisplaystring
}

tOperatingSystem OBJECT-TYPE
	SYNTAX		SEQUENCE OF SOperatingSystem
	ACCESS		not-accessible
	STATUS		mandatory
	DESCRIPTION	"This group defines general information about operating systems
installedon this system."
	::= {dmtfGroups 66}

eOperatingSystem OBJECT-TYPE
	SYNTAX		SOperatingSystem
	ACCESS		not-accessible
	STATUS		mandatory
	DESCRIPTION	""
	INDEX		{DmiComponentIndex, a66OperatingSystemIndex}
	::= {tOperatingSystem 1}

a66OperatingSystemIndex OBJECT-TYPE
	SYNTAX		DmiInteger
	ACCESS		read-only
	STATUS		mandatory
	DESCRIPTION	"The index into the operating system table."
	::= {eOperatingSystem 1}

a66OperatingSystemName OBJECT-TYPE
	SYNTAX		DmiDisplaystring
	ACCESS		read-only
	STATUS		mandatory
	DESCRIPTION	"The name of this operating system."
	::= {eOperatingSystem 2}

a66OperatingSystemVersion OBJECT-TYPE
	SYNTAX		DmiDisplaystring
	ACCESS		read-only
	STATUS		mandatory
	DESCRIPTION	"The version number of this operating system."
	::= {eOperatingSystem 3}

a66PrimaryOperatingSystem OBJECT-TYPE
	SYNTAX		INTEGER {
		vFalse                                  	(0),
		vTrue                                   	(1)
	}
	ACCESS		read-only
	STATUS		mandatory
	DESCRIPTION	"If true, this is the primary operating system."
	::= {eOperatingSystem 4}

a66OperatingSystemBootDeviceStorageType OBJECT-TYPE
	SYNTAX		INTEGER {
		vOther                                  	(1),
		vUnknown                                	(2),
		vHardDisk                               	(3),
		vFloppyDisk                             	(4),
		vOpticalRom                             	(5),
		vOpticalWorm                            	(6),
		vOpticalRw                              	(7),
		vCompactDisk                            	(8),
		vFlashDisk                              	(9),
		vBernoulli                              	(10),
		vOpticalFloppyDisk                      	(11)
	}
	ACCESS		read-only
	STATUS		mandatory
	DESCRIPTION	"An index into the Disks Table to indicate the device from
which thisoperating system was booted. To fully access the Disks Table, this
index must becombined with the attribute Boot Device Index."
	::= {eOperatingSystem 5}

a66OperatingSystemBootDeviceIndex OBJECT-TYPE
	SYNTAX		DmiInteger
	ACCESS		read-only
	STATUS		mandatory
	DESCRIPTION	"An index into the Disks Table."
	::= {eOperatingSystem 6}

a66OperatingSystemBootPartitionIndex OBJECT-TYPE
	SYNTAX		DmiInteger
	ACCESS		read-only
	STATUS		mandatory
	DESCRIPTION	"An index into the Partition table indicating the partition
from which thisoperating system booted."
	::= {eOperatingSystem 7}

a66OperatingSystemDescription OBJECT-TYPE
	SYNTAX		DmiDisplaystring
	ACCESS		read-only
	STATUS		mandatory
	DESCRIPTION	"A description of this operating system."
	::= {eOperatingSystem 8}

SPowerUnitGlobalTable ::= SEQUENCE {
	a67PowerUnitIndex                       	DmiInteger,
	a67PowerUnitRedundancyStatus            	DmiInteger
}

tPowerUnitGlobalTable OBJECT-TYPE
	SYNTAX		SEQUENCE OF SPowerUnitGlobalTable
	ACCESS		not-accessible
	STATUS		mandatory
	DESCRIPTION	"This global table describes all of the Power Units in thissystem
component. The unique index of each Power Unit is the keyinto this table.
A Power Unit is composed of potentially more than onePower Supply in a redundant
configuration. Individual power supplies are described inthe 'Power Supply'
standard group. In that group, each individual power supply entry willpoint
to a Power Unit in this table by using the index of the row in this table
that describesthe Power Unit. If a Power Unit is redundant, mo"
	::= {dmtfGroups 67}

ePowerUnitGlobalTable OBJECT-TYPE
	SYNTAX		SPowerUnitGlobalTable
	ACCESS		not-accessible
	STATUS		mandatory
	DESCRIPTION	""
	INDEX		{DmiComponentIndex, a67PowerUnitIndex}
	::= {tPowerUnitGlobalTable 1}

a67PowerUnitIndex OBJECT-TYPE
	SYNTAX		DmiInteger
	ACCESS		read-only
	STATUS		mandatory
	DESCRIPTION	"The unique index given to each Power Unit being describedby
this table. This unique index is the key into this table."
	::= {ePowerUnitGlobalTable 1}

a67PowerUnitRedundancyStatus OBJECT-TYPE
	SYNTAX		INTEGER {
		vOther                                  	(1),
		vUnknown                                	(2),
		vNotApplicableUnitNotRedundant          	(3),
		vOffline                                	(4),
		vFullyRedundant                         	(5),
		vDegradedRedundancy                     	(6),
		vRedundancyLost                         	(7)
	}
	ACCESS		read-only
	STATUS		mandatory
	DESCRIPTION	"Gives the redundancy status of the Power Unit.'Fully Redundant'
means that all of the configured redundancy is stillavailable; 'Degraded
Redundancy' means that some failures have beenexperienced but some reduced
amount of redundancy is still available;'Redundancy Lost' means that a sufficien
 number of failures have beenexperienced that no redundancy is available
and the next failure experiencedwithin the Power Unit will cause overall
Power Unit failure."
	::= {ePowerUnitGlobalTable 2}

SParallelPorts ::= SEQUENCE {
	a74ParallelPortIndex                    	DmiInteger,
	a74ParallelBaseIoAddress                	DmiInteger64X,
	a74IrqUsed                              	DmiInteger,
	a74LogicalName                          	DmiDisplaystring,
	a74ConnectorType                        	DmiInteger,
	a74ConnectorPinout                      	DmiInteger,
	a74DmaSupport                           	DmiInteger,
	a74ParallelPortCapabilities             	DmiInteger,
	a74OperationalGroupIndex                	DmiInteger,
	a74ParallelPortSecuritySettings         	DmiInteger
}

tParallelPorts OBJECT-TYPE
	SYNTAX		SEQUENCE OF SParallelPorts
	ACCESS		not-accessible
	STATUS		mandatory
	DESCRIPTION	"This group defines the attributes for parallel ports in this
system."
	::= {dmtfGroups 74}

eParallelPorts OBJECT-TYPE
	SYNTAX		SParallelPorts
	ACCESS		not-accessible
	STATUS		mandatory
	DESCRIPTION	""
	INDEX		{DmiComponentIndex, a74ParallelPortIndex}
	::= {tParallelPorts 1}

a74ParallelPortIndex OBJECT-TYPE
	SYNTAX		DmiInteger
	ACCESS		read-only
	STATUS		mandatory
	DESCRIPTION	"An index into the parallel ports table."
	::= {eParallelPorts 1}

a74ParallelBaseIoAddress OBJECT-TYPE
	SYNTAX		DmiInteger64X
	ACCESS		read-only
	STATUS		mandatory
	DESCRIPTION	"Base I/O address for this parallel port."
	::= {eParallelPorts 2}

a74IrqUsed OBJECT-TYPE
	SYNTAX		DmiInteger
	ACCESS		read-only
	STATUS		mandatory
	DESCRIPTION	"IRQ number that is being used by this parallel port."
	::= {eParallelPorts 3}

a74LogicalName OBJECT-TYPE
	SYNTAX		DmiDisplaystring
	ACCESS		read-only
	STATUS		mandatory
	DESCRIPTION	"The logical name of the I/O device on this parallel port,
under thisoperating environment."
	::= {eParallelPorts 4}

a74ConnectorType OBJECT-TYPE
	SYNTAX		INTEGER {
		vOther                                  	(1),
		vUnknown                                	(2),
		vDb-25Female                            	(3),
		vDb-25Male                              	(4),
		vCentronics                             	(5),
		vMini-centronics                        	(6),
		vProprietary                            	(7),
		vCentronics-14                          	(160),
		vDb-36Female                            	(161),
		vMini-centronics-20                     	(162)
	}
	ACCESS		read-only
	STATUS		mandatory
	DESCRIPTION	"The connector used to interface with the I/O device on this
parallel port."
	::= {eParallelPorts 5}

a74ConnectorPinout OBJECT-TYPE
	SYNTAX		INTEGER {
		vOther                                  	(1),
		vUnknown                                	(2),
		vXtat                                   	(3),
		vPs2                                    	(4),
		vIeee1284                               	(5),
		vProprietary                            	(6),
		vPc-98                                  	(160),
		vPc-98-hireso                           	(161),
		vPc-h98                                 	(162),
		vPc-98note                              	(163),
		vPc-98full                              	(164)
	}
	ACCESS		read-only
	STATUS		mandatory
	DESCRIPTION	"The pinout used by the I/O device on this parallel port."
	::= {eParallelPorts 6}

a74DmaSupport OBJECT-TYPE
	SYNTAX		INTEGER {
		vFalse                                  	(0),
		vTrue                                   	(1)
	}
	ACCESS		read-only
	STATUS		mandatory
	DESCRIPTION	"If true, DMA is supported."
	::= {eParallelPorts 7}

a74ParallelPortCapabilities OBJECT-TYPE
	SYNTAX		DmiInteger
	ACCESS		read-only
	STATUS		mandatory
	DESCRIPTION	"Capabilities of this parallel port. This is a bit field mask
with the bitsdefined as follows: Bit 0 (2^0) set = XT/AT compatibleBit 1
(2^1) set = PS/2 compatibleBit 2 (2^2) set = ECPBit 3 (2^3) set = EPPBit
4 (2^4) set = PC-98Bit 5 (2^5) set = PC-98-HiresoBit 6 (2^6) set = PC-H98"
	::= {eParallelPorts 8}

a74OperationalGroupIndex OBJECT-TYPE
	SYNTAX		DmiInteger
	ACCESS		read-only
	STATUS		mandatory
	DESCRIPTION	"The index into the Operational State Table for this device."
	::= {eParallelPorts 9}

a74ParallelPortSecuritySettings OBJECT-TYPE
	SYNTAX		INTEGER {
		vOther                                  	(1),
		vUnknown                                	(2),
		vNone                                   	(3),
		vExternalInterfaceLockedOut             	(4),
		vExternalInterfaceEnabled               	(5),
		vBoot-bypass                            	(6)
	}
	ACCESS		read-only
	STATUS		mandatory
	DESCRIPTION	"Attribute describing the current hardware security settings
on this device"
	::= {eParallelPorts 10}

SSerialPorts ::= SEQUENCE {
	a75SerialPortIndex                      	DmiInteger,
	a75SerialBaseIoAddress                  	DmiInteger64X,
	a75IrqUsed                              	DmiInteger,
	a75LogicalName                          	DmiDisplaystring,
	a75ConnectorType                        	DmiInteger,
	a75MaximumSpeed                         	DmiInteger,
	a75SerialPortCapabilities               	DmiInteger,
	a75OperationalGroupIndex                	DmiInteger,
	a75SerialPortSecuritySettings           	DmiInteger
}

tSerialPorts OBJECT-TYPE
	SYNTAX		SEQUENCE OF SSerialPorts
	ACCESS		not-accessible
	STATUS		mandatory
	DESCRIPTION	"This group defines the attributes for serial ports in this
system."
	::= {dmtfGroups 75}

eSerialPorts OBJECT-TYPE
	SYNTAX		SSerialPorts
	ACCESS		not-accessible
	STATUS		mandatory
	DESCRIPTION	""
	INDEX		{DmiComponentIndex, a75SerialPortIndex}
	::= {tSerialPorts 1}

a75SerialPortIndex OBJECT-TYPE
	SYNTAX		DmiInteger
	ACCESS		read-only
	STATUS		mandatory
	DESCRIPTION	"An index into the serial ports table."
	::= {eSerialPorts 1}

a75SerialBaseIoAddress OBJECT-TYPE
	SYNTAX		DmiInteger64X
	ACCESS		read-only
	STATUS		mandatory
	DESCRIPTION	"Base I/O address for this serial port."
	::= {eSerialPorts 2}

a75IrqUsed OBJECT-TYPE
	SYNTAX		DmiInteger
	ACCESS		read-only
	STATUS		mandatory
	DESCRIPTION	"IRQ number that is being used by this serial port."
	::= {eSerialPorts 3}

a75LogicalName OBJECT-TYPE
	SYNTAX		DmiDisplaystring
	ACCESS		read-only
	STATUS		mandatory
	DESCRIPTION	"The logical name of this serial port under this operating
environment."
	::= {eSerialPorts 4}

a75ConnectorType OBJECT-TYPE
	SYNTAX		INTEGER {
		vOther                                  	(1),
		vUnknown                                	(2),
		vDb-9PinMale                            	(3),
		vDb-9PinFemale                          	(4),
		vDb-25PinMale                           	(5),
		vDb-25PinFemale                         	(6),
		vRj-11                                  	(7),
		vRj-45                                  	(8),
		vProprietary                            	(9),
		vCircularDin-8Male                      	(10),
		vCircularDin-8Female                    	(11),
		vMini-centronicsType-14                 	(160),
		vMini-centronicsType-26                 	(161)
	}
	ACCESS		read-only
	STATUS		mandatory
	DESCRIPTION	"The connector used to interface with the I/O device on this
serial port."
	::= {eSerialPorts 5}

a75MaximumSpeed OBJECT-TYPE
	SYNTAX		DmiInteger
	ACCESS		read-only
	STATUS		mandatory
	DESCRIPTION	"Maximum transfer speed of the device on this serial port
in bits persecond."
	::= {eSerialPorts 6}

a75SerialPortCapabilities OBJECT-TYPE
	SYNTAX		INTEGER {
		vOther                                  	(1),
		vUnknown                                	(2),
		vXtatCompatible                         	(3),
		v16450Compatible                        	(4),
		v16550Compatible                        	(5),
		v16550aCompatible                       	(6),
		v8251Compatible                         	(160),
		v8251fifoCompatible                     	(161)
	}
	ACCESS		read-only
	STATUS		mandatory
	DESCRIPTION	"The capabilities of this Serial port."
	::= {eSerialPorts 7}

a75OperationalGroupIndex OBJECT-TYPE
	SYNTAX		DmiInteger
	ACCESS		read-only
	STATUS		mandatory
	DESCRIPTION	"The index into the Operational State Table for this device."
	::= {eSerialPorts 8}

a75SerialPortSecuritySettings OBJECT-TYPE
	SYNTAX		INTEGER {
		vOther                                  	(1),
		vUnknown                                	(2),
		vNone                                   	(3),
		vExternalInterfaceLockedOut             	(4),
		vExternalInterfaceEnabled               	(5),
		vBoot-bypass                            	(6)
	}
	ACCESS		read-only
	STATUS		mandatory
	DESCRIPTION	"Attribute describing the current hardware security settings
on this device"
	::= {eSerialPorts 9}

SCoolingDevice ::= SEQUENCE {
	a81CoolingDeviceTableIndex              	DmiInteger,
	a81FruGroupIndex                        	DmiInteger,
	a81OperationalGroupIndex                	DmiInteger,
	a81CoolingUnitIndex                     	DmiInteger,
	a81CoolingDeviceType                    	DmiInteger,
	a81TemperatureProbeIndex                	DmiInteger
}

tCoolingDevice OBJECT-TYPE
	SYNTAX		SEQUENCE OF SCoolingDevice
	ACCESS		not-accessible
	STATUS		mandatory
	DESCRIPTION	"This group defines various attributes for cooling devices
in this system."
	::= {dmtfGroups 81}

eCoolingDevice OBJECT-TYPE
	SYNTAX		SCoolingDevice
	ACCESS		not-accessible
	STATUS		mandatory
	DESCRIPTION	""
	INDEX		{DmiComponentIndex, a81CoolingDeviceTableIndex}
	::= {tCoolingDevice 1}

a81CoolingDeviceTableIndex OBJECT-TYPE
	SYNTAX		DmiInteger
	ACCESS		read-only
	STATUS		mandatory
	DESCRIPTION	"An index into the cooling device table."
	::= {eCoolingDevice 1}

a81FruGroupIndex OBJECT-TYPE
	SYNTAX		DmiInteger
	ACCESS		read-only
	STATUS		mandatory
	DESCRIPTION	"If this is a Field Replaceable Unit or if it is part of another
FRU, thisprovides an index into the FRU table; 'value = -1' indicates that
the group is not a FRU."
	::= {eCoolingDevice 2}

a81OperationalGroupIndex OBJECT-TYPE
	SYNTAX		DmiInteger
	ACCESS		read-only
	STATUS		mandatory
	DESCRIPTION	"The index into the Operational State table for this device."
	::= {eCoolingDevice 3}

a81CoolingUnitIndex OBJECT-TYPE
	SYNTAX		DmiInteger
	ACCESS		read-only
	STATUS		mandatory
	DESCRIPTION	"This is the ID of the Cooling Unit (logical cooling device)
of which thisCooling Device is a part. This value matches up with the Cooling
Unit Table Indexattribute defined in the Cooling Unit Globe Table."
	::= {eCoolingDevice 4}

a81CoolingDeviceType OBJECT-TYPE
	SYNTAX		INTEGER {
		vOther                                  	(1),
		vUnknown                                	(2),
		vFan                                    	(3),
		vCentrifugalBlower                      	(4),
		vChipFan                                	(5),
		vCabinetFan                             	(6),
		vPowerSupplyFan                         	(7),
		vHeatPipe                               	(8),
		vIntegratedRefrigeration                	(9),
		vActiveCooling                          	(32),
		vPassiveCooling                         	(33)
	}
	ACCESS		read-only
	STATUS		mandatory
	DESCRIPTION	"The type of Cooling Device that this is e.g. Fan, Heat Pipe,
etc."
	::= {eCoolingDevice 5}

a81TemperatureProbeIndex OBJECT-TYPE
	SYNTAX		DmiInteger
	ACCESS		read-only
	STATUS		mandatory
	DESCRIPTION	"Index into the Temperature Probe table identifying the temperatu
eprobe monitoring this cooling device. 0 indicates no probe provided."
	::= {eCoolingDevice 6}

SVideo ::= SEQUENCE {
	a83VideoIndex                           	DmiInteger,
	a83VideoType                            	DmiInteger,
	a83CurrentVideoMode                     	DmiInteger,
	a83MinimumRefreshRate                   	DmiInteger,
	a83MaximumRefreshRate                   	DmiInteger,
	a83VideoMemoryType                      	DmiInteger,
	a83VideoRamMemorySize                   	DmiInteger,
	a83ScanMode                             	DmiInteger,
	a83VideoPhysicalLocation                	DmiInteger,
	a83CurrentVerticalResolution            	DmiInteger,
	a83CurrentHorizontalResolution          	DmiInteger,
	a83CurrentNumberOfBitsPerPixel          	DmiInteger,
	a83CurrentNumberOfRows                  	DmiInteger,
	a83CurrentNumberOfColumns               	DmiInteger,
	a83CurrentRefreshRate                   	DmiInteger,
	a83FruGroupIndex                        	DmiInteger,
	a83OperationalGroupIndex                	DmiInteger
}

tVideo OBJECT-TYPE
	SYNTAX		SEQUENCE OF SVideo
	ACCESS		not-accessible
	STATUS		mandatory
	DESCRIPTION	"This group defines the attributes of video devices in this
system."
	::= {dmtfGroups 83}

eVideo OBJECT-TYPE
	SYNTAX		SVideo
	ACCESS		not-accessible
	STATUS		mandatory
	DESCRIPTION	""
	INDEX		{DmiComponentIndex, a83VideoIndex}
	::= {tVideo 1}

a83VideoIndex OBJECT-TYPE
	SYNTAX		DmiInteger
	ACCESS		read-only
	STATUS		mandatory
	DESCRIPTION	"An index into the video table."
	::= {eVideo 1}

a83VideoType OBJECT-TYPE
	SYNTAX		INTEGER {
		vOther                                  	(1),
		vUnknown                                	(2),
		vCga                                    	(3),
		vEga                                    	(4),
		vVga                                    	(5),
		vSvga                                   	(6),
		vMda                                    	(7),
		vHgc                                    	(8),
		vMcga                                   	(9),
		v8514a                                  	(10),
		vXga                                    	(11),
		vLinearFrameBuffer                      	(12),
		vPc-98                                  	(160)
	}
	ACCESS		read-only
	STATUS		mandatory
	DESCRIPTION	"The architecture of the video subsystem in this system."
	::= {eVideo 2}

a83CurrentVideoMode OBJECT-TYPE
	SYNTAX		DmiInteger
	ACCESS		read-only
	STATUS		mandatory
	DESCRIPTION	"The current video mode in this system."
	::= {eVideo 3}

a83MinimumRefreshRate OBJECT-TYPE
	SYNTAX		DmiInteger
	ACCESS		read-only
	STATUS		mandatory
	DESCRIPTION	"The minimum refresh rate for this video subsystem in Hz."
	::= {eVideo 4}

a83MaximumRefreshRate OBJECT-TYPE
	SYNTAX		DmiInteger
	ACCESS		read-only
	STATUS		mandatory
	DESCRIPTION	"The maximum refresh rate for this video subsystem in Hz."
	::= {eVideo 5}

a83VideoMemoryType OBJECT-TYPE
	SYNTAX		INTEGER {
		vOther                                  	(1),
		vUnknown                                	(2),
		vVram                                   	(3),
		vDram                                   	(4),
		vSram                                   	(5),
		vWram                                   	(6),
		vEdoRam                                 	(7),
		vBurstSynchronousDram                   	(8),
		vPipelinedBurstSram                     	(9)
	}
	ACCESS		read-only
	STATUS		mandatory
	DESCRIPTION	"The type of video memory for this adapter."
	::= {eVideo 6}

a83VideoRamMemorySize OBJECT-TYPE
	SYNTAX		DmiInteger
	ACCESS		read-only
	STATUS		mandatory
	DESCRIPTION	"Video adapter memory size in kilobytes."
	::= {eVideo 7}

a83ScanMode OBJECT-TYPE
	SYNTAX		INTEGER {
		vOther                                  	(1),
		vUnknown                                	(2),
		vInterlaced                             	(3),
		vNonInterlaced                          	(4)
	}
	ACCESS		read-only
	STATUS		mandatory
	DESCRIPTION	"The scan mode for this video device."
	::= {eVideo 8}

a83VideoPhysicalLocation OBJECT-TYPE
	SYNTAX		INTEGER {
		vOther                                  	(1),
		vUnknown                                	(2),
		vIntegrated                             	(3),
		vAdd-onCard                             	(4)
	}
	ACCESS		read-only
	STATUS		mandatory
	DESCRIPTION	"The location of the video controller circuitry."
	::= {eVideo 9}

a83CurrentVerticalResolution OBJECT-TYPE
	SYNTAX		DmiInteger
	ACCESS		read-only
	STATUS		mandatory
	DESCRIPTION	"The current number of vertical pixels."
	::= {eVideo 10}

a83CurrentHorizontalResolution OBJECT-TYPE
	SYNTAX		DmiInteger
	ACCESS		read-only
	STATUS		mandatory
	DESCRIPTION	"The current number of horizontal pixels."
	::= {eVideo 11}

a83CurrentNumberOfBitsPerPixel OBJECT-TYPE
	SYNTAX		DmiInteger
	ACCESS		read-only
	STATUS		mandatory
	DESCRIPTION	"The number of bits used to display each pixel for this video
device."
	::= {eVideo 12}

a83CurrentNumberOfRows OBJECT-TYPE
	SYNTAX		DmiInteger
	ACCESS		read-only
	STATUS		mandatory
	DESCRIPTION	"The number of rows in character mode for this video device."
	::= {eVideo 13}

a83CurrentNumberOfColumns OBJECT-TYPE
	SYNTAX		DmiInteger
	ACCESS		read-only
	STATUS		mandatory
	DESCRIPTION	"The number of columns in character mode for this video device."
	::= {eVideo 14}

a83CurrentRefreshRate OBJECT-TYPE
	SYNTAX		DmiInteger
	ACCESS		read-only
	STATUS		mandatory
	DESCRIPTION	"The current refresh rate in Hz for this video device."
	::= {eVideo 15}

a83FruGroupIndex OBJECT-TYPE
	SYNTAX		DmiInteger
	ACCESS		read-only
	STATUS		mandatory
	DESCRIPTION	"If this is a Field Replaceable Unit or if it is part of another
FRU, thisprovides an index into the FRU table; 'value = -1' indicates that
the group is not a FRU."
	::= {eVideo 16}

a83OperationalGroupIndex OBJECT-TYPE
	SYNTAX		DmiInteger
	ACCESS		read-only
	STATUS		mandatory
	DESCRIPTION	"The index into the Operational State table for this device."
	::= {eVideo 17}

SVideoBios ::= SEQUENCE {
	a84VideoBiosIndex                       	DmiInteger,
	a84VideoBiosManufacturer                	DmiDisplaystring,
	a84VideoBiosVersion                     	DmiDisplaystring,
	a84VideoBiosReleaseDate                 	DmiDateX,
	a84VideoBiosShadowingState              	DmiInteger
}

tVideoBios OBJECT-TYPE
	SYNTAX		SEQUENCE OF SVideoBios
	ACCESS		not-accessible
	STATUS		mandatory
	DESCRIPTION	"This group defines the attributes for the Video BIOS."
	::= {dmtfGroups 84}

eVideoBios OBJECT-TYPE
	SYNTAX		SVideoBios
	ACCESS		not-accessible
	STATUS		mandatory
	DESCRIPTION	""
	INDEX		{DmiComponentIndex, a84VideoBiosIndex}
	::= {tVideoBios 1}

a84VideoBiosIndex OBJECT-TYPE
	SYNTAX		DmiInteger
	ACCESS		read-only
	STATUS		mandatory
	DESCRIPTION	"The index into the Video BIOS table."
	::= {eVideoBios 1}

a84VideoBiosManufacturer OBJECT-TYPE
	SYNTAX		DmiDisplaystring
	ACCESS		read-only
	STATUS		mandatory
	DESCRIPTION	"The name of the company that wrote this Video BIOS."
	::= {eVideoBios 2}

a84VideoBiosVersion OBJECT-TYPE
	SYNTAX		DmiDisplaystring
	ACCESS		read-only
	STATUS		mandatory
	DESCRIPTION	"The version number or version string of this Video BIOS."
	::= {eVideoBios 3}

a84VideoBiosReleaseDate OBJECT-TYPE
	SYNTAX		DmiDateX
	ACCESS		read-only
	STATUS		mandatory
	DESCRIPTION	"The Video BIOS release date."
	::= {eVideoBios 4}

a84VideoBiosShadowingState OBJECT-TYPE
	SYNTAX		INTEGER {
		vFalse                                  	(0),
		vTrue                                   	(1)
	}
	ACCESS		read-only
	STATUS		mandatory
	DESCRIPTION	"If true, the Video BIOS is currently being shadowed."
	::= {eVideoBios 5}

SMouse ::= SEQUENCE {
	a91MouseInterface                       	DmiInteger,
	a91MouseIrq                             	DmiInteger,
	a91MouseButtons                         	DmiInteger,
	a91MousePortName                        	DmiDisplaystring,
	a91MouseDriverName                      	DmiDisplaystring,
	a91MouseDriverVersion                   	DmiDisplaystring,
	a91FruGroupIndex                        	DmiInteger,
	a91OperationalGroupIndex                	DmiInteger,
	a91SecuritySettings                     	DmiInteger
}

tMouse OBJECT-TYPE
	SYNTAX		SEQUENCE OF SMouse
	ACCESS		not-accessible
	STATUS		mandatory
	DESCRIPTION	"This group defines the characteristics of a mouse input device."
	::= {dmtfGroups 91}

eMouse OBJECT-TYPE
	SYNTAX		SMouse
	ACCESS		not-accessible
	STATUS		mandatory
	DESCRIPTION	""
	INDEX		{DmiComponentIndex}
	::= {tMouse 1}

a91MouseInterface OBJECT-TYPE
	SYNTAX		INTEGER {
		vOther                                  	(1),
		vUnknown                                	(2),
		vSerial                                 	(3),
		vPs2                                    	(4),
		vInfrared                               	(5),
		vHp-hil                                 	(6),
		vBusMouse                               	(7),
		vAdb                                    	(8),
		vBusMouseDb-9                           	(160),
		vBusMouseMicro-din                      	(161)
	}
	ACCESS		read-only
	STATUS		mandatory
	DESCRIPTION	"The interface type of this mouse."
	::= {eMouse 1}

a91MouseIrq OBJECT-TYPE
	SYNTAX		DmiInteger
	ACCESS		read-only
	STATUS		mandatory
	DESCRIPTION	"The IRQ number used by this mouse."
	::= {eMouse 2}

a91MouseButtons OBJECT-TYPE
	SYNTAX		DmiInteger
	ACCESS		read-only
	STATUS		mandatory
	DESCRIPTION	"The number of mouse buttons on this mouse."
	::= {eMouse 3}

a91MousePortName OBJECT-TYPE
	SYNTAX		DmiDisplaystring
	ACCESS		read-only
	STATUS		mandatory
	DESCRIPTION	"The name of the port currently being used by this mouse."
	::= {eMouse 4}

a91MouseDriverName OBJECT-TYPE
	SYNTAX		DmiDisplaystring
	ACCESS		read-only
	STATUS		mandatory
	DESCRIPTION	"The name of the mouse driver."
	::= {eMouse 5}

a91MouseDriverVersion OBJECT-TYPE
	SYNTAX		DmiDisplaystring
	ACCESS		read-only
	STATUS		mandatory
	DESCRIPTION	"The version number of the mouse driver."
	::= {eMouse 6}

a91FruGroupIndex OBJECT-TYPE
	SYNTAX		DmiInteger
	ACCESS		read-only
	STATUS		mandatory
	DESCRIPTION	"If this is a Field Replaceable Unit or if it is part of another
FRU, thisprovides an index into the FRU table; 'value = -1' indicates that
the group is not a FRU."
	::= {eMouse 7}

a91OperationalGroupIndex OBJECT-TYPE
	SYNTAX		DmiInteger
	ACCESS		read-only
	STATUS		mandatory
	DESCRIPTION	"The index into the Operational State table for this device."
	::= {eMouse 8}

a91SecuritySettings OBJECT-TYPE
	SYNTAX		INTEGER {
		vOther                                  	(1),
		vUnknown                                	(2),
		vNone                                   	(3),
		vExternalInterfaceLockedOut             	(4),
		vExternalInterfaceEnabled               	(5)
	}
	ACCESS		read-only
	STATUS		mandatory
	DESCRIPTION	"Enum describing the current hardware security settings on
this device"
	::= {eMouse 9}

SKeyboard ::= SEQUENCE {
	a92KeyboardLayout                       	DmiDisplaystring,
	a92KeyboardType                         	DmiDisplaystring,
	a92KeyboardConnectorType                	DmiInteger,
	a92FruGroupIndex                        	DmiInteger,
	a92OperationalGroupIndex                	DmiInteger,
	a92SecuritySettings                     	DmiInteger
}

tKeyboard OBJECT-TYPE
	SYNTAX		SEQUENCE OF SKeyboard
	ACCESS		not-accessible
	STATUS		mandatory
	DESCRIPTION	"This group defines the characteristics of the system keyboard."
	::= {dmtfGroups 92}

eKeyboard OBJECT-TYPE
	SYNTAX		SKeyboard
	ACCESS		not-accessible
	STATUS		mandatory
	DESCRIPTION	""
	INDEX		{DmiComponentIndex}
	::= {tKeyboard 1}

a92KeyboardLayout OBJECT-TYPE
	SYNTAX		DmiDisplaystring
	ACCESS		read-only
	STATUS		mandatory
	DESCRIPTION	"A description of the layout of this keyboard."
	::= {eKeyboard 1}

a92KeyboardType OBJECT-TYPE
	SYNTAX		DmiDisplaystring
	ACCESS		read-only
	STATUS		mandatory
	DESCRIPTION	"The type description of this keyboard."
	::= {eKeyboard 2}

a92KeyboardConnectorType OBJECT-TYPE
	SYNTAX		INTEGER {
		vOther                                  	(1),
		vUnknown                                	(2),
		vMini-din                               	(3),
		vMicro-din                              	(4),
		vPs2                                    	(5),
		vInfrared                               	(6),
		vHp-hil                                 	(7),
		vDb-9                                   	(8),
		vAccessBus                              	(9),
		vPc-98                                  	(160)
	}
	ACCESS		read-only
	STATUS		mandatory
	DESCRIPTION	"The type of keyboard connector used by this keyboard."
	::= {eKeyboard 3}

a92FruGroupIndex OBJECT-TYPE
	SYNTAX		DmiInteger
	ACCESS		read-only
	STATUS		mandatory
	DESCRIPTION	"If this is a Field Replaceable Unit or if it is part of another
FRU, thisprovides an index into the FRU table; 'value = -1' indicates that
the group is not a FRU."
	::= {eKeyboard 4}

a92OperationalGroupIndex OBJECT-TYPE
	SYNTAX		DmiInteger
	ACCESS		read-only
	STATUS		mandatory
	DESCRIPTION	"The index into the Operational State table for this device."
	::= {eKeyboard 5}

a92SecuritySettings OBJECT-TYPE
	SYNTAX		INTEGER {
		vOther                                  	(1),
		vUnknown                                	(2),
		vNone                                   	(3),
		vExternalInterfaceLockedOut             	(4),
		vExternalInterfaceEnabled               	(5)
	}
	ACCESS		read-only
	STATUS		mandatory
	DESCRIPTION	"Enum describing the current hardware security settings on
this device"
	::= {eKeyboard 6}

SEventGenerationForProcessor ::= SEQUENCE {
	a100EventType                           	DmiInteger,
	a100EventSeverity                       	DmiInteger,
	a100IsEventState-based                  	DmiInteger,
	a100EventStateKey                       	DmiInteger,
	a100AssociatedGroup                     	DmiDisplaystring,
	a100EventSystem                         	DmiInteger,
	a100EventSubsystem                      	DmiInteger,
	a100IsInstanceDataPresent               	DmiInteger,
	a100EventMessage                        	DmiDisplaystring
}

tEventGenerationForProcessor OBJECT-TYPE
	SYNTAX		SEQUENCE OF SEventGenerationForProcessor
	ACCESS		not-accessible
	STATUS		mandatory
	DESCRIPTION	""
	::= {dmtfGroups 100}

eEventGenerationForProcessor OBJECT-TYPE
	SYNTAX		SEventGenerationForProcessor
	ACCESS		not-accessible
	STATUS		mandatory
	DESCRIPTION	""
	INDEX		{DmiComponentIndex, a100AssociatedGroup}
	::= {tEventGenerationForProcessor 1}

a100EventType OBJECT-TYPE
	SYNTAX		INTEGER {
		vProcessorInternalError                 	(256),
		vProcessorThermalTrip                   	(257),
		vProcessorFrb-3Failure                  	(258)
	}
	ACCESS		read-only
	STATUS		mandatory
	DESCRIPTION	"The type of event that has occurred."
	::= {eEventGenerationForProcessor 1}

a100EventSeverity OBJECT-TYPE
	SYNTAX		INTEGER {
		vMonitor                                	(1),
		vInformation                            	(2),
		vOk                                     	(4),
		vNon-critical1                          	(8),
		vCritical                               	(16),
		vNon-recoverable                        	(32)
	}
	ACCESS		read-only
	STATUS		mandatory
	DESCRIPTION	"The severity of this event."
	::= {eEventGenerationForProcessor 2}

a100IsEventState-based OBJECT-TYPE
	SYNTAX		INTEGER {
		vFalse                                  	(0),
		vTrue                                   	(1)
	}
	ACCESS		read-only
	STATUS		mandatory
	DESCRIPTION	"The value of this attributedetermines whether the Event being
reportedis a state-based Event or not. If the valueof this attribute is TRUE
then the Event isstate-based. Otherwise the Event is notstate-based."
	::= {eEventGenerationForProcessor 3}

a100EventStateKey OBJECT-TYPE
	SYNTAX		DmiInteger
	ACCESS		read-only
	STATUS		mandatory
	DESCRIPTION	"A unique, single integer key into the EventState group if
this is a state-based Event.If this is not a state-based Event then thisthis
attribute's value is not defined."
	::= {eEventGenerationForProcessor 4}

a100AssociatedGroup OBJECT-TYPE
	SYNTAX		DmiDisplaystring
	ACCESS		read-only
	STATUS		mandatory
	DESCRIPTION	"The class name of the group that is associatedwith the events
defined in this EventGeneration group."
	::= {eEventGenerationForProcessor 5}

a100EventSystem OBJECT-TYPE
	SYNTAX		INTEGER {
		vOther                                  	(0),
		vUnknown                                	(1)
	}
	ACCESS		read-only
	STATUS		mandatory
	DESCRIPTION	"The major functional aspect of the productcausing the fault."
	::= {eEventGenerationForProcessor 6}

a100EventSubsystem OBJECT-TYPE
	SYNTAX		INTEGER {
		vOther                                  	(0),
		vUnknown                                	(1)
	}
	ACCESS		read-only
	STATUS		mandatory
	DESCRIPTION	"The minor functional aspect of the productcausing the fault."
	::= {eEventGenerationForProcessor 7}

a100IsInstanceDataPresent OBJECT-TYPE
	SYNTAX		INTEGER {
		vFalse                                  	(0),
		vTrue                                   	(1)
	}
	ACCESS		read-only
	STATUS		mandatory
	DESCRIPTION	"Indicates whether the second event block containsinstance-specif
c data."
	::= {eEventGenerationForProcessor 9}

a100EventMessage OBJECT-TYPE
	SYNTAX		DmiDisplaystring
	ACCESS		read-only
	STATUS		mandatory
	DESCRIPTION	"Auxillary information releated to the eventThis text contains
the name of the Probe"
	::= {eEventGenerationForProcessor 10}

SEventGenerationForPowerSupply ::= SEQUENCE {
	a104EventType                           	DmiInteger,
	a104EventSeverity                       	DmiInteger,
	a104IsEventState-based                  	DmiInteger,
	a104EventStateKey                       	DmiInteger,
	a104AssociatedGroup                     	DmiDisplaystring,
	a104EventSystem                         	DmiInteger,
	a104EventSubsystem                      	DmiInteger,
	a104IsInstanceDataPresent               	DmiInteger,
	a104EventMessage                        	DmiDisplaystring
}

tEventGenerationForPowerSupply OBJECT-TYPE
	SYNTAX		SEQUENCE OF SEventGenerationForPowerSupply
	ACCESS		not-accessible
	STATUS		mandatory
	DESCRIPTION	""
	::= {dmtfGroups 104}

eEventGenerationForPowerSupply OBJECT-TYPE
	SYNTAX		SEventGenerationForPowerSupply
	ACCESS		not-accessible
	STATUS		mandatory
	DESCRIPTION	""
	INDEX		{DmiComponentIndex, a104AssociatedGroup}
	::= {tEventGenerationForPowerSupply 1}

a104EventType OBJECT-TYPE
	SYNTAX		INTEGER {
		vPowerSupplyFailed                      	(256),
		vPowerSupplyOk                          	(257),
		vPowerSupplyLikelyToFail                	(258)
	}
	ACCESS		read-only
	STATUS		mandatory
	DESCRIPTION	"The type of event that has occurred."
	::= {eEventGenerationForPowerSupply 1}

a104EventSeverity OBJECT-TYPE
	SYNTAX		INTEGER {
		vMonitor                                	(1),
		vInformation                            	(2),
		vOk                                     	(4),
		vNon-critical                           	(8),
		vCritical                               	(16),
		vNon-recoverable                        	(32)
	}
	ACCESS		read-only
	STATUS		mandatory
	DESCRIPTION	"The severity of this event."
	::= {eEventGenerationForPowerSupply 2}

a104IsEventState-based OBJECT-TYPE
	SYNTAX		INTEGER {
		vFalse                                  	(0),
		vTrue                                   	(1)
	}
	ACCESS		read-only
	STATUS		mandatory
	DESCRIPTION	"The value of this attributedetermines whether the Event being
reportedis a state-based Event or not. If the valueof this attribute is TRUE
then the Event isstate-based. Otherwise the Event is notstate-based."
	::= {eEventGenerationForPowerSupply 3}

a104EventStateKey OBJECT-TYPE
	SYNTAX		DmiInteger
	ACCESS		read-only
	STATUS		mandatory
	DESCRIPTION	"A unique, single integer key into the EventState group if
this is a state-based Event.If this is not a state-based Event then thisthis
attribute's value is not defined."
	::= {eEventGenerationForPowerSupply 4}

a104AssociatedGroup OBJECT-TYPE
	SYNTAX		DmiDisplaystring
	ACCESS		read-only
	STATUS		mandatory
	DESCRIPTION	"The class name of the group that is associatedwith the events
defined in this EventGeneration group."
	::= {eEventGenerationForPowerSupply 5}

a104EventSystem OBJECT-TYPE
	SYNTAX		INTEGER {
		vOther                                  	(0),
		vUnknown                                	(1)
	}
	ACCESS		read-only
	STATUS		mandatory
	DESCRIPTION	"The major functional aspect of the productcausing the fault."
	::= {eEventGenerationForPowerSupply 6}

a104EventSubsystem OBJECT-TYPE
	SYNTAX		INTEGER {
		vOther                                  	(0),
		vUnknown                                	(1)
	}
	ACCESS		read-only
	STATUS		mandatory
	DESCRIPTION	"The minor functional aspect of the productcausing the fault."
	::= {eEventGenerationForPowerSupply 7}

a104IsInstanceDataPresent OBJECT-TYPE
	SYNTAX		INTEGER {
		vFalse                                  	(0),
		vTrue                                   	(1)
	}
	ACCESS		read-only
	STATUS		mandatory
	DESCRIPTION	"Indicates whether the second event block containsinstance-specif
c data."
	::= {eEventGenerationForPowerSupply 9}

a104EventMessage OBJECT-TYPE
	SYNTAX		DmiDisplaystring
	ACCESS		read-only
	STATUS		mandatory
	DESCRIPTION	"Auxillary information releated to the eventThis text contains
the name of the Probe"
	::= {eEventGenerationForPowerSupply 10}

SEventGenerationForPhysicalMemory ::= SEQUENCE {
	a108EventType                           	DmiInteger,
	a108EventSeverity                       	DmiInteger,
	a108IsEventState-based                  	DmiInteger,
	a108EventStateKey                       	DmiInteger,
	a108AssociatedGroup                     	DmiDisplaystring,
	a108EventSystem                         	DmiInteger,
	a108EventSubsystem                      	DmiInteger,
	a108IsInstanceDataPresent               	DmiInteger,
	a108EventMessage                        	DmiDisplaystring
}

tEventGenerationForPhysicalMemory OBJECT-TYPE
	SYNTAX		SEQUENCE OF SEventGenerationForPhysicalMemory
	ACCESS		not-accessible
	STATUS		mandatory
	DESCRIPTION	""
	::= {dmtfGroups 108}

eEventGenerationForPhysicalMemory OBJECT-TYPE
	SYNTAX		SEventGenerationForPhysicalMemory
	ACCESS		not-accessible
	STATUS		mandatory
	DESCRIPTION	""
	INDEX		{DmiComponentIndex, a108AssociatedGroup}
	::= {tEventGenerationForPhysicalMemory 1}

a108EventType OBJECT-TYPE
	SYNTAX		INTEGER {
		vSingle-bitMemoryError                  	(256),
		vMulti-bitMemoryErrorFromPreviousBoot   	(257)
	}
	ACCESS		read-only
	STATUS		mandatory
	DESCRIPTION	"The type of event that has occurred."
	::= {eEventGenerationForPhysicalMemory 1}

a108EventSeverity OBJECT-TYPE
	SYNTAX		INTEGER {
		vMonitor                                	(1),
		vInformation                            	(2),
		vOk                                     	(4),
		vNon-critical                           	(8),
		vCritical                               	(16),
		vNon-recoverable                        	(32)
	}
	ACCESS		read-only
	STATUS		mandatory
	DESCRIPTION	"The severity of this event."
	::= {eEventGenerationForPhysicalMemory 2}

a108IsEventState-based OBJECT-TYPE
	SYNTAX		INTEGER {
		vFalse                                  	(0),
		vTrue                                   	(1)
	}
	ACCESS		read-only
	STATUS		mandatory
	DESCRIPTION	"The value of this attributedetermines whether the Event being
reportedis a state-based Event or not. If the valueof this attribute is TRUE
then the Event isstate-based. Otherwise the Event is notstate-based."
	::= {eEventGenerationForPhysicalMemory 3}

a108EventStateKey OBJECT-TYPE
	SYNTAX		DmiInteger
	ACCESS		read-only
	STATUS		mandatory
	DESCRIPTION	"A unique, single integer key into the EventState group if
this is a state-based Event.If this is not a state-based Event then thisthis
attribute's value is not defined."
	::= {eEventGenerationForPhysicalMemory 4}

a108AssociatedGroup OBJECT-TYPE
	SYNTAX		DmiDisplaystring
	ACCESS		read-only
	STATUS		mandatory
	DESCRIPTION	"The class name of the group that is associatedwith the events
defined in this EventGeneration group."
	::= {eEventGenerationForPhysicalMemory 5}

a108EventSystem OBJECT-TYPE
	SYNTAX		INTEGER {
		vOther                                  	(0),
		vUnknown                                	(1)
	}
	ACCESS		read-only
	STATUS		mandatory
	DESCRIPTION	"The major functional aspect of the productcausing the fault."
	::= {eEventGenerationForPhysicalMemory 6}

a108EventSubsystem OBJECT-TYPE
	SYNTAX		INTEGER {
		vOther                                  	(0),
		vUnknown                                	(1)
	}
	ACCESS		read-only
	STATUS		mandatory
	DESCRIPTION	"The minor functional aspect of the productcausing the fault."
	::= {eEventGenerationForPhysicalMemory 7}

a108IsInstanceDataPresent OBJECT-TYPE
	SYNTAX		INTEGER {
		vFalse                                  	(0),
		vTrue                                   	(1)
	}
	ACCESS		read-only
	STATUS		mandatory
	DESCRIPTION	"Indicates whether the second event block containsinstance-specif
c data."
	::= {eEventGenerationForPhysicalMemory 9}

a108EventMessage OBJECT-TYPE
	SYNTAX		DmiDisplaystring
	ACCESS		read-only
	STATUS		mandatory
	DESCRIPTION	"Auxillary information releated to the eventThis text contains
the name of the Probe"
	::= {eEventGenerationForPhysicalMemory 10}

SEventGenerationForVoltageProbe ::= SEQUENCE {
	a113EventType                           	DmiInteger,
	a113EventSeverity                       	DmiInteger,
	a113IsEventState-based                  	DmiInteger,
	a113EventStateKey                       	DmiInteger,
	a113AssociatedGroup                     	DmiDisplaystring,
	a113EventSystem                         	DmiInteger,
	a113EventSubsystem                      	DmiInteger,
	a113IsInstanceDataPresent               	DmiInteger,
	a113EventMessage                        	DmiDisplaystring
}

tEventGenerationForVoltageProbe OBJECT-TYPE
	SYNTAX		SEQUENCE OF SEventGenerationForVoltageProbe
	ACCESS		not-accessible
	STATUS		mandatory
	DESCRIPTION	""
	::= {dmtfGroups 113}

eEventGenerationForVoltageProbe OBJECT-TYPE
	SYNTAX		SEventGenerationForVoltageProbe
	ACCESS		not-accessible
	STATUS		mandatory
	DESCRIPTION	""
	INDEX		{DmiComponentIndex, a113AssociatedGroup}
	::= {tEventGenerationForVoltageProbe 1}

a113EventType OBJECT-TYPE
	SYNTAX		INTEGER {
		vStatusChangedToOk                      	(256),
		vStatusChangedToUpperCritical           	(257),
		vStatusChangedToLowerCritical           	(258),
		vStatusChangedFromOkToUpperNon-critical 	(259),
		vStatusChangedFromOkToLowerNon-critical 	(260),
		vStatusChangedFromUpperCriticalToUpperNo	(261),
		vStatusChangedFromLowerCriticalToLowerNo	(262)
	}
	ACCESS		read-only
	STATUS		mandatory
	DESCRIPTION	"The type of event that has occurred."
	::= {eEventGenerationForVoltageProbe 1}

a113EventSeverity OBJECT-TYPE
	SYNTAX		INTEGER {
		vMonitor                                	(1),
		vInformation                            	(2),
		vOk                                     	(4),
		vNon-critical                           	(8),
		vCritical                               	(16),
		vNon-recoverable                        	(32)
	}
	ACCESS		read-only
	STATUS		mandatory
	DESCRIPTION	"The severity of this event."
	::= {eEventGenerationForVoltageProbe 2}

a113IsEventState-based OBJECT-TYPE
	SYNTAX		INTEGER {
		vFalse                                  	(0),
		vTrue                                   	(1)
	}
	ACCESS		read-only
	STATUS		mandatory
	DESCRIPTION	"The value of this attributedetermines whether the Event being
reportedis a state-based Event or not. If the valueof this attribute is TRUE
then the Event isstate-based. Otherwise the Event is notstate-based."
	::= {eEventGenerationForVoltageProbe 3}

a113EventStateKey OBJECT-TYPE
	SYNTAX		DmiInteger
	ACCESS		read-only
	STATUS		mandatory
	DESCRIPTION	"A unique, single integer key into the EventState group if
this is a state-based Event.If this is not a state-based Event then thisthis
attribute's value is not defined."
	::= {eEventGenerationForVoltageProbe 4}

a113AssociatedGroup OBJECT-TYPE
	SYNTAX		DmiDisplaystring
	ACCESS		read-only
	STATUS		mandatory
	DESCRIPTION	"The class name of the group that is associatedwith the events
defined in this EventGeneration group."
	::= {eEventGenerationForVoltageProbe 5}

a113EventSystem OBJECT-TYPE
	SYNTAX		INTEGER {
		vOther                                  	(0),
		vUnknown                                	(1)
	}
	ACCESS		read-only
	STATUS		mandatory
	DESCRIPTION	"The major functional aspect of the productcausing the fault."
	::= {eEventGenerationForVoltageProbe 6}

a113EventSubsystem OBJECT-TYPE
	SYNTAX		INTEGER {
		vOther                                  	(0),
		vUnknown                                	(1)
	}
	ACCESS		read-only
	STATUS		mandatory
	DESCRIPTION	"The minor functional aspect of the productcausing the fault."
	::= {eEventGenerationForVoltageProbe 7}

a113IsInstanceDataPresent OBJECT-TYPE
	SYNTAX		INTEGER {
		vFalse                                  	(0),
		vTrue                                   	(1)
	}
	ACCESS		read-only
	STATUS		mandatory
	DESCRIPTION	"Indicates whether the second event block containsinstance-specif
c data."
	::= {eEventGenerationForVoltageProbe 9}

a113EventMessage OBJECT-TYPE
	SYNTAX		DmiDisplaystring
	ACCESS		read-only
	STATUS		mandatory
	DESCRIPTION	"Auxillary information releated to the eventThis text contains
the name of the Probe"
	::= {eEventGenerationForVoltageProbe 10}

SEventGenerationForTemperatureProbe ::= SEQUENCE {
	a114EventType                           	DmiInteger,
	a114EventSeverity                       	DmiInteger,
	a114IsEventState-based                  	DmiInteger,
	a114EventStateKey                       	DmiInteger,
	a114AssociatedGroup                     	DmiDisplaystring,
	a114EventSystem                         	DmiInteger,
	a114EventSubsystem                      	DmiInteger,
	a114IsInstanceDataPresent               	DmiInteger,
	a114EventMessage                        	DmiDisplaystring
}

tEventGenerationForTemperatureProbe OBJECT-TYPE
	SYNTAX		SEQUENCE OF SEventGenerationForTemperatureProbe
	ACCESS		not-accessible
	STATUS		mandatory
	DESCRIPTION	""
	::= {dmtfGroups 114}

eEventGenerationForTemperatureProbe OBJECT-TYPE
	SYNTAX		SEventGenerationForTemperatureProbe
	ACCESS		not-accessible
	STATUS		mandatory
	DESCRIPTION	""
	INDEX		{DmiComponentIndex, a114AssociatedGroup}
	::= {tEventGenerationForTemperatureProbe 1}

a114EventType OBJECT-TYPE
	SYNTAX		INTEGER {
		vStatusChangedToOk                      	(256),
		vStatusChangedToUpperCritical           	(257),
		vStatusChangedToLowerCritical           	(258),
		vStatusChangedFromOkToUpperNon-critical 	(259),
		vStatusChangedFromOkToLowerNon-critical 	(260),
		vStatusChangedFromUpperCriticalToUpperNo	(261),
		vStatusChangedFromLowerCriticalToLowerNo	(262)
	}
	ACCESS		read-only
	STATUS		mandatory
	DESCRIPTION	"The type of event that has occurred."
	::= {eEventGenerationForTemperatureProbe 1}

a114EventSeverity OBJECT-TYPE
	SYNTAX		INTEGER {
		vMonitor                                	(1),
		vInformation                            	(2),
		vOk                                     	(4),
		vNon-critical                           	(8),
		vCritical                               	(16),
		vNon-recoverable                        	(32)
	}
	ACCESS		read-only
	STATUS		mandatory
	DESCRIPTION	"The severity of this event."
	::= {eEventGenerationForTemperatureProbe 2}

a114IsEventState-based OBJECT-TYPE
	SYNTAX		INTEGER {
		vFalse                                  	(0),
		vTrue                                   	(1)
	}
	ACCESS		read-only
	STATUS		mandatory
	DESCRIPTION	"The value of this attributedetermines whether the Event being
reportedis a state-based Event or not. If the valueof this attribute is TRUE
then the Event isstate-based. Otherwise the Event is notstate-based."
	::= {eEventGenerationForTemperatureProbe 3}

a114EventStateKey OBJECT-TYPE
	SYNTAX		DmiInteger
	ACCESS		read-only
	STATUS		mandatory
	DESCRIPTION	"A unique, single integer key into the EventState group if
this is a state-based Event.If this is not a state-based Event then thisthis
attribute's value is not defined."
	::= {eEventGenerationForTemperatureProbe 4}

a114AssociatedGroup OBJECT-TYPE
	SYNTAX		DmiDisplaystring
	ACCESS		read-only
	STATUS		mandatory
	DESCRIPTION	"The class name of the group that is associatedwith the events
defined in this EventGeneration group."
	::= {eEventGenerationForTemperatureProbe 5}

a114EventSystem OBJECT-TYPE
	SYNTAX		INTEGER {
		vOther                                  	(0),
		vUnknown                                	(1)
	}
	ACCESS		read-only
	STATUS		mandatory
	DESCRIPTION	"The major functional aspect of the productcausing the fault."
	::= {eEventGenerationForTemperatureProbe 6}

a114EventSubsystem OBJECT-TYPE
	SYNTAX		INTEGER {
		vOther                                  	(0),
		vUnknown                                	(1)
	}
	ACCESS		read-only
	STATUS		mandatory
	DESCRIPTION	"The minor functional aspect of the productcausing the fault."
	::= {eEventGenerationForTemperatureProbe 7}

a114IsInstanceDataPresent OBJECT-TYPE
	SYNTAX		INTEGER {
		vFalse                                  	(0),
		vTrue                                   	(1)
	}
	ACCESS		read-only
	STATUS		mandatory
	DESCRIPTION	"Indicates whether the second event block containsinstance-specif
c data."
	::= {eEventGenerationForTemperatureProbe 9}

a114EventMessage OBJECT-TYPE
	SYNTAX		DmiDisplaystring
	ACCESS		read-only
	STATUS		mandatory
	DESCRIPTION	"Auxillary information releated to the eventThis text contains
the name of the Probe"
	::= {eEventGenerationForTemperatureProbe 10}

SEventGenerationForPhysicalContainer ::= SEQUENCE {
	a116EventType                           	DmiInteger,
	a116EventSeverity                       	DmiInteger,
	a116IsEventState-based                  	DmiInteger,
	a116EventStateKey                       	DmiInteger,
	a116AssociatedGroup                     	DmiDisplaystring,
	a116EventSystem                         	DmiInteger,
	a116EventSubsystem                      	DmiInteger,
	a116IsInstanceDataPresent               	DmiInteger,
	a116EventMessage                        	DmiDisplaystring
}

tEventGenerationForPhysicalContainer OBJECT-TYPE
	SYNTAX		SEQUENCE OF SEventGenerationForPhysicalContainer
	ACCESS		not-accessible
	STATUS		mandatory
	DESCRIPTION	""
	::= {dmtfGroups 116}

eEventGenerationForPhysicalContainer OBJECT-TYPE
	SYNTAX		SEventGenerationForPhysicalContainer
	ACCESS		not-accessible
	STATUS		mandatory
	DESCRIPTION	""
	INDEX		{DmiComponentIndex, a116AssociatedGroup}
	::= {tEventGenerationForPhysicalContainer 1}

a116EventType OBJECT-TYPE
	SYNTAX		INTEGER {
		vContainerSecurityBreach                	(6),
		vContainerSecurityStatusOk              	(256)
	}
	ACCESS		read-only
	STATUS		mandatory
	DESCRIPTION	"The type of event that has occurred."
	::= {eEventGenerationForPhysicalContainer 1}

a116EventSeverity OBJECT-TYPE
	SYNTAX		INTEGER {
		vMonitor                                	(1),
		vInformation                            	(2),
		vOk                                     	(4),
		vNon-critical                           	(8),
		vCritical                               	(16),
		vNon-recoverable                        	(32)
	}
	ACCESS		read-only
	STATUS		mandatory
	DESCRIPTION	"The severity of this event."
	::= {eEventGenerationForPhysicalContainer 2}

a116IsEventState-based OBJECT-TYPE
	SYNTAX		INTEGER {
		vFalse                                  	(0),
		vTrue                                   	(1)
	}
	ACCESS		read-only
	STATUS		mandatory
	DESCRIPTION	"The value of this attributedetermines whether the Event being
reportedis a state-based Event or not. If the valueof this attribute is TRUE
then the Event isstate-based. Otherwise the Event is notstate-based."
	::= {eEventGenerationForPhysicalContainer 3}

a116EventStateKey OBJECT-TYPE
	SYNTAX		DmiInteger
	ACCESS		read-only
	STATUS		mandatory
	DESCRIPTION	"A unique, single integer key into the EventState group if
this is a state-based Event.If this is not a state-based Event then thisthis
attribute's value is not defined."
	::= {eEventGenerationForPhysicalContainer 4}

a116AssociatedGroup OBJECT-TYPE
	SYNTAX		DmiDisplaystring
	ACCESS		read-only
	STATUS		mandatory
	DESCRIPTION	"The class name of the group that is associatedwith the events
defined in this EventGeneration group."
	::= {eEventGenerationForPhysicalContainer 5}

a116EventSystem OBJECT-TYPE
	SYNTAX		INTEGER {
		vOther                                  	(0),
		vUnknown                                	(1)
	}
	ACCESS		read-only
	STATUS		mandatory
	DESCRIPTION	"The major functional aspect of the productcausing the fault."
	::= {eEventGenerationForPhysicalContainer 6}

a116EventSubsystem OBJECT-TYPE
	SYNTAX		INTEGER {
		vOther                                  	(0),
		vUnknown                                	(1)
	}
	ACCESS		read-only
	STATUS		mandatory
	DESCRIPTION	"The minor functional aspect of the productcausing the fault."
	::= {eEventGenerationForPhysicalContainer 7}

a116IsInstanceDataPresent OBJECT-TYPE
	SYNTAX		INTEGER {
		vFalse                                  	(0),
		vTrue                                   	(1)
	}
	ACCESS		read-only
	STATUS		mandatory
	DESCRIPTION	"Indicates whether the second event block containsinstance-specif
c data."
	::= {eEventGenerationForPhysicalContainer 9}

a116EventMessage OBJECT-TYPE
	SYNTAX		DmiDisplaystring
	ACCESS		read-only
	STATUS		mandatory
	DESCRIPTION	"Auxillary information releated to the eventThis text contains
the name of the Probe"
	::= {eEventGenerationForPhysicalContainer 10}

SBusGlobalTable ::= SEQUENCE {
	a128BusId                               	DmiInteger,
	a128BusType                             	DmiInteger
}

tBusGlobalTable OBJECT-TYPE
	SYNTAX		SEQUENCE OF SBusGlobalTable
	ACCESS		not-accessible
	STATUS		mandatory
	DESCRIPTION	"This global table has one entry for each of the Busesin this
Component. The unique ID provided to each bus is the index into this table."
	::= {dmtfGroups 128}

eBusGlobalTable OBJECT-TYPE
	SYNTAX		SBusGlobalTable
	ACCESS		not-accessible
	STATUS		mandatory
	DESCRIPTION	""
	INDEX		{DmiComponentIndex, a128BusId}
	::= {tBusGlobalTable 1}

a128BusId OBJECT-TYPE
	SYNTAX		DmiInteger
	ACCESS		read-only
	STATUS		mandatory
	DESCRIPTION	"Unique index provided to each Bus in this Component and usedas
a key into the Bus Global Table."
	::= {eBusGlobalTable 1}

a128BusType OBJECT-TYPE
	SYNTAX		INTEGER {
		vOther                                  	(1),
		vUnknown                                	(2),
		vEisa                                   	(3),
		vIsa                                    	(4),
		vPci                                    	(5),
		vScsi                                   	(6),
		vIde                                    	(7),
		vDiagnostic                             	(8),
		vI2c                                    	(9),
		vPower                                  	(10)
	}
	ACCESS		read-only
	STATUS		mandatory
	DESCRIPTION	"The type of the bus being described by this entry in the
BusGlobal Table."
	::= {eBusGlobalTable 2}

SPhysicalExpansionSitesTable ::= SEQUENCE {
	a129ExpansionSiteIndex                  	DmiInteger,
	a129ExpansionSiteType                   	DmiInteger,
	a129VirtualExpansionSite                	DmiInteger,
	a129ExpansionSiteName                   	DmiDisplaystring,
	a129ExpansionSiteDescription            	DmiDisplaystring,
	a129ExpansionSiteCurrentlyOccupied      	DmiInteger
}

tPhysicalExpansionSitesTable OBJECT-TYPE
	SYNTAX		SEQUENCE OF SPhysicalExpansionSitesTable
	ACCESS		not-accessible
	STATUS		mandatory
	DESCRIPTION	"This global table describes all of the expansion sites in
this expandablecomponent in the system. The unique index of each expansion
site is the key into thistable. Card/Bus slots, disk bays, hot-plug power
supply bays, etc., are all examples of  expansion sites."
	::= {dmtfGroups 129}

ePhysicalExpansionSitesTable OBJECT-TYPE
	SYNTAX		SPhysicalExpansionSitesTable
	ACCESS		not-accessible
	STATUS		mandatory
	DESCRIPTION	""
	INDEX		{DmiComponentIndex, a129ExpansionSiteIndex}
	::= {tPhysicalExpansionSitesTable 1}

a129ExpansionSiteIndex OBJECT-TYPE
	SYNTAX		DmiInteger
	ACCESS		read-only
	STATUS		mandatory
	DESCRIPTION	"The unique integer index into Physical Expansion Sites table."
	::= {ePhysicalExpansionSitesTable 1}

a129ExpansionSiteType OBJECT-TYPE
	SYNTAX		INTEGER {
		vOther                                  	(1),
		vUnknown                                	(2),
		vBusSlot                                	(3),
		vDriveBay                               	(4),
		vPowerUnitBay                           	(5),
		vSubchassisSlot                         	(6),
		vPcmciaSlot                             	(7)
	}
	ACCESS		read-only
	STATUS		mandatory
	DESCRIPTION	"This attribute describes the type of expansion sitethat is
being defined by this entry in the Physical Expansion SitesTable."
	::= {ePhysicalExpansionSitesTable 2}

a129VirtualExpansionSite OBJECT-TYPE
	SYNTAX		INTEGER {
		vFalse                                  	(0),
		vTrue                                   	(1)
	}
	ACCESS		read-only
	STATUS		mandatory
	DESCRIPTION	"This attribute indicates whether this is a 'virtual'expansion
site or not. A virtual expansion site is one that ispermanently occupied
because of the level of integration ofan expandable component. An example
of a virtual expansion site isan I/O bus load taken up by a LAN controller
that is integrated onto amotherboard."
	::= {ePhysicalExpansionSitesTable 3}

a129ExpansionSiteName OBJECT-TYPE
	SYNTAX		DmiDisplaystring
	ACCESS		read-only
	STATUS		mandatory
	DESCRIPTION	"Name chosen by the vendor of this component toname this particul
r expansion site within this component, e.g. 'Slot 6', 'DriveBay 1'."
	::= {ePhysicalExpansionSitesTable 4}

a129ExpansionSiteDescription OBJECT-TYPE
	SYNTAX		DmiDisplaystring
	ACCESS		read-only
	STATUS		mandatory
	DESCRIPTION	"This is a vendor-settable string that describes theexpandable
site in whatever way is desired."
	::= {ePhysicalExpansionSitesTable 5}

a129ExpansionSiteCurrentlyOccupied OBJECT-TYPE
	SYNTAX		INTEGER {
		vFalse                                  	(0),
		vTrue                                   	(1)
	}
	ACCESS		read-only
	STATUS		mandatory
	DESCRIPTION	"A boolean whose value indicates whether thisExpansion Site
is currently occupied or not."
	::= {ePhysicalExpansionSitesTable 6}

SEventGenerationForCoolingDevice ::= SEQUENCE {
	a140EventType                           	DmiInteger,
	a140EventSeverity                       	DmiInteger,
	a140IsEventState-based	                 	DmiInteger,
	a140EventStateKey                       	DmiInteger,
	a140AssociatedGroup                     	DmiDisplaystring,
	a140EventSystem                         	DmiInteger,
	a140EventSubsystem                      	DmiInteger
}

tEventGenerationForCoolingDevice OBJECT-TYPE
	SYNTAX		SEQUENCE OF SEventGenerationForCoolingDevice
	ACCESS		not-accessible
	STATUS		mandatory
	DESCRIPTION	""
	::= {dmtfGroups 140}

eEventGenerationForCoolingDevice OBJECT-TYPE
	SYNTAX		SEventGenerationForCoolingDevice
	ACCESS		not-accessible
	STATUS		mandatory
	DESCRIPTION	""
	INDEX		{DmiComponentIndex, a140AssociatedGroup}
	::= {tEventGenerationForCoolingDevice 1}

a140EventType OBJECT-TYPE
	SYNTAX		INTEGER {
		vCoolingDeviceStatusChange              	(1),
		vTemperatureFault                       	(2)
	}
	ACCESS		read-only
	STATUS		mandatory
	DESCRIPTION	"The type of event that has occurred."
	::= {eEventGenerationForCoolingDevice 1}

a140EventSeverity OBJECT-TYPE
	SYNTAX		INTEGER {
		vMonitor                                	(1),
		vInformation                            	(2),
		vOk                                     	(4),
		vNon-critical                           	(8),
		vCritical                               	(16),
		vNon-recoverable                        	(32)
	}
	ACCESS		read-only
	STATUS		mandatory
	DESCRIPTION	"The severity of this event."
	::= {eEventGenerationForCoolingDevice 2}

a140IsEventState-based OBJECT-TYPE
	SYNTAX		INTEGER {
		vFalse                                  	(0),
		vTrue                                   	(1)
	}
	ACCESS		read-only
	STATUS		mandatory
	DESCRIPTION	"The value of this attributedetermines whether the Event being
reportedis a state-based Event or not. If the valueof this attribute is TRUE
then the Event isstate-based. Otherwise the Event is notstate-based."
	::= {eEventGenerationForCoolingDevice 3}

a140EventStateKey OBJECT-TYPE
	SYNTAX		DmiInteger
	ACCESS		read-only
	STATUS		mandatory
	DESCRIPTION	"A unique, single integer key into the EventState group if
this is a state-based Event.If this is not a state-based Event then thisthis
attribute's value is not defined."
	::= {eEventGenerationForCoolingDevice 4}

a140AssociatedGroup OBJECT-TYPE
	SYNTAX		DmiDisplaystring
	ACCESS		read-only
	STATUS		mandatory
	DESCRIPTION	"The class name of the group that is associatedwith the events
defined in this EventGeneration group."
	::= {eEventGenerationForCoolingDevice 5}

a140EventSystem OBJECT-TYPE
	SYNTAX		INTEGER {
		vOther                                  	(0),
		vUnknown                                	(1)
	}
	ACCESS		read-only
	STATUS		mandatory
	DESCRIPTION	"The major functional aspect of the productcausing the fault."
	::= {eEventGenerationForCoolingDevice 6}

a140EventSubsystem OBJECT-TYPE
	SYNTAX		INTEGER {
		vOther                                  	(0),
		vUnknown                                	(1)
	}
	ACCESS		read-only
	STATUS		mandatory
	DESCRIPTION	"The minor functional aspect of the productcausing the fault."
	::= {eEventGenerationForCoolingDevice 7}

SEventGenerationForPowerUnit ::= SEQUENCE {
	a201EventType                           	DmiInteger,
	a201EventSeverity                       	DmiInteger,
	a201IsEventState-based                  	DmiInteger,
	a201EventStateKey                       	DmiInteger,
	a201AssociatedGroup                     	DmiDisplaystring,
	a201EventSystem                         	DmiInteger,
	a201EventSubsystem                      	DmiInteger,
	a201IsInstanceDataPresent               	DmiInteger,
	a201EventMessage                        	DmiDisplaystring
}

tEventGenerationForPowerUnit OBJECT-TYPE
	SYNTAX		SEQUENCE OF SEventGenerationForPowerUnit
	ACCESS		not-accessible
	STATUS		mandatory
	DESCRIPTION	""
	::= {dmtfGroups 201}

eEventGenerationForPowerUnit OBJECT-TYPE
	SYNTAX		SEventGenerationForPowerUnit
	ACCESS		not-accessible
	STATUS		mandatory
	DESCRIPTION	""
	INDEX		{DmiComponentIndex, a201AssociatedGroup}
	::= {tEventGenerationForPowerUnit 1}

a201EventType OBJECT-TYPE
	SYNTAX		INTEGER {
		vPowerUnitRedundancyLost                	(1),
		vPowerUnitRedundancyRegained            	(2),
		vPowerUnitRedundancyDegraded            	(3),
		vPowerUnitVaShutdownConditionCleared    	(4),
		vPowerUnitVaShutdownLimitExceeded       	(5)
	}
	ACCESS		read-only
	STATUS		mandatory
	DESCRIPTION	"The type of event that has occurred."
	::= {eEventGenerationForPowerUnit 1}

a201EventSeverity OBJECT-TYPE
	SYNTAX		INTEGER {
		vMonitor                                	(1),
		vInformation                            	(2),
		vOk                                     	(4),
		vNon-critical                           	(8),
		vCritical                               	(16),
		vNon-recoverable                        	(32)
	}
	ACCESS		read-only
	STATUS		mandatory
	DESCRIPTION	"The severity of this event."
	::= {eEventGenerationForPowerUnit 2}

a201IsEventState-based OBJECT-TYPE
	SYNTAX		INTEGER {
		vFalse                                  	(0),
		vTrue                                   	(1)
	}
	ACCESS		read-only
	STATUS		mandatory
	DESCRIPTION	"The value of this attributedetermines whether the Event being
reportedis a state-based Event or not. If the valueof this attribute is TRUE
then the Event isstate-based. Otherwise the Event is notstate-based."
	::= {eEventGenerationForPowerUnit 3}

a201EventStateKey OBJECT-TYPE
	SYNTAX		DmiInteger
	ACCESS		read-only
	STATUS		mandatory
	DESCRIPTION	"A unique, single integer key into the EventState group if
this is a state-based Event.If this is not a state-based Event then thisthis
attribute's value is not defined."
	::= {eEventGenerationForPowerUnit 4}

a201AssociatedGroup OBJECT-TYPE
	SYNTAX		DmiDisplaystring
	ACCESS		read-only
	STATUS		mandatory
	DESCRIPTION	"The class name of the group that is associatedwith the events
defined in this EventGeneration group."
	::= {eEventGenerationForPowerUnit 5}

a201EventSystem OBJECT-TYPE
	SYNTAX		INTEGER {
		vOther                                  	(0),
		vUnknown                                	(1)
	}
	ACCESS		read-only
	STATUS		mandatory
	DESCRIPTION	"The major functional aspect of the productcausing the fault."
	::= {eEventGenerationForPowerUnit 6}

a201EventSubsystem OBJECT-TYPE
	SYNTAX		INTEGER {
		vOther                                  	(0),
		vUnknown                                	(1)
	}
	ACCESS		read-only
	STATUS		mandatory
	DESCRIPTION	"The minor functional aspect of the productcausing the fault."
	::= {eEventGenerationForPowerUnit 7}

a201IsInstanceDataPresent OBJECT-TYPE
	SYNTAX		INTEGER {
		vFalse                                  	(0),
		vTrue                                   	(1)
	}
	ACCESS		read-only
	STATUS		mandatory
	DESCRIPTION	"Indicates whether the second event block containsinstance-specif
c data."
	::= {eEventGenerationForPowerUnit 9}

a201EventMessage OBJECT-TYPE
	SYNTAX		DmiDisplaystring
	ACCESS		read-only
	STATUS		mandatory
	DESCRIPTION	"Auxillary information releated to the eventThis text contains
the name of the Probe"
	::= {eEventGenerationForPowerUnit 10}

SEventGenerationForCoolingSensors ::= SEQUENCE {
	a202EventType                           	DmiInteger,
	a202EventSeverity                       	DmiInteger,
	a202IsEventState-based                  	DmiInteger,
	a202EventStateKey                       	DmiInteger,
	a202AssociatedGroup                     	DmiDisplaystring,
	a202EventSystem                         	DmiInteger,
	a202EventSubsystem                      	DmiInteger,
	a202IsInstanceDataPresent               	DmiInteger,
	a202EventMessage                        	DmiDisplaystring
}

tEventGenerationForCoolingSensors OBJECT-TYPE
	SYNTAX		SEQUENCE OF SEventGenerationForCoolingSensors
	ACCESS		not-accessible
	STATUS		mandatory
	DESCRIPTION	""
	::= {dmtfGroups 202}

eEventGenerationForCoolingSensors OBJECT-TYPE
	SYNTAX		SEventGenerationForCoolingSensors
	ACCESS		not-accessible
	STATUS		mandatory
	DESCRIPTION	""
	INDEX		{DmiComponentIndex, a202AssociatedGroup}
	::= {tEventGenerationForCoolingSensors 1}

a202EventType OBJECT-TYPE
	SYNTAX		INTEGER {
		vCoolingDeviceFailure                   	(256),
		vCoolingDeviceOk                        	(257)
	}
	ACCESS		read-only
	STATUS		mandatory
	DESCRIPTION	"The type of event that has occurred."
	::= {eEventGenerationForCoolingSensors 1}

a202EventSeverity OBJECT-TYPE
	SYNTAX		INTEGER {
		vMonitor                                	(1),
		vInformation                            	(2),
		vOk                                     	(4),
		vNon-critical                           	(8),
		vCritical                               	(16),
		vNon-recoverable                        	(32)
	}
	ACCESS		read-only
	STATUS		mandatory
	DESCRIPTION	"The severity of this event."
	::= {eEventGenerationForCoolingSensors 2}

a202IsEventState-based OBJECT-TYPE
	SYNTAX		INTEGER {
		vFalse                                  	(0),
		vTrue                                   	(1)
	}
	ACCESS		read-only
	STATUS		mandatory
	DESCRIPTION	"The value of this attributedetermines whether the Event being
reportedis a state-based Event or not. If the valueof this attribute is TRUE
then the Event isstate-based. Otherwise the Event is notstate-based."
	::= {eEventGenerationForCoolingSensors 3}

a202EventStateKey OBJECT-TYPE
	SYNTAX		DmiInteger
	ACCESS		read-only
	STATUS		mandatory
	DESCRIPTION	"A unique, single integer key into the EventState group if
this is a state-based Event.If this is not a state-based Event then thisthis
attribute's value is not defined."
	::= {eEventGenerationForCoolingSensors 4}

a202AssociatedGroup OBJECT-TYPE
	SYNTAX		DmiDisplaystring
	ACCESS		read-only
	STATUS		mandatory
	DESCRIPTION	"The class name of the group that is associatedwith the events
defined in this EventGeneration group."
	::= {eEventGenerationForCoolingSensors 5}

a202EventSystem OBJECT-TYPE
	SYNTAX		INTEGER {
		vOther                                  	(0),
		vUnknown                                	(1)
	}
	ACCESS		read-only
	STATUS		mandatory
	DESCRIPTION	"The major functional aspect of the productcausing the fault."
	::= {eEventGenerationForCoolingSensors 6}

a202EventSubsystem OBJECT-TYPE
	SYNTAX		INTEGER {
		vOther                                  	(0),
		vUnknown                                	(1)
	}
	ACCESS		read-only
	STATUS		mandatory
	DESCRIPTION	"The minor functional aspect of the productcausing the fault."
	::= {eEventGenerationForCoolingSensors 7}

a202IsInstanceDataPresent OBJECT-TYPE
	SYNTAX		INTEGER {
		vFalse                                  	(0),
		vTrue                                   	(1)
	}
	ACCESS		read-only
	STATUS		mandatory
	DESCRIPTION	"Indicates whether the second event block containsinstance-specif
c data."
	::= {eEventGenerationForCoolingSensors 9}

a202EventMessage OBJECT-TYPE
	SYNTAX		DmiDisplaystring
	ACCESS		read-only
	STATUS		mandatory
	DESCRIPTION	"Auxillary information releated to the eventThis text contains
the name of the Probe"
	::= {eEventGenerationForCoolingSensors 10}

SMiftomib ::= SEQUENCE {
	a1001MibName                            	DmiDisplaystring,
	a1001MibOid                             	DmiDisplaystring,
	a1001DisableTrap                        	DmiInteger
}

tMiftomib OBJECT-TYPE
	SYNTAX		SEQUENCE OF SMiftomib
	ACCESS		not-accessible
	STATUS		mandatory
	DESCRIPTION	"This group defines attributes required for DMI to
SNMP translati
n."
	::= {dmtfGroups 1001}

eMiftomib OBJECT-TYPE
	SYNTAX		SMiftomib
	ACCESS		not-accessible
	STATUS		mandatory
	DESCRIPTION	""
	INDEX		{DmiComponentIndex}
	::= {tMiftomib 1}

a1001MibName OBJECT-TYPE
	SYNTAX		DmiDisplaystring
	ACCESS		read-only
	STATUS		mandatory
	DESCRIPTION	"The MIB name that defines this MIF"
	::= {eMiftomib 1}

a1001MibOid OBJECT-TYPE
	SYNTAX		DmiDisplaystring
	ACCESS		read-only
	STATUS		mandatory
	DESCRIPTION	"The MIB Object Identifier that corresponds to this MIF"
	::= {eMiftomib 2}

a1001DisableTrap OBJECT-TYPE
	SYNTAX		DmiInteger
	ACCESS		read-write
	STATUS		mandatory
	DESCRIPTION	"This attribute can be changed to disable sending oftraps
from this component"
	::= {eMiftomib 3}

SSystemControl ::= SEQUENCE {
	a1004Selfid                             	DmiInteger,
	a1004ResetSystem                        	DmiInteger,
	a1004TimedResetIncrement                	DmiInteger,
	a1004TimedResetResolution               	DmiInteger,
	a1004TimeUntilSystemReset               	DmiInteger,
	a1004SystemPowerCapabilities            	DmiInteger,
	a1004SystemPowerStatus                  	DmiInteger,
	a1004EventLoggingCapability             	DmiInteger,
	a1004WatchdogTimerIncrement             	DmiInteger,
	a1004WatchdogTimerResolution            	DmiInteger,
	a1004WatchdogUpdateInterval             	DmiInteger,
	a1004UseSystemWatchdogFeature           	DmiInteger,
	a1004ResetSystemAfterDelay              	DmiInteger,
	a1004SavePersistentData                 	DmiInteger,
	a1004RestoreFactoryDefaults             	DmiInteger,
	a1004ShutdownOs                         	DmiInteger,
	a1004ShutdownOsAndPowerOff              	DmiInteger,
	a1004ShutdownOsAndHardwareReset         	DmiInteger,
	a1004IssueAHardwareNmi                  	DmiInteger
}

tSystemControl OBJECT-TYPE
	SYNTAX		SEQUENCE OF SSystemControl
	ACCESS		not-accessible
	STATUS		mandatory
	DESCRIPTION	"Status and control of global system control features."
	::= {dmtfGroups 1004}

eSystemControl OBJECT-TYPE
	SYNTAX		SSystemControl
	ACCESS		not-accessible
	STATUS		mandatory
	DESCRIPTION	""
	INDEX		{DmiComponentIndex, a1004Selfid}
	::= {tSystemControl 1}

a1004Selfid OBJECT-TYPE
	SYNTAX		DmiInteger
	ACCESS		read-only
	STATUS		mandatory
	DESCRIPTION	"A unique number that identifies this row."
	::= {eSystemControl 1}

a1004ResetSystem OBJECT-TYPE
	SYNTAX		INTEGER {
		vDoNotReset                             	(0),
		vInitiateReset                          	(1),
		vUnsupported                            	(2)
	}
	ACCESS		read-write
	STATUS		mandatory
	DESCRIPTION	"Writing to the attribute initiates an immediate  
system
hard reset.  The value for this attribute 
is either Do Not Reset or Initiate
Reset."
	::= {eSystemControl 2}

a1004TimedResetIncrement OBJECT-TYPE
	SYNTAX		DmiInteger
	ACCESS		read-only
	STATUS		mandatory
	DESCRIPTION	"This attribute contains the increments in which a 
timed
reset can be set, in microseconds."
	::= {eSystemControl 3}

a1004TimedResetResolution OBJECT-TYPE
	SYNTAX		DmiInteger
	ACCESS		read-only
	STATUS		mandatory
	DESCRIPTION	"This attribute contains the resolution to which a   
Timed
Reset can be set, in microseconds.  For       
example, a resolution of 1
second and an increment  
of 10 seconds would indicate that a 10 second delay

interval setting produces a 9 to 10 second delay.   
"
	::= {eSystemControl 4}

a1004TimeUntilSystemReset OBJECT-TYPE
	SYNTAX		DmiInteger
	ACCESS		read-write
	STATUS		mandatory
	DESCRIPTION	"This attribute contains the interval for timed resets, 
in
units of the Timed Reset Increment attribute.       
Writing a non-zero value,
and setting the Timed Reset  
Enable on, initiates a timed reset countdown.
         
"
	::= {eSystemControl 5}

a1004SystemPowerCapabilities OBJECT-TYPE
	SYNTAX		INTEGER {
		vUnknown                                	(0),
		vUnsupported                            	(1),
		vOnAndOff                               	(2),
		vOffOnly                                	(3),
		vOnOnly                                 	(4)
	}
	ACCESS		read-only
	STATUS		mandatory
	DESCRIPTION	"This attribute describes the system power control 
capabilities.
 It can have one of the following   
values:  Unknown, On And Off, Off Only,
or On Only."
	::= {eSystemControl 6}

a1004SystemPowerStatus OBJECT-TYPE
	SYNTAX		INTEGER {
		vOff                                    	(0),
		vOn                                     	(1),
		vUnsupported                            	(2)
	}
	ACCESS		read-write
	STATUS		mandatory
	DESCRIPTION	"This attribute provides access to the status and 
control
of system power.  Its value is either On 
or Off."
	::= {eSystemControl 7}

a1004EventLoggingCapability OBJECT-TYPE
	SYNTAX		INTEGER {
		vUnknown                                	(0),
		vUnsupported                            	(1),
		vActive                                 	(2),
		vInactive                               	(3)
	}
	ACCESS		read-only
	STATUS		mandatory
	DESCRIPTION	"This attribute describes the Event Logging Capabilities.
The
attribute value can be : Unknown, Unsupported,
Active, or Inactive. If the
Event logging capability
is Active, the BIOS logs the system errors to the
FLASH.
The LSC reads this FLASH log and takes appropriate 
actions. If this
feature is Inactive, the LSC will read
the values from the system registers
directly.
The Event logging capability can be set to Active or 
Inactive
using the System Configuration Utility (SCU)."
	::= {eSystemControl 8}

a1004WatchdogTimerIncrement OBJECT-TYPE
	SYNTAX		DmiInteger
	ACCESS		read-only
	STATUS		mandatory
	DESCRIPTION	"This attribute contains the increments in which a
watchdog
update interval can be set. This value is
maintained internally by instrumentati
n code 
in microseconds.
In LSC Local Console, this value is shown in Seconds."
	::= {eSystemControl 9}

a1004WatchdogTimerResolution OBJECT-TYPE
	SYNTAX		DmiInteger
	ACCESS		read-only
	STATUS		mandatory
	DESCRIPTION	"Resolution to which a watchdog update interval can be 
set.
 For example, a watchdog timer resolution of 
R microsecond and an watchdog
timer increment of 
I microseconds would indicate that a watchdog update
interva
 setting of N will produce a (N*I)-R to (N*I)
microseconds delay.
In LSC
Local Console, this value is shown in Seconds."
	::= {eSystemControl 10}

a1004WatchdogUpdateInterval OBJECT-TYPE
	SYNTAX		DmiInteger
	ACCESS		read-write
	STATUS		mandatory
	DESCRIPTION	"This attribute specifies the Interval for watchdog 
resets,
in minutes.
If the system software does not update the watchdog
timer within
this interval, a hard reset will occur.
Selecting a non-zero value for this
attribute and 
setting the Use System Watchdog Feature attribute 
to 'On'
starts the watchdog reset timer countdown.
"
	::= {eSystemControl 11}

a1004UseSystemWatchdogFeature OBJECT-TYPE
	SYNTAX		INTEGER {
		vOff                                    	(0),
		vOn                                     	(1),
		vUnsupported                            	(2)
	}
	ACCESS		read-write
	STATUS		mandatory
	DESCRIPTION	"If this value is On, then the Watchdog feature is
enabled
and the Watchdog Update Interval value is valid.

If enabled this feature
automatically resets the server
if the LSC software does not reset the watchdog
timer
within the specified Watchdog Update Interval.
NOTE : This is a hard
reset that will immediately reset
the system without taking NetWare down.
This might 
result in some files being corrupted."
	::= {eSystemControl 12}

a1004ResetSystemAfterDelay OBJECT-TYPE
	SYNTAX		INTEGER {
		vOff                                    	(0),
		vOn                                     	(1),
		vUnsupported                            	(2)
	}
	ACCESS		read-write
	STATUS		mandatory
	DESCRIPTION	"This attribute controls whether or not the timed reset 
function
is enabled.  If the value is On, then the     
system will reset when the
Timed Reset Interval expires."
	::= {eSystemControl 13}

a1004SavePersistentData OBJECT-TYPE
	SYNTAX		INTEGER {
		vOff                                    	(0),
		vOn                                     	(1),
		vUnsupported                            	(2)
	}
	ACCESS		read-write
	STATUS		mandatory
	DESCRIPTION	"When this attribute value is set to ON all the persistent
data
like thresholds are stored into the persistent 
data Table.
"
	::= {eSystemControl 15}

a1004RestoreFactoryDefaults OBJECT-TYPE
	SYNTAX		INTEGER {
		vOff                                    	(0),
		vOn                                     	(1),
		vUnsupported                            	(2)
	}
	ACCESS		read-write
	STATUS		mandatory
	DESCRIPTION	"When this attribute value is set to ON all the Factory
default
thresholds are restored.
"
	::= {eSystemControl 16}

a1004ShutdownOs OBJECT-TYPE
	SYNTAX		INTEGER {
		vDoNotShutdown                          	(0),
		vShutdownOs                             	(1),
		vUnsupported                            	(2)
	}
	ACCESS		read-write
	STATUS		mandatory
	DESCRIPTION	"Writing to this attribute initiates an immediate
OS shutdown.
 The value of this attribute is    
either Do Not Shutdown or Shutdown OS."
	::= {eSystemControl 17}

a1004ShutdownOsAndPowerOff OBJECT-TYPE
	SYNTAX		INTEGER {
		vDoNotShutdownAndPowerOff               	(0),
		vShutdownAndPowerOff                    	(1),
		vUnsupported                            	(2)
	}
	ACCESS		read-write
	STATUS		mandatory
	DESCRIPTION	"Writing to this attribute initiates an immediate
OS shutdown
and Power Off of the system. The value of
this attribute is either Do Not
Shutdown and Power Off or 
Shutdown OS and Power Off."
	::= {eSystemControl 18}

a1004ShutdownOsAndHardwareReset OBJECT-TYPE
	SYNTAX		INTEGER {
		vDoNotShutdownAndHardwareReset          	(0),
		vShutdownAndHardwareReset               	(1),
		vUnsupported                            	(2)
	}
	ACCESS		read-write
	STATUS		mandatory
	DESCRIPTION	"Writing to this attribute initiates an immediate
OS shutdown.
 The value of this attribute is either 
Do Not Shutdown and Hardware Reset
or Shutdown OS and 
Hardware Reset."
	::= {eSystemControl 19}

a1004IssueAHardwareNmi OBJECT-TYPE
	SYNTAX		INTEGER {
		vDoNotIssueAnNmi                        	(0),
		vIssueAnNmi                             	(1),
		vUnsupported                            	(2)
	}
	ACCESS		read-write
	STATUS		mandatory
	DESCRIPTION	"Writing to this attribute causes a hardware NMI 
(Non Maskabale
Interrup). It will have one of the two values. 
Issue an NMI, or Do Not Issue
an NMI
"
	::= {eSystemControl 20}

SCoolingSensors ::= SEQUENCE {
	a1005Selfid                             	DmiInteger,
	a1005FruGroupIndex                      	DmiInteger,
	a1005OperationalGroupIndex              	DmiInteger,
	a1005CoolingDeviceType                  	DmiInteger,
	a1005CfmRating                          	DmiInteger,
	a1005FanUnits                           	DmiInteger,
	a1005MaximumReading                     	DmiInteger,
	a1005MinimumReading                     	DmiInteger,
	a1005CurrentReading                     	DmiInteger,
	a1005SensorAccuracy                     	DmiInteger,
	a1005SensorTolerancePlus                	DmiInteger,
	a1005SensorToleranceMinus               	DmiInteger,
	a1005Non-criticalThreshold              	DmiInteger,
	a1005CriticalThreshold                  	DmiInteger,
	a1005Non-recoverableThreshold           	DmiInteger,
	a1005CoolingSensorDescription           	DmiDisplaystring,
	a1005NominalReading                     	DmiInteger,
	a1005LowestNormalReading                	DmiInteger,
	a1005HighestNormalReading               	DmiInteger
}

tCoolingSensors OBJECT-TYPE
	SYNTAX		SEQUENCE OF SCoolingSensors
	ACCESS		not-accessible
	STATUS		mandatory
	DESCRIPTION	"This table contains one row for each cooling fan 
in the
system.  Each row contains the status and 
control information for a single
fan."
	::= {dmtfGroups 1005}

eCoolingSensors OBJECT-TYPE
	SYNTAX		SCoolingSensors
	ACCESS		not-accessible
	STATUS		mandatory
	DESCRIPTION	""
	INDEX		{DmiComponentIndex, a1005Selfid}
	::= {tCoolingSensors 1}

a1005Selfid OBJECT-TYPE
	SYNTAX		DmiInteger
	ACCESS		read-only
	STATUS		mandatory
	DESCRIPTION	"A unique number that identifies this row."
	::= {eCoolingSensors 1}

a1005FruGroupIndex OBJECT-TYPE
	SYNTAX		DmiInteger
	ACCESS		read-only
	STATUS		mandatory
	DESCRIPTION	"If this is a Field Replaceable Unit or if it is part of another
FRU, thisprovides an index into the FRU table; 'value = -1' indicates that
the group is not a FRU."
	::= {eCoolingSensors 2}

a1005OperationalGroupIndex OBJECT-TYPE
	SYNTAX		DmiInteger
	ACCESS		read-only
	STATUS		mandatory
	DESCRIPTION	"The index into the Operational State table for this device."
	::= {eCoolingSensors 3}

a1005CoolingDeviceType OBJECT-TYPE
	SYNTAX		INTEGER {
		vOther                                  	(1),
		vUnknown                                	(2),
		vFan                                    	(3),
		vCentrifugalBlower                      	(4),
		vChipFan                                	(5),
		vCabinetFan                             	(6),
		vPowerSupplyFan                         	(7),
		vHeatPipe                               	(8),
		vIntegratedRefrigeration                	(9),
		vActiveCooling                          	(32),
		vPassiveCooling                         	(33)
	}
	ACCESS		read-only
	STATUS		mandatory
	DESCRIPTION	"This attribute describes the fan type.  It has one 
of the
following values:  Muffin, Axial, Piezo, or 
Squirrel Cage."
	::= {eCoolingSensors 6}

a1005CfmRating OBJECT-TYPE
	SYNTAX		DmiInteger
	ACCESS		read-only
	STATUS		mandatory
	DESCRIPTION	"This attribute presents the maximum CFM rating of 
this fan."
	::= {eCoolingSensors 7}

a1005FanUnits OBJECT-TYPE
	SYNTAX		INTEGER {
		vRpm                                    	(0),
		vCfm                                    	(1),
		vOkfatal                                	(2)
	}
	ACCESS		read-only
	STATUS		mandatory
	DESCRIPTION	"This attribute describes the units of fan status   
measurement.
 It has one of the following values:  
RPM, CFM, or OK/Fatal."
	::= {eCoolingSensors 8}

a1005MaximumReading OBJECT-TYPE
	SYNTAX		DmiInteger
	ACCESS		read-only
	STATUS		mandatory
	DESCRIPTION	"This attribute contains the highest reading supported 
on
this fan's sensor, measured in the units specified 
by the Fan Units attribute.
 This attribute may not   
apply to all fan types."
	::= {eCoolingSensors 9}

a1005MinimumReading OBJECT-TYPE
	SYNTAX		DmiInteger
	ACCESS		read-only
	STATUS		mandatory
	DESCRIPTION	"This attribute contains the lowest reading supported  
on
this fan's sensor, measured in the units specified 
Fan Units attribute.
 This attribute may not apply to 
all fan types."
	::= {eCoolingSensors 10}

a1005CurrentReading OBJECT-TYPE
	SYNTAX		DmiInteger
	ACCESS		read-only
	STATUS		mandatory
	DESCRIPTION	"This attribute contains the current fan sensor  
reading,
measured in the units specified by the 
Fan Units attribute.  This attribute
will display as    
Unsupported if the hardware does not support this 
feature.
"
	::= {eCoolingSensors 11}

a1005SensorAccuracy OBJECT-TYPE
	SYNTAX		DmiInteger
	ACCESS		read-write
	STATUS		mandatory
	DESCRIPTION	"This attribute describes the sensor's accuracy in 
+/- hundredth
 of a percent."
	::= {eCoolingSensors 13}

a1005SensorTolerancePlus OBJECT-TYPE
	SYNTAX		DmiInteger
	ACCESS		read-write
	STATUS		mandatory
	DESCRIPTION	"This attribute describes the sensor's '+' tolerance 
in the
units specified by the Fan Units attribute."
	::= {eCoolingSensors 14}

a1005SensorToleranceMinus OBJECT-TYPE
	SYNTAX		DmiInteger
	ACCESS		read-write
	STATUS		mandatory
	DESCRIPTION	"This attribute describes the sensor's '-' tolerance 
in the
units specified by the Fan Units attribute."
	::= {eCoolingSensors 15}

a1005Non-criticalThreshold OBJECT-TYPE
	SYNTAX		DmiInteger
	ACCESS		read-write
	STATUS		mandatory
	DESCRIPTION	"This attribute contains the warning threshold level 
for
the fan.  The threshold is given in the units   
specified by the Fan Units
attribute."
	::= {eCoolingSensors 16}

a1005CriticalThreshold OBJECT-TYPE
	SYNTAX		DmiInteger
	ACCESS		read-write
	STATUS		mandatory
	DESCRIPTION	"This attribute contains the major error threshold 
level
for the fan.  The threshold is given in the 
units specified by the Fan Units
attribute."
	::= {eCoolingSensors 17}

a1005Non-recoverableThreshold OBJECT-TYPE
	SYNTAX		DmiInteger
	ACCESS		read-write
	STATUS		mandatory
	DESCRIPTION	"This attribute contains the fatal error threshold 
level
for the fan.  The threshold is given in the 
units specified by the Fan Units
attribute."
	::= {eCoolingSensors 18}

a1005CoolingSensorDescription OBJECT-TYPE
	SYNTAX		DmiDisplaystring
	ACCESS		read-only
	STATUS		mandatory
	DESCRIPTION	"Additional descriptive information about the Cooling sensor
orsensor's location."
	::= {eCoolingSensors 19}

a1005NominalReading OBJECT-TYPE
	SYNTAX		DmiInteger
	ACCESS		read-only
	STATUS		mandatory
	DESCRIPTION	"Nominal reading for this fan, in units. 80000000h  
indicates
that this attribute is not supported."
	::= {eCoolingSensors 21}

a1005LowestNormalReading OBJECT-TYPE
	SYNTAX		DmiInteger
	ACCESS		read-only
	STATUS		mandatory
	DESCRIPTION	"Specified lowest normal reading for this fan, in   
units.
Readings beyond this value indicate an      
abnormal condition. 80000000h
indicates that this  
attribute is not supported."
	::= {eCoolingSensors 22}

a1005HighestNormalReading OBJECT-TYPE
	SYNTAX		DmiInteger
	ACCESS		read-only
	STATUS		mandatory
	DESCRIPTION	"Specified lowest normal reading for this fan, in   
units.
Readings beyond this value indicate an      
abnormal condition. 80000000h
indicates that this  
attribute is not supported."
	::= {eCoolingSensors 23}

SSystemEventLog ::= SEQUENCE {
	a1006Selfid                             	DmiInteger,
	a1006Timestamp                          	DmiDateX,
	a1006RecordType                         	DmiInteger,
	a1006RecordLength                       	DmiInteger,
	a1006RecordData                         	DmiOctetstring
}

tSystemEventLog OBJECT-TYPE
	SYNTAX		SEQUENCE OF SSystemEventLog
	ACCESS		not-accessible
	STATUS		mandatory
	DESCRIPTION	"This group provides raw access to System Event Log (SEL)
recordsThis data is intended for use by a Service & Support person"
	::= {dmtfGroups 1006}

eSystemEventLog OBJECT-TYPE
	SYNTAX		SSystemEventLog
	ACCESS		not-accessible
	STATUS		mandatory
	DESCRIPTION	""
	INDEX		{DmiComponentIndex, a1006Selfid}
	::= {tSystemEventLog 1}

a1006Selfid OBJECT-TYPE
	SYNTAX		DmiInteger
	ACCESS		read-only
	STATUS		mandatory
	DESCRIPTION	"A unique number that identifies this row."
	::= {eSystemEventLog 1}

a1006Timestamp OBJECT-TYPE
	SYNTAX		DmiDateX
	ACCESS		read-only
	STATUS		mandatory
	DESCRIPTION	"The time and date when this record was written."
	::= {eSystemEventLog 2}

a1006RecordType OBJECT-TYPE
	SYNTAX		DmiInteger
	ACCESS		read-only
	STATUS		mandatory
	DESCRIPTION	"Type of this record."
	::= {eSystemEventLog 3}

a1006RecordLength OBJECT-TYPE
	SYNTAX		DmiInteger
	ACCESS		read-only
	STATUS		mandatory
	DESCRIPTION	"Length of this record."
	::= {eSystemEventLog 4}

a1006RecordData OBJECT-TYPE
	SYNTAX		DmiOctetstring
	ACCESS		read-only
	STATUS		mandatory
	DESCRIPTION	"Binary Data associated with this record"
	::= {eSystemEventLog 5}

--
-- Trap definitions - not generated by MIFTOMIB tool
--

trap1ForProcessor TRAP-TYPE
    ENTERPRISE eEventGenerationForProcessor
    VARIABLES  {
	a100EventType,
	a100EventSeverity,
	a100IsEventState-based,
	a100EventStateKey,
	a100AssociatedGroup,
	a100EventSystem,
	a100EventSubsystem,
	a100IsInstanceDataPresent,
	a100EventMessage,
	a6ProcessorIndex
       }

    DESCRIPTION "Processor Internal Error"

    ::= 256

trap2ForProcessor TRAP-TYPE
    ENTERPRISE eEventGenerationForProcessor
    VARIABLES  {
	a100EventType,
	a100EventSeverity,
	a100IsEventState-based,
	a100EventStateKey,
	a100AssociatedGroup,
	a100EventSystem,
	a100EventSubsystem,
	a100IsInstanceDataPresent,
	a100EventMessage,
	a6ProcessorIndex
       }

    DESCRIPTION "Processor Thermal Trip"

    ::= 257

trap3ForProcessor TRAP-TYPE
    ENTERPRISE eEventGenerationForProcessor
    VARIABLES  {
	a100EventType,
	a100EventSeverity,
	a100IsEventState-based,
	a100EventStateKey,
	a100AssociatedGroup,
	a100EventSystem,
	a100EventSubsystem,
	a100IsInstanceDataPresent,
	a100EventMessage,
	a6ProcessorIndex
       }

    DESCRIPTION "Processor FRB-3 Failure"

    ::= 258

trap1ForPowerSupply TRAP-TYPE
    ENTERPRISE eEventGenerationForPowerSupply
    VARIABLES  {
	a104EventType,
	a104EventSeverity,
	a104IsEventState-based,
	a104EventStateKey,
	a104AssociatedGroup,
	a104EventSystem,
	a104EventSubsystem,
	a104IsInstanceDataPresent,
	a17PowerSupplyIndex
       }

    DESCRIPTION "Power Supply Failed"

    ::= 256

trap2ForPowerSupply TRAP-TYPE
    ENTERPRISE eEventGenerationForPowerSupply
    VARIABLES  {
	a104EventType,
	a104EventSeverity,
	a104IsEventState-based,
	a104EventStateKey,
	a104AssociatedGroup,
	a104EventSystem,
	a104EventSubsystem,
	a104IsInstanceDataPresent,
	a17PowerSupplyIndex
       }

    DESCRIPTION "Power Supply OK"

    ::= 257

trap3ForPowerSupply TRAP-TYPE
    ENTERPRISE eEventGenerationForPowerSupply
    VARIABLES  {
	a104EventType,
	a104EventSeverity,
	a104IsEventState-based,
	a104EventStateKey,
	a104AssociatedGroup,
	a104EventSystem,
	a104EventSubsystem,
	a104IsInstanceDataPresent,
	a17PowerSupplyIndex
       }

    DESCRIPTION "Power Supply Likely To Fail"

    ::= 258

trap1ForPhysicalMemory TRAP-TYPE
    ENTERPRISE eEventGenerationForPhysicalMemory
    VARIABLES  {
	a108EventType,
	a108EventSeverity,
	a108IsEventState-based,
	a108EventStateKey,
	a108AssociatedGroup,
	a108EventSystem,
	a108EventSubsystem,
	a108IsInstanceDataPresent,
	a34MemoryArrayTableIndex
       }

    DESCRIPTION "Single BIT ECC Error"

    ::= 256

trap2ForPhysicalMemory TRAP-TYPE
    ENTERPRISE eEventGenerationForPhysicalMemory
    VARIABLES  {
	a108EventType,
	a108EventSeverity,
	a108IsEventState-based,
	a108EventStateKey,
	a108AssociatedGroup,
	a108EventSystem,
	a108EventSubsystem,
	a108IsInstanceDataPresent,
	a34MemoryArrayTableIndex
       }

    DESCRIPTION "Multi BIT ECC Error from previous boot"

    ::= 257


trap1ForVoltageProbe TRAP-TYPE
    ENTERPRISE eEventGenerationForVoltageProbe
    VARIABLES  {
	a113EventType,
	a113EventSeverity,
	a113IsEventState-based,
	a113EventStateKey,
	a113AssociatedGroup,
	a113EventSystem,
	a113EventSubsystem,
	a113IsInstanceDataPresent,
	a54VoltageProbeIndex
       }

    DESCRIPTION "Status Changed to OK"

    ::= 256

trap2ForVoltageProbe TRAP-TYPE
    ENTERPRISE eEventGenerationForVoltageProbe
    VARIABLES  {
	a113EventType,
	a113EventSeverity,
	a113IsEventState-based,
	a113EventStateKey,
	a113AssociatedGroup,
	a113EventSystem,
	a113EventSubsystem,
	a113IsInstanceDataPresent,
	a54VoltageProbeIndex
       }

    DESCRIPTION "Status Changed to Upper Critical"

    ::= 257

trap3ForVoltageProbe TRAP-TYPE
    ENTERPRISE eEventGenerationForVoltageProbe
    VARIABLES  {
	a113EventType,
	a113EventSeverity,
	a113IsEventState-based,
	a113EventStateKey,
	a113AssociatedGroup,
	a113EventSystem,
	a113EventSubsystem,
	a113IsInstanceDataPresent,
	a54VoltageProbeIndex
       }

    DESCRIPTION "Status Changed to Lower Critical"

    ::= 258

trap4ForVoltageProbe TRAP-TYPE
    ENTERPRISE eEventGenerationForVoltageProbe
    VARIABLES  {
	a113EventType,
	a113EventSeverity,
	a113IsEventState-based,
	a113EventStateKey,
	a113AssociatedGroup,
	a113EventSystem,
	a113EventSubsystem,
	a113IsInstanceDataPresent,
	a54VoltageProbeIndex
       }

    DESCRIPTION "Status Changed to from OK to Upper Non Critical"

    ::= 259

trap5ForVoltageProbe TRAP-TYPE
    ENTERPRISE eEventGenerationForVoltageProbe
    VARIABLES  {
	a113EventType,
	a113EventSeverity,
	a113IsEventState-based,
	a113EventStateKey,
	a113AssociatedGroup,
	a113EventSystem,
	a113EventSubsystem,
	a113IsInstanceDataPresent,
	a54VoltageProbeIndex
       }

    DESCRIPTION "Status Changed to from OK to Lower Non Critical"

    ::= 260

trap6ForVoltageProbe TRAP-TYPE
    ENTERPRISE eEventGenerationForVoltageProbe
    VARIABLES  {
	a113EventType,
	a113EventSeverity,
	a113IsEventState-based,
	a113EventStateKey,
	a113AssociatedGroup,
	a113EventSystem,
	a113EventSubsystem,
	a113IsInstanceDataPresent,
	a54VoltageProbeIndex
       }

    DESCRIPTION "Status Changed to from Upper Critical to Upper Non Critical"

    ::= 261

trap7ForVoltageProbe TRAP-TYPE
    ENTERPRISE eEventGenerationForVoltageProbe
    VARIABLES  {
	a113EventType,
	a113EventSeverity,
	a113IsEventState-based,
	a113EventStateKey,
	a113AssociatedGroup,
	a113EventSystem,
	a113EventSubsystem,
	a113IsInstanceDataPresent,
	a54VoltageProbeIndex
       }

    DESCRIPTION "Status Changed to from Lower Critical to Lower Non Critical"

    ::= 262


trap1ForTemperatureProbe TRAP-TYPE
    ENTERPRISE eEventGenerationForTemperatureProbe
    VARIABLES  {
	a114EventType,
	a114EventSeverity,
	a114IsEventState-based,
	a114EventStateKey,
	a114AssociatedGroup,
	a114EventSystem,
	a114EventSubsystem,
	a114IsInstanceDataPresent,
	a55TemperatureProbeTableIndex
       }

    DESCRIPTION "Status Changed to OK"

    ::= 256

trap2ForTemperatureProbe TRAP-TYPE
    ENTERPRISE eEventGenerationForTemperatureProbe
    VARIABLES  {
	a114EventType,
	a114EventSeverity,
	a114IsEventState-based,
	a114EventStateKey,
	a114AssociatedGroup,
	a114EventSystem,
	a114EventSubsystem,
	a114IsInstanceDataPresent,
	a55TemperatureProbeTableIndex
       }

    DESCRIPTION "Status Changed to Upper Critical"

    ::= 257

trap3ForTemperatureProbe TRAP-TYPE
    ENTERPRISE eEventGenerationForTemperatureProbe
    VARIABLES  {
	a114EventType,
	a114EventSeverity,
	a114IsEventState-based,
	a114EventStateKey,
	a114AssociatedGroup,
	a114EventSystem,
	a114EventSubsystem,
	a114IsInstanceDataPresent,
	a55TemperatureProbeTableIndex
       }

    DESCRIPTION "Status Changed to Lower Critical"

    ::= 258

trap4ForTemperatureProbe TRAP-TYPE
    ENTERPRISE eEventGenerationForTemperatureProbe
    VARIABLES  {
	a114EventType,
	a114EventSeverity,
	a114IsEventState-based,
	a114EventStateKey,
	a114AssociatedGroup,
	a114EventSystem,
	a114EventSubsystem,
	a114IsInstanceDataPresent,
	a55TemperatureProbeTableIndex
       }

    DESCRIPTION "Status Changed to from OK to Upper Non Critical"

    ::= 259

trap5ForTemperatureProbe TRAP-TYPE
    ENTERPRISE eEventGenerationForTemperatureProbe
    VARIABLES  {
	a114EventType,
	a114EventSeverity,
	a114IsEventState-based,
	a114EventStateKey,
	a114AssociatedGroup,
	a114EventSystem,
	a114EventSubsystem,
	a114IsInstanceDataPresent,
	a55TemperatureProbeTableIndex
       }

    DESCRIPTION "Status Changed to from OK to Lower Non Critical"

    ::= 260

trap6ForTemperatureProbe TRAP-TYPE
    ENTERPRISE eEventGenerationForTemperatureProbe
    VARIABLES  {
	a114EventType,
	a114EventSeverity,
	a114IsEventState-based,
	a114EventStateKey,
	a114AssociatedGroup,
	a114EventSystem,
	a114EventSubsystem,
	a114IsInstanceDataPresent,
	a55TemperatureProbeTableIndex
       }

    DESCRIPTION "Status Changed to from Upper Critical to Upper Non Critical"

    ::= 261

trap7ForTemperatureProbe TRAP-TYPE
    ENTERPRISE eEventGenerationForTemperatureProbe
    VARIABLES  {
	a114EventType,
	a114EventSeverity,
	a114IsEventState-based,
	a114EventStateKey,
	a114AssociatedGroup,
	a114EventSystem,
	a114EventSubsystem,
	a114IsInstanceDataPresent,
	a55TemperatureProbeTableIndex
       }

    DESCRIPTION "Status Changed to from Lower Critical to Lower Non Critical"

    ::= 262

trap1ForPhysicalContainer TRAP-TYPE
    ENTERPRISE eEventGenerationForPhysicalContainer
    VARIABLES  {
	a116EventType,
	a116EventSeverity,
	a116IsEventState-based,
	a116EventStateKey,
	a116AssociatedGroup,
	a116EventSystem,
	a116EventSubsystem,
	a116IsInstanceDataPresent,
	a64ContainerIndex
       }

    DESCRIPTION "Container Security Breached"

    ::= 6

trap2ForPhysicalContainer TRAP-TYPE
    ENTERPRISE eEventGenerationForPhysicalContainer
    VARIABLES  {
	a116EventType,
	a116EventSeverity,
	a116IsEventState-based,
	a116EventStateKey,
	a116AssociatedGroup,
	a116EventSystem,
	a116EventSubsystem,
	a116IsInstanceDataPresent,
	a64ContainerIndex
       }

    DESCRIPTION "Container Secured"

    ::= 256

trap1ForPowerUnit TRAP-TYPE
    ENTERPRISE eEventGenerationForPowerUnit
    VARIABLES  {
	a201EventType,
	a201EventSeverity,
	a201IsEventState-based,
	a201EventStateKey,
	a201AssociatedGroup,
	a201EventSystem,
	a201EventSubsystem,
	a201IsInstanceDataPresent,
	a67PowerUnitIndex
       }

    DESCRIPTION "Power Unit Redundancy Lost"

    ::= 1

trap2ForPowerUnit TRAP-TYPE
    ENTERPRISE eEventGenerationForPowerUnit
    VARIABLES  {
	a201EventType,
	a201EventSeverity,
	a201IsEventState-based,
	a201EventStateKey,
	a201AssociatedGroup,
	a201EventSystem,
	a201EventSubsystem,
	a201IsInstanceDataPresent,
	a67PowerUnitIndex
       }

    DESCRIPTION "Power Unit Redundancy Regained"

    ::= 2

trap3ForPowerUnit TRAP-TYPE
    ENTERPRISE eEventGenerationForPowerUnit
    VARIABLES  {
	a201EventType,
	a201EventSeverity,
	a201IsEventState-based,
	a201EventStateKey,
	a201AssociatedGroup,
	a201EventSystem,
	a201EventSubsystem,
	a201IsInstanceDataPresent,
	a67PowerUnitIndex
       }

    DESCRIPTION "Power Unit Redundancy Degraded"

    ::= 3

trap4ForPowerUnit TRAP-TYPE
    ENTERPRISE eEventGenerationForPowerUnit
    VARIABLES  {
	a201EventType,
	a201EventSeverity,
	a201IsEventState-based,
	a201EventStateKey,
	a201AssociatedGroup,
	a201EventSystem,
	a201EventSubsystem,
	a201IsInstanceDataPresent,
	a67PowerUnitIndex
       }

    DESCRIPTION "Power Unit VA Shutdown Condition Cleared"

    ::= 4

trap5ForPowerUnit TRAP-TYPE
    ENTERPRISE eEventGenerationForPowerUnit
    VARIABLES  {
	a201EventType,
	a201EventSeverity,
	a201IsEventState-based,
	a201EventStateKey,
	a201AssociatedGroup,
	a201EventSystem,
	a201EventSubsystem,
	a201IsInstanceDataPresent,
	a67PowerUnitIndex
       }

    DESCRIPTION "Power Unit VA Shutdown Limit Exceeded"

    ::= 5

trap1ForCoolingSensors TRAP-TYPE
    ENTERPRISE eEventGenerationForCoolingSensors
    VARIABLES  {
	a202EventType,
	a202EventSeverity,
	a202IsEventState-based,
	a202EventStateKey,
	a202AssociatedGroup,
	a202EventSystem,
	a202EventSubsystem,
	a202IsInstanceDataPresent,
	a1005Selfid
       }

    DESCRIPTION "Cooling Device Failure"

    ::= 256

trap2ForCoolingSensors TRAP-TYPE
    ENTERPRISE eEventGenerationForCoolingSensors
    VARIABLES  {
	a202EventType,
	a202EventSeverity,
	a202IsEventState-based,
	a202EventStateKey,
	a202AssociatedGroup,
	a202EventSystem,
	a202EventSubsystem,
	a202IsInstanceDataPresent,
	a1005Selfid
       }

    DESCRIPTION "Cooling Device OK"

    ::= 257

END
