-- SCCS version: "@(#)att_fr.mib	4.1.2.2"

--
--		Copyright 1992 AT&T
--		All Rights Reserved
--
--	NOTICE
--	------
--	The information in this document is subject to change
--	without notice. AT&T assumes no responsibility for
--	any errors that may appear in this document.
--
--	Notwithstanding any other lease or license agreement
--	that may pertain to, or accompany the delivery of,
--	this computer software, the rights of the Government
--	regarding its use, reproduction and disclosure are as
--	set forth in Government contract no. GS00K89AGS6495.
--

--
-- Title: AT&T Frame Relay MIB for Customer Network Management
--	


	ATT-CNM-FRAME-RELAY-MIB DEFINITIONS ::= BEGIN

	IMPORTS
		enterprises, Gauge
			FROM RFC1155-SMI
		DisplayString
			FROM RFC1213-MIB
		OBJECT-TYPE
			FROM RFC-1212;

	--
	-- Object Identifiers
	--

	att-2		OBJECT IDENTIFIER ::= { enterprises 74 }
	att-products	OBJECT IDENTIFIER ::= { att-2 1 }
	att-mgmt	OBJECT IDENTIFIER ::= { att-2 2 }
	att-cnmAgent	OBJECT IDENTIFIER ::= { att-products 9 }
	att-cnm		OBJECT IDENTIFIER ::= { att-mgmt 15 }
	att-cnm-fr	OBJECT IDENTIFIER ::= { att-cnm 7 }


	--
	-- the Frame Relay group of objects (att-cnm-fr) include:
	--
        --	the Frame Relay Configuration table
	--	the Frame Relay Measurements table
	--	the Frame Relay PVC-level Measurements table
	--	the Frame Relay PVC-level Status table
	--


        -- the Frame Relay Configuration table

        --
        -- This table provides configuration information
        -- the Frame Relay interfaces supported by this system.
        --

        attCNMfrConfigTable OBJECT-TYPE
                SYNTAX  SEQUENCE OF AttCNMfrConfigEntry
                ACCESS  not-accessible
                STATUS  mandatory
                DESCRIPTION
                        "A list of entries containing configuration
                        information for all Frame Relay interfaces managed by
                        this system."
                ::= { att-cnm-fr 1 }

        attCNMfrConfigEntry OBJECT-TYPE
                SYNTAX  AttCNMfrConfigEntry
                ACCESS  not-accessible
                STATUS  mandatory
                DESCRIPTION
                        "An entry containing configuration information
                        for a particular Frame Relay interface."
                INDEX   { attCNMfrConfigIndex }
                ::= { attCNMfrConfigTable 1 }

        AttCNMfrConfigEntry ::=
                SEQUENCE {
                    attCNMfrConfigIndex
                        INTEGER,
                    attCNMfrMeasMaxIntervals
                        INTEGER,
                    attCNMfrMeasIntervalLen
                        INTEGER,
                    attCNMfrPVCMeasMaxIntervals
                        INTEGER,
                    attCNMfrPVCMeasIntervalLen
                        INTEGER
                }

        attCNMfrConfigIndex OBJECT-TYPE
                SYNTAX  INTEGER
                ACCESS  read-only
                STATUS  mandatory
                DESCRIPTION
                        "A unique value for each Frame Relay interface.
			The interface identified by a particular value of
			this index is the same interface as identified by
			the same value of an attCNMifConfigIndex object
			instance."
                ::= { attCNMfrConfigEntry 1 }

        attCNMfrMeasMaxIntervals OBJECT-TYPE
                SYNTAX  INTEGER
                ACCESS  read-only
                STATUS  mandatory
                DESCRIPTION
                        "This variable identifies the maximum number
			of measurement intervals supported for the
			measurements maintained by this Frame Relay
			interface in the attCNMfrMeasTable."
                ::= { attCNMfrConfigEntry 2 }

        attCNMfrMeasIntervalLen OBJECT-TYPE
                SYNTAX  INTEGER
                ACCESS  read-only
                STATUS  mandatory
                DESCRIPTION
                        "This variable identifies the number of seconds
			that make up one complete measurement interval for
                        for the measurements maintained by this Frame Relay
                        interface in the attCNMfrMeasTable."
                ::= { attCNMfrConfigEntry 3 }

        attCNMfrPVCMeasMaxIntervals OBJECT-TYPE
                SYNTAX  INTEGER
                ACCESS  read-only
                STATUS  mandatory
                DESCRIPTION
                        "This variable identifies the maximum number
			of measurement intervals supported for the
			measurements maintained by this Frame Relay
			interface in the attCNMfrPVCMeasTable."
                ::= { attCNMfrConfigEntry 4 }

        attCNMfrPVCMeasIntervalLen OBJECT-TYPE
                SYNTAX  INTEGER
                ACCESS  read-only
                STATUS  mandatory
                DESCRIPTION
                        "This variable identifies the number of seconds
			that make up one complete measurement interval for
                        for the measurements maintained by this Frame Relay
                        interface in the attCNMfrPVCMeasTable."
                ::= { attCNMfrConfigEntry 5 }


	-- the Frame Relay Measurements table

	--
	-- This table provides counts on the various measurement
	-- counts maintained by a Frame Relay interface during
	-- the specified measurement interval.
	--

	attCNMfrMeasTable OBJECT-TYPE
		SYNTAX	SEQUENCE OF AttCNMfrMeasEntry
		ACCESS  not-accessible
		STATUS  mandatory
		DESCRIPTION
			"A list of entries containing measurement counts,
			maintained during the specified measurement interval,
			for all Frame Relay interfaces managed by this
			system."
		::= { att-cnm-fr 2 }

	attCNMfrMeasEntry OBJECT-TYPE
		SYNTAX  AttCNMfrMeasEntry
		ACCESS  not-accessible
		STATUS  mandatory
		DESCRIPTION
			"An entry containing measurement counts, maintained
			during the specified measurement interval, for a
			particular Frame Relay interface."
		INDEX	{ attCNMfrMeasIndex,
			    attCNMfrMeasInterval }
		::= { attCNMfrMeasTable 1 }

	AttCNMfrMeasEntry ::=
		SEQUENCE {
		    attCNMfrMeasIndex
			INTEGER,
		    attCNMfrMeasInterval
			INTEGER,
		    attCNMfrMeasTimeStamp
			INTEGER,
		    attCNMfrMeasLocalTime
			DisplayString,
		    attCNMfrReceivedOctets
			Gauge,
		    attCNMfrSentOctets
			Gauge,
		    attCNMfrReceivedFrames
			Gauge,
		    attCNMfrSentFrames
			Gauge,
		    attCNMfrBadFrames
			Gauge,
		    attCNMfrReceiverOverruns
			Gauge
		}

	attCNMfrMeasIndex OBJECT-TYPE
		SYNTAX	INTEGER
		ACCESS	read-only
		STATUS	mandatory
		DESCRIPTION
			"A unique value for each Frame Relay interface.
			The interface identified by a particular value of
			this index is the same interface as identified by
			the same value of an attCNMifConfigIndex object
			instance."
		::= { attCNMfrMeasEntry 1 }

	attCNMfrMeasInterval OBJECT-TYPE
		SYNTAX  INTEGER
		ACCESS  read-only
		STATUS  mandatory
		DESCRIPTION
			"This variable identifies the measurement interval
			number for which measurement is provided. It is a
			number between 1 and XX, where 1 identifies the most
			recently completed measurement interval and XX is
			the least recently completed measurement interval.

                        The value of XX is specified by the
                        attCNMfrMeasMaxIntervals object given in the
                        attCNMfrConfigTable.

                        The maximum length of each measurement interval is
                        specified by the attCNMfrMeasIntervalLen object given
                        in the attCNMfrConfigTable."
		::= { attCNMfrMeasEntry 2 }

	attCNMfrMeasTimeStamp OBJECT-TYPE
		SYNTAX  INTEGER
		ACCESS  read-only
		STATUS  mandatory
		DESCRIPTION
			"The time stamp corresponding to the end of the
			specified measurement interval, as measured in
			seconds from 00:00:00 UTC (Coordinated Universal
			Time) January 1, 1970. Any fraction is rounded up."
		::= { attCNMfrMeasEntry 3 }

	attCNMfrMeasLocalTime OBJECT-TYPE
		SYNTAX  DisplayString(SIZE(0..255))
		ACCESS  read-only
		STATUS  mandatory
		DESCRIPTION
			"The time stamp corresponding to the end of the
			specified measurement interval.  Any fraction is
			rounded up. It is given as a printable ASCII string
			showing the local time at the end of the interval."
		::= { attCNMfrMeasEntry 4 }

	attCNMfrReceivedOctets OBJECT-TYPE
		SYNTAX	Gauge
		ACCESS	read-only
		STATUS	mandatory
		DESCRIPTION
			"The counter associated with the number of bytes
			received by this Frame Relay interface during the
			specified measurement interval."
		::= { attCNMfrMeasEntry 5 }

	attCNMfrSentOctets OBJECT-TYPE
		SYNTAX	Gauge
		ACCESS	read-only
		STATUS	mandatory
		DESCRIPTION
			"The counter associated with the number of bytes
			sent by this Frame Relay interface during the
			specified measurement interval."
		::= { attCNMfrMeasEntry 6 }

	attCNMfrReceivedFrames OBJECT-TYPE
		SYNTAX	Gauge
		ACCESS	read-only
		STATUS	mandatory
		DESCRIPTION
			"The counter associated with the number of frames
			received by this Frame Relay interface during the
			specified measurement interval."
		::= { attCNMfrMeasEntry 7 }

	attCNMfrSentFrames OBJECT-TYPE
		SYNTAX	Gauge
		ACCESS	read-only
		STATUS	mandatory
		DESCRIPTION
			"The counter associated with the number of frames
			received by this Frame Relay interface during the
			specified measurement interval."
		::= { attCNMfrMeasEntry 8 }

	attCNMfrBadFrames OBJECT-TYPE
		SYNTAX	Gauge
		ACCESS	read-only
		STATUS	mandatory
		DESCRIPTION
			"The counter associated with the number of frames
			received by this interface that are faulty.

			A bad frame could be a frame with a non-integral
			number of octets, or an aborted frame, or a frame
			with a bad Frame Check Sequence (FCS)."
		::= { attCNMfrMeasEntry 9 }

	attCNMfrReceiverOverruns OBJECT-TYPE
		SYNTAX	Gauge
		ACCESS	read-only
		STATUS	mandatory
		DESCRIPTION
			"The counter associated with the number of receiver
			overruns occurred at this interface during the
			specified measurement interval.

			A receiver overrun occurs when frames are received
			faster than they can be stored and forwarded."
		::= { attCNMfrMeasEntry 10 }


	-- the Frame Relay PVC-level Measurements table

	--
	-- This table provides counts on the various PVC-level
	-- measurement counts maintained by a Frame Relay interface
	-- during the specified measurement interval.
	--

	attCNMfrPVCMeasTable OBJECT-TYPE
		SYNTAX	SEQUENCE OF AttCNMfrPVCMeasEntry
		ACCESS  not-accessible
		STATUS  mandatory
		DESCRIPTION
			"A list of entries containing PVC-level measurement
			counts, maintained during the specified measurement
			interval, for all the Frame Relay interfaces managed
			by this system."
		::= { att-cnm-fr 3 }

	attCNMfrPVCMeasEntry OBJECT-TYPE
		SYNTAX  AttCNMfrPVCMeasEntry
		ACCESS  not-accessible
		STATUS  mandatory
		DESCRIPTION
			"An entry containing measurement counts, maintained
			during the specified measurement interval, for a
			particular PVC on a specific Frame Relay interface."
		INDEX	{ attCNMfrPVCMeasIfIndex,
			    attCNMfrPVCMeasIndex,
			      attCNMfrPVCMeasInterval }
		::= { attCNMfrPVCMeasTable 1 }

	AttCNMfrPVCMeasEntry ::=
		SEQUENCE {
		    attCNMfrPVCMeasIfIndex
			INTEGER,
		    attCNMfrPVCMeasIndex
			INTEGER,
		    attCNMfrPVCMeasInterval
			INTEGER,
		    attCNMfrPVCMeasTimeStamp
			INTEGER,
		    attCNMfrPVCMeasLocalTime
			DisplayString,
		    attCNMfrCongestionAtIngress
			Gauge,
		    attCNMfrCongestionAtEgress
			Gauge
		}

	attCNMfrPVCMeasIfIndex OBJECT-TYPE
		SYNTAX	INTEGER
		ACCESS	read-only
		STATUS	mandatory
		DESCRIPTION
			"A unique value for each Frame Relay interface.
			The interface identified by a particular value of
			this index is the same interface as identified by
			the same value of an attCNMifConfigIndex object
			instance."
		::= { attCNMfrPVCMeasEntry 1 }

	attCNMfrPVCMeasIndex OBJECT-TYPE
		SYNTAX	INTEGER
		ACCESS	read-only
		STATUS	mandatory
		DESCRIPTION
			"The DLCI number on a Frame Relay interface that
			identifies a unique Data Link Connection."
		::= { attCNMfrPVCMeasEntry 2 }

	attCNMfrPVCMeasInterval OBJECT-TYPE
		SYNTAX  INTEGER
		ACCESS  read-only
		STATUS  mandatory
		DESCRIPTION
			"This variable identifies the measurement interval
			number for which measurement is provided. It is a
			number between 1 and XX, where 1 identifies the most
			recently completed measurement interval and XX is
			the least recently completed measurement interval."
		::= { attCNMfrPVCMeasEntry 3 }

	attCNMfrPVCMeasTimeStamp OBJECT-TYPE
		SYNTAX  INTEGER
		ACCESS  read-only
		STATUS  mandatory
		DESCRIPTION
			"The time stamp corresponding to the end of the
			specified measurement interval, as measured in
			seconds from 00:00:00 UTC (Coordinated Universal
			Time) January 1, 1970. Any fraction is rounded up."
		::= { attCNMfrPVCMeasEntry 4 }

	attCNMfrPVCMeasLocalTime OBJECT-TYPE
		SYNTAX  DisplayString(SIZE(0..255))
		ACCESS  read-only
		STATUS  mandatory
		DESCRIPTION
			"The time stamp corresponding to the end of the
			specified measurement interval.  Any fraction is
			rounded up. It is given as a printable ASCII string
			showing the local time at the end of the interval."
		::= { attCNMfrPVCMeasEntry 5 }

	attCNMfrCongestionAtIngress OBJECT-TYPE
		SYNTAX	Gauge
		ACCESS	read-only
		STATUS	mandatory
		DESCRIPTION
			"The counter associated with the number of times
			frames received by this PVC had to be discarded
			because buffers were unavailable or congestion
			control was being enforced during the specified
			measurement interval."
		::= { attCNMfrPVCMeasEntry 6 }

	attCNMfrCongestionAtEgress OBJECT-TYPE
		SYNTAX	Gauge
		ACCESS	read-only
		STATUS	mandatory
		DESCRIPTION
			"The counter associated with the number of times
			frames sent by this PVC had to be discarded
			because buffers were unavailable or congestion
			control was being enforced during the specified
			measurement interval."
		::= { attCNMfrPVCMeasEntry 7 }

	-- the Frame Relay PVC-level Status table

	--
	-- This table provides status information on
	-- Data Link Connections on all Frame Relay interfaces
	-- supported by this system.
	--

	attCNMfrPVCStatusTable OBJECT-TYPE
		SYNTAX	SEQUENCE OF AttCNMfrPVCStatusEntry
		ACCESS  not-accessible
		STATUS  mandatory
		DESCRIPTION
			"A list of entries containing status information
			about Data Link Connections on Frame Relay interfaces
			managed by this system."
		::= { att-cnm-fr 4 }

	attCNMfrPVCStatusEntry OBJECT-TYPE
		SYNTAX  AttCNMfrPVCStatusEntry
		ACCESS  not-accessible
		STATUS  mandatory
		DESCRIPTION
			"An entry containing status information about
			a particular Data Link Connection on a specific
			Frame Relay interface."
		INDEX	{ attCNMfrPVCStatusIfIndex,
			    attCNMfrPVCStatusIndex }
		::= { attCNMfrPVCStatusTable 1 }

	AttCNMfrPVCStatusEntry ::=
		SEQUENCE {
		    attCNMfrPVCStatusIfIndex
			INTEGER,
		    attCNMfrPVCStatusIndex
			INTEGER,
		    attCNMfrPVCAdminStatus
			INTEGER,
		    attCNMfrPVCOperStatus
			INTEGER
		}

	attCNMfrPVCStatusIfIndex OBJECT-TYPE
		SYNTAX	INTEGER
		ACCESS	read-only
		STATUS	mandatory
		DESCRIPTION
			"A unique value for each Frame Relay interface.
			The interface identified by a particular value of
			this index is the same interface as identified by
			the same value of an attCNMifConfigIndex object
			instance."
		::= { attCNMfrPVCStatusEntry 1 }

	attCNMfrPVCStatusIndex OBJECT-TYPE
		SYNTAX	INTEGER
		ACCESS	read-only
		STATUS	mandatory
		DESCRIPTION
			"The DLCI number on a Frame Relay interface that
			identifies a unique Data Link Connection."
		::= { attCNMfrPVCStatusEntry 2 }

	attCNMfrPVCAdminStatus OBJECT-TYPE
		SYNTAX  INTEGER {
			    up(1),
			    down(2),
			    testing(3),
			    unknown(4)
			}
		ACCESS  read-only
		STATUS  mandatory
		DESCRIPTION
			"The desired state of this Data Link Connection."
		::= { attCNMfrPVCStatusEntry 3 }

	attCNMfrPVCOperStatus OBJECT-TYPE
		SYNTAX  INTEGER {
			    up(1),
			    down(2),
			    testing(3),
			    unknown(4)
			}
		ACCESS  read-only
		STATUS  mandatory
		DESCRIPTION
			"The current operational state of this Data Link
			Connection."
		::= { attCNMfrPVCStatusEntry 4 }

	END
