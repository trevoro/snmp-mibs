--
--  Title:  Appian Physical Port DS1 MIB
--
--  Dated:  23.Jan.2000
--  Author: D. Theriault
--
--  Description:
--
--  This MIB file contains the definitions and support for the Appian
--  DS1 Access Interfaces on the Optical Services Access Platform(s).
--
--
APPIAN-PPORT-DS1-MIB DEFINITIONS ::= BEGIN

     IMPORTS
          acPport, AcOpStatus,
          AcSlotNumber, AcPortNumber, 
          AcAdminStatus, AcNodeId                 FROM APPIAN-SMI-MIB 

          acChassisCurrentTime, acChassisRingId   FROM APPIAN-CHASSIS-MIB

          DisplayString, TimeStamp, TruthValue    FROM SNMPv2-TC
          
          MODULE-IDENTITY, OBJECT-TYPE,
          NOTIFICATION-TYPE                       FROM SNMPv2-SMI
          
          PerfIntervalCount                       FROM PerfHist-TC-MIB;


     acDs1 MODULE-IDENTITY
         LAST-UPDATED "0009070000Z"
         ORGANIZATION "Appian Communications, Inc."
         CONTACT-INFO "Rick Koch"

         DESCRIPTION
              "The MIB module to describe the Appian DS1 interfaces objects.
              The tables for this DS1 are NOT SHARED between OSAPs."

         ::= { acPport 4 }

     -- The Appian DS1 Near End Group

     -- The Appian DS1 Near End Group consists of five tables:
     --    DS1 Configuration
     --    DS1 Current
     --    DS1 Interval
     --    DS1 Total
     --    DS1 Channel Table

     -- The Appian DS1 Configuration Table

     acDs1ConfigTable OBJECT-TYPE
          SYNTAX  SEQUENCE OF AcDs1ConfigEntry
          MAX-ACCESS  not-accessible
          STATUS  current
          DESCRIPTION
                 "The DS1 Configuration table.  This table is created
                 by the EMS/CLI."
     ::= { acDs1 1 }

     acDs1ConfigEntry OBJECT-TYPE
          SYNTAX  AcDs1ConfigEntry
          MAX-ACCESS  not-accessible
          STATUS  current
          DESCRIPTION
                 "An entry in the DS1 Configuration table."
          INDEX   { acDs1ConfigNodeId, acDs1ConfigSlot, acDs1ConfigPort }
          ::= { acDs1ConfigTable 1 }

     AcDs1ConfigEntry ::=
          SEQUENCE {
              acDs1ConfigNodeId                     AcNodeId,
              acDs1ConfigSlot                       AcSlotNumber,
              acDs1ConfigPort                       AcPortNumber,
              acDs1ConfigAdminStatus                AcAdminStatus,
              acDs1ConfigOpStatus                   AcOpStatus,
              acDs1ConfigTimeElapsedInterval        INTEGER,
              acDs1ConfigValidIntervals             INTEGER,
              acDs1ConfigTimeElapsedDay             INTEGER,
              acDs1ConfigValidDays                  INTEGER,
              acDs1ConfigTimeElapsedFarEndInterval  INTEGER,
              acDs1ConfigValidFarEndIntervals       INTEGER,
              acDs1ConfigTimeElapsedFarEndDay       INTEGER,
              acDs1ConfigValidFarEndDays            INTEGER,
              acDs1ConfigLineType                   INTEGER,
              acDs1ConfigLineCoding                 INTEGER,
              acDs1ConfigCircuitIdentifier          DisplayString,
              acDs1ConfigLoopbackConfig             INTEGER,
              acDs1ConfigLineStatus                 INTEGER,
              acDs1ConfigSignalMode                 INTEGER,
              acDs1ConfigTransmitClockSource        INTEGER,
              acDs1ConfigFdl                        INTEGER,
              acDs1ConfigInvalidIntervals           INTEGER,
              acDs1ConfigInvalidDays                INTEGER,
              acDs1ConfigInvalidFarEndIntervals     INTEGER,
              acDs1ConfigInvalidFarEndDays          INTEGER,
              acDs1ConfigLineStatusLastChange       TimeStamp,
              acDs1ConfigLineStatusChangeTrapEnable INTEGER,
              acDs1ConfigLoopbackStatus             INTEGER,
              acDs1ConfigInterfaceName              DisplayString,
              acDs1ConfigTimeSlotIndex              INTEGER
     }

     acDs1ConfigNodeId OBJECT-TYPE
          SYNTAX  AcNodeId
          MAX-ACCESS  accessible-for-notify
          STATUS  current
          DESCRIPTION
                 "The node id is the id for this specific node in the OSAP 
                 ring."
          ::= { acDs1ConfigEntry 1 }

     acDs1ConfigSlot OBJECT-TYPE
          SYNTAX  AcSlotNumber
          MAX-ACCESS  accessible-for-notify
          STATUS  current
          DESCRIPTION
                 " The physical slot number of the port."
          ::= { acDs1ConfigEntry 2 }

     acDs1ConfigPort OBJECT-TYPE
          SYNTAX  AcPortNumber
          MAX-ACCESS  accessible-for-notify
          STATUS  current
          DESCRIPTION
                 " The physical port number of the port"
          ::= { acDs1ConfigEntry 3 }

     acDs1ConfigAdminStatus OBJECT-TYPE
          SYNTAX  AcAdminStatus
          MAX-ACCESS read-create
          STATUS  current
          DESCRIPTION
                 "Appian Administrative Status attribute used to set the 
                 provisioning state as either activate(1), delete(2) or 
                 inactivate(3).  Refer to the Appian-SMI.mib file for 
                 additional information."
          DEFVAL { inactivate }
          
          ::= { acDs1ConfigEntry 4 }

     acDs1ConfigOpStatus OBJECT-TYPE
          SYNTAX  AcOpStatus
          MAX-ACCESS read-only
          STATUS  current
          DESCRIPTION
                 "The operational or actual state of this ds1."
          
          ::= { acDs1ConfigEntry 5 }
          
     acDs1ConfigTimeElapsedInterval OBJECT-TYPE
          SYNTAX  INTEGER (0..899)
          MAX-ACCESS  read-only
          STATUS  current
          DESCRIPTION
                   "The number of seconds that have elapsed since
                   the beginning of the near end current error-
                   measurement period.  If, for some reason, such
                   as an adjustment in the system's time-of-day
                   clock, the current interval exceeds the maximum
                   value, the agent will return the maximum value."

          ::= { acDs1ConfigEntry 6 }

     acDs1ConfigValidIntervals OBJECT-TYPE
          SYNTAX  INTEGER (0..96)
          MAX-ACCESS  read-only
          STATUS  current
          DESCRIPTION
                 "The number of previous near end intervals for
                 which data was collected.  The value will be
                 96 unless the interface was brought online within
                 the last 24 hours, in which case the value will be
                 the number of complete 15 minute near end
                 intervals since the interface has been online.  In
                 the case where the agent is a proxy, it is
                 possible that some intervals are unavailable.  In
                 this case, this interval is the maximum interval
                 number for which data is available."

          ::= { acDs1ConfigEntry 7 }

     acDs1ConfigTimeElapsedDay OBJECT-TYPE
          SYNTAX  INTEGER (0..86399)
          MAX-ACCESS  read-only
          STATUS  current
          DESCRIPTION
                   "The number of seconds that have elapsed since
                   the beginning of the near end current day error-
                   measurement period.  If, for some reason, such
                   as an adjustment in the system's time-of-day
                   clock, the current day interval exceeds the maximum
                   value, the agent will return the maximum value."

          ::= { acDs1ConfigEntry 8 }

     acDs1ConfigValidDays OBJECT-TYPE
          SYNTAX  INTEGER (0..30)
          MAX-ACCESS  read-only
          STATUS  current
          DESCRIPTION
                 "The number of previous near end days for
                 which data was collected.  The value will be
                 30 unless the interface was brought online within
                 the last 30 days, in which case the value will be
                 the number of complete 24 hr near end days
                 since the interface has been online.  In
                 the case where the agent is a proxy, it is
                 possible that some intervals are unavailable.  In
                 this case, this interval is the maximum interval
                 number for which data is available."

          ::= { acDs1ConfigEntry 9 }

     acDs1ConfigTimeElapsedFarEndInterval OBJECT-TYPE
          SYNTAX  INTEGER (0..899)
          MAX-ACCESS  read-only
          STATUS  current
          DESCRIPTION
                 "The number of seconds that have elapsed since the
                 beginning of the far end current error-measurement
                 period.  If, for some reason, such as an
                 adjustment in the system's time-of-day clock, the
                 current interval exceeds the maximum value, the
                 agent will return the maximum value."
          ::= { acDs1ConfigEntry 10 }

     acDs1ConfigValidFarEndIntervals OBJECT-TYPE
          SYNTAX  INTEGER (0..96)
          MAX-ACCESS  read-only
          STATUS  current
          DESCRIPTION
                 "The number of previous near end intervals for
                 which data was collected.  The value will be
                 96 unless the interface was brought online within
                 the last 24 hours, in which case the value will be
                 the number of complete 15 minute near end
                 intervals since the interface has been online.  In
                 the case where the agent is a proxy, it is
                 possible that some intervals are unavailable.  In
                 this case, this interval is the maximum interval
                 number for which data is available."
          ::= { acDs1ConfigEntry 11 }

     acDs1ConfigTimeElapsedFarEndDay OBJECT-TYPE
          SYNTAX  INTEGER (0..86399)
          MAX-ACCESS  read-only
          STATUS  current
          DESCRIPTION
                   "The number of seconds that have elapsed since
                   the beginning of the far end current day error-
                   measurement period.  If, for some reason, such
                   as an adjustment in the system's time-of-day
                   clock, the current day interval exceeds the maximum
                   value, the agent will return the maximum value."
          ::= { acDs1ConfigEntry 12 }

     acDs1ConfigValidFarEndDays OBJECT-TYPE
          SYNTAX  INTEGER (0..30)
          MAX-ACCESS  read-only
          STATUS  current
          DESCRIPTION
                 "The number of previous near end days for
                 which data was collected.  The value will be
                 30 unless the far/near end interface was brought online 
                 within the last 30 days, in which case the value will be
                 the number of complete 24 hr far end days
                 since the interface has been online.  In
                 the case where the agent is a proxy, it is
                 possible that some intervals are unavailable.  In
                 this case, this interval is the maximum interval
                 number for which data is available."
          ::= { acDs1ConfigEntry 13 }

     acDs1ConfigLineType OBJECT-TYPE
          SYNTAX  INTEGER {
                     esf(1),
                     d4(2)
                 }
          MAX-ACCESS  read-create
          STATUS  current
          DESCRIPTION
                 "This variable indicates  the  variety  of  DS1
                 Line  implementing  this  circuit.  The type of
                 circuit affects the number of bits  per  second
                 that  the circuit can reasonably carry, as well
                 as the interpretation of the  usage  and  error
                 statistics.  The values, in sequence, describe:

                 TITLE:         SPECIFICATION:
                 esf              Extended SuperFrame DS1 (T1.107)
                 d4               AT&T D4 format DS1 (T1.107)"

          DEFVAL { esf }
          ::= { acDs1ConfigEntry 14 }

     acDs1ConfigLineCoding OBJECT-TYPE
          SYNTAX  INTEGER {
                     b8zs(1),
                     ami(2)
                 }
          MAX-ACCESS  read-create
          STATUS  current
          DESCRIPTION
                 "This variable describes the variety of Zero Code
                 Suppression used on this interface, which in turn
                 affects a number of its characteristics.

                 b8zs refers to the use of a specified pattern
                 of normal bits and bipolar violations which are
                 used to replace a sequence of eight zero bits.

                 ami refers to a mode wherein no zero code
                 suppression is present and the line encoding does
                 not solve the problem directly.  In this
                 application, the higher layer must provide data
                 which meets or exceeds the pulse density
                 requirements, such as inverting HDLC data."

          DEFVAL { b8zs }
          
          ::= { acDs1ConfigEntry 15 }

     acDs1ConfigCircuitIdentifier OBJECT-TYPE
          SYNTAX  DisplayString (SIZE (0..255))
          MAX-ACCESS  read-create
          STATUS  current
          DESCRIPTION
                 "This variable contains the transmission vendor's
                 circuit identifier, for the purpose of
                 facilitating troubleshooting."
          DEFVAL { "" }
          ::= { acDs1ConfigEntry 16 }

     acDs1ConfigLoopbackConfig OBJECT-TYPE
          SYNTAX  INTEGER {
                      none(1),
                      payload(2),
                      facility(3),
                      other(4),
                      terminal(5),
                      dual(6)
                    }
          MAX-ACCESS  read-create
          STATUS  current
          DESCRIPTION
                 "This variable represents the desired loopback
                 configuration of the DS1 interface.  Agents
                 supporting read/write access should return
                 inconsistentValue in response to a requested
                 loopback state that the interface does not
                 support.  The values mean:

                 none
                  Not in the loopback state.  A device that is not
                 capable of performing a loopback on the interface
                 shall always return this as its value.

                 payload
                  The received signal at this interface is looped
                 through the device.  Typically the received signal
                 is looped back for retransmission after it has
                 passed through the device's framing function.

                 facility
                  The received signal at this interface does not go
                 through the device (minimum penetration) but is
                 looped back out.

                 other
                  Loopbacks that are not defined here.

                 terminal
                  The transmitted signal at this interface is
                 looped back and received by the same interface.
                 What is transmitted onto the line is product
                 dependent.

                 dual
                  Both acDs1LineLoop and acDs1InwardLoop will be
                 active simultaneously.
                 **NOADMINDOWN**"
          DEFVAL { none }
          
          ::= { acDs1ConfigEntry 17 }

     acDs1ConfigLineStatus OBJECT-TYPE
          SYNTAX  INTEGER (1..131071)
          MAX-ACCESS  read-only
          STATUS  current
          DESCRIPTION
                 "This variable indicates the Line Status of the
                 interface.  It contains loopback, failure,
                 received 'alarm' and transmitted 'alarms
                 information.

                 The acDs1ConfigLineStatus is a bit map represented as a
                 sum, therefore, it can represent multiple failures
                 (alarms) and a LoopbackState simultaneously.

                 acDs1NoAlarm must be set if and only if no other
                 flag is set.

                 If the acDs1loopbackState bit is set, the loopback
                 in effect can be determined from the
                 acDs1loopbackConfig object.
       The various bit positions are:
      1     acDs1NoAlarm           No alarm present
      2     acDs1RcvFarEndLOF      Far end LOF (a.k.a., Yellow Alarm)
      4     acDs1XmtFarEndLOF      Near end sending LOF Indication
      8     acDs1RcvAIS            Far end sending AIS
     16     acDs1XmtAIS            Near end sending AIS
     32     acDs1LossOfFrame       Near end LOF (a.k.a., Red Alarm)
     64     acDs1LossOfSignal      Near end Loss Of Signal
    128     acDs1LoopbackState     Near end is looped
    512     acDs1RcvFarEndLOMF     Far End Sending TS16 LOMF
   1024     acDs1XmtFarEndLOMF     Near End Sending TS16 LOMF
   2048     acDs1RcvTestCode       Near End detects a test code
   4096     acDs1RcvFarEndRAI      any line status not defined here
   8192     acDs1RcvFarEndUnEqp    Far End sending VT 1.5 labelled UNEQUIPPED
  16384     acDs1NetEquipOOS       Carrier Equipment Out of Service"
     ::= { acDs1ConfigEntry 18 }

     acDs1ConfigSignalMode OBJECT-TYPE
          SYNTAX  INTEGER {
                     none(1),
                     message(2),
                     other (3)
                 }
          MAX-ACCESS  read-only
          STATUS  current
          DESCRIPTION
            "'none' indicates that no bits are reserved for
            signaling on this channel.

            'message' indicates that Common  Chan-
            nel Signaling is in use on channel 24 of a DS1."
          DEFVAL { none }
          ::= { acDs1ConfigEntry 19 }

     acDs1ConfigTransmitClockSource OBJECT-TYPE
          SYNTAX  INTEGER {
                     bits(1),
                     local(2),
                     through(3)
                 }
          MAX-ACCESS  read-only
          STATUS  current
          DESCRIPTION
            "The source of Transmit Clock.
             'bits' indicates that recovered receive
            clock through a bits device is used as
            the transmit clock.

             'localTiming' indicates that a local clock
            source is used or when an external clock is
            attached to the box containing the interface.

             'throughTiming' indicates that recovered re-
            ceive clock from another interface is used as
            the transmit clock."
          
          DEFVAL { through }
          
          ::= { acDs1ConfigEntry 20 }

     acDs1ConfigFdl OBJECT-TYPE
          SYNTAX  INTEGER (1..15)
          MAX-ACCESS  read-only
          STATUS  current
          DESCRIPTION
            "This bitmap describes the use of  the  facili-
            ties data link, and is the sum of the capabili-
            ties.  Set any bits that are appropriate:

            other(1),
            ansi(2),
            att(4),
            none(8)

             'other' indicates that a protocol  other  than
            one following is used.

             'ansi' refers to the  FDL  exchange
            recommended by ANSI.

             'att' refers to ESF FDL exchanges.

             'none' indicates that the device  does
            not use the FDL."
          DEFVAL { 2 }
          ::= { acDs1ConfigEntry 21 }

     acDs1ConfigInvalidIntervals OBJECT-TYPE
          SYNTAX  INTEGER (0..96)
          MAX-ACCESS  read-only
          STATUS  current
          DESCRIPTION
                 "The number of intervals in the range from 0 to
                 acDs1ValidIntervals for which no data is
                 available.  This object will typically be zero
                 except in cases where the data for some intervals
                 are not available (e.g., in proxy situations)."
          ::= { acDs1ConfigEntry 22 }

     acDs1ConfigInvalidDays OBJECT-TYPE
          SYNTAX  INTEGER (0..30)
          MAX-ACCESS  read-only
          STATUS  current
          DESCRIPTION
                 "The number of days in the range from 0 to
                 acDs1ConfigValidDays for which no data is
                 available.  This object will typically be zero
                 except in cases where the data for some intervals
                 are not available (e.g., in proxy situations)."
          ::= { acDs1ConfigEntry 23 }

     acDs1ConfigInvalidFarEndIntervals OBJECT-TYPE
          SYNTAX  INTEGER (0..96)
          MAX-ACCESS  read-only
          STATUS  current
          DESCRIPTION
                 "The number of intervals in the range from 0 to
                 acDs1ConfigValidFarEndIntervals for which no data is
                 available.  This object will typically be zero
                 except in cases where the data for some intervals
                 are not available (e.g., in proxy situations)."
          ::= { acDs1ConfigEntry 24 }

     acDs1ConfigInvalidFarEndDays OBJECT-TYPE
          SYNTAX  INTEGER (0..30)
          MAX-ACCESS  read-only
          STATUS  current
          DESCRIPTION
                 "The number of days in the range from 0 to
                 acDs1ConfigValidFarEndDays for which no data is
                 available.  This object will typically be zero
                 except in cases where the data for some intervals
                 are not available (e.g., in proxy situations)."
          ::= { acDs1ConfigEntry 25 }

     acDs1ConfigLineStatusLastChange OBJECT-TYPE
          SYNTAX  TimeStamp
          MAX-ACCESS  read-only
          STATUS  current
          DESCRIPTION
                 "The value of MIB II's sysUpTime object at the
                 time this DS1 entered its current line status
                 state.  If the current state was entered prior to
                 the last re-initialization of the proxy-agent,
                 then this object contains a zero value."
          ::= { acDs1ConfigEntry 26 }

     acDs1ConfigLineStatusChangeTrapEnable  OBJECT-TYPE
          SYNTAX      INTEGER {
                         enabled(1),
                         disabled(2)
                      }
          MAX-ACCESS  read-create
          STATUS      current
          DESCRIPTION
                 "Indicates whether acDs1ConfigLineStatusChange traps
                 should be generated for this interface."
          DEFVAL { disabled }
          ::= { acDs1ConfigEntry 27 }

     acDs1ConfigLoopbackStatus  OBJECT-TYPE
          SYNTAX      INTEGER (1..127)
          MAX-ACCESS  read-only
          STATUS      current
          DESCRIPTION
                 "This variable represents the current state of the
                 loopback on the DS1 interface.  It contains
                 information about loopbacks established by a
                 manager and remotely from the far end.

                 The acDs1ConfigLoopbackStatus is a bit map represented as
                 a sum, therefore is can represent multiple
                 loopbacks simultaneously.

                 The various bit positions are:
                  1  acDs1NoLoopback
                  2  acDs1NearEndPayloadLoopback
                  4  acDs1NearEndLineLoopback
                  8  acDs1NearEndOtherLoopback
                 16  acDs1NearEndInwardLoopback
                 32  acDs1FarEndPayloadLoopback
                 64  acDs1FarEndLineLoopback"

          DEFVAL { 1 }
     ::= { acDs1ConfigEntry 28 }

     acDs1ConfigInterfaceName  OBJECT-TYPE
          SYNTAX    DisplayString (SIZE(0..64))
          MAX-ACCESS  read-create
          STATUS      current
          DESCRIPTION
          "A user configurable interface name which can be up to 
          64 bytes in length which uniquely identifies this DS1
          interface."

          DEFVAL { "DS-1/TDM Interface" }
          
     ::= { acDs1ConfigEntry 29 }

     acDs1ConfigTimeSlotIndex OBJECT-TYPE
          SYNTAX  INTEGER
          MAX-ACCESS read-create
          STATUS  current
          DESCRIPTION
                 "This index corresponds to the desired timeslot
                  row in the Shared Timeslot Table with a payload
                  type of ds1tdm."
          
     ::= { acDs1ConfigEntry 30 }


     -- The Appian DS1 Interval Table
     acDs1IntervalTable OBJECT-TYPE
          SYNTAX  SEQUENCE OF AcDs1IntervalEntry
          MAX-ACCESS  not-accessible
          STATUS  current
          DESCRIPTION
                 "The Appian DS1 Interval Table contains various
                 statistics collected by each DS1 Interface over
                 the previous 24 hours of operation as well as over
                 the current period.  The past 24 hours are broken 
                 into 96 completed 15 minute intervals.  The first
                 row in this table (identified by acDs1IntervalNumber=1)
                 represents the current interval statistics.  The next 96
                 rows in this table (represented by 
                 acDs1IntervalNumber=2..97) represents one of the past 
                 15 minute intervals. The final row (identified by 
                 acDs1IntervalNumber=98) is the total of all the past 
                 intervals (2..97).   This table is created automatically."
          ::= { acDs1 2 }

     acDs1IntervalEntry OBJECT-TYPE
          SYNTAX  AcDs1IntervalEntry
          MAX-ACCESS  not-accessible
          STATUS  current
          DESCRIPTION
                 "An entry in the Appian DS1 Interval table."
          INDEX   { acDs1IntervalNodeId, 
                    acDs1IntervalSlot, 
                    acDs1IntervalPort,
                    acDs1IntervalNumber }
          ::= { acDs1IntervalTable 1 }

     AcDs1IntervalEntry ::=
          SEQUENCE {
              acDs1IntervalNodeId            AcNodeId,
              acDs1IntervalSlot              AcSlotNumber,
              acDs1IntervalPort              AcPortNumber,
              acDs1IntervalNumber            INTEGER,
              acDs1IntervalValidStats        TruthValue,
              acDs1IntervalResetStats        TruthValue,
              acDs1IntervalESs               PerfIntervalCount,
              acDs1IntervalSESs              PerfIntervalCount,
              acDs1IntervalSEFSs             PerfIntervalCount,
              acDs1IntervalUASs              PerfIntervalCount,
              acDs1IntervalCSSs              PerfIntervalCount,
              acDs1IntervalPCVs              PerfIntervalCount,
              acDs1IntervalLESs              PerfIntervalCount,
              acDs1IntervalBESs              PerfIntervalCount,
              acDs1IntervalDMs               PerfIntervalCount,
              acDs1IntervalLCVs              PerfIntervalCount
     }

     acDs1IntervalNodeId OBJECT-TYPE
          SYNTAX  AcNodeId
          MAX-ACCESS  accessible-for-notify
          STATUS  current
          DESCRIPTION
                 "The node id is the id for this specific node in the OSAP 
                 ring."
          ::= { acDs1IntervalEntry 1 }

     acDs1IntervalSlot OBJECT-TYPE
          SYNTAX  AcSlotNumber
          MAX-ACCESS  accessible-for-notify
          STATUS  current
          DESCRIPTION
                 "The physical slot number for this port."
          ::= { acDs1IntervalEntry 2 }

     acDs1IntervalPort OBJECT-TYPE
          SYNTAX  AcPortNumber
          MAX-ACCESS  accessible-for-notify
          STATUS  current
          DESCRIPTION
                 "The physical port number for this port."
          ::= { acDs1IntervalEntry 3 }

     acDs1IntervalNumber OBJECT-TYPE
          SYNTAX  INTEGER (1..98)
          MAX-ACCESS  accessible-for-notify
          STATUS  current
          DESCRIPTION
                 "A number between 1 and 98, where 1 is the current
                 15 minute interval in progress, 2 is the most
                 recently completed 15 minute interval and 97 is
                 the 15 minutes interval completed 23 hours and 45
                 minutes prior to interval 2, and 98 is the total (sum)
                 of all of the previous completed intervals (2..97)."
          ::= { acDs1IntervalEntry 4 }

     acDs1IntervalValidStats OBJECT-TYPE
          SYNTAX TruthValue
          MAX-ACCESS read-only
          STATUS current
          DESCRIPTION
                 "This variable indicates if the data for this
                 interval is valid. For acDs1IntervalNumber=98,
                 this value will only be true if all data is valid
                 for intervals 2..97."
          ::= { acDs1IntervalEntry 5 }

     acDs1IntervalResetStats OBJECT-TYPE
          SYNTAX TruthValue
          MAX-ACCESS read-write
          STATUS current
          DESCRIPTION
                 "This variable allows the data for the current
                 interval (acDs1IntervalNumber = 1) to be reset.
                 The acDs1IntervalValidFlag will be set to False
                 after the reset for the current interval.  This 
                 field has no effect on acDs1IntervalNumber 2..98.
                 This field will always show a value of False when
                 read."
          ::= { acDs1IntervalEntry 6 }


     acDs1IntervalESs OBJECT-TYPE
          SYNTAX  PerfIntervalCount
          MAX-ACCESS  read-only
          STATUS  current
          DESCRIPTION
                 "The number of Errored Seconds."
          ::= { acDs1IntervalEntry 7 }

     acDs1IntervalSESs OBJECT-TYPE
          SYNTAX  PerfIntervalCount
          MAX-ACCESS  read-only
          STATUS  current
          DESCRIPTION
                 "The number of Severely Errored Seconds."
          ::= { acDs1IntervalEntry 8 }

     acDs1IntervalSEFSs OBJECT-TYPE
          SYNTAX  PerfIntervalCount
          MAX-ACCESS  read-only
          STATUS  current
          DESCRIPTION
                 "The number of Severely Errored Framing Seconds."
          ::= { acDs1IntervalEntry 9 }

     acDs1IntervalUASs OBJECT-TYPE
          SYNTAX  PerfIntervalCount
          MAX-ACCESS  read-only
          STATUS  current
          DESCRIPTION
                 "The number of Unavailable Seconds.  This object
                 may decrease if the occurance of unavailable
                 seconds occurs across an inteval boundary."
          ::= { acDs1IntervalEntry 10 }

     acDs1IntervalCSSs OBJECT-TYPE
          SYNTAX  PerfIntervalCount
          MAX-ACCESS  read-only
          STATUS  current
          DESCRIPTION
                 "The number of Controlled Slip Seconds."
          ::= { acDs1IntervalEntry 11 }

     acDs1IntervalPCVs OBJECT-TYPE
          SYNTAX  PerfIntervalCount
          MAX-ACCESS  read-only
          STATUS  current
          DESCRIPTION
                 "The number of Path Coding Violations."
          ::= { acDs1IntervalEntry 12 }

     acDs1IntervalLESs OBJECT-TYPE
          SYNTAX  PerfIntervalCount
          MAX-ACCESS  read-only
          STATUS  current
          DESCRIPTION
                 "The number of Line Errored Seconds."
          ::= { acDs1IntervalEntry 13 }

     acDs1IntervalBESs OBJECT-TYPE
          SYNTAX PerfIntervalCount
          MAX-ACCESS read-only
          STATUS current
          DESCRIPTION
                 "The number of Bursty Errored Seconds."
          ::= { acDs1IntervalEntry 14 }

     acDs1IntervalDMs OBJECT-TYPE
          SYNTAX PerfIntervalCount
          MAX-ACCESS read-only
          STATUS current
          DESCRIPTION
                 "The number of Degraded Minutes."
          ::= { acDs1IntervalEntry 15 }

     acDs1IntervalLCVs OBJECT-TYPE
          SYNTAX PerfIntervalCount
          MAX-ACCESS read-only
          STATUS current
          DESCRIPTION
                 "The number of Line Code Violations."
          ::= { acDs1IntervalEntry 16 }


     -- The Appian DS1 Day Table
     acDs1DayTable OBJECT-TYPE
          SYNTAX  SEQUENCE OF AcDs1DayEntry
          MAX-ACCESS  not-accessible
          STATUS  current
          DESCRIPTION
                 "The Appian  DS1 Day Table contains various
                 statistics collected by each DS1 Interface over
                 the previous 30 days of operation as well as over
                 the current day period. The first row in this table 
                 (identified by acDs1DayNumber=1) represents the current 
                 day statistics.  The next 30 rows in this table 
                 (represented by acDs1DayNumber=2..31) represents one 
                 of the past 24 hr periods (day).   This table is created 
                 automatically."
          ::= { acDs1 3 }

     acDs1DayEntry OBJECT-TYPE
          SYNTAX  AcDs1DayEntry
          MAX-ACCESS  not-accessible
          STATUS  current
          DESCRIPTION
                 "An entry in the Appian DS1 Day table."
          INDEX   { acDs1DayNodeId, 
                    acDs1DaySlot, 
                    acDs1DayPort,
                    acDs1DayNumber }
          ::= { acDs1DayTable 1 }

     AcDs1DayEntry ::=
          SEQUENCE {
              acDs1DayNodeId            AcNodeId,
              acDs1DaySlot              AcSlotNumber,
              acDs1DayPort              AcPortNumber,
              acDs1DayNumber            INTEGER,
              acDs1DayValidStats        TruthValue,
              acDs1DayResetStats        TruthValue,
              acDs1DayESs               PerfIntervalCount,
              acDs1DaySESs              PerfIntervalCount,
              acDs1DaySEFSs             PerfIntervalCount,
              acDs1DayUASs              PerfIntervalCount,
              acDs1DayCSSs              PerfIntervalCount,
              acDs1DayPCVs              PerfIntervalCount,
              acDs1DayLESs              PerfIntervalCount,
              acDs1DayBESs              PerfIntervalCount,
              acDs1DayDMs               PerfIntervalCount,
              acDs1DayLCVs              PerfIntervalCount
     }

     acDs1DayNodeId OBJECT-TYPE
          SYNTAX  AcNodeId
          MAX-ACCESS  accessible-for-notify
          STATUS  current
          DESCRIPTION
                 "The node id is the id for this specific node in the OSAP 
                 ring."
          ::= { acDs1DayEntry 1 }

     acDs1DaySlot OBJECT-TYPE
          SYNTAX  AcSlotNumber
          MAX-ACCESS  accessible-for-notify
          STATUS  current
          DESCRIPTION
                 "The physical slot number of the port."
          ::= { acDs1DayEntry 2 }

     acDs1DayPort OBJECT-TYPE
          SYNTAX  AcPortNumber
          MAX-ACCESS  accessible-for-notify
          STATUS  current
          DESCRIPTION
                 "The physical port number of the port."
          ::= { acDs1DayEntry 3 }

     acDs1DayNumber OBJECT-TYPE
          SYNTAX  INTEGER (1..31)
          MAX-ACCESS  accessible-for-notify
          STATUS  current
          DESCRIPTION
                 "A number between 1 and 31, where 1 is the current
                 24 hour interval in progress (day), 2 is the most
                 recently completed 24 hour interval and 31 is
                 the 24 hour interval completed 29 days prior to 
                 interval 1."
          ::= { acDs1DayEntry 4 }

     acDs1DayValidStats OBJECT-TYPE
          SYNTAX TruthValue
          MAX-ACCESS read-only
          STATUS current
          DESCRIPTION
                 "This variable indicates if the data for this
                 interval is valid."
          ::= { acDs1DayEntry 5 }

     acDs1DayResetStats OBJECT-TYPE
          SYNTAX TruthValue
          MAX-ACCESS read-write
          STATUS current
          DESCRIPTION
                 "This variable allows the data for the current
                 day (acDs1DayIndex = 1) to be reset.
                 The acDs1DayValidFlag will be set to False
                 after the reset for the current day.  This 
                 field has no effect on acDs1DayIndex 2..31.
                 This field will always show a value of False 
                 when read."
          ::= { acDs1DayEntry 6 }

     acDs1DayESs OBJECT-TYPE
          SYNTAX  PerfIntervalCount
          MAX-ACCESS  read-only
          STATUS  current
          DESCRIPTION
                 "The number of Errored Seconds."
          ::= { acDs1DayEntry 7 }

     acDs1DaySESs OBJECT-TYPE
          SYNTAX  PerfIntervalCount
          MAX-ACCESS  read-only
          STATUS  current
          DESCRIPTION
                 "The number of Severely Errored Seconds."
          ::= { acDs1DayEntry 8 }

     acDs1DaySEFSs OBJECT-TYPE
          SYNTAX  PerfIntervalCount
          MAX-ACCESS  read-only
          STATUS  current
          DESCRIPTION
                 "The number of Severely Errored Framing Seconds."
          ::= { acDs1DayEntry 9 }

     acDs1DayUASs OBJECT-TYPE
          SYNTAX  PerfIntervalCount
          MAX-ACCESS  read-only
          STATUS  current
          DESCRIPTION
                 "The number of Unavailable Seconds.  This object
                 may decrease if the occurance of unavailable
                 seconds occurs across an inteval boundary."
          ::= { acDs1DayEntry 10 }

     acDs1DayCSSs OBJECT-TYPE
          SYNTAX  PerfIntervalCount
          MAX-ACCESS  read-only
          STATUS  current
          DESCRIPTION
                 "The number of Controlled Slip Seconds."
          ::= { acDs1DayEntry 11 }

     acDs1DayPCVs OBJECT-TYPE
          SYNTAX  PerfIntervalCount
          MAX-ACCESS  read-only
          STATUS  current
          DESCRIPTION
                 "The number of Path Coding Violations."
          ::= { acDs1DayEntry 12 }

     acDs1DayLESs OBJECT-TYPE
          SYNTAX  PerfIntervalCount
          MAX-ACCESS  read-only
          STATUS  current
          DESCRIPTION
                 "The number of Line Errored Seconds."
          ::= { acDs1DayEntry 13 }

     acDs1DayBESs OBJECT-TYPE
          SYNTAX PerfIntervalCount
          MAX-ACCESS read-only
          STATUS current
          DESCRIPTION
                 "The number of Bursty Errored Seconds."
          ::= { acDs1DayEntry 14 }

     acDs1DayDMs OBJECT-TYPE
          SYNTAX PerfIntervalCount
          MAX-ACCESS read-only
          STATUS current
          DESCRIPTION
                 "The number of Degraded Minutes."
          ::= { acDs1DayEntry 15 }

     acDs1DayLCVs OBJECT-TYPE
          SYNTAX PerfIntervalCount
          MAX-ACCESS read-only
          STATUS current
          DESCRIPTION
                 "The number of Line Code Violations."
          ::= { acDs1DayEntry 16 }

     -- The Appian  DS1 Far End Group

     -- The Appian DS1 Far End Group consists of two tables:
     --    DS1  Far End Interval
     --    DS1  Far End Day

     -- The Appian DS1  Far End Interval Table


     acDs1FarEndIntervalTable OBJECT-TYPE
          SYNTAX  SEQUENCE OF AcDs1FarEndIntervalEntry
          MAX-ACCESS  not-accessible
          STATUS  current
          DESCRIPTION
                 "The DS1  Far End Interval Table contains various 
                 statistics collected by each DS1 interface over the 
                 previous 24 hours of operation.  The past 24 hours are 
                 broken into 96 completed 15 minute intervals. Each row in 
                 this table represents one such interval (identified by 
                 acDs1FarEndIntervalNumber) for one specific instance 
                 (identified by acDs1FarEndIntervalSlot,
                 acDs1FarEndIntervalPort).  This table is created
                 automatically."
          ::= { acDs1 4 }

     acDs1FarEndIntervalEntry OBJECT-TYPE
          SYNTAX  AcDs1FarEndIntervalEntry
          MAX-ACCESS  not-accessible
          STATUS  current
          DESCRIPTION
                 "An entry in the DS1 Far End Interval table."

          INDEX   { acDs1FarEndIntervalNodeId,
                    acDs1FarEndIntervalSlot,
                    acDs1FarEndIntervalPort,
                    acDs1FarEndIntervalNumber }
          ::= { acDs1FarEndIntervalTable 1 }

     AcDs1FarEndIntervalEntry ::=
          SEQUENCE {
              acDs1FarEndIntervalNodeId      AcNodeId,
              acDs1FarEndIntervalSlot        AcSlotNumber,
              acDs1FarEndIntervalPort        AcPortNumber,
              acDs1FarEndIntervalNumber      INTEGER,
              acDs1FarEndIntervalValidStats  TruthValue,
              acDs1FarEndIntervalResetStats  TruthValue,
              acDs1FarEndIntervalESs         PerfIntervalCount,
              acDs1FarEndIntervalSESs        PerfIntervalCount,
              acDs1FarEndIntervalSEFSs       PerfIntervalCount,
              acDs1FarEndIntervalUASs        PerfIntervalCount,
              acDs1FarEndIntervalCSSs        PerfIntervalCount,
              acDs1FarEndIntervalLESs        PerfIntervalCount,
              acDs1FarEndIntervalPCVs        PerfIntervalCount,
              acDs1FarEndIntervalBESs        PerfIntervalCount,
              acDs1FarEndIntervalDMs         PerfIntervalCount
     }


     acDs1FarEndIntervalNodeId OBJECT-TYPE
          SYNTAX  AcNodeId
          MAX-ACCESS  accessible-for-notify
          STATUS  current
          DESCRIPTION
                 "The node id is the id for this specific node in the OSAP 
                 ring."
          ::= { acDs1FarEndIntervalEntry 1 }

     acDs1FarEndIntervalSlot OBJECT-TYPE
          SYNTAX  AcSlotNumber
          MAX-ACCESS  accessible-for-notify
          STATUS  current
          DESCRIPTION
                 "The physical slot number of the port."
          ::= { acDs1FarEndIntervalEntry 2 }

     acDs1FarEndIntervalPort OBJECT-TYPE
          SYNTAX  AcPortNumber
          MAX-ACCESS  accessible-for-notify
          STATUS  current
          DESCRIPTION
                 "The physical port number of the port."
          ::= { acDs1FarEndIntervalEntry 3 }

     acDs1FarEndIntervalNumber OBJECT-TYPE
          SYNTAX  INTEGER (1..98)
          MAX-ACCESS  accessible-for-notify
          STATUS  current
          DESCRIPTION
                 "A number between 1 and 98, where 1 is current
                 15 minute interval in progress, 2 is the most
                 recently completed 15 minute interval and 97 is
                 the 15 minutes interval completed 23 hours and 45
                 minutes prior to interval 2, and 98 is the total
                 of intervals 2..97 (sum)."
          ::= { acDs1FarEndIntervalEntry 4 }

     acDs1FarEndIntervalValidStats OBJECT-TYPE
          SYNTAX TruthValue
          MAX-ACCESS read-only
          STATUS current
          DESCRIPTION
                 "This variable indicates if the data for this
                 interval is valid.  For acDs1FarEndIntervalNumber=98,
                 this value will only be true if all data is valid
                 for intervals 2..97."
          ::= { acDs1FarEndIntervalEntry 5 }

     acDs1FarEndIntervalResetStats OBJECT-TYPE
          SYNTAX TruthValue
          MAX-ACCESS read-write
          STATUS current
          DESCRIPTION
                 "This variable allows the data for the current
                 interval (acDs1FarEndIntervalNumber = 1) to be reset.
                 The acDs1FarEndIntervalValidFlag will be set to False
                 after the reset for the current interval.  This 
                 field has no effect on acDs1FarEndIntervalNumber 2..98. 
                 This field will always show a value of false when read."
          ::= { acDs1FarEndIntervalEntry 6 }

     acDs1FarEndIntervalESs OBJECT-TYPE
          SYNTAX  PerfIntervalCount
          MAX-ACCESS  read-only
          STATUS  current
          DESCRIPTION
                 "The number of Far End Errored Seconds."
          ::= { acDs1FarEndIntervalEntry 7 }

     acDs1FarEndIntervalSESs OBJECT-TYPE
          SYNTAX  PerfIntervalCount
          MAX-ACCESS  read-only
          STATUS  current
          DESCRIPTION
                 "The number of Far End Severely Errored Seconds."
          ::= { acDs1FarEndIntervalEntry 8 }

     acDs1FarEndIntervalSEFSs OBJECT-TYPE
          SYNTAX  PerfIntervalCount
          MAX-ACCESS  read-only
          STATUS  current
          DESCRIPTION
                 "The number of Far End Severely Errored Framing
                 Seconds."
          ::= { acDs1FarEndIntervalEntry 9 }

     acDs1FarEndIntervalUASs OBJECT-TYPE
          SYNTAX  PerfIntervalCount
          MAX-ACCESS  read-only
          STATUS  current
          DESCRIPTION
                 "The number of Unavailable Seconds."
          ::= { acDs1FarEndIntervalEntry 10 }

     acDs1FarEndIntervalCSSs OBJECT-TYPE
          SYNTAX  PerfIntervalCount
          MAX-ACCESS  read-only
          STATUS  current
          DESCRIPTION
                 "The number of Far End Controlled Slip Seconds."
          ::= { acDs1FarEndIntervalEntry 11 }

     acDs1FarEndIntervalLESs OBJECT-TYPE
          SYNTAX  PerfIntervalCount
          MAX-ACCESS  read-only
          STATUS  current
          DESCRIPTION
                 "The number of Far End Line Errored Seconds."

          ::= { acDs1FarEndIntervalEntry 12 }

     acDs1FarEndIntervalPCVs OBJECT-TYPE
          SYNTAX  PerfIntervalCount
          MAX-ACCESS  read-only
          STATUS  current
          DESCRIPTION
                 "The number of Far End Path Coding Violations."
          ::= { acDs1FarEndIntervalEntry 13 }

     acDs1FarEndIntervalBESs OBJECT-TYPE
          SYNTAX PerfIntervalCount
          MAX-ACCESS read-only
          STATUS current
          DESCRIPTION
                 "The number of Far End Bursty Errored Seconds."
          ::= { acDs1FarEndIntervalEntry 14 }

     acDs1FarEndIntervalDMs OBJECT-TYPE
          SYNTAX PerfIntervalCount
          MAX-ACCESS read-only
          STATUS current
          DESCRIPTION
                 "The number of Far End Degraded Minutes."
          ::= { acDs1FarEndIntervalEntry 15 }

   -- The Appian DS1  Far End Day Table

     acDs1FarEndDayTable OBJECT-TYPE
          SYNTAX  SEQUENCE OF AcDs1FarEndDayEntry
          MAX-ACCESS  not-accessible
          STATUS  current
          DESCRIPTION
                 "The DS1  Far End Day Table contains various
                 statistics collected by each DS1 interface over
                 the previous 30 days of operation. Each row in this 
                 table represents a one day interval (identified by 
                 acDs1FarEndDayNumber).  This table is created 
                 automatically."
          ::= { acDs1 5 }

     acDs1FarEndDayEntry OBJECT-TYPE
          SYNTAX  AcDs1FarEndDayEntry
          MAX-ACCESS  not-accessible
          STATUS  current
          DESCRIPTION
                 "An entry in the DS1 Far End Day table."

          INDEX   { acDs1FarEndDayNodeId,
                    acDs1FarEndDaySlot,
                    acDs1FarEndDayPort,
                    acDs1FarEndDayNumber }
          ::= { acDs1FarEndDayTable 1 }

     AcDs1FarEndDayEntry ::=
          SEQUENCE {
              acDs1FarEndDayNodeId      AcNodeId,
              acDs1FarEndDaySlot        AcSlotNumber,
              acDs1FarEndDayPort        AcPortNumber,
              acDs1FarEndDayNumber      INTEGER,
              acDs1FarEndDayValidStats  TruthValue,
              acDs1FarEndDayResetStats  TruthValue,
              acDs1FarEndDayESs         PerfIntervalCount,
              acDs1FarEndDaySESs        PerfIntervalCount,
              acDs1FarEndDaySEFSs       PerfIntervalCount,
              acDs1FarEndDayUASs        PerfIntervalCount,
              acDs1FarEndDayCSSs        PerfIntervalCount,
              acDs1FarEndDayLESs        PerfIntervalCount,
              acDs1FarEndDayPCVs        PerfIntervalCount,
              acDs1FarEndDayBESs        PerfIntervalCount,
              acDs1FarEndDayDMs         PerfIntervalCount
     }


     acDs1FarEndDayNodeId OBJECT-TYPE
          SYNTAX  AcNodeId
          MAX-ACCESS  accessible-for-notify
          STATUS  current
          DESCRIPTION
                 "The node id is the id for this specific node in the OSAP 
                 ring."
          ::= { acDs1FarEndDayEntry 1 }

     acDs1FarEndDaySlot OBJECT-TYPE
          SYNTAX  AcSlotNumber
          MAX-ACCESS  accessible-for-notify
          STATUS  current
          DESCRIPTION
                 "The physical slot number of the port."
          ::= { acDs1FarEndDayEntry 2 }

     acDs1FarEndDayPort OBJECT-TYPE
          SYNTAX  AcPortNumber
          MAX-ACCESS  accessible-for-notify
          STATUS  current
          DESCRIPTION
                 "The physical port number of the port."
          ::= { acDs1FarEndDayEntry 3 }

     acDs1FarEndDayNumber OBJECT-TYPE
          SYNTAX  INTEGER (1..31)
          MAX-ACCESS  accessible-for-notify
          STATUS  current
          DESCRIPTION
                 "A number between 1 and 31, where 1 is current
                 24 hour day interval in progress, 2 is the most
                 recently completed 24 hour day interval and 31 is
                 the 24 hour day interval completed 29 days prior 
                 to interval 2."
          ::= { acDs1FarEndDayEntry 4 }

     acDs1FarEndDayValidStats OBJECT-TYPE
          SYNTAX TruthValue
          MAX-ACCESS read-only
          STATUS current
          DESCRIPTION
                 "This variable indicates if the data for this
                 interval is valid."
          ::= { acDs1FarEndDayEntry 5 }

     acDs1FarEndDayResetStats OBJECT-TYPE
          SYNTAX TruthValue
          MAX-ACCESS read-write
          STATUS current
          DESCRIPTION
                 "This variable allows the data for the current
                 day (acDs1FarEndDayIndex = 1) to be reset.
                 The acDs1FarEndDayValidFlag will be set to False
                 after the reset for the current interval.  This 
                 field has no effect on acDs1FarEndDayIndex 2..31. 
                 This field will always show a value of false when read."
          ::= { acDs1FarEndDayEntry 6 }

     acDs1FarEndDayESs OBJECT-TYPE
          SYNTAX  PerfIntervalCount
          MAX-ACCESS  read-only
          STATUS  current
          DESCRIPTION
                 "The number of Far End Errored Seconds."
          ::= { acDs1FarEndDayEntry 7 }

     acDs1FarEndDaySESs OBJECT-TYPE
          SYNTAX  PerfIntervalCount
          MAX-ACCESS  read-only
          STATUS  current
          DESCRIPTION
                 "The number of Far End Severely Errored Seconds."
          ::= { acDs1FarEndDayEntry 8 }

     acDs1FarEndDaySEFSs OBJECT-TYPE
          SYNTAX  PerfIntervalCount
          MAX-ACCESS  read-only
          STATUS  current
          DESCRIPTION
                 "The number of Far End Severely Errored Framing
                 Seconds."
          ::= { acDs1FarEndDayEntry 9 }

     acDs1FarEndDayUASs OBJECT-TYPE
          SYNTAX  PerfIntervalCount
          MAX-ACCESS  read-only
          STATUS  current
          DESCRIPTION
                 "The number of Unavailable Seconds."
          ::= { acDs1FarEndDayEntry 10 }

     acDs1FarEndDayCSSs OBJECT-TYPE
          SYNTAX  PerfIntervalCount
          MAX-ACCESS  read-only
          STATUS  current
          DESCRIPTION
                 "The number of Far End Controlled Slip Seconds."
          ::= { acDs1FarEndDayEntry 11 }

     acDs1FarEndDayLESs OBJECT-TYPE
          SYNTAX  PerfIntervalCount
          MAX-ACCESS  read-only
          STATUS  current
          DESCRIPTION
                 "The number of Far End Line Errored Seconds."

          ::= { acDs1FarEndDayEntry 12 }

     acDs1FarEndDayPCVs OBJECT-TYPE
          SYNTAX  PerfIntervalCount
          MAX-ACCESS  read-only
          STATUS  current
          DESCRIPTION
                 "The number of Far End Path Coding Violations."
          ::= { acDs1FarEndDayEntry 13 }

     acDs1FarEndDayBESs OBJECT-TYPE
          SYNTAX PerfIntervalCount
          MAX-ACCESS read-only
          STATUS current
          DESCRIPTION
                 "The number of Far End Bursty Errored Seconds."
          ::= { acDs1FarEndDayEntry 14 }

     acDs1FarEndDayDMs OBJECT-TYPE
          SYNTAX PerfIntervalCount
          MAX-ACCESS read-only
          STATUS current
          DESCRIPTION
                 "The number of Far End Degraded Minutes."
          ::= { acDs1FarEndDayEntry 15 }


     --
     -- The Appian DS1  Threshold Table
     -- 


     acDs1ThresholdTable OBJECT-TYPE
          SYNTAX SEQUENCE OF AcDs1ThresholdEntry
          MAX-ACCESS  not-accessible
          STATUS  current
          DESCRIPTION
                 "The Appian DS1  Threshold Table allows the 
                 user to configure the threshold values for each of the 
                 statistics found in the interval table base on
                 the 15 minute interval on the day.  This table is
                 created automatically."
          ::= { acDs1 6 }

     acDs1ThresholdEntry OBJECT-TYPE
          SYNTAX  AcDs1ThresholdEntry
          MAX-ACCESS  not-accessible
          STATUS  current
          DESCRIPTION
                 "An entry in the Appian DS1 Threshold table."
          INDEX   { acDs1ThresholdNodeId,
                    acDs1ThresholdSlot,  
                    acDs1ThresholdPort}
          ::= { acDs1ThresholdTable 1 }

     AcDs1ThresholdEntry ::=
          SEQUENCE {
              acDs1ThresholdNodeId                 AcNodeId,
              acDs1ThresholdSlot                   AcSlotNumber,
              acDs1ThresholdPort                   AcPortNumber,
              acDs1ThresholdNEIntervalESs          INTEGER,
              acDs1ThresholdNEIntervalSESs         INTEGER,
              acDs1ThresholdNEIntervalSEFSs        INTEGER,
              acDs1ThresholdNEIntervalUASs         INTEGER,
              acDs1ThresholdNEIntervalCSSs         INTEGER,
              acDs1ThresholdNEIntervalPCVs         INTEGER,
              acDs1ThresholdNEIntervalLESs         INTEGER,
              acDs1ThresholdNEIntervalBESs         INTEGER,
              acDs1ThresholdNEIntervalDMs          INTEGER,
              acDs1ThresholdNEIntervalLCVs         INTEGER,
              acDs1ThresholdNEDayESs               INTEGER,
              acDs1ThresholdNEDaySESs              INTEGER,
              acDs1ThresholdNEDaySEFSs             INTEGER,
              acDs1ThresholdNEDayUASs              INTEGER,
              acDs1ThresholdNEDayCSSs              INTEGER,
              acDs1ThresholdNEDayPCVs              INTEGER,
              acDs1ThresholdNEDayLESs              INTEGER,
              acDs1ThresholdNEDayBESs              INTEGER,
              acDs1ThresholdNEDayDMs               INTEGER,
              acDs1ThresholdNEDayLCVs              INTEGER,
              acDs1ThresholdFEIntervalESs          INTEGER,
              acDs1ThresholdFEIntervalSESs         INTEGER,
              acDs1ThresholdFEIntervalSEFSs        INTEGER,
              acDs1ThresholdFEIntervalUASs         INTEGER,
              acDs1ThresholdFEIntervalCSSs         INTEGER,
              acDs1ThresholdFEIntervalLESs         INTEGER,
              acDs1ThresholdFEIntervalPCVs         INTEGER,
              acDs1ThresholdFEIntervalBESs         INTEGER,
              acDs1ThresholdFEIntervalDMs          INTEGER,
              acDs1ThresholdFEDayESs               INTEGER,
              acDs1ThresholdFEDaySESs              INTEGER,
              acDs1ThresholdFEDaySEFSs             INTEGER,
              acDs1ThresholdFEDayUASs              INTEGER,
              acDs1ThresholdFEDayCSSs              INTEGER,
              acDs1ThresholdFEDayLESs              INTEGER,
              acDs1ThresholdFEDayPCVs              INTEGER,
              acDs1ThresholdFEDayBESs              INTEGER,
              acDs1ThresholdFEDayDMs               INTEGER
     }


     acDs1ThresholdNodeId OBJECT-TYPE
          SYNTAX  AcNodeId
          MAX-ACCESS  accessible-for-notify
          STATUS  current
          DESCRIPTION
                 "The node id is the id for this specific node in the OSAP 
                 ring."
          ::= { acDs1ThresholdEntry 1 }

     acDs1ThresholdSlot OBJECT-TYPE
          SYNTAX  AcSlotNumber
          MAX-ACCESS  accessible-for-notify
          STATUS  current
          DESCRIPTION
                 "The physical slot number of the port."
          ::= { acDs1ThresholdEntry 2 }

     acDs1ThresholdPort OBJECT-TYPE
          SYNTAX  AcPortNumber
          MAX-ACCESS  accessible-for-notify
          STATUS  current
          DESCRIPTION
                 "The physical port number of the port."
          ::= { acDs1ThresholdEntry 3 }

     acDs1ThresholdNEIntervalESs OBJECT-TYPE
          SYNTAX  INTEGER
          MAX-ACCESS  read-write
          STATUS  current
          DESCRIPTION
                 "The threshold value for interval number of Errored 
                 Seconds.  A value of 0 disables the threshold mechanism 
                 for this attribute."
          DEFVAL { 0 }
          ::= { acDs1ThresholdEntry 4 }

     acDs1ThresholdNEIntervalSESs OBJECT-TYPE
          SYNTAX  INTEGER
          MAX-ACCESS  read-write
          STATUS  current
          DESCRIPTION
                 "The threshold value for the interval number of 
                 Severely Errored Seconds.  A value of 0 disables the 
                 threshold mechanism for this attribute."
          DEFVAL { 0 }
          ::= { acDs1ThresholdEntry 5 }

     acDs1ThresholdNEIntervalSEFSs OBJECT-TYPE
          SYNTAX  INTEGER
          MAX-ACCESS  read-write
          STATUS  current
          DESCRIPTION
                 "The threshold for the interval number of Severely 
                 Errored Framing Seconds.  A value of 0 disables the 
                 threshold mechanism for this attribute."
          DEFVAL { 0 }
          ::= { acDs1ThresholdEntry 6 }

     acDs1ThresholdNEIntervalUASs OBJECT-TYPE
          SYNTAX  INTEGER
          MAX-ACCESS  read-write
          STATUS  current
          DESCRIPTION
                 "The threshold for the interval number of Unavailable 
                 Seconds.  A value of 0 disables the threshold mechanism 
                 for this attribute."
          DEFVAL { 0 }
          ::= { acDs1ThresholdEntry 7 }

     acDs1ThresholdNEIntervalCSSs OBJECT-TYPE
          SYNTAX  INTEGER
          MAX-ACCESS  read-write
          STATUS  current
          DESCRIPTION
                 "The threshold for the interval number of Controlled 
                 Slip Seconds.  A value of 0 disables the threshold 
                 mechanism for this attribute."
          DEFVAL { 0 }
          ::= { acDs1ThresholdEntry 8 }

     acDs1ThresholdNEIntervalPCVs OBJECT-TYPE
          SYNTAX  INTEGER
          MAX-ACCESS  read-write
          STATUS  current
          DESCRIPTION
                 "The threshold for the interval number of Path Coding 
                 Violations.  A value of 0 disables the threshold 
                 mechanism for this attribute."
          DEFVAL { 0 }
          ::= { acDs1ThresholdEntry 9 }

     acDs1ThresholdNEIntervalLESs OBJECT-TYPE
          SYNTAX  INTEGER
          MAX-ACCESS  read-write
          STATUS  current
          DESCRIPTION
                 "The threshold value for the interval number of 
                 Line Errored Seconds.  A value of 0 disables the 
                 threshold mechanism for this attribute."
          DEFVAL { 0 }
          ::= { acDs1ThresholdEntry 10 }

     acDs1ThresholdNEIntervalBESs OBJECT-TYPE
          SYNTAX INTEGER
          MAX-ACCESS read-write
          STATUS current
          DESCRIPTION
                 "The threshold for the interval number of Bursty Errored 
                 Seconds.  A value of 0 disables the threshold mechanism 
                 for this attribute."
          DEFVAL { 0 }
          ::= { acDs1ThresholdEntry 11 }


     acDs1ThresholdNEIntervalDMs OBJECT-TYPE
          SYNTAX INTEGER
          MAX-ACCESS read-write
          STATUS current
          DESCRIPTION
                 "The threshold for the interval number of Degraded 
                 Minutes.  A value of 0 disables the threshold mechanism 
                 for this attribute."
          DEFVAL { 0 }
          ::= { acDs1ThresholdEntry 12 }

     acDs1ThresholdNEIntervalLCVs OBJECT-TYPE
          SYNTAX INTEGER
          MAX-ACCESS read-write
          STATUS current
          DESCRIPTION
                 "The threshold for the interval number of Line Code 
                 Violations.  A value of 0 disables the threshold mechanism 
                 for this attribute."
          DEFVAL { 0 }
          ::= { acDs1ThresholdEntry 13 }

     acDs1ThresholdNEDayESs OBJECT-TYPE
          SYNTAX  INTEGER
          MAX-ACCESS  read-write
          STATUS  current
          DESCRIPTION
                 "The threshold value for day number of Errored Seconds.
                 A value of 0 disables the threshold mechanism for this 
                 attribute."
          DEFVAL { 0 }
          ::= { acDs1ThresholdEntry 14 }

     acDs1ThresholdNEDaySESs OBJECT-TYPE
          SYNTAX  INTEGER
          MAX-ACCESS  read-write
          STATUS  current
          DESCRIPTION
                 "The threshold for the day number of Severely Errored 
                 Seconds.  A value of 0 disables the threshold mechanism 
                 for this attribute."
          DEFVAL { 0 }
          ::= { acDs1ThresholdEntry 15 }

     acDs1ThresholdNEDaySEFSs OBJECT-TYPE
          SYNTAX  INTEGER
          MAX-ACCESS  read-write
          STATUS  current
          DESCRIPTION
                 "The threshold value for the day number of Severely 
                 Errored Framing Seconds.  A value of 0 disables the 
                 threshold mechanism for this attribute."
          DEFVAL { 0 }
          ::= { acDs1ThresholdEntry 16 }

     acDs1ThresholdNEDayUASs OBJECT-TYPE
          SYNTAX  INTEGER
          MAX-ACCESS  read-write
          STATUS  current
          DESCRIPTION
                 "The threshold value for the day number of Unavailable 
                 Seconds.  A value of 0 disables the threshold mechanism 
                 for this attribute."
          DEFVAL { 0 }
          ::= { acDs1ThresholdEntry 17 }

     acDs1ThresholdNEDayCSSs OBJECT-TYPE
          SYNTAX  INTEGER
          MAX-ACCESS  read-write
          STATUS  current
          DESCRIPTION
                 "The threshold for the day number of Controlled Slip 
                 Seconds.  A value of 0 disables the threshold mechanism 
                 for this attribute."
          DEFVAL { 0 }
          ::= { acDs1ThresholdEntry 18 }

     acDs1ThresholdNEDayPCVs OBJECT-TYPE
          SYNTAX  INTEGER
          MAX-ACCESS  read-write
          STATUS  current
          DESCRIPTION
                 "The threshold value for the day number of Path Coding 
                 Violations.  A value of 0 disables the threshold mechanism 
                 for this attribute."
          DEFVAL { 0 }
          ::= { acDs1ThresholdEntry 19 }

     acDs1ThresholdNEDayLESs OBJECT-TYPE
          SYNTAX  INTEGER
          MAX-ACCESS  read-write
          STATUS  current
          DESCRIPTION
                 "The threshold for the day number of Line Errored Seconds.
                 A value of 0 disables the threshold mechanism for this 
                 attribute."
          DEFVAL { 0 }
          ::= { acDs1ThresholdEntry 20 }

     acDs1ThresholdNEDayBESs OBJECT-TYPE
          SYNTAX INTEGER
          MAX-ACCESS read-write
          STATUS current
          DESCRIPTION
                 "The threshold for the day number of Bursty Errored 
                 Seconds.  A value of 0 disables the threshold mechanism 
                 for this attribute."
          DEFVAL { 0 }
          ::= { acDs1ThresholdEntry 21 }

     acDs1ThresholdNEDayDMs OBJECT-TYPE
          SYNTAX INTEGER
          MAX-ACCESS read-write
          STATUS current
          DESCRIPTION
                 "The threshold for the day number of Degraded Minutes.
                 A value of 0 disables the threshold mechanism for this 
                 attribute."
          DEFVAL { 0 }
          ::= { acDs1ThresholdEntry 22 }

     acDs1ThresholdNEDayLCVs OBJECT-TYPE
          SYNTAX INTEGER
          MAX-ACCESS read-write
          STATUS current
          DESCRIPTION
                 "The threshold for the day number of Line Code Violations.
                 A value of 0 disables the threshold mechanism for this 
                 attribute."
          DEFVAL { 0 }
          ::= { acDs1ThresholdEntry 23 }

     acDs1ThresholdFEIntervalESs OBJECT-TYPE
          SYNTAX  INTEGER
          MAX-ACCESS  read-write
          STATUS  current
          DESCRIPTION
                 "The threshold for the far end interval number of 
                 Far End Errored Seconds.  A value of 0 disables the 
                 threshold mechanism for this attribute."
          DEFVAL { 0 }
          ::= { acDs1ThresholdEntry 24 }

     acDs1ThresholdFEIntervalSESs OBJECT-TYPE
          SYNTAX  INTEGER
          MAX-ACCESS  read-write
          STATUS  current
          DESCRIPTION
                 "The threshold for the far end interval number of Far
                 End Severely Errored Seconds.  A value of 0 disables 
                 the threshold mechanism for this attribute."
          DEFVAL { 0 }
          ::= { acDs1ThresholdEntry 25 }

     acDs1ThresholdFEIntervalSEFSs OBJECT-TYPE
          SYNTAX  INTEGER
          MAX-ACCESS  read-write
          STATUS  current
          DESCRIPTION
                 "The threshold for the far end interval number of Far 
                 End Severely Errored Framing Seconds.  A value of 0 
                 disables the threshold mechanism for this attribute."
          DEFVAL { 0 }
          ::= { acDs1ThresholdEntry 26 }

     acDs1ThresholdFEIntervalUASs OBJECT-TYPE
          SYNTAX  INTEGER
          MAX-ACCESS  read-write
          STATUS  current
          DESCRIPTION
                 "The threshold value for the far end interval number of 
                 Unavailable Seconds.  A value of 0 disables the threshold 
                 mechanism for this attribute."
          DEFVAL { 0 }
          ::= { acDs1ThresholdEntry 27 }

     acDs1ThresholdFEIntervalCSSs OBJECT-TYPE
          SYNTAX  INTEGER
          MAX-ACCESS  read-write
          STATUS  current
          DESCRIPTION
                 "The threshold value for the far end interval number of 
                 Far End Controlled Slip Seconds.  A value of 0 disables  
                 the threshold mechanism for this attribute."
          DEFVAL { 0 }
          ::= { acDs1ThresholdEntry 28 }

     acDs1ThresholdFEIntervalLESs OBJECT-TYPE
          SYNTAX  INTEGER
          MAX-ACCESS  read-write
          STATUS  current
          DESCRIPTION
                 "The threshold value for the far end interal number of 
                 Far End Line Errored Seconds.  A value of 0 disables 
                 the threshold mechanism for this attribute."
          DEFVAL { 0 }
          ::= { acDs1ThresholdEntry 29 }

     acDs1ThresholdFEIntervalPCVs OBJECT-TYPE
          SYNTAX  INTEGER
          MAX-ACCESS  read-write
          STATUS  current
          DESCRIPTION
                 "The threshold for the far end internal number of Far
                 End Path Coding Violations.  A value of 0 disables the 
                 threshold mechanism for this attribute."
          DEFVAL { 0 }
          ::= { acDs1ThresholdEntry 30 }

     acDs1ThresholdFEIntervalBESs OBJECT-TYPE
          SYNTAX INTEGER
          MAX-ACCESS read-write
          STATUS current
          DESCRIPTION
                 "The threshold for the far end interval number of Far 
                 End Bursty Errored Seconds.  A value of 0 disables the 
                 threshold mechanism for this attribute."
          DEFVAL { 0 }
          ::= { acDs1ThresholdEntry 31 }

     acDs1ThresholdFEIntervalDMs OBJECT-TYPE
          SYNTAX INTEGER
          MAX-ACCESS read-write
          STATUS current
          DESCRIPTION
                 "The threshold for the far end interval number of Far 
                 End Degraded Minutes.  A value of 0 disables the 
                 threshold mechanism for this attribute."
          DEFVAL { 0 }
          ::= { acDs1ThresholdEntry 32 }

     acDs1ThresholdFEDayESs OBJECT-TYPE
          SYNTAX  INTEGER
          MAX-ACCESS  read-write
          STATUS  current
          DESCRIPTION
                 "The threshold for the far end day number of 
                 Far End Errored Seconds.  A value of 0 disables the 
                 threshold mechanism for this attribute."
          DEFVAL { 0 }
          ::= { acDs1ThresholdEntry 33 }

     acDs1ThresholdFEDaySESs OBJECT-TYPE
          SYNTAX  INTEGER
          MAX-ACCESS  read-write
          STATUS  current
          DESCRIPTION
                 "The threshold for the far end day number of Far
                 End Severely Errored Seconds.  A value of 0 disables 
                 the threshold mechanism for this attribute."
          DEFVAL { 0 }
          ::= { acDs1ThresholdEntry 34 }

     acDs1ThresholdFEDaySEFSs OBJECT-TYPE
          SYNTAX  INTEGER
          MAX-ACCESS  read-write
          STATUS  current
          DESCRIPTION
                 "The threshold for the far end day number of Far 
                 End Severely Errored Framing Seconds.  A value of 0 
                 disables the threshold mechanism for this attribute."
          DEFVAL { 0 }
          ::= { acDs1ThresholdEntry 35 }

     acDs1ThresholdFEDayUASs OBJECT-TYPE
          SYNTAX  INTEGER
          MAX-ACCESS  read-write
          STATUS  current
          DESCRIPTION
                 "The threshold value for the far end day number of 
                 Unavailable Seconds.  A value of 0 disables the  
                 threshold mechanism for this attribute."
          DEFVAL { 0 }
          ::= { acDs1ThresholdEntry 36 }

     acDs1ThresholdFEDayCSSs OBJECT-TYPE
          SYNTAX  INTEGER
          MAX-ACCESS  read-write
          STATUS  current
          DESCRIPTION
                 "The threshold value for the far end day number of 
                 Far End Controlled Slip Seconds.  A value of 0 disables 
                 the threshold mechanism for this attribute."
          DEFVAL { 0 }
          ::= { acDs1ThresholdEntry 37 }

     acDs1ThresholdFEDayLESs OBJECT-TYPE
          SYNTAX  INTEGER
          MAX-ACCESS  read-write
          STATUS  current
          DESCRIPTION
                 "The threshold value for the far end interal number of 
                 Far End Line Errored Seconds.  A value of 0 disables 
                 the threshold mechanism for this attribute."
          DEFVAL { 0 }
          ::= { acDs1ThresholdEntry 38 }

     acDs1ThresholdFEDayPCVs OBJECT-TYPE
          SYNTAX  INTEGER
          MAX-ACCESS  read-write
          STATUS  current
          DESCRIPTION
                 "The threshold for the far end internal number of Far
                 End Path Coding Violations.  A value of 0 disables the 
                 threshold mechanism for this attribute."
          DEFVAL { 0 }
          ::= { acDs1ThresholdEntry 39 }

     acDs1ThresholdFEDayBESs OBJECT-TYPE
          SYNTAX INTEGER
          MAX-ACCESS read-write
          STATUS current
          DESCRIPTION
                 "The threshold for the far end day number of Far 
                 End Bursty Errored Seconds.  A value of 0 disables 
                 the threshold mechanism for this attribute."
          DEFVAL { 0 }
          ::= { acDs1ThresholdEntry 40 }

     acDs1ThresholdFEDayDMs OBJECT-TYPE
          SYNTAX INTEGER
          MAX-ACCESS read-write
          STATUS current
          DESCRIPTION
                 "The threshold for the far end day number of Far 
                 End Degraded Minutes.  A value of 0 disables the 
                 threshold mechanism for this attribute."
          DEFVAL { 0 }
          ::= { acDs1ThresholdEntry 41 }



-- 
--   Ds1 TRAPS
--
--

acDs1Traps   OBJECT IDENTIFIER ::= { acDs1 0 }


acDs1LineStatusChangeTrap NOTIFICATION-TYPE
    OBJECTS { acChassisCurrentTime, acChassisRingId, acDs1ConfigNodeId,
              acDs1ConfigSlot,
              acDs1ConfigPort,
              acDs1ConfigLineStatus, 
              acDs1ConfigLineStatusLastChange }
    STATUS  current
    DESCRIPTION
    "An acLogcialDs1LineStatusChange trap is sent when the value of an 
    instance acDs1ConfigLineStatus changes. It can be utilized by 
    an NMS to trigger polls."

    ::= { acDs1Traps 1 }

acDs1StatsResetTrap  NOTIFICATION-TYPE 
    OBJECTS { acChassisCurrentTime, acChassisRingId, acDs1ConfigNodeId,
              acDs1ConfigSlot,
              acDs1ConfigPort }
    STATUS  current
    DESCRIPTION
    "The  Ds1 statistics for this interface have been reset to zero (0) 
    which may effect long term trending functions monitoring this interface."
    
    ::= { acDs1Traps 2 }

acDs1CfgErrorTrap  NOTIFICATION-TYPE 
    OBJECTS { acChassisCurrentTime, acChassisRingId, acDs1ConfigNodeId,
              acDs1ConfigSlot,
              acDs1ConfigPort }
    STATUS  current
    DESCRIPTION
    "A configuration request to the  Ds1 configuration table for an 
    interface has been detected as invalid or corrupt."
    
    ::= { acDs1Traps 3 }


acDs1LinkDownTrap  NOTIFICATION-TYPE
    OBJECTS { acChassisCurrentTime, acChassisRingId, acDs1ConfigNodeId,
              acDs1ConfigSlot,
              acDs1ConfigPort }
    STATUS  current
    DESCRIPTION
    "The link for this physical ds1 interface has obtained sync."

    ::= { acDs1Traps 4 }

acDs1LinkUpTrap  NOTIFICATION-TYPE
    OBJECTS { acChassisCurrentTime, acChassisRingId, acDs1ConfigNodeId,
              acDs1ConfigSlot,
              acDs1ConfigPort }
    STATUS  current
    DESCRIPTION
    "The link for this physical ds1 interface has been lost."

    ::= { acDs1Traps 5 }

acDs1ExceededThresholdNEIntervalESsTrap NOTIFICATION-TYPE
    OBJECTS { acChassisCurrentTime, acChassisRingId, acDs1ThresholdNodeId,
              acDs1ThresholdSlot,
              acDs1ThresholdPort }
    STATUS  current
    DESCRIPTION
    "The threshold value speficed has been exceeded for this interface."

    ::= { acDs1Traps 7 }
        
acDs1ExceededThresholdNEIntervalSESsTrap NOTIFICATION-TYPE
    OBJECTS { acChassisCurrentTime, acChassisRingId, acDs1ThresholdNodeId,
              acDs1ThresholdSlot,
              acDs1ThresholdPort }
    STATUS  current
    DESCRIPTION
    "The threshold value speficed has been exceeded for this interface."

    ::= { acDs1Traps 8 }
        
acDs1ExceededThresholdNEIntervalSEFSsTrap NOTIFICATION-TYPE
    OBJECTS { acChassisCurrentTime, acChassisRingId, acDs1ThresholdNodeId,
              acDs1ThresholdSlot,
              acDs1ThresholdPort }
    STATUS  current
    DESCRIPTION
    "The threshold value speficed has been exceeded for this interface."

    ::= { acDs1Traps 9 }
        
acDs1ExceededThresholdNEIntervalUASsTrap NOTIFICATION-TYPE
    OBJECTS { acChassisCurrentTime, acChassisRingId, acDs1ThresholdNodeId,
              acDs1ThresholdSlot,
              acDs1ThresholdPort }
    STATUS  current
    DESCRIPTION
    "The threshold value speficed has been exceeded for this interface."

    ::= { acDs1Traps 10 }
        
acDs1ExceededThresholdNEIntervalCSSsTrap NOTIFICATION-TYPE
    OBJECTS { acChassisCurrentTime, acChassisRingId, acDs1ThresholdNodeId,
              acDs1ThresholdSlot,
              acDs1ThresholdPort }
    STATUS  current
    DESCRIPTION
    "The threshold value speficed has been exceeded for this interface."

    ::= { acDs1Traps 11 }
        
acDs1ExceededThresholdNEIntervalPCVsTrap NOTIFICATION-TYPE
    OBJECTS { acChassisCurrentTime, acChassisRingId, acDs1ThresholdNodeId,
              acDs1ThresholdSlot,
              acDs1ThresholdPort }
    STATUS  current
    DESCRIPTION
    "The threshold value speficed has been exceeded for this interface."

    ::= { acDs1Traps 12 }
        
acDs1ExceededThresholdNEIntervalLESsTrap NOTIFICATION-TYPE
    OBJECTS { acChassisCurrentTime, acChassisRingId, acDs1ThresholdNodeId,
              acDs1ThresholdSlot,
              acDs1ThresholdPort }
    STATUS  current
    DESCRIPTION
    "The threshold value speficed has been exceeded for this interface."

    ::= { acDs1Traps 13 }
        
acDs1ExceededThresholdNEIntervalBESsTrap NOTIFICATION-TYPE
    OBJECTS { acChassisCurrentTime, acChassisRingId, acDs1ThresholdNodeId,
              acDs1ThresholdSlot,
              acDs1ThresholdPort }
    STATUS  current
    DESCRIPTION
    "The threshold value speficed has been exceeded for this interface."

    ::= { acDs1Traps 14 }
        
acDs1ExceededThresholdNEIntervalDMsTrap NOTIFICATION-TYPE
    OBJECTS { acChassisCurrentTime, acChassisRingId, acDs1ThresholdNodeId,
              acDs1ThresholdSlot,
              acDs1ThresholdPort }
    STATUS  current
    DESCRIPTION
    "The threshold value speficed has been exceeded for this interface."

    ::= { acDs1Traps 15 }
        
acDs1ExceededThresholdNEIntervalLCVsTrap NOTIFICATION-TYPE
    OBJECTS { acChassisCurrentTime, acChassisRingId, acDs1ThresholdNodeId,
              acDs1ThresholdSlot,
              acDs1ThresholdPort }
    STATUS  current
    DESCRIPTION
    "The threshold value speficed has been exceeded for this interface."

    ::= { acDs1Traps 16 }
        
acDs1ExceededThresholdNEDayESsTrap NOTIFICATION-TYPE
    OBJECTS { acChassisCurrentTime, acChassisRingId, acDs1ThresholdNodeId,
              acDs1ThresholdSlot,
              acDs1ThresholdPort }
    STATUS  current
    DESCRIPTION
    "The threshold value speficed has been exceeded for this interface."

    ::= { acDs1Traps 17 }
        
acDs1ExceededThresholdNEDaySESsTrap NOTIFICATION-TYPE
    OBJECTS { acChassisCurrentTime, acChassisRingId, acDs1ThresholdNodeId,
              acDs1ThresholdSlot,
              acDs1ThresholdPort }
    STATUS  current
    DESCRIPTION
    "The threshold value speficed has been exceeded for this interface."

    ::= { acDs1Traps 18 }
        
acDs1ExceededThresholdNEDaySEFSTrap NOTIFICATION-TYPE
    OBJECTS { acChassisCurrentTime, acChassisRingId, acDs1ThresholdNodeId,
              acDs1ThresholdSlot,
              acDs1ThresholdPort }
    STATUS  current
    DESCRIPTION
    "The threshold value speficed has been exceeded for this interface."

    ::= { acDs1Traps 19 }
        
acDs1ExceededThresholdNEDayUASsTrap NOTIFICATION-TYPE
    OBJECTS { acChassisCurrentTime, acChassisRingId, acDs1ThresholdNodeId,
              acDs1ThresholdSlot,
              acDs1ThresholdPort }
    STATUS  current
    DESCRIPTION
    "The threshold value speficed has been exceeded for this interface."

    ::= { acDs1Traps 20 }
        
acDs1ExceededThresholdNEDayCSSsTrap NOTIFICATION-TYPE
    OBJECTS { acChassisCurrentTime, acChassisRingId, acDs1ThresholdNodeId,
              acDs1ThresholdSlot,
              acDs1ThresholdPort }
    STATUS  current
    DESCRIPTION
    "The threshold value speficed has been exceeded for this interface."

    ::= { acDs1Traps 21 }
        
acDs1ExceededThresholdNEDayPCVsTrap NOTIFICATION-TYPE
    OBJECTS { acChassisCurrentTime, acChassisRingId, acDs1ThresholdNodeId,
              acDs1ThresholdSlot,
              acDs1ThresholdPort }
    STATUS  current
    DESCRIPTION
    "The threshold value speficed has been exceeded for this interface."

    ::= { acDs1Traps 22 }
        
acDs1ExceededThresholdNEDayLESsTrap NOTIFICATION-TYPE
    OBJECTS { acChassisCurrentTime, acChassisRingId, acDs1ThresholdNodeId,
              acDs1ThresholdSlot,
              acDs1ThresholdPort }
    STATUS  current
    DESCRIPTION
    "The threshold value speficed has been exceeded for this interface."

    ::= { acDs1Traps 23 }
        
acDs1ExceededThresholdNEDayBESsTrap NOTIFICATION-TYPE
    OBJECTS { acChassisCurrentTime, acChassisRingId, acDs1ThresholdNodeId,
              acDs1ThresholdSlot,
              acDs1ThresholdPort }
    STATUS  current
    DESCRIPTION
    "The threshold value speficed has been exceeded for this interface."

    ::= { acDs1Traps 24 }
        
acDs1ExceededThresholdNEDayDMsTrap NOTIFICATION-TYPE
    OBJECTS { acChassisCurrentTime, acChassisRingId, acDs1ThresholdNodeId,
              acDs1ThresholdSlot,
              acDs1ThresholdPort }
    STATUS  current
    DESCRIPTION
    "The threshold value speficed has been exceeded for this interface."

    ::= { acDs1Traps 25 }
        
acDs1ExceededThresholdNEDayLCVsTrap NOTIFICATION-TYPE
    OBJECTS { acChassisCurrentTime, acChassisRingId, acDs1ThresholdNodeId,
              acDs1ThresholdSlot,
              acDs1ThresholdPort }
    STATUS  current
    DESCRIPTION
    "The threshold value speficed has been exceeded for this interface."

    ::= { acDs1Traps 26 }
        
acDs1ExceededThresholdFEIntervalESsTrap NOTIFICATION-TYPE
    OBJECTS { acChassisCurrentTime, acChassisRingId, acDs1ThresholdNodeId,
              acDs1ThresholdSlot,
              acDs1ThresholdPort }
    STATUS  current
    DESCRIPTION
    "The threshold value speficed has been exceeded for this interface."

    ::= { acDs1Traps 27 }
        
acDs1ExceededThresholdFEIntervalSESsTrap NOTIFICATION-TYPE
    OBJECTS { acChassisCurrentTime, acChassisRingId, acDs1ThresholdNodeId,
              acDs1ThresholdSlot,
              acDs1ThresholdPort }
    STATUS  current
    DESCRIPTION
    "The threshold value speficed has been exceeded for this interface."

    ::= { acDs1Traps 28 }
        
acDs1ExceededThresholdFEIntervalSEFSsTrap NOTIFICATION-TYPE
    OBJECTS { acChassisCurrentTime, acChassisRingId, acDs1ThresholdNodeId,
              acDs1ThresholdSlot,
              acDs1ThresholdPort }
    STATUS  current
    DESCRIPTION
    "The threshold value speficed has been exceeded for this interface."

    ::= { acDs1Traps 29 }
        
acDs1ExceededThresholdFEIntervalUASsTrap NOTIFICATION-TYPE
    OBJECTS { acChassisCurrentTime, acChassisRingId, acDs1ThresholdNodeId,
              acDs1ThresholdSlot,
              acDs1ThresholdPort }
    STATUS  current
    DESCRIPTION
    "The threshold value speficed has been exceeded for this interface."

    ::= { acDs1Traps 30 }
        
acDs1ExceededThresholdFEIntervalCSSsTrap NOTIFICATION-TYPE
    OBJECTS { acChassisCurrentTime, acChassisRingId, acDs1ThresholdNodeId,
              acDs1ThresholdSlot,
              acDs1ThresholdPort }
    STATUS  current
    DESCRIPTION
    "The threshold value speficed has been exceeded for this interface."

    ::= { acDs1Traps 31 }
        
acDs1ExceededThresholdFEIntervalLESsTrap NOTIFICATION-TYPE
    OBJECTS { acChassisCurrentTime, acChassisRingId, acDs1ThresholdNodeId,
              acDs1ThresholdSlot,
              acDs1ThresholdPort }
    STATUS  current
    DESCRIPTION
    "The threshold value speficed has been exceeded for this interface."

    ::= { acDs1Traps 32 }
        
acDs1ExceededThresholdFEIntervalPCVsTrap NOTIFICATION-TYPE
    OBJECTS { acChassisCurrentTime, acChassisRingId, acDs1ThresholdNodeId,
              acDs1ThresholdSlot,
              acDs1ThresholdPort }
    STATUS  current
    DESCRIPTION
    "The threshold value speficed has been exceeded for this interface."

    ::= { acDs1Traps 33 }
        
acDs1ExceededThresholdFEIntervalBESsTrap NOTIFICATION-TYPE
    OBJECTS { acChassisCurrentTime, acChassisRingId, acDs1ThresholdNodeId,
              acDs1ThresholdSlot,
              acDs1ThresholdPort }
    STATUS  current
    DESCRIPTION
    "The threshold value speficed has been exceeded for this interface."

    ::= { acDs1Traps 34 }
        
acDs1ExceededThresholdFEIntervalDMsTrap NOTIFICATION-TYPE
    OBJECTS { acChassisCurrentTime, acChassisRingId, acDs1ThresholdNodeId,
              acDs1ThresholdSlot,
              acDs1ThresholdPort }
    STATUS  current
    DESCRIPTION
    "The threshold value speficed has been exceeded for this interface."

    ::= { acDs1Traps 35 }
        
acDs1ExceededThresholdFEDayESsTrap NOTIFICATION-TYPE
    OBJECTS { acChassisCurrentTime, acChassisRingId, acDs1ThresholdNodeId,
              acDs1ThresholdSlot,
              acDs1ThresholdPort }
    STATUS  current
    DESCRIPTION
    "The threshold value speficed has been exceeded for this interface."

    ::= { acDs1Traps 36 }
        
acDs1ExceededThresholdFEDaySESsTrap NOTIFICATION-TYPE
    OBJECTS { acChassisCurrentTime, acChassisRingId, acDs1ThresholdNodeId,
              acDs1ThresholdSlot,
              acDs1ThresholdPort }
    STATUS  current
    DESCRIPTION
    "The threshold value speficed has been exceeded for this interface."

    ::= { acDs1Traps 37 }
        
acDs1ExceededThresholdFEDaySEFSsTrap NOTIFICATION-TYPE
    OBJECTS { acChassisCurrentTime, acChassisRingId, acDs1ThresholdNodeId,
              acDs1ThresholdSlot,
              acDs1ThresholdPort }
    STATUS  current
    DESCRIPTION
    "The threshold value speficed has been exceeded for this interface."

    ::= { acDs1Traps 38 }
        
acDs1ExceededThresholdFEDayUASsTrap NOTIFICATION-TYPE
    OBJECTS { acChassisCurrentTime, acChassisRingId, acDs1ThresholdNodeId,
              acDs1ThresholdSlot,
              acDs1ThresholdPort }
    STATUS  current
    DESCRIPTION
    "The threshold value speficed has been exceeded for this interface."

    ::= { acDs1Traps 39 }
        
acDs1ExceededThresholdFEDayCSSsTrap NOTIFICATION-TYPE
    OBJECTS { acChassisCurrentTime, acChassisRingId, acDs1ThresholdNodeId,
              acDs1ThresholdSlot,
              acDs1ThresholdPort }
    STATUS  current
    DESCRIPTION
    "The threshold value speficed has been exceeded for this interface."

    ::= { acDs1Traps 40 }
        
acDs1ExceededThresholdFEDayLESsTrap NOTIFICATION-TYPE
    OBJECTS { acChassisCurrentTime, acChassisRingId, acDs1ThresholdNodeId,
              acDs1ThresholdSlot,
              acDs1ThresholdPort }
    STATUS  current
    DESCRIPTION
    "The threshold value speficed has been exceeded for this interface."

    ::= { acDs1Traps 41 }
        
acDs1ExceededThresholdFEDayPCVsTrap NOTIFICATION-TYPE
    OBJECTS { acChassisCurrentTime, acChassisRingId, acDs1ThresholdNodeId,
              acDs1ThresholdSlot,
              acDs1ThresholdPort }
    STATUS  current
    DESCRIPTION
    "The threshold value speficed has been exceeded for this interface."

    ::= { acDs1Traps 42 }
        
acDs1ExceededThresholdFEDayBESsTrap NOTIFICATION-TYPE
    OBJECTS { acChassisCurrentTime, acChassisRingId, acDs1ThresholdNodeId,
              acDs1ThresholdSlot,
              acDs1ThresholdPort }
    STATUS  current
    DESCRIPTION
    "The threshold value speficed has been exceeded for this interface."

    ::= { acDs1Traps 43 }
        
acDs1ExceededThresholdFEDayDMsTrap NOTIFICATION-TYPE
    OBJECTS { acChassisCurrentTime, acChassisRingId, acDs1ThresholdNodeId,
              acDs1ThresholdSlot,
              acDs1ThresholdPort }
    STATUS  current
    DESCRIPTION
    "The threshold value speficed has been exceeded for this interface."

    ::= { acDs1Traps 44 }
        

END
