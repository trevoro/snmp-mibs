Nortel-Magellan-Passport-ServerAccessRsaMIB
DEFINITIONS ::= BEGIN



IMPORTS

      OBJECT-TYPE
   FROM RFC-1212

      components,
      passportMIBs
   FROM Nortel-Magellan-Passport-UsefulDefinitionsMIB

      Counter32,
      RowPointer,
      DisplayString,
      StorageType,
      RowStatus,
      Integer32,
      Unsigned32
   FROM Nortel-Magellan-Passport-StandardTextualConventionsMIB

      AsciiString,
      Hex,
      NonReplicated,
      EnterpriseDateAndTime,
      Link,
      AsciiStringIndex,
      DigitString
   FROM Nortel-Magellan-Passport-TextualConventionsMIB;




-- LAST-UPDATED   "9902010000Z"
-- ORGANIZATION   "Nortel"
-- CONTACT-INFO   "
--         Nortel Magellan Network Management
--         
--         Postal: P.O. Box 5080, Station F 
--                 Ottawa, Ontario 
--                 Canada  K2C 3T1
--         
--         Email:  nm_plm@nt.com"
-- DESCRIPTION
--    "The module describing the Nortel Magellan Passport
--     ServerAccessRsa Enterprise MIB."

serverAccessRsaMIB OBJECT IDENTIFIER ::= { passportMIBs 116 }










-- RemoteServerAgent/<string>
-- The Rsa component provides non-Passport based applications 
-- access to Passport servers via a Frame Relay SVC connection. The 
-- Rsa component can be provisioned on any Passport module in the 
-- network. Multiple Rsa components can be provisioned for load 
-- sharing and/or backup purposes. The component instance value is a 
-- unique string within the module.

rsa OBJECT IDENTIFIER ::= { components 108 }



rsaRowStatusTable OBJECT-TYPE
   SYNTAX     SEQUENCE OF RsaRowStatusEntry
   ACCESS     not-accessible
   STATUS     mandatory
   DESCRIPTION
     "This entry controls the addition and deletion of 
      rsa components."
::= { rsa 1 }

rsaRowStatusEntry OBJECT-TYPE
   SYNTAX     RsaRowStatusEntry
   ACCESS     not-accessible
   STATUS     mandatory
   DESCRIPTION
     "A single entry in the table represents a single 
      rsa component."
   INDEX {
      rsaIndex }
::= { rsaRowStatusTable 1 }

RsaRowStatusEntry ::= SEQUENCE {
   rsaRowStatus
      RowStatus,
   rsaComponentName
      DisplayString,
   rsaStorageType
      StorageType,
   rsaIndex
      AsciiStringIndex }

rsaRowStatus OBJECT-TYPE
   SYNTAX     RowStatus 
   ACCESS     read-write
   STATUS     mandatory
   DESCRIPTION
     "This variable is used as the basis for SNMP naming of
      rsa components.
      These components can be added and deleted."
::= { rsaRowStatusEntry 1 }

rsaComponentName OBJECT-TYPE
   SYNTAX     DisplayString 
   ACCESS     read-only
   STATUS     mandatory
   DESCRIPTION
     "This variable provides the component's string name for
      use with the ASCII Console Interface"
::= { rsaRowStatusEntry 2 }

rsaStorageType OBJECT-TYPE
   SYNTAX     StorageType 
   ACCESS     read-only
   STATUS     mandatory
   DESCRIPTION
     "This variable represents the storage type value for the
      rsa tables."
::= { rsaRowStatusEntry 4 }

rsaIndex OBJECT-TYPE
   SYNTAX     AsciiStringIndex (SIZE (1..8))
   ACCESS     not-accessible
   STATUS     mandatory
   DESCRIPTION
     "This variable represents the index for the rsa tables."
::= { rsaRowStatusEntry 10 }

rsaOptionsTable OBJECT-TYPE
   SYNTAX     SEQUENCE OF RsaOptionsEntry
   ACCESS     not-accessible
   STATUS     mandatory
   DESCRIPTION
     "The Options group defines provisionable attributes associated with 
      the Rsa component."
::= { rsa 10 }

rsaOptionsEntry OBJECT-TYPE
   SYNTAX     RsaOptionsEntry
   ACCESS     not-accessible
   STATUS     mandatory
   DESCRIPTION
     "An entry in the rsaOptionsTable."
   INDEX {
      rsaIndex }
::= { rsaOptionsTable 1 }

RsaOptionsEntry ::= SEQUENCE {
   rsaLogicalProcessor
      Link }

rsaLogicalProcessor OBJECT-TYPE
   SYNTAX     Link 
   ACCESS     read-write
   STATUS     mandatory
   DESCRIPTION
     "This attribute specifies the logical processor on which the RSA 
      process will execute."
::= { rsaOptionsEntry 2 }

rsaStateTable OBJECT-TYPE
   SYNTAX     SEQUENCE OF RsaStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { rsa 11 }

rsaStateEntry OBJECT-TYPE
   SYNTAX     RsaStateEntry
   ACCESS     not-accessible
   STATUS     mandatory
   DESCRIPTION
     "An entry in the rsaStateTable."
   INDEX {
      rsaIndex }
::= { rsaStateTable 1 }

RsaStateEntry ::= SEQUENCE {
   rsaAdminState
      INTEGER,
   rsaOperationalState
      INTEGER,
   rsaUsageState
      INTEGER }

rsaAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { rsaStateEntry 1 }

rsaOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { rsaStateEntry 2 }

rsaUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { rsaStateEntry 3 }

rsaOperationalTable OBJECT-TYPE
   SYNTAX     SEQUENCE OF RsaOperationalEntry
   ACCESS     not-accessible
   STATUS     mandatory
   DESCRIPTION
     "The Operational group defines operational attributes associated 
      with the Rsa component."
::= { rsa 12 }

rsaOperationalEntry OBJECT-TYPE
   SYNTAX     RsaOperationalEntry
   ACCESS     not-accessible
   STATUS     mandatory
   DESCRIPTION
     "An entry in the rsaOperationalTable."
   INDEX {
      rsaIndex }
::= { rsaOperationalTable 1 }

RsaOperationalEntry ::= SEQUENCE {
   rsaMaxRsiConnections
      INTEGER,
   rsaRsiConnections
      INTEGER }

rsaMaxRsiConnections OBJECT-TYPE
   SYNTAX     INTEGER (1000)
   ACCESS     read-only
   STATUS     mandatory
   DESCRIPTION
     "This attribute specifies the maximum number of RSI connections 
      which can be supported by this Rsa."
::= { rsaOperationalEntry 2 }

rsaRsiConnections OBJECT-TYPE
   SYNTAX     INTEGER (0..1000)
   ACCESS     read-only
   STATUS     mandatory
   DESCRIPTION
     "This attribute specifies the number of active RSI connections 
      currently supported by the Rsa component."
::= { rsaOperationalEntry 3 }


-- Rsa/n DataNetworkAddress
-- This is the description of the Remote Server Agent Dna component. 
-- It includes the attributes which apply to a Vc between the RSI and 
-- RSA.

rsaDna OBJECT IDENTIFIER ::= { rsa 2 }



rsaDnaRowStatusTable OBJECT-TYPE
   SYNTAX     SEQUENCE OF RsaDnaRowStatusEntry
   ACCESS     not-accessible
   STATUS     mandatory
   DESCRIPTION
     "This entry controls the addition and deletion of 
      rsaDna components."
::= { rsaDna 1 }

rsaDnaRowStatusEntry OBJECT-TYPE
   SYNTAX     RsaDnaRowStatusEntry
   ACCESS     not-accessible
   STATUS     mandatory
   DESCRIPTION
     "A single entry in the table represents a single 
      rsaDna component."
   INDEX {
      rsaIndex,
      rsaDnaIndex }
::= { rsaDnaRowStatusTable 1 }

RsaDnaRowStatusEntry ::= SEQUENCE {
   rsaDnaRowStatus
      RowStatus,
   rsaDnaComponentName
      DisplayString,
   rsaDnaStorageType
      StorageType,
   rsaDnaIndex
      NonReplicated }

rsaDnaRowStatus OBJECT-TYPE
   SYNTAX     RowStatus 
   ACCESS     read-only
   STATUS     mandatory
   DESCRIPTION
     "This variable is used as the basis for SNMP naming of
      rsaDna components.
      These components cannot be added nor deleted."
::= { rsaDnaRowStatusEntry 1 }

rsaDnaComponentName OBJECT-TYPE
   SYNTAX     DisplayString 
   ACCESS     read-only
   STATUS     mandatory
   DESCRIPTION
     "This variable provides the component's string name for
      use with the ASCII Console Interface"
::= { rsaDnaRowStatusEntry 2 }

rsaDnaStorageType OBJECT-TYPE
   SYNTAX     StorageType 
   ACCESS     read-only
   STATUS     mandatory
   DESCRIPTION
     "This variable represents the storage type value for the
      rsaDna tables."
::= { rsaDnaRowStatusEntry 4 }

rsaDnaIndex OBJECT-TYPE
   SYNTAX     NonReplicated 
   ACCESS     not-accessible
   STATUS     mandatory
   DESCRIPTION
     "This variable represents the index for the rsaDna tables."
::= { rsaDnaRowStatusEntry 10 }

rsaDnaAddressTable OBJECT-TYPE
   SYNTAX     SEQUENCE OF RsaDnaAddressEntry
   ACCESS     not-accessible
   STATUS     mandatory
   DESCRIPTION
     "The Address group contains attributes common to all Dna's. Every 
      Dna used in the network is defined with this group of 2 attributes. 
      The string of address digits is complemented by the type of address 
      or Npi. These attributes are used to interpret the format of the 
      address digits."
::= { rsaDna 10 }

rsaDnaAddressEntry OBJECT-TYPE
   SYNTAX     RsaDnaAddressEntry
   ACCESS     not-accessible
   STATUS     mandatory
   DESCRIPTION
     "An entry in the rsaDnaAddressTable."
   INDEX {
      rsaIndex,
      rsaDnaIndex }
::= { rsaDnaAddressTable 1 }

RsaDnaAddressEntry ::= SEQUENCE {
   rsaDnaNumberingPlanIndicator
      INTEGER,
   rsaDnaDataNetworkAddress
      DigitString }

rsaDnaNumberingPlanIndicator OBJECT-TYPE
   SYNTAX     INTEGER  {
                 x121(0),
                 e164(1) }
   ACCESS     read-write
   STATUS     mandatory
   DESCRIPTION
     "This attribute indicates the Numbering Plan Indicator (NPI) of the 
      Dna that is entered. An address may belong to the X.121 or E.164 
      numbering plans. X.121 is used in packet switched data networks."
   DEFVAL     { x121 }
::= { rsaDnaAddressEntry 1 }

rsaDnaDataNetworkAddress OBJECT-TYPE
   SYNTAX     DigitString (SIZE (1..15))
   ACCESS     read-write
   STATUS     mandatory
   DESCRIPTION
     "The Dna attribute contains digits which form a unique identifier of 
      the customer interface. It can be compared (approximation only) to 
      a telephone number where each phone number identifies a unique 
      telephone set. Dna digits are selected and assigned by network 
      operators."
::= { rsaDnaAddressEntry 2 }

rsaDnaOutgoingOptionsTable OBJECT-TYPE
   SYNTAX     SEQUENCE OF RsaDnaOutgoingOptionsEntry
   ACCESS     not-accessible
   STATUS     mandatory
   DESCRIPTION
     "The OutgoingOptions group defines call options of a Dna for calls 
      which are made out of the interface represented by the Dna. These 
      options are not used for calls arriving to the interface represented by 
      the Dna."
::= { rsaDna 11 }

rsaDnaOutgoingOptionsEntry OBJECT-TYPE
   SYNTAX     RsaDnaOutgoingOptionsEntry
   ACCESS     not-accessible
   STATUS     mandatory
   DESCRIPTION
     "An entry in the rsaDnaOutgoingOptionsTable."
   INDEX {
      rsaIndex,
      rsaDnaIndex }
::= { rsaDnaOutgoingOptionsTable 1 }

RsaDnaOutgoingOptionsEntry ::= SEQUENCE {
   rsaDnaOutCalls
      INTEGER }

rsaDnaOutCalls OBJECT-TYPE
   SYNTAX     INTEGER  {
                 disallowed(0),
                 allowed(1) }
   ACCESS     read-only
   STATUS     mandatory
   DESCRIPTION
     "This attribute, if set to a value of allowed indicates that outgoing 
      calls (from the DTE to the network) can be made using this 
      particular Dna. If set to a value of disallowed, then outgoing calls 
      cannot be made using this Dna - such calls will be cleared by the 
      local DCE. This attribute corresponds to the ITU-T 'Outgoing Calls 
      Barred' feature for Dnas in that outgoing calls are barred if this 
      attribute is set to a value of disallowed. Either outCalls, or incCalls 
      (or both) must be set to a value of allowed for this Dna to be usable."
   DEFVAL     { disallowed }
::= { rsaDnaOutgoingOptionsEntry 1 }

rsaDnaIncomingOptionsTable OBJECT-TYPE
   SYNTAX     SEQUENCE OF RsaDnaIncomingOptionsEntry
   ACCESS     not-accessible
   STATUS     mandatory
   DESCRIPTION
     "IncomingOptions defines the set of options for incoming calls. 
      These options are used for calls arriving to the interface represented 
      by the Dna. For calls originated from the interface, 
      IncomingOptions attributes are not used."
::= { rsaDna 12 }

rsaDnaIncomingOptionsEntry OBJECT-TYPE
   SYNTAX     RsaDnaIncomingOptionsEntry
   ACCESS     not-accessible
   STATUS     mandatory
   DESCRIPTION
     "An entry in the rsaDnaIncomingOptionsTable."
   INDEX {
      rsaIndex,
      rsaDnaIndex }
::= { rsaDnaIncomingOptionsTable 1 }

RsaDnaIncomingOptionsEntry ::= SEQUENCE {
   rsaDnaIncCalls
      INTEGER,
   rsaDnaIncAccess
      INTEGER }

rsaDnaIncCalls OBJECT-TYPE
   SYNTAX     INTEGER  {
                 disallowed(0),
                 allowed(1) }
   ACCESS     read-only
   STATUS     mandatory
   DESCRIPTION
     "This attribute, if set to a value of allowed indicates that incoming 
      calls (from the network to the DTE) can be made to this Dna. If set 
      to a value of disallowed, then incoming calls cannot be made to this 
      Dna - such calls will be cleared by the local DCE. This attribute 
      corresponds to the ITU-T 'Incoming Calls Barred' feature for Dna's 
      in that incoming calls are barred if this attribute is set to a value of 
      disallowed.
      Either outCalls, or incCalls (or both) must be set to a value of 
      allowed for this Dna to be usable."
   DEFVAL     { allowed }
::= { rsaDnaIncomingOptionsEntry 1 }

rsaDnaIncAccess OBJECT-TYPE
   SYNTAX     INTEGER  {
                 disallowed(0),
                 allowed(1) }
   ACCESS     read-write
   STATUS     mandatory
   DESCRIPTION
     "This attribute is an extension of the Closed User Group (CUG) 
      facility, as follows:
      This attribute, if set to a value of allowed indicates that incoming 
      calls (from the network to the DTE) from the open (non-CUG) part 
      of the network are permitted. It also permits incoming calls from 
      DTEs that have Outgoing Access capabilities. If set to a value of 
      disallowed, then such calls cannot be made to this Dna - such calls 
      will be cleared by the local DCE.
      This attribute corresponds to the ITU-T 'Closed User Group with 
      Incoming Access' feature for Dnas in that incoming access is 
      granted if this attribute is set to a value of allowed."
   DEFVAL     { disallowed }
::= { rsaDnaIncomingOptionsEntry 9 }


-- Rsa/n Dna ClosedUserGroup
-- ClosedUserGroup defines options associated with a national or 
-- international Cug Identifier. Other Dnas in the network can have 
-- Cugs defined which group these Dnas by Cug interlockCode. If 
-- Dnas are defined with Cugs, calls from Dnas which do not have the 
-- same interlockCode defined are refused. Attributes incAccess and 
-- outAccess can override this rule.

rsaDnaCug OBJECT IDENTIFIER ::= { rsaDna 2 }



rsaDnaCugRowStatusTable OBJECT-TYPE
   SYNTAX     SEQUENCE OF RsaDnaCugRowStatusEntry
   ACCESS     not-accessible
   STATUS     mandatory
   DESCRIPTION
     "This entry controls the addition and deletion of 
      rsaDnaCug components."
::= { rsaDnaCug 1 }

rsaDnaCugRowStatusEntry OBJECT-TYPE
   SYNTAX     RsaDnaCugRowStatusEntry
   ACCESS     not-accessible
   STATUS     mandatory
   DESCRIPTION
     "A single entry in the table represents a single 
      rsaDnaCug component."
   INDEX {
      rsaIndex,
      rsaDnaIndex,
      rsaDnaCugIndex }
::= { rsaDnaCugRowStatusTable 1 }

RsaDnaCugRowStatusEntry ::= SEQUENCE {
   rsaDnaCugRowStatus
      RowStatus,
   rsaDnaCugComponentName
      DisplayString,
   rsaDnaCugStorageType
      StorageType,
   rsaDnaCugIndex
      Integer32 }

rsaDnaCugRowStatus OBJECT-TYPE
   SYNTAX     RowStatus 
   ACCESS     read-write
   STATUS     mandatory
   DESCRIPTION
     "This variable is used as the basis for SNMP naming of
      rsaDnaCug components.
      These components can be added and deleted."
::= { rsaDnaCugRowStatusEntry 1 }

rsaDnaCugComponentName OBJECT-TYPE
   SYNTAX     DisplayString 
   ACCESS     read-only
   STATUS     mandatory
   DESCRIPTION
     "This variable provides the component's string name for
      use with the ASCII Console Interface"
::= { rsaDnaCugRowStatusEntry 2 }

rsaDnaCugStorageType OBJECT-TYPE
   SYNTAX     StorageType 
   ACCESS     read-only
   STATUS     mandatory
   DESCRIPTION
     "This variable represents the storage type value for the
      rsaDnaCug tables."
::= { rsaDnaCugRowStatusEntry 4 }

rsaDnaCugIndex OBJECT-TYPE
   SYNTAX     Integer32 (0..255)
   ACCESS     not-accessible
   STATUS     mandatory
   DESCRIPTION
     "This variable represents the index for the rsaDnaCug tables."
::= { rsaDnaCugRowStatusEntry 10 }

rsaDnaCugCugOptionsTable OBJECT-TYPE
   SYNTAX     SEQUENCE OF RsaDnaCugCugOptionsEntry
   ACCESS     not-accessible
   STATUS     mandatory
   DESCRIPTION
     "Attributes in this group define ClosedUserGroup options associated 
      with this particular interlockCode. Dna's with the same Cug 
      (interlockCode) can make calls within this group. Various 
      combinations which permit or prevent calls in the same Cug group 
      are defined here."
::= { rsaDnaCug 10 }

rsaDnaCugCugOptionsEntry OBJECT-TYPE
   SYNTAX     RsaDnaCugCugOptionsEntry
   ACCESS     not-accessible
   STATUS     mandatory
   DESCRIPTION
     "An entry in the rsaDnaCugCugOptionsTable."
   INDEX {
      rsaIndex,
      rsaDnaIndex,
      rsaDnaCugIndex }
::= { rsaDnaCugCugOptionsTable 1 }

RsaDnaCugCugOptionsEntry ::= SEQUENCE {
   rsaDnaCugType
      INTEGER,
   rsaDnaCugDnic
      DigitString,
   rsaDnaCugInterlockCode
      Unsigned32,
   rsaDnaCugPreferential
      INTEGER,
   rsaDnaCugOutCalls
      INTEGER,
   rsaDnaCugIncCalls
      INTEGER,
   rsaDnaCugPrivileged
      INTEGER }

rsaDnaCugType OBJECT-TYPE
   SYNTAX     INTEGER  {
                 national(0),
                 international(1) }
   ACCESS     read-write
   STATUS     mandatory
   DESCRIPTION
     "This attribute specifies the Cug type - the Cug is either a national 
      Cug, or an international Cug. International closed user groups are 
      usually established between DTEs for which there is an X.75 
      Gateway between; whereas national closed user groups are usually 
      established between DTEs for which there is no X.75 Gateway 
      between. (National Cugs cannot normally traverse an X.75 
      Gateway).
      If this attribute is set to national, then the Cug is a national Cug, in 
      which case, the dnic should be left at its default value since it is not 
      part of a national Cug. If this attribute is set to international, then 
      the Cug is an international Cug, in which case, the dnic should be 
      set appropriately as part of the Cug interlockCode."
   DEFVAL     { national }
::= { rsaDnaCugCugOptionsEntry 1 }

rsaDnaCugDnic OBJECT-TYPE
   SYNTAX     DigitString (SIZE (4))
   ACCESS     read-write
   STATUS     mandatory
   DESCRIPTION
     "This attribute specifies the dnic (Data Network ID Code) of the Cug 
      by which packet networks are identified. This attribute is not 
      applicable if the Cug is a national Cug, as specified by the Cug type 
      attribute. There are usually 1 or 2 dnics assigned per country, for 
      public networks. The U.S. is an exception where each BOC has a 
      dnic. Also, a group of private networks can have its own dnic.
      dnic value is not an arbitrary number. It is assigned by international 
      agreement and controlled by ITU-T."
   DEFVAL     { '30303030'H }  -- "0000"
::= { rsaDnaCugCugOptionsEntry 2 }

rsaDnaCugInterlockCode OBJECT-TYPE
   SYNTAX     Unsigned32 (0..65535)
   ACCESS     read-write
   STATUS     mandatory
   DESCRIPTION
     "This attribute specifies the Cug identifier of a national or 
      international Cug call. It is an arbitrary number and it also can be 
      called Cug in some descriptions. Interfaces (Dna's) defined with 
      this number can make calls to Dna's with the same interlockCode."
   DEFVAL     { 0 }
::= { rsaDnaCugCugOptionsEntry 3 }

rsaDnaCugPreferential OBJECT-TYPE
   SYNTAX     INTEGER  {
                 no(0),
                 yes(1) }
   ACCESS     read-only
   STATUS     mandatory
   DESCRIPTION
     "This attribute, if set to yes indicates that this Cug is the preferential 
      Cug, in which case it will be used during the call establishment 
      phase if the DTE has not explicitly specified a Cug index in the call 
      request packet. If set to no, then this Cug is not the preferential 
      Cug.
      Only one of the Cugs associated with a particular Dna can be the 
      preferential Cug - only one Cug can have this attribute set to yes."
   DEFVAL     { no }
::= { rsaDnaCugCugOptionsEntry 4 }

rsaDnaCugOutCalls OBJECT-TYPE
   SYNTAX     INTEGER  {
                 disallowed(0),
                 allowed(1) }
   ACCESS     read-only
   STATUS     mandatory
   DESCRIPTION
     "This attribute, if set to allowed indicates that outgoing calls (from 
      the DTE into the network) can be made using this particular Cug. If 
      set to a value of disallowed, then outgoing calls cannot be made 
      using this Cug - such calls will be cleared by the local DCE.
      This attribute corresponds to the ITU-T 'Outgoing Calls Barred' 
      feature for Cugs in that outgoing calls are barred if this attribute is 
      set to a value of disallowed."
   DEFVAL     { disallowed }
::= { rsaDnaCugCugOptionsEntry 5 }

rsaDnaCugIncCalls OBJECT-TYPE
   SYNTAX     INTEGER  {
                 disallowed(0),
                 allowed(1) }
   ACCESS     read-only
   STATUS     mandatory
   DESCRIPTION
     "This attribute, if set to allowed indicates that incoming calls (from 
      the network to the DTE) can be made using this particular Cug. If 
      set to disallowed, then incoming calls cannot be made using this 
      Cug - such calls will be cleared by the local DCE.
      This attribute corresponds to the ITU-T 'Incoming Calls Barred' 
      feature for Cugs in that incoming calls are barred if this attribute is 
      set to a value of disallowed."
   DEFVAL     { allowed }
::= { rsaDnaCugCugOptionsEntry 6 }

rsaDnaCugPrivileged OBJECT-TYPE
   SYNTAX     INTEGER  {
                 no(0),
                 yes(1) }
   ACCESS     read-only
   STATUS     mandatory
   DESCRIPTION
     "This attribute, if set to yes indicates that this Cug is a privileged 
      Cug. In DPN, at least one side of a call setup within a Cug must 
      have the Cug as a privileged Cug. If set to no, then the Cug is not 
      privileged.
      If both the local DTE and the remote DTE subscribe to the Cug, but 
      it is not privileged, then the call will be cleared. This attribute is 
      typically used for a host DTE which must accept calls from many 
      other DTEs in which case the other DTEs cannot call one another, 
      but can call the host. In this example, the host would have the 
      privileged Cug, and the other DTEs would belong to the same Cug, 
      but it would not be privileged."
   DEFVAL     { yes }
::= { rsaDnaCugCugOptionsEntry 7 }


-- Rsa/<string> VncsAccess
-- The VncsAccess component provides access to the Passport Voice 
-- Networking Call Server.

rsaVncsAccess OBJECT IDENTIFIER ::= { rsa 3 }



rsaVncsAccessRowStatusTable OBJECT-TYPE
   SYNTAX     SEQUENCE OF RsaVncsAccessRowStatusEntry
   ACCESS     not-accessible
   STATUS     mandatory
   DESCRIPTION
     "This entry controls the addition and deletion of 
      rsaVncsAccess components."
::= { rsaVncsAccess 1 }

rsaVncsAccessRowStatusEntry OBJECT-TYPE
   SYNTAX     RsaVncsAccessRowStatusEntry
   ACCESS     not-accessible
   STATUS     mandatory
   DESCRIPTION
     "A single entry in the table represents a single 
      rsaVncsAccess component."
   INDEX {
      rsaIndex,
      rsaVncsAccessIndex }
::= { rsaVncsAccessRowStatusTable 1 }

RsaVncsAccessRowStatusEntry ::= SEQUENCE {
   rsaVncsAccessRowStatus
      RowStatus,
   rsaVncsAccessComponentName
      DisplayString,
   rsaVncsAccessStorageType
      StorageType,
   rsaVncsAccessIndex
      NonReplicated }

rsaVncsAccessRowStatus OBJECT-TYPE
   SYNTAX     RowStatus 
   ACCESS     read-write
   STATUS     mandatory
   DESCRIPTION
     "This variable is used as the basis for SNMP naming of
      rsaVncsAccess components.
      These components can be added and deleted."
::= { rsaVncsAccessRowStatusEntry 1 }

rsaVncsAccessComponentName OBJECT-TYPE
   SYNTAX     DisplayString 
   ACCESS     read-only
   STATUS     mandatory
   DESCRIPTION
     "This variable provides the component's string name for
      use with the ASCII Console Interface"
::= { rsaVncsAccessRowStatusEntry 2 }

rsaVncsAccessStorageType OBJECT-TYPE
   SYNTAX     StorageType 
   ACCESS     read-only
   STATUS     mandatory
   DESCRIPTION
     "This variable represents the storage type value for the
      rsaVncsAccess tables."
::= { rsaVncsAccessRowStatusEntry 4 }

rsaVncsAccessIndex OBJECT-TYPE
   SYNTAX     NonReplicated 
   ACCESS     not-accessible
   STATUS     mandatory
   DESCRIPTION
     "This variable represents the index for the rsaVncsAccess tables."
::= { rsaVncsAccessRowStatusEntry 10 }

rsaVncsAccessProvisionedTable OBJECT-TYPE
   SYNTAX     SEQUENCE OF RsaVncsAccessProvisionedEntry
   ACCESS     not-accessible
   STATUS     mandatory
   DESCRIPTION
     "The Provisioned group defines provisioned attributes associated 
      with the VncsAccess component."
::= { rsaVncsAccess 10 }

rsaVncsAccessProvisionedEntry OBJECT-TYPE
   SYNTAX     RsaVncsAccessProvisionedEntry
   ACCESS     not-accessible
   STATUS     mandatory
   DESCRIPTION
     "An entry in the rsaVncsAccessProvisionedTable."
   INDEX {
      rsaIndex,
      rsaVncsAccessIndex }
::= { rsaVncsAccessProvisionedTable 1 }

RsaVncsAccessProvisionedEntry ::= SEQUENCE {
   rsaVncsAccessTimeToLive
      INTEGER }

rsaVncsAccessTimeToLive OBJECT-TYPE
   SYNTAX     INTEGER (1..5)
   ACCESS     read-write
   STATUS     mandatory
   DESCRIPTION
     "This attribute specifies the length of time VNCS requests are 
      allowed to remain queued for transmission before they are 
      considered too old and are discarded. This attribute should be set in 
      considereation with the voice application timeout interval."
   DEFVAL     { 2 }
::= { rsaVncsAccessProvisionedEntry 1 }

rsaVncsAccessStateTable OBJECT-TYPE
   SYNTAX     SEQUENCE OF RsaVncsAccessStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { rsaVncsAccess 11 }

rsaVncsAccessStateEntry OBJECT-TYPE
   SYNTAX     RsaVncsAccessStateEntry
   ACCESS     not-accessible
   STATUS     mandatory
   DESCRIPTION
     "An entry in the rsaVncsAccessStateTable."
   INDEX {
      rsaIndex,
      rsaVncsAccessIndex }
::= { rsaVncsAccessStateTable 1 }

RsaVncsAccessStateEntry ::= SEQUENCE {
   rsaVncsAccessAdminState
      INTEGER,
   rsaVncsAccessOperationalState
      INTEGER,
   rsaVncsAccessUsageState
      INTEGER }

rsaVncsAccessAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { rsaVncsAccessStateEntry 1 }

rsaVncsAccessOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { rsaVncsAccessStateEntry 2 }

rsaVncsAccessUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { rsaVncsAccessStateEntry 3 }

rsaVncsAccessOperationalTable OBJECT-TYPE
   SYNTAX     SEQUENCE OF RsaVncsAccessOperationalEntry
   ACCESS     not-accessible
   STATUS     mandatory
   DESCRIPTION
     "The Operational group defines operational attributes associated 
      with the VncsAccess component."
::= { rsaVncsAccess 12 }

rsaVncsAccessOperationalEntry OBJECT-TYPE
   SYNTAX     RsaVncsAccessOperationalEntry
   ACCESS     not-accessible
   STATUS     mandatory
   DESCRIPTION
     "An entry in the rsaVncsAccessOperationalTable."
   INDEX {
      rsaIndex,
      rsaVncsAccessIndex }
::= { rsaVncsAccessOperationalTable 1 }

RsaVncsAccessOperationalEntry ::= SEQUENCE {
   rsaVncsAccessRequestsSent
      Counter32,
   rsaVncsAccessRepliesReceived
      Counter32,
   rsaVncsAccessRequestsQueued
      INTEGER,
   rsaVncsAccessRequestsDiscarded
      Counter32 }

rsaVncsAccessRequestsSent OBJECT-TYPE
   SYNTAX     Counter32 
   ACCESS     read-only
   STATUS     mandatory
   DESCRIPTION
     "This attribute counts the number of translation requests sent to 
      VNCS. This counter wraps to zero when it reaches its maximum 
      value."
::= { rsaVncsAccessOperationalEntry 1 }

rsaVncsAccessRepliesReceived OBJECT-TYPE
   SYNTAX     Counter32 
   ACCESS     read-only
   STATUS     mandatory
   DESCRIPTION
     "This attribute counts the number of translation replies received from 
      VNCS. This counter wraps to zero when it reaches its maximum 
      value."
::= { rsaVncsAccessOperationalEntry 2 }

rsaVncsAccessRequestsQueued OBJECT-TYPE
   SYNTAX     INTEGER (0..65535)
   ACCESS     read-only
   STATUS     mandatory
   DESCRIPTION
     "This attribute indicates the number of translation requests queued 
      for transmission to VNCS."
   DEFVAL     { 0 }
::= { rsaVncsAccessOperationalEntry 3 }

rsaVncsAccessRequestsDiscarded OBJECT-TYPE
   SYNTAX     Counter32 
   ACCESS     read-only
   STATUS     mandatory
   DESCRIPTION
     "This attribute counts the number of translation requests discarded 
      before being sent to VNCS. Requests are discarded if the queue 
      becomes too large or the VNCS server is unavailable. This counter 
      wraps to zero when it reaches its maximum value."
::= { rsaVncsAccessOperationalEntry 4 }

-- 
-- *** THIS SUBTREE CURRENTLY NOT IMPLEMENTED ***
-- 

-- Rsa/<string> Connection/n
-- Rsi Connection/n
-- The Connection component contains information relating to the 
-- connection between the RSA and RSI. This component is named by 
-- the logical channel number of the connection. 

rsaConnection OBJECT IDENTIFIER ::= { rsa 4 }



rsaConnectionRowStatusTable OBJECT-TYPE
   SYNTAX     SEQUENCE OF RsaConnectionRowStatusEntry
   ACCESS     not-accessible
   STATUS     mandatory
   DESCRIPTION
     "*** THIS TABLE CURRENTLY NOT IMPLEMENTED ***

      This entry controls the addition and deletion of 
      rsaConnection components."
::= { rsaConnection 1 }

rsaConnectionRowStatusEntry OBJECT-TYPE
   SYNTAX     RsaConnectionRowStatusEntry
   ACCESS     not-accessible
   STATUS     mandatory
   DESCRIPTION
     "A single entry in the table represents a single 
      rsaConnection component."
   INDEX {
      rsaIndex,
      rsaConnectionIndex }
::= { rsaConnectionRowStatusTable 1 }

RsaConnectionRowStatusEntry ::= SEQUENCE {
   rsaConnectionRowStatus
      RowStatus,
   rsaConnectionComponentName
      DisplayString,
   rsaConnectionStorageType
      StorageType,
   rsaConnectionIndex
      Integer32 }

rsaConnectionRowStatus OBJECT-TYPE
   SYNTAX     RowStatus 
   ACCESS     read-only
   STATUS     mandatory
   DESCRIPTION
     "This variable is used as the basis for SNMP naming of
      rsaConnection components.
      These components cannot be added nor deleted."
::= { rsaConnectionRowStatusEntry 1 }

rsaConnectionComponentName OBJECT-TYPE
   SYNTAX     DisplayString 
   ACCESS     read-only
   STATUS     mandatory
   DESCRIPTION
     "This variable provides the component's string name for
      use with the ASCII Console Interface"
::= { rsaConnectionRowStatusEntry 2 }

rsaConnectionStorageType OBJECT-TYPE
   SYNTAX     StorageType 
   ACCESS     read-only
   STATUS     mandatory
   DESCRIPTION
     "This variable represents the storage type value for the
      rsaConnection tables."
::= { rsaConnectionRowStatusEntry 4 }

rsaConnectionIndex OBJECT-TYPE
   SYNTAX     Integer32 (1..1000)
   ACCESS     not-accessible
   STATUS     mandatory
   DESCRIPTION
     "This variable represents the index for the rsaConnection tables."
::= { rsaConnectionRowStatusEntry 10 }

rsaConnectionOperationalTable OBJECT-TYPE
   SYNTAX     SEQUENCE OF RsaConnectionOperationalEntry
   ACCESS     not-accessible
   STATUS     mandatory
   DESCRIPTION
     "*** THIS TABLE CURRENTLY NOT IMPLEMENTED ***

      The Operational group defines operational attributes associated 
      with the Connection component."
::= { rsaConnection 10 }

rsaConnectionOperationalEntry OBJECT-TYPE
   SYNTAX     RsaConnectionOperationalEntry
   ACCESS     not-accessible
   STATUS     mandatory
   DESCRIPTION
     "An entry in the rsaConnectionOperationalTable."
   INDEX {
      rsaIndex,
      rsaConnectionIndex }
::= { rsaConnectionOperationalTable 1 }

RsaConnectionOperationalEntry ::= SEQUENCE {
   rsaConnectionRemoteName
      AsciiString,
   rsaConnectionCallState
      INTEGER }

rsaConnectionRemoteName OBJECT-TYPE
   SYNTAX     AsciiString (SIZE (0..32))
   ACCESS     read-only
   STATUS     mandatory
   DESCRIPTION
     "This attribute specifies an ASCII string identifier for the remote 
      module which is retrieved from the call request as user data."
::= { rsaConnectionOperationalEntry 1 }

rsaConnectionCallState OBJECT-TYPE
   SYNTAX     INTEGER  {
                 initializing(0),
                 creatingVc(1),
                 calling(2),
                 acceptingCall(3),
                 registeringFmo(4),
                 establishingLapf(5),
                 dataTransfer(6),
                 clearingCall(7),
                 terminating(8),
                 terminatingVc(9),
                 terminated(10) }
   ACCESS     read-only
   STATUS     mandatory
   DESCRIPTION
     "This attribute indicates the state of the connection. The normal state 
      for the connection is dataTransfer. The other states are transient 
      states used to setup or clear the connection."
::= { rsaConnectionOperationalEntry 2 }

rsaConnectionServerStatsTable OBJECT-TYPE
   SYNTAX     SEQUENCE OF RsaConnectionServerStatsEntry
   ACCESS     not-accessible
   STATUS     mandatory
   DESCRIPTION
     "*** THIS TABLE CURRENTLY NOT IMPLEMENTED ***

      The ServerStatistics group provides individual server usage 
      statistics for the connection."
::= { rsaConnection 11 }

rsaConnectionServerStatsEntry OBJECT-TYPE
   SYNTAX     RsaConnectionServerStatsEntry
   ACCESS     not-accessible
   STATUS     mandatory
   DESCRIPTION
     "An entry in the rsaConnectionServerStatsTable."
   INDEX {
      rsaIndex,
      rsaConnectionIndex }
::= { rsaConnectionServerStatsTable 1 }

RsaConnectionServerStatsEntry ::= SEQUENCE {
   rsaConnectionVncsRequests
      Counter32,
   rsaConnectionVncsReplies
      Counter32 }

rsaConnectionVncsRequests OBJECT-TYPE
   SYNTAX     Counter32 
   ACCESS     read-only
   STATUS     mandatory
   DESCRIPTION
     "This attribute counts the number of VNCS translation requests sent 
      or received on this connection."
::= { rsaConnectionServerStatsEntry 1 }

rsaConnectionVncsReplies OBJECT-TYPE
   SYNTAX     Counter32 
   ACCESS     read-only
   STATUS     mandatory
   DESCRIPTION
     "This attribute counts the number of VNCS translation replies sent or 
      received on this connection."
::= { rsaConnectionServerStatsEntry 2 }

rsaConnectionLapfStatusTable OBJECT-TYPE
   SYNTAX     SEQUENCE OF RsaConnectionLapfStatusEntry
   ACCESS     not-accessible
   STATUS     mandatory
   DESCRIPTION
     "*** THIS TABLE CURRENTLY NOT IMPLEMENTED ***

      This group contains the LAPF status."
::= { rsaConnection 12 }

rsaConnectionLapfStatusEntry OBJECT-TYPE
   SYNTAX     RsaConnectionLapfStatusEntry
   ACCESS     not-accessible
   STATUS     mandatory
   DESCRIPTION
     "An entry in the rsaConnectionLapfStatusTable."
   INDEX {
      rsaIndex,
      rsaConnectionIndex }
::= { rsaConnectionLapfStatusTable 1 }

RsaConnectionLapfStatusEntry ::= SEQUENCE {
   rsaConnectionLapfState
      INTEGER,
   rsaConnectionLapfQueueSize
      Counter32 }

rsaConnectionLapfState OBJECT-TYPE
   SYNTAX     INTEGER  {
                 disconnected(1),
                 linkSetup(2),
                 disconnectRequest(4),
                 informationTransfer(5),
                 waitingAck(7) }
   ACCESS     read-only
   STATUS     mandatory
   DESCRIPTION
     "This attribute shows the current state of the LAPF interface. The 
      normal states are informationTransfer and waitingAck. Since the 
      LAPF interface is not over a physical link the other states are 
      transitional."
::= { rsaConnectionLapfStatusEntry 1 }

rsaConnectionLapfQueueSize OBJECT-TYPE
   SYNTAX     Counter32 
   ACCESS     read-only
   STATUS     mandatory
   DESCRIPTION
     "This attribute indicates the number of frames in the LAPF transmit 
      queue."
::= { rsaConnectionLapfStatusEntry 4 }

rsaConnectionLapfStatsTable OBJECT-TYPE
   SYNTAX     SEQUENCE OF RsaConnectionLapfStatsEntry
   ACCESS     not-accessible
   STATUS     mandatory
   DESCRIPTION
     "*** THIS TABLE CURRENTLY NOT IMPLEMENTED ***

      This group contains the LAPF statistics."
::= { rsaConnection 13 }

rsaConnectionLapfStatsEntry OBJECT-TYPE
   SYNTAX     RsaConnectionLapfStatsEntry
   ACCESS     not-accessible
   STATUS     mandatory
   DESCRIPTION
     "An entry in the rsaConnectionLapfStatsTable."
   INDEX {
      rsaIndex,
      rsaConnectionIndex }
::= { rsaConnectionLapfStatsTable 1 }

RsaConnectionLapfStatsEntry ::= SEQUENCE {
   rsaConnectionLapfStateChanges
      Counter32,
   rsaConnectionLapfRemoteBusy
      Counter32,
   rsaConnectionLapfAckTimeouts
      Counter32,
   rsaConnectionLapfRejectFramesRx
      Counter32,
   rsaConnectionLapfIFramesTx
      Counter32,
   rsaConnectionLapfIFramesTxDiscarded
      Counter32,
   rsaConnectionLapfIFramesRx
      Counter32,
   rsaConnectionLapfIFramesRxDiscarded
      Counter32 }

rsaConnectionLapfStateChanges OBJECT-TYPE
   SYNTAX     Counter32 
   ACCESS     read-only
   STATUS     mandatory
   DESCRIPTION
     "This attribute counts the number of times the LAPF interface has 
      changed state. While the LAPF interface is in informationTransfer 
      state, this counter will increment on each expiry of idleProbeTimer 
      as its state goes from informationTransfer to waitingAck and back. 
      When this count reaches maximum, it wraps to zero."
::= { rsaConnectionLapfStatsEntry 1 }

rsaConnectionLapfRemoteBusy OBJECT-TYPE
   SYNTAX     Counter32 
   ACCESS     read-only
   STATUS     mandatory
   DESCRIPTION
     "This attribute counts the number of times transmission of an I-frame 
      was unsuccessful due to a perceived remote busy condition 
      (window closed or remote busy). When this count reaches 
      maximum, it wraps to zero."
::= { rsaConnectionLapfStatsEntry 2 }

rsaConnectionLapfAckTimeouts OBJECT-TYPE
   SYNTAX     Counter32 
   ACCESS     read-only
   STATUS     mandatory
   DESCRIPTION
     "This attribute counts the number of times the ackTimer has expired. 
      Frequent increments of this counter indicate improper values have 
      been chosen for ackTimer and ackDelayTimer between the local 
      and remote ends. When this count reaches maximum, it wraps to 
      zero."
::= { rsaConnectionLapfStatsEntry 3 }

rsaConnectionLapfRejectFramesRx OBJECT-TYPE
   SYNTAX     Counter32 
   ACCESS     read-only
   STATUS     mandatory
   DESCRIPTION
     "This attribute counts the number of REJ frames received. When this 
      count reaches maximum, it wraps to zero."
::= { rsaConnectionLapfStatsEntry 4 }

rsaConnectionLapfIFramesTx OBJECT-TYPE
   SYNTAX     Counter32 
   ACCESS     read-only
   STATUS     mandatory
   DESCRIPTION
     "This attribute counts the number of I-frames transmitted. An I-
      frame may be counted more than once if there are retransmissions. 
      When this count reaches maximum, it wraps to zero."
::= { rsaConnectionLapfStatsEntry 5 }

rsaConnectionLapfIFramesTxDiscarded OBJECT-TYPE
   SYNTAX     Counter32 
   ACCESS     read-only
   STATUS     mandatory
   DESCRIPTION
     "This attribute counts the number of transmit I-frames that have been 
      discarded. Discard reasons may be one of the following:
      1.		The frame length is beyond allowed limit.
      2.		The LAPF interface is in disconnected state.
      3.		The transmit queue has been purged because the queue length
      has reached the reset threshold.
      When this count reaches maximum, it wraps to zero."
::= { rsaConnectionLapfStatsEntry 6 }

rsaConnectionLapfIFramesRx OBJECT-TYPE
   SYNTAX     Counter32 
   ACCESS     read-only
   STATUS     mandatory
   DESCRIPTION
     "This attribute counts the number of I-frames received. When this 
      count reaches maximum, it wraps to zero."
::= { rsaConnectionLapfStatsEntry 7 }

rsaConnectionLapfIFramesRxDiscarded OBJECT-TYPE
   SYNTAX     Counter32 
   ACCESS     read-only
   STATUS     mandatory
   DESCRIPTION
     "This attribute counts the number of received I-frames that have been 
      discarded. The discard reasons are:
      1.	Incorrect frame size.
      2.	Frame is out of sequence.
      3.	Frame received while not in informationTransfer or waitingAck 
      state.
      When this count reaches maximum, it wraps to zero."
::= { rsaConnectionLapfStatsEntry 8 }

-- 
-- *** THIS SUBTREE CURRENTLY NOT IMPLEMENTED ***
-- 

-- This component defines attributes collected by Frame Relay Vc.

rsaConnectionVc OBJECT IDENTIFIER ::= { rsaConnection 2 }



rsaConnectionVcRowStatusTable OBJECT-TYPE
   SYNTAX     SEQUENCE OF RsaConnectionVcRowStatusEntry
   ACCESS     not-accessible
   STATUS     mandatory
   DESCRIPTION
     "*** THIS TABLE CURRENTLY NOT IMPLEMENTED ***

      This entry controls the addition and deletion of 
      rsaConnectionVc components."
::= { rsaConnectionVc 1 }

rsaConnectionVcRowStatusEntry OBJECT-TYPE
   SYNTAX     RsaConnectionVcRowStatusEntry
   ACCESS     not-accessible
   STATUS     mandatory
   DESCRIPTION
     "A single entry in the table represents a single 
      rsaConnectionVc component."
   INDEX {
      rsaIndex,
      rsaConnectionIndex,
      rsaConnectionVcIndex }
::= { rsaConnectionVcRowStatusTable 1 }

RsaConnectionVcRowStatusEntry ::= SEQUENCE {
   rsaConnectionVcRowStatus
      RowStatus,
   rsaConnectionVcComponentName
      DisplayString,
   rsaConnectionVcStorageType
      StorageType,
   rsaConnectionVcIndex
      NonReplicated }

rsaConnectionVcRowStatus OBJECT-TYPE
   SYNTAX     RowStatus 
   ACCESS     read-only
   STATUS     mandatory
   DESCRIPTION
     "This variable is used as the basis for SNMP naming of
      rsaConnectionVc components.
      These components cannot be added nor deleted."
::= { rsaConnectionVcRowStatusEntry 1 }

rsaConnectionVcComponentName OBJECT-TYPE
   SYNTAX     DisplayString 
   ACCESS     read-only
   STATUS     mandatory
   DESCRIPTION
     "This variable provides the component's string name for
      use with the ASCII Console Interface"
::= { rsaConnectionVcRowStatusEntry 2 }

rsaConnectionVcStorageType OBJECT-TYPE
   SYNTAX     StorageType 
   ACCESS     read-only
   STATUS     mandatory
   DESCRIPTION
     "This variable represents the storage type value for the
      rsaConnectionVc tables."
::= { rsaConnectionVcRowStatusEntry 4 }

rsaConnectionVcIndex OBJECT-TYPE
   SYNTAX     NonReplicated 
   ACCESS     not-accessible
   STATUS     mandatory
   DESCRIPTION
     "This variable represents the index for the rsaConnectionVc tables."
::= { rsaConnectionVcRowStatusEntry 10 }

rsaConnectionVcCadTable OBJECT-TYPE
   SYNTAX     SEQUENCE OF RsaConnectionVcCadEntry
   ACCESS     not-accessible
   STATUS     mandatory
   DESCRIPTION
     "*** THIS TABLE CURRENTLY NOT IMPLEMENTED ***

      This group represents operational call data related to Frame Relay 
      Vc. It can be displayed only for Frame Relay Vc which is created by 
      application."
::= { rsaConnectionVc 10 }

rsaConnectionVcCadEntry OBJECT-TYPE
   SYNTAX     RsaConnectionVcCadEntry
   ACCESS     not-accessible
   STATUS     mandatory
   DESCRIPTION
     "An entry in the rsaConnectionVcCadTable."
   INDEX {
      rsaIndex,
      rsaConnectionIndex,
      rsaConnectionVcIndex }
::= { rsaConnectionVcCadTable 1 }

RsaConnectionVcCadEntry ::= SEQUENCE {
   rsaConnectionVcType
      INTEGER,
   rsaConnectionVcState
      INTEGER,
   rsaConnectionVcPreviousState
      INTEGER,
   rsaConnectionVcDiagnosticCode
      Unsigned32,
   rsaConnectionVcPreviousDiagnosticCode
      Unsigned32,
   rsaConnectionVcCalledNpi
      INTEGER,
   rsaConnectionVcCalledDna
      DigitString,
   rsaConnectionVcCalledLcn
      Unsigned32,
   rsaConnectionVcCallingNpi
      INTEGER,
   rsaConnectionVcCallingDna
      DigitString,
   rsaConnectionVcCallingLcn
      Unsigned32,
   rsaConnectionVcAccountingEnabled
      INTEGER,
   rsaConnectionVcFastSelectCall
      INTEGER,
   rsaConnectionVcPathReliability
      INTEGER,
   rsaConnectionVcAccountingEnd
      INTEGER,
   rsaConnectionVcPriority
      INTEGER,
   rsaConnectionVcSegmentSize
      Unsigned32,
   rsaConnectionVcMaxSubnetPktSize
      Unsigned32,
   rsaConnectionVcRcosToNetwork
      INTEGER,
   rsaConnectionVcRcosFromNetwork
      INTEGER,
   rsaConnectionVcEmissionPriorityToNetwork
      INTEGER,
   rsaConnectionVcEmissionPriorityFromNetwork
      INTEGER,
   rsaConnectionVcDataPath
      AsciiString }

rsaConnectionVcType OBJECT-TYPE
   SYNTAX     INTEGER  {
                 svc(0),
                 pvc(1),
                 spvc(2) }
   ACCESS     read-only
   STATUS     mandatory
   DESCRIPTION
     "This attribute displays the type of call, pvc,svc or spvc."
::= { rsaConnectionVcCadEntry 1 }

rsaConnectionVcState OBJECT-TYPE
   SYNTAX     INTEGER  {
                 creating(0),
                 readyP1(1),
                 dteWaitingP2(2),
                 dceWaitingP3(3),
                 dataTransferP4(4),
                 unsupportedP5(5),
                 dteClearRequestP6(6),
                 dceClearIndicationP7(7),
                 termination(8) }
   ACCESS     read-only
   STATUS     mandatory
   DESCRIPTION
     "This attribute displays the state of call control. P5 state is not 
      supported but is listed for completness. Transitions from one state to 
      another take very short time. state most often displayed is 
      dataTransferP4."
::= { rsaConnectionVcCadEntry 2 }

rsaConnectionVcPreviousState OBJECT-TYPE
   SYNTAX     INTEGER  {
                 creating(0),
                 readyP1(1),
                 dteWaitingP2(2),
                 dceWaitingP3(3),
                 dataTransferP4(4),
                 unsupportedP5(5),
                 dteClearRequestP6(6),
                 dceClearIndicationP7(7),
                 termination(8) }
   ACCESS     read-only
   STATUS     mandatory
   DESCRIPTION
     "This attribute displays the previous state of call control. This is a 
      valuable field to determine how the processing is progressing."
::= { rsaConnectionVcCadEntry 3 }

rsaConnectionVcDiagnosticCode OBJECT-TYPE
   SYNTAX     Unsigned32 (0..255)
   ACCESS     read-only
   STATUS     mandatory
   DESCRIPTION
     "This attribute displays the internal substate of call control. It is used 
      to further refine state of call processing."
::= { rsaConnectionVcCadEntry 4 }

rsaConnectionVcPreviousDiagnosticCode OBJECT-TYPE
   SYNTAX     Unsigned32 (0..255)
   ACCESS     read-only
   STATUS     mandatory
   DESCRIPTION
     "This attribute displays the internal substate of call control. It is used 
      to further refine state of call processing."
::= { rsaConnectionVcCadEntry 5 }

rsaConnectionVcCalledNpi OBJECT-TYPE
   SYNTAX     INTEGER  {
                 x121(0),
                 e164(1) }
   ACCESS     read-only
   STATUS     mandatory
   DESCRIPTION
     "This attribute displays the Numbering Plan Indicator (NPI) of the 
      called end."
::= { rsaConnectionVcCadEntry 6 }

rsaConnectionVcCalledDna OBJECT-TYPE
   SYNTAX     DigitString (SIZE (1..15))
   ACCESS     read-only
   STATUS     mandatory
   DESCRIPTION
     "This attribute displays the Data Network Address (Dna) of the 
      called (destination) DTE to which this call is sent. This address if 
      defined at recieving end will complete Vc connection."
::= { rsaConnectionVcCadEntry 7 }

rsaConnectionVcCalledLcn OBJECT-TYPE
   SYNTAX     Unsigned32 (1..65535)
   ACCESS     read-only
   STATUS     mandatory
   DESCRIPTION
     "This attribute displays the Logical Channel Number of the called 
      end. It is valid only after both ends of Vc exchanged relevant 
      information."
::= { rsaConnectionVcCadEntry 8 }

rsaConnectionVcCallingNpi OBJECT-TYPE
   SYNTAX     INTEGER  {
                 x121(0),
                 e164(1) }
   ACCESS     read-only
   STATUS     mandatory
   DESCRIPTION
     "This attribute displays the Numbering Plan Indicator (NPI) of the 
      calling end."
::= { rsaConnectionVcCadEntry 9 }

rsaConnectionVcCallingDna OBJECT-TYPE
   SYNTAX     DigitString (SIZE (1..15))
   ACCESS     read-only
   STATUS     mandatory
   DESCRIPTION
     "This attribute displays the Data Network Address (Dna) of the 
      calling end."
::= { rsaConnectionVcCadEntry 10 }

rsaConnectionVcCallingLcn OBJECT-TYPE
   SYNTAX     Unsigned32 (1..65535)
   ACCESS     read-only
   STATUS     mandatory
   DESCRIPTION
     "This attribute displays the Logical Channel Number of the calling 
      end."
::= { rsaConnectionVcCadEntry 11 }

rsaConnectionVcAccountingEnabled OBJECT-TYPE
   SYNTAX     INTEGER  {
                 yes(0),
                 no(1) }
   ACCESS     read-only
   STATUS     mandatory
   DESCRIPTION
     "This attribute indicates that this optional section of accounting 
      record is suppressed or permitted. If accountingEnabled is yes, 
      conditions for generation of accounting record were met. These 
      conditions include billing options, vc recovery conditions and 
      Module wide accounting data options."
::= { rsaConnectionVcCadEntry 12 }

rsaConnectionVcFastSelectCall OBJECT-TYPE
   SYNTAX     INTEGER  {
                 no(0),
                 yes(1) }
   ACCESS     read-only
   STATUS     mandatory
   DESCRIPTION
     "This attribute displays that this is a fast select call."
::= { rsaConnectionVcCadEntry 13 }

rsaConnectionVcPathReliability OBJECT-TYPE
   SYNTAX     INTEGER  {
                 high(0),
                 normal(1) }
   ACCESS     read-only
   STATUS     mandatory
   DESCRIPTION
     "This attribute displays the path reliability."
::= { rsaConnectionVcCadEntry 19 }

rsaConnectionVcAccountingEnd OBJECT-TYPE
   SYNTAX     INTEGER  {
                 callingEnd(0),
                 calledEnd(1) }
   ACCESS     read-only
   STATUS     mandatory
   DESCRIPTION
     "This attribute indicates if this end should generate an accounting 
      record. Normally, callingEnd is the end to generate an accounting 
      record."
::= { rsaConnectionVcCadEntry 20 }

rsaConnectionVcPriority OBJECT-TYPE
   SYNTAX     INTEGER  {
                 normal(0),
                 high(1) }
   ACCESS     read-only
   STATUS     mandatory
   DESCRIPTION
     "This attribute displays whether the call is a normal or a high 
      priority call."
::= { rsaConnectionVcCadEntry 21 }

rsaConnectionVcSegmentSize OBJECT-TYPE
   SYNTAX     Unsigned32 (0..4096)
   ACCESS     read-only
   STATUS     mandatory
   DESCRIPTION
     "This attribute displays the segment size (in bytes) used on the call. 
      It is used to calculate the number of segments transmitted and 
      received."
::= { rsaConnectionVcCadEntry 22 }

rsaConnectionVcMaxSubnetPktSize OBJECT-TYPE
   SYNTAX     Unsigned32 (0..4096)
   ACCESS     read-only
   STATUS     mandatory
   DESCRIPTION
     "This attribute indicates the maximum packet size allowed on the Vc."
::= { rsaConnectionVcCadEntry 27 }

rsaConnectionVcRcosToNetwork OBJECT-TYPE
   SYNTAX     INTEGER  {
                 throughput(0),
                 delay(1),
                 multimedia(2) }
   ACCESS     read-only
   STATUS     mandatory
   DESCRIPTION
     "This attribute indicates the routing metric routing class of service to
      the network."
::= { rsaConnectionVcCadEntry 28 }

rsaConnectionVcRcosFromNetwork OBJECT-TYPE
   SYNTAX     INTEGER  {
                 throughput(0),
                 delay(1),
                 multimedia(2) }
   ACCESS     read-only
   STATUS     mandatory
   DESCRIPTION
     "This attribute displays the routing metric Routing Class of Service 
      from the Network."
::= { rsaConnectionVcCadEntry 29 }

rsaConnectionVcEmissionPriorityToNetwork OBJECT-TYPE
   SYNTAX     INTEGER  {
                 normal(0),
                 high(1),
                 interrupting(2) }
   ACCESS     read-only
   STATUS     mandatory
   DESCRIPTION
     "This attribute displays the network internal emission priotity to the 
      network."
::= { rsaConnectionVcCadEntry 30 }

rsaConnectionVcEmissionPriorityFromNetwork OBJECT-TYPE
   SYNTAX     INTEGER  {
                 normal(0),
                 high(1),
                 interrupting(2) }
   ACCESS     read-only
   STATUS     mandatory
   DESCRIPTION
     "This attribute displays the network internal emission priotity from 
      the network."
::= { rsaConnectionVcCadEntry 31 }

rsaConnectionVcDataPath OBJECT-TYPE
   SYNTAX     AsciiString (SIZE (0..32))
   ACCESS     read-only
   STATUS     mandatory
   DESCRIPTION
     "This attribute indicates the data path used by the connection. The 
      data path is provisioned in Dna and DirectCall components. The 
      displayed value of this attribute can be different from the 
      provisioned value.
      
      If the connection is using dprsOnly data path, the string 
      dprsOnly is displayed. (dynamic packet routing system)
      
      If the connection is using dprsMcsOnly data path, the string 
      dprsMcsOnly is displayed.
      
      If the connection is using dprsMcsFirst data path, the string 
      dprsMcsFirst is displayed."
::= { rsaConnectionVcCadEntry 32 }

rsaConnectionVcIntdTable OBJECT-TYPE
   SYNTAX     SEQUENCE OF RsaConnectionVcIntdEntry
   ACCESS     not-accessible
   STATUS     mandatory
   DESCRIPTION
     "*** THIS TABLE CURRENTLY NOT IMPLEMENTED ***

      This group defines display of interval data collected by Vc. Data in 
      this group is variable and may depend on time when this display 
      command is issued."
::= { rsaConnectionVc 11 }

rsaConnectionVcIntdEntry OBJECT-TYPE
   SYNTAX     RsaConnectionVcIntdEntry
   ACCESS     not-accessible
   STATUS     mandatory
   DESCRIPTION
     "An entry in the rsaConnectionVcIntdTable."
   INDEX {
      rsaIndex,
      rsaConnectionIndex,
      rsaConnectionVcIndex }
::= { rsaConnectionVcIntdTable 1 }

RsaConnectionVcIntdEntry ::= SEQUENCE {
   rsaConnectionVcCallReferenceNumber
      Hex,
   rsaConnectionVcElapsedTimeTillNow
      Unsigned32,
   rsaConnectionVcSegmentsRx
      Unsigned32,
   rsaConnectionVcSegmentsSent
      Unsigned32,
   rsaConnectionVcStartTime
      EnterpriseDateAndTime }

rsaConnectionVcCallReferenceNumber OBJECT-TYPE
   SYNTAX     Hex (0..16777215)
   ACCESS     read-only
   STATUS     mandatory
   DESCRIPTION
     "This attribute displays the call reference number which is a unique 
      number generated by the switch.The same Call Reference Number 
      is stored in the interval data (accounting record) at both ends of the 
      call. It can be used as one of the attributes in matching duplicate 
      records generated at each end of the call."
::= { rsaConnectionVcIntdEntry 1 }

rsaConnectionVcElapsedTimeTillNow OBJECT-TYPE
   SYNTAX     Unsigned32 (0..16777215)
   ACCESS     read-only
   STATUS     mandatory
   DESCRIPTION
     "This attribute displays the elapsed time representing the period of 
      this interval data. It is elapsed time in 0.1 second increments since 
      Vc started."
::= { rsaConnectionVcIntdEntry 2 }

rsaConnectionVcSegmentsRx OBJECT-TYPE
   SYNTAX     Unsigned32 (0..16777215)
   ACCESS     read-only
   STATUS     mandatory
   DESCRIPTION
     "This attribute displays the number of segments received at the time 
      command was issued. This is the segment received count 
      maintained by accounting at each end of the Vc. This counter is 
      updated only when the packet cannot be successfully delivered out 
      of the sink Vc and to the sink AP Conditions in which packets may 
      be discarded by the sink Vc include: missing packets due to subnet 
      discards, segmentation protocol violations due to subnet discard, 
      duplicated and out-of-ranged packets and packets that arrive while 
      Vc is in path recovery state."
::= { rsaConnectionVcIntdEntry 3 }

rsaConnectionVcSegmentsSent OBJECT-TYPE
   SYNTAX     Unsigned32 (0..16777215)
   ACCESS     read-only
   STATUS     mandatory
   DESCRIPTION
     "This attribute displays the number of segments sent at the time 
      command was issued. This is the segment sent count maintained by 
      accounting at the source Vc. Vc only counts packets that Vc thinks 
      can be delivered successfully into the subnet. In reality, these 
      packets may be dropped by trunking, for instance. This counter is 
      not updated when splitting fails, when Vc is in a path recovery state, 
      when packet forwarding fails to forward this packet and when 
      subsequent packets have to be discarded as we want to minimize the 
      chance of out-of-sequence and do not intentionally send out-of-
      sequenced packets into the subnet."
::= { rsaConnectionVcIntdEntry 4 }

rsaConnectionVcStartTime OBJECT-TYPE
   SYNTAX     EnterpriseDateAndTime (SIZE (0 | 19))
   ACCESS     read-only
   STATUS     mandatory
   DESCRIPTION
     "This attribute displays the start time of this interval period. If Vc 
      spans 12 hour time or time of day change startTime reflects new 
      time as recorded at 12 hour periods or time of day changes."
::= { rsaConnectionVcIntdEntry 5 }

rsaConnectionVcFrdTable OBJECT-TYPE
   SYNTAX     SEQUENCE OF RsaConnectionVcFrdEntry
   ACCESS     not-accessible
   STATUS     mandatory
   DESCRIPTION
     "*** THIS TABLE CURRENTLY NOT IMPLEMENTED ***

      This group defines Frame Relay attributes collected by Frame Relay 
      Vc.
      The purpose of Vc attributes is to aid end users and verification 
      people to understand the Vc internal behavior. This is particularly 
      useful when the network has experienced abnormality and we want 
      to isolate problems and pinpoint trouble spots. 
      Attributes are collected on a per Vc basis. Until a need is identified, 
      statistics are not collected at a processor level. Each attribute is 
      stored in a 32 bit field and is initialized to zero when a Vc enters 
      into the data transfer state. When a PVC is disconnected and then 
      connected again, the attributes will be reset. Attributes cannot be 
      reset through other methods. 
      Frame Relay Vc uses a best effort data packet delivery protocol and 
      a different packet segmentation and combination methods from the 
      General Vc. The Frame Relay Vc uses the same call setup and 
      control mechanism (e.g. the support of non-flow control data 
      packets) as in a General Vc. Most General Vc statistics and internal 
      variables are used in a Frame Relay Vc and are displayed by 
      software developers"
::= { rsaConnectionVc 12 }

rsaConnectionVcFrdEntry OBJECT-TYPE
   SYNTAX     RsaConnectionVcFrdEntry
   ACCESS     not-accessible
   STATUS     mandatory
   DESCRIPTION
     "An entry in the rsaConnectionVcFrdTable."
   INDEX {
      rsaIndex,
      rsaConnectionIndex,
      rsaConnectionVcIndex }
::= { rsaConnectionVcFrdTable 1 }

RsaConnectionVcFrdEntry ::= SEQUENCE {
   rsaConnectionVcFrmCongestedToSubnet
      Unsigned32,
   rsaConnectionVcCannotForwardToSubnet
      Unsigned32,
   rsaConnectionVcNotDataXferToSubnet
      Unsigned32,
   rsaConnectionVcOutOfRangeFrmFromSubnet
      Unsigned32,
   rsaConnectionVcCombErrorsFromSubnet
      Unsigned32,
   rsaConnectionVcDuplicatesFromSubnet
      Unsigned32,
   rsaConnectionVcNotDataXferFromSubnet
      Unsigned32,
   rsaConnectionVcFrmLossTimeouts
      Unsigned32,
   rsaConnectionVcOoSeqByteCntExceeded
      Unsigned32,
   rsaConnectionVcPeakOoSeqPktCount
      Unsigned32,
   rsaConnectionVcPeakOoSeqFrmForwarded
      Unsigned32,
   rsaConnectionVcSendSequenceNumber
      Unsigned32,
   rsaConnectionVcPktRetryTimeouts
      Unsigned32,
   rsaConnectionVcPeakRetryQueueSize
      Unsigned32,
   rsaConnectionVcSubnetRecoveries
      Unsigned32,
   rsaConnectionVcOoSeqPktCntExceeded
      Unsigned32,
   rsaConnectionVcPeakOoSeqByteCount
      Unsigned32 }

rsaConnectionVcFrmCongestedToSubnet OBJECT-TYPE
   SYNTAX     Unsigned32 (0..5000)
   ACCESS     read-only
   STATUS     mandatory
   DESCRIPTION
     "This attribute displays the number of frames from link discarded 
      due to lack of resources. It keeps track of the number of frames 
      from link that have to be discarded. The discard reasons include 
      insufficient memory for splitting the frame into smaller subnet 
      packet size."
::= { rsaConnectionVcFrdEntry 2 }

rsaConnectionVcCannotForwardToSubnet OBJECT-TYPE
   SYNTAX     Unsigned32 (0..5000)
   ACCESS     read-only
   STATUS     mandatory
   DESCRIPTION
     "This attribute displays the number of discarded packets that can not 
      be forwarded into the subnet because of subnet congestion.
      Number of frames from link discarded due to failure in forwarding 
      a packet from Vc into the subnet.- This attribute is increased when 
      packet forwarding fails to forward a packet into the subnet. If a 
      frame is split into multiple subnet packets and a partial packet has 
      to be discarded, all subsequent partial packets that have not yet been 
      delivered to the subnet will be discarded as well."
::= { rsaConnectionVcFrdEntry 3 }

rsaConnectionVcNotDataXferToSubnet OBJECT-TYPE
   SYNTAX     Unsigned32 (0..5000)
   ACCESS     read-only
   STATUS     mandatory
   DESCRIPTION
     "This attribute records the number of frames from link discarded 
      when the Vc tries to recover from internal path failure."
::= { rsaConnectionVcFrdEntry 4 }

rsaConnectionVcOutOfRangeFrmFromSubnet OBJECT-TYPE
   SYNTAX     Unsigned32 (0..5000)
   ACCESS     read-only
   STATUS     mandatory
   DESCRIPTION
     "This attribute displays the number of frames from subnet discarded 
      due to out of sequence range for arriving too late."
::= { rsaConnectionVcFrdEntry 5 }

rsaConnectionVcCombErrorsFromSubnet OBJECT-TYPE
   SYNTAX     Unsigned32 (0..5000)
   ACCESS     read-only
   STATUS     mandatory
   DESCRIPTION
     "This attribute records the number of subnet packets discarded at the 
      sink Vc due to the Vc segmentation and combination protocol error. 
      Usually, this occurs when the subnet discards packets and thus this 
      statistics can be used to guest the number of subnet packets that are 
      not delivered to the Vc. It cannot be used as an actual measure 
      because some subnet packets may have been delivered to Vc but 
      have to be discarded because these are partial packets to a frame in 
      which some other partial packets have not been properly delivered 
      to Vc"
::= { rsaConnectionVcFrdEntry 6 }

rsaConnectionVcDuplicatesFromSubnet OBJECT-TYPE
   SYNTAX     Unsigned32 (0..5000)
   ACCESS     read-only
   STATUS     mandatory
   DESCRIPTION
     "This attribute displays the number of subnet packets discarded due 
      to duplication. Although packets are not retransmitted by the Frame 
      Relay Vc, it is possible for the subnet to retransmit packets. When 
      packets are out-of-sequenced and copies of the same packets arrive, 
      then this attribute is increased."
::= { rsaConnectionVcFrdEntry 7 }

rsaConnectionVcNotDataXferFromSubnet OBJECT-TYPE
   SYNTAX     Unsigned32 (0..5000)
   ACCESS     read-only
   STATUS     mandatory
   DESCRIPTION
     "This attribute displays the number of subnet packets discarded when 
      data transfer is suspended in Vc recovery."
::= { rsaConnectionVcFrdEntry 8 }

rsaConnectionVcFrmLossTimeouts OBJECT-TYPE
   SYNTAX     Unsigned32 (0..5000)
   ACCESS     read-only
   STATUS     mandatory
   DESCRIPTION
     "This attribute displays the number of lost frame timer expiries.
      When this count is excessive, the network is very congested and 
      packets have been discarded in the subnet."
::= { rsaConnectionVcFrdEntry 9 }

rsaConnectionVcOoSeqByteCntExceeded OBJECT-TYPE
   SYNTAX     Unsigned32 (0..5000)
   ACCESS     read-only
   STATUS     mandatory
   DESCRIPTION
     "This attribute displays the number times that the out of sequence 
      byte threshold is exceeded. When the threshold is exceeded, this 
      condition is treated as if the loss frame timer has expired and all 
      frames queued at the sink Vc are delivered to the AP. We need to 
      keep this count to examine if the threshold is engineered properly. 
      This should be used in conjunction with the peak value of out-of-
      sequenced queue and the number of times the loss frame timer has 
      expired. This count should be relatively small when compared with 
      loss frame timer expiry count."
::= { rsaConnectionVcFrdEntry 10 }

rsaConnectionVcPeakOoSeqPktCount OBJECT-TYPE
   SYNTAX     Unsigned32 (0..5000)
   ACCESS     read-only
   STATUS     mandatory
   DESCRIPTION
     "This attribute displays the frame relay peak packet count of the out 
      of sequence queue. This attribute records the maximum queue 
      length of the out-of-sequenced queue. The counter can be used to 
      deduce the message buffer requirement on a Vc."
::= { rsaConnectionVcFrdEntry 11 }

rsaConnectionVcPeakOoSeqFrmForwarded OBJECT-TYPE
   SYNTAX     Unsigned32 (0..5000)
   ACCESS     read-only
   STATUS     mandatory
   DESCRIPTION
     "This attribute displays the frame relay peak size of the 
      sequence packet queue. The subnet may deliver packets out-of-
      sequenced. These packets are then queued in an out-of-sequenced 
      queue, waiting for a packet with the expected sequence number to 
      come. When that packet arrives, this attribute records the maximum 
      number of packets that were out-of-sequenced, but now have 
      become in-sequenced. The statistics is used to measure expected 
      queue size due to normal subnet packet disorder (not due to subnet 
      packet discard). Current implementation also uses this statistics to 
      set a maximum size for the out-of-sequenced queue."
::= { rsaConnectionVcFrdEntry 12 }

rsaConnectionVcSendSequenceNumber OBJECT-TYPE
   SYNTAX     Unsigned32 (0..5000)
   ACCESS     read-only
   STATUS     mandatory
   DESCRIPTION
     "This attribute displays the Vc internal packet's send sequence 
      number. Note that a 'packet' in this context, may be either a user 
      data packet, or an OAM frame."
::= { rsaConnectionVcFrdEntry 13 }

rsaConnectionVcPktRetryTimeouts OBJECT-TYPE
   SYNTAX     Unsigned32 (0..5000)
   ACCESS     read-only
   STATUS     mandatory
   DESCRIPTION
     "This attribute displays the number of packets which have 
      retransmission time-outs. When this count is excessive, the network 
      is very congested and packets have been discarded in the subnet."
::= { rsaConnectionVcFrdEntry 15 }

rsaConnectionVcPeakRetryQueueSize OBJECT-TYPE
   SYNTAX     Unsigned32 (0..5000)
   ACCESS     read-only
   STATUS     mandatory
   DESCRIPTION
     "This attribute displays the peak size of retransmission queue.
      This attribute is used as an indicator of the acknowledgment 
      behavior across the subnet. Records the largest body of 
      unacknowledged packets."
::= { rsaConnectionVcFrdEntry 16 }

rsaConnectionVcSubnetRecoveries OBJECT-TYPE
   SYNTAX     Unsigned32 (0..5000)
   ACCESS     read-only
   STATUS     mandatory
   DESCRIPTION
     "This attribute displays the number of successful Vc recovery 
      attempts."
::= { rsaConnectionVcFrdEntry 17 }

rsaConnectionVcOoSeqPktCntExceeded OBJECT-TYPE
   SYNTAX     Unsigned32 (0..255)
   ACCESS     read-only
   STATUS     mandatory
   DESCRIPTION
     "This attribute displays the number times that the out of sequence 
      packet threshold is exceeded. When the threshold is exceeded, this 
      condition is treated as if the loss frame timer has expired and all 
      frames queued at the sink Vc are delivered to the AP. We need to 
      keep this count to examine if the threshold is engineered properly. 
      This should be used in conjunction with the peak value of out-of-
      sequenced queue and the number of times the loss frame timer has 
      expired. This count should be relatively small when compared with 
      loss frame timer expiry count."
::= { rsaConnectionVcFrdEntry 19 }

rsaConnectionVcPeakOoSeqByteCount OBJECT-TYPE
   SYNTAX     Unsigned32 (0..50000)
   ACCESS     read-only
   STATUS     mandatory
   DESCRIPTION
     "This attribute displays the frame relay peak byte count of the out of 
      sequence queue. This attribute records the maximum queue length 
      of the out-of-sequenced queue. The counter can be used to deduce 
      the message buffer requirement on a Vc."
::= { rsaConnectionVcFrdEntry 20 }

rsaConnectionVcDmepTable OBJECT-TYPE
   SYNTAX     SEQUENCE OF RsaConnectionVcDmepEntry
   ACCESS     not-accessible
   STATUS     mandatory
   DESCRIPTION
     "*** THIS TABLE CURRENTLY NOT IMPLEMENTED ***

      This attribute displays the data path used by the connection. Data 
      path is provisioned in Dna and DirectCall components.
      
      If the connection is using dprsOnly data path, this attribute is 
      empty.
      
      If the connection is using dprsMcsOnly or dprsMcsFirst data path, 
      this attribute displays component name of the dprsMcsEndPoint."
::= { rsaConnectionVc 417 }

rsaConnectionVcDmepEntry OBJECT-TYPE
   SYNTAX     RsaConnectionVcDmepEntry
   ACCESS     not-accessible
   STATUS     mandatory
   DESCRIPTION
     "An entry in the rsaConnectionVcDmepTable."
   INDEX {
      rsaIndex,
      rsaConnectionIndex,
      rsaConnectionVcIndex,
      rsaConnectionVcDmepValue }
::= { rsaConnectionVcDmepTable 1 }

RsaConnectionVcDmepEntry ::= SEQUENCE {
   rsaConnectionVcDmepValue
      RowPointer }

rsaConnectionVcDmepValue OBJECT-TYPE
   SYNTAX     RowPointer 
   ACCESS     read-only
   STATUS     mandatory
   DESCRIPTION
     "This variable represents both the value and the index for the
      rsaConnectionVcDmepTable."
::= { rsaConnectionVcDmepEntry 1 }




-- 
-- Version and Compliance statements
-- 



-- Object-Group Statement:
-- A list of all current accessible leaf objects.

-- OBJECTS { rsaConnectionVcFastSelectCall,
--           rsaDnaCugInterlockCode,
--           rsaConnectionVcComponentName,
--           rsaDnaNumberingPlanIndicator,
--           rsaVncsAccessAdminState,
--           rsaLogicalProcessor,
--           rsaConnectionVcMaxSubnetPktSize,
--           rsaDnaCugOutCalls,
--           rsaVncsAccessRowStatus,
--           rsaConnectionLapfAckTimeouts,
--           rsaConnectionVcCalledLcn,
--           rsaConnectionVcPathReliability,
--           rsaConnectionVcSendSequenceNumber,
--           rsaConnectionVcPriority,
--           rsaDnaCugPreferential,
--           rsaConnectionVcCallReferenceNumber,
--           rsaVncsAccessUsageState,
--           rsaConnectionVcState,
--           rsaComponentName,
--           rsaMaxRsiConnections,
--           rsaConnectionLapfIFramesTx,
--           rsaVncsAccessOperationalState,
--           rsaConnectionVcEmissionPriorityToNetwork,
--           rsaDnaCugStorageType,
--           rsaConnectionVcPeakOoSeqByteCount,
--           rsaConnectionLapfQueueSize,
--           rsaDnaCugPrivileged,
--           rsaRsiConnections,
--           rsaDnaCugIncCalls,
--           rsaConnectionVcStorageType,
--           rsaConnectionVncsReplies,
--           rsaConnectionVcCallingLcn,
--           rsaConnectionVcAccountingEnd,
--           rsaConnectionVcCalledNpi,
--           rsaConnectionVcElapsedTimeTillNow,
--           rsaConnectionLapfIFramesRx,
--           rsaConnectionVcPeakOoSeqPktCount,
--           rsaDnaCugRowStatus,
--           rsaConnectionVcNotDataXferToSubnet,
--           rsaConnectionLapfRemoteBusy,
--           rsaConnectionVcCannotForwardToSubnet,
--           rsaDnaCugComponentName,
--           rsaConnectionVcEmissionPriorityFromNetwork,
--           rsaConnectionCallState,
--           rsaConnectionLapfStateChanges,
--           rsaStorageType,
--           rsaConnectionVcRowStatus,
--           rsaConnectionVcPreviousDiagnosticCode,
--           rsaVncsAccessRequestsDiscarded,
--           rsaDnaCugDnic,
--           rsaConnectionLapfIFramesTxDiscarded,
--           rsaConnectionRemoteName,
--           rsaDnaComponentName,
--           rsaConnectionVcCombErrorsFromSubnet,
--           rsaConnectionVcCallingDna,
--           rsaAdminState,
--           rsaConnectionVcPeakOoSeqFrmForwarded,
--           rsaConnectionVcSegmentsRx,
--           rsaConnectionVcFrmCongestedToSubnet,
--           rsaVncsAccessRequestsQueued,
--           rsaConnectionVcRcosToNetwork,
--           rsaRowStatus,
--           rsaConnectionVcCallingNpi,
--           rsaConnectionVncsRequests,
--           rsaDnaOutCalls,
--           rsaConnectionVcNotDataXferFromSubnet,
--           rsaVncsAccessRepliesReceived,
--           rsaConnectionVcDmepValue,
--           rsaUsageState,
--           rsaVncsAccessComponentName,
--           rsaConnectionStorageType,
--           rsaConnectionVcRcosFromNetwork,
--           rsaConnectionVcDuplicatesFromSubnet,
--           rsaConnectionVcStartTime,
--           rsaOperationalState,
--           rsaConnectionVcDiagnosticCode,
--           rsaVncsAccessTimeToLive,
--           rsaConnectionLapfRejectFramesRx,
--           rsaDnaDataNetworkAddress,
--           rsaConnectionRowStatus,
--           rsaConnectionVcOoSeqByteCntExceeded,
--           rsaDnaStorageType,
--           rsaDnaCugType,
--           rsaConnectionVcPktRetryTimeouts,
--           rsaConnectionVcOutOfRangeFrmFromSubnet,
--           rsaDnaIncCalls,
--           rsaConnectionVcCalledDna,
--           rsaConnectionVcType,
--           rsaConnectionVcAccountingEnabled,
--           rsaConnectionVcFrmLossTimeouts,
--           rsaVncsAccessRequestsSent,
--           rsaConnectionVcPreviousState,
--           rsaConnectionLapfIFramesRxDiscarded,
--           rsaConnectionVcSubnetRecoveries,
--           rsaConnectionVcOoSeqPktCntExceeded,
--           rsaConnectionVcPeakRetryQueueSize,
--           rsaDnaRowStatus,
--           rsaConnectionLapfState,
--           rsaConnectionComponentName,
--           rsaVncsAccessStorageType,
--           rsaDnaIncAccess,
--           rsaConnectionVcSegmentSize,
--           rsaConnectionVcSegmentsSent,
--           rsaConnectionVcDataPath }
-- STATUS  mandatory
-- DESCRIPTION
--   "A list of all current accessible leaf objects."

serverAccessRsaGroup OBJECT IDENTIFIER ::= { serverAccessRsaMIB 1 }
serverAccessRsaGroupBE OBJECT IDENTIFIER ::= { serverAccessRsaGroup 5 }
serverAccessRsaGroupBE01 OBJECT IDENTIFIER ::= { serverAccessRsaGroupBE 2 }
serverAccessRsaGroupBE01A OBJECT IDENTIFIER ::= { serverAccessRsaGroupBE01 2 }



-- Agent-Capabilities Statement:

-- PRODUCT-RELEASE "Passport Release 7.0 ServerAccessRsa."
-- STATUS          mandatory
-- DESCRIPTION     "ServerAccessRsa MIB: MIB Version BE01A,
--                  Software Version BG00S4C."
-- SUPPORTS        Nortel-Magellan-Passport-ServerAccessRsaMIB
--    INCLUDES     { serverAccessRsaGroupBE01A }

serverAccessRsaCapabilities OBJECT IDENTIFIER ::= { serverAccessRsaMIB 3 }
serverAccessRsaCapabilitiesBE OBJECT IDENTIFIER ::= { serverAccessRsaCapabilities 5 }
serverAccessRsaCapabilitiesBE01 OBJECT IDENTIFIER ::= { serverAccessRsaCapabilitiesBE 2 }
serverAccessRsaCapabilitiesBE01A OBJECT IDENTIFIER ::= { serverAccessRsaCapabilitiesBE01 2 }





END
