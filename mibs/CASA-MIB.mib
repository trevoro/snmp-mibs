CASA-MIB DEFINITIONS ::= BEGIN

        IMPORTS
            MODULE-IDENTITY, enterprises
                FROM SNMPv2-SMI;


		-- Casa Systems enterprise module definition

        casa MODULE-IDENTITY
            LAST-UPDATED "200407080000Z" -- July 8, 2004 
            ORGANIZATION "Casa Systems Inc."
            CONTACT-INFO "10 New England Business Center Drive
                          Andover, MA 01810
                          Tel: 978-688-6706
                          Fax: 978-688-6584
                          E-mail:  pluo@casa-systems.com

                          Peng Luo 
                          Casa Systems, Inc. "
            DESCRIPTION
                    "MIB module definition for Casa systems inc."
            REVISION     "200603220000Z"
            DESCRIPTION
                    "Initial creation."
            REVISION     "200603220000Z"
            DESCRIPTION
                    "CASA mib root"
            ::= { enterprises 20858 }

    END
