-- *****************************************************************************
-- Unisphere-Data-Policy-Manager-CONF
--
-- SNMP Agent Capabilities definitions for the Policy Manager MIB.
--
-- Copyright (c) 2001, 2002 Unisphere Networks, Inc.
-- Copyright (c) 2002 Juniper Networks, Inc.
--   All rights reserved.
-- *****************************************************************************

Unisphere-Data-Policy-Manager-CONF DEFINITIONS ::= BEGIN

IMPORTS
    MODULE-IDENTITY, OBJECT-IDENTITY
        FROM SNMPv2-SMI
    AGENT-CAPABILITIES
        FROM SNMPv2-CONF
    usDataAgents
        FROM Unisphere-Data-Agents
    usdPolicyBaseGroup, usdClassifierControlListGroup2, usdPolicyIfAttachGroup,
    usdPolicyAttachProfileGroup, usdPolicyAttachStatisticsGroup,
    usdRateLimitGroup, usdTrafficShapeGroup, usdLogRuleGroup,
    usdNextHopRulesGroup, usdFilterRulesGroup, usdNextInterfaceRulesGroup,
    usdMarkingRulesGroup, usdForwardRulesGroup, usdColorRulesGroup,
    usdTrafficClassRulesGroup, usdRateLimitGroup2
        FROM Unisphere-Data-POLICY-MIB;

usdPolicyManagerAgent MODULE-IDENTITY
    LAST-UPDATED "200208021207Z"  -- 02-Aug-02 08:07 AM EDT
    ORGANIZATION "Juniper Networks, Inc."
    CONTACT-INFO
        "       Juniper Networks, Inc.
        Postal: 10 Technology Park Drive
                Westford, MA  01886
                USA
        Tel:    +1 978 589 5800
        E-mail: mib@UnisphereNetworks.com"
    DESCRIPTION
        "The agent capabilities definitions for the Policy Manager component of
        the SNMP agent in the Unisphere Routing Switch family of products."
    -- Revision History
    REVISION    "200208021207Z"  -- 02-Aug-02 08:07 AM EDT  - RX 4.0
    DESCRIPTION
        "Added a capabilities statement for traffic class rules management.
         Extended rate limit profile objects.
         Obsoleted policy traffic shaped capabilities."
    REVISION    "200109071527Z"  -- 07-Sep-01 11:27 AM EDT  - RX 3.2
    DESCRIPTION
        "The initial release of this management information module."
    ::= { usDataAgents 31 }


-- *****************************************************************************
-- The basic Policy Manager agent capabilities.
-- *****************************************************************************
usdPolicyManagerBaseAgent OBJECT-IDENTITY
    STATUS      current
    DESCRIPTION
        "The basic Policy Manager component of the Policy Manager application.
        MIB support for each specific policy rule type can run as a subcomponent
        in addition to this base component."
    ::= { usdPolicyManagerAgent 1 }

usdPolicyManagerBaseAgentV1 AGENT-CAPABILITIES
    PRODUCT-RELEASE
        "Version 1 of the Policy Manager base component of the Unisphere Routing
        Switch SNMP agent.  This version of the Policy Manager base component is
        supported in the Unisphere RX 3.2 and subsequent system releases."
    STATUS      current
    DESCRIPTION
        "The MIB groups supported by the SNMP agent for the base component of
        the Policy Manager application in the Unisphere Routing Switch."
    SUPPORTS    Unisphere-Data-POLICY-MIB
        INCLUDES  {
            usdPolicyBaseGroup,
            usdClassifierControlListGroup2,
            usdPolicyIfAttachGroup,
            usdPolicyAttachProfileGroup,
            usdPolicyAttachStatisticsGroup }
    ::= { usdPolicyManagerBaseAgent 1 }


-- *****************************************************************************
-- The rate limit Policy Manager agent capabilities.
-- *****************************************************************************
usdPolicyManagerRateLimitAgent OBJECT-IDENTITY
    STATUS      current
    DESCRIPTION
        "The rate limit policy management component of the Policy Manager
        application.  MIB support for this specific policy rule type
        subcomponent can run independently of the other subcomponents but
        requires the base component."
    ::= { usdPolicyManagerAgent 2 }

usdPolicyManagerRateLimitAgentV1 AGENT-CAPABILITIES
    PRODUCT-RELEASE
        "Version 1 of the rate limit management subcomponent of the Policy
        Manager component of the Unisphere Routing Switch SNMP agent.  This
        version of the rate limit policy management subcomponent was supported
        in the Unisphere RX 3.2 and subsequent 3.x system releases."
    STATUS      obsolete
    DESCRIPTION
        "The MIB group supported by the SNMP agent for the rate limit policy
        management subcomponent of the Policy Manager application in the
        Unisphere Routing Switch.  These capabilities became obsolete when
        support was added for new rate limit objects."
    SUPPORTS    Unisphere-Data-POLICY-MIB
        INCLUDES  {
            usdRateLimitGroup }
    ::= { usdPolicyManagerRateLimitAgent 1 }

usdPolicyManagerRateLimitAgentV2 AGENT-CAPABILITIES
    PRODUCT-RELEASE
        "Version 2 of the rate limit management subcomponent of the Policy
        Manager component of the Unisphere Routing Switch SNMP agent.  This
        version of the rate limit policy management subcomponent is supported in
        the Unisphere RX 4.0 and subsequent system releases."
    STATUS      current
    DESCRIPTION
        "The MIB group supported by the SNMP agent for the rate limit policy
        management subcomponent of the Policy Manager application in the
        Unisphere Routing Switch."
    SUPPORTS    Unisphere-Data-POLICY-MIB
        INCLUDES  {
            usdRateLimitGroup2 }
    ::= { usdPolicyManagerRateLimitAgent 2 }


-- *****************************************************************************
-- The traffic shape Policy Manager agent capabilities.
-- *****************************************************************************
usdPolicyManagerTrafficShapeAgent OBJECT-IDENTITY
    STATUS      current
    DESCRIPTION
        "The traffic shape policy management component of the Policy Manager
        application.  MIB support for this specific policy rule type
        subcomponent can run independently of the other subcomponents but
        requires the base component."
    ::= { usdPolicyManagerAgent 3 }

usdPolicyManagerTrafficShapeAgentV1 AGENT-CAPABILITIES
    PRODUCT-RELEASE
        "Version 1 of the traffic shape management subcomponent of the Policy
        Manager component of the Unisphere Routing Switch SNMP agent.  This
        version of the traffic shape policy management subcomponent was
        supported in the Unisphere RX 3.2 and subsequent 3.x system releases. "
    STATUS      obsolete
    DESCRIPTION
        "The MIB group supported by the SNMP agent for the traffic shape policy
        management subcomponent of the Policy Manager application in the
        Unisphere Routing Switch.  These capabilities became obsolete when the
        policy shaper capability was moved into the quality of service
        component."
    SUPPORTS    Unisphere-Data-POLICY-MIB
        INCLUDES  {
            usdTrafficShapeGroup }
    ::= { usdPolicyManagerTrafficShapeAgent 1 }


-- *****************************************************************************
-- The log rules Policy Manager agent capabilities.
-- *****************************************************************************
usdPolicyManagerLogRulesAgent OBJECT-IDENTITY
    STATUS      current
    DESCRIPTION
        "The log policy rules component of the Policy Manager application.  MIB
        support for this specific policy rule type subcomponent requires the
        base component but can run independently of the other subcomponents."
    ::= { usdPolicyManagerAgent 4 }

usdPolicyManagerLogRulesAgentV1 AGENT-CAPABILITIES
    PRODUCT-RELEASE
        "Version 1 of the log rules subcomponent of the Policy Manager component
        of the Unisphere Routing Switch SNMP agent.  This version of the log
        policy rules subcomponent is supported in the Unisphere RX 3.2 and
        subsequent system releases."
    STATUS      current
    DESCRIPTION
        "The MIB group supported by the SNMP agent for the log policy rules
        subcomponent of the Policy Manager application in the Unisphere Routing
        Switch."
    SUPPORTS    Unisphere-Data-POLICY-MIB
        INCLUDES  {
            usdLogRuleGroup }
    ::= { usdPolicyManagerLogRulesAgent 1 }


-- *****************************************************************************
-- The next-hop rules Policy Manager agent capabilities.
-- *****************************************************************************
usdPolicyManagerNextHopRulesAgent OBJECT-IDENTITY
    STATUS      current
    DESCRIPTION
        "The next-hop policy rules component of the Policy Manager application.
        MIB support for this specific policy rule type subcomponent can run
        independently of the other subcomponents but requires the base
        component."
    ::= { usdPolicyManagerAgent 5 }

usdPolicyManagerNextHopRulesAgentV1 AGENT-CAPABILITIES
    PRODUCT-RELEASE
        "Version 1 of the next-hop rules subcomponent of the Policy Manager
        component of the Unisphere Routing Switch SNMP agent.  This version of
        the next-hop policy rules subcomponent is supported in the Unisphere RX
        3.2 and subsequent system releases."
    STATUS      current
    DESCRIPTION
        "The MIB group supported by the SNMP agent for the next-hop policy rules
        subcomponent of the Policy Manager application in the Unisphere Routing
        Switch."
    SUPPORTS    Unisphere-Data-POLICY-MIB
        INCLUDES  {
            usdNextHopRulesGroup }
    ::= { usdPolicyManagerNextHopRulesAgent 1 }


-- *****************************************************************************
-- The filter rules Policy Manager agent capabilities.
-- *****************************************************************************
usdPolicyManagerFilterRulesAgent OBJECT-IDENTITY
    STATUS      current
    DESCRIPTION
        "The filter policy rules component of the Policy Manager application.
        MIB support for this specific policy rule type subcomponent requires the
        base component but can run independently of the other subcomponents."
    ::= { usdPolicyManagerAgent 6 }

usdPolicyManagerFilterRulesAgentV1 AGENT-CAPABILITIES
    PRODUCT-RELEASE
        "Version 1 of the filter rules subcomponent of the Policy Manager
        component of the Unisphere Routing Switch SNMP agent.  This version of
        the filter policy rules subcomponent is supported in the Unisphere RX
        3.2 and subsequent system releases."
    STATUS      current
    DESCRIPTION
        "The MIB group supported by the SNMP agent for the filter policy rules
        subcomponent of the Policy Manager application in the Unisphere Routing
        Switch."
    SUPPORTS    Unisphere-Data-POLICY-MIB
        INCLUDES  {
            usdFilterRulesGroup }
    ::= { usdPolicyManagerFilterRulesAgent 1 }


-- *****************************************************************************
-- The next-interface rules Policy Manager agent capabilities.
-- *****************************************************************************
usdPolicyManagerNextInterfaceRulesAgent OBJECT-IDENTITY
    STATUS      current
    DESCRIPTION
        "The next-interface policy rules component of the Policy Manager
        application.  MIB support for this specific policy rule type
        subcomponent requires the base component but can run independently of
        the other subcomponents."
    ::= { usdPolicyManagerAgent 7 }

usdPolicyManagerNextInterfaceRulesAgentV1 AGENT-CAPABILITIES
    PRODUCT-RELEASE
        "Version 1 of the next-interface rules subcomponent of the Policy
        Manager component of the Unisphere Routing Switch SNMP agent.  This
        version of the next-interface policy rules subcomponent is supported in
        the Unisphere RX 3.2 and subsequent system releases."
    STATUS      current
    DESCRIPTION
        "The MIB group supported by the SNMP agent for the next-interface policy
        rules subcomponent of the Policy Manager application in the Unisphere
        Routing Switch."
    SUPPORTS    Unisphere-Data-POLICY-MIB
        INCLUDES  {
            usdNextInterfaceRulesGroup }
    ::= { usdPolicyManagerNextInterfaceRulesAgent 1 }


-- *****************************************************************************
-- The marking rules Policy Manager agent capabilities.
-- *****************************************************************************
usdPolicyManagerMarkingRulesAgent OBJECT-IDENTITY
    STATUS      current
    DESCRIPTION
        "The marking policy rules component of the Policy Manager application.
        MIB support for this specific policy rule type subcomponent requires the
        base component but can run independently of the other subcomponents."
    ::= { usdPolicyManagerAgent 8 }

usdPolicyManagerMarkingRulesAgentV1 AGENT-CAPABILITIES
    PRODUCT-RELEASE
        "Version 1 of the marking rules subcomponent of the Policy Manager
        component of the Unisphere Routing Switch SNMP agent.  This version of
        the marking policy rules subcomponent is supported in the Unisphere RX
        3.2 and subsequent system releases."
    STATUS      current
    DESCRIPTION
        "The MIB group supported by the SNMP agent for the marking policy rules
        subcomponent of the Policy Manager application in the Unisphere Routing
        Switch."
    SUPPORTS    Unisphere-Data-POLICY-MIB
        INCLUDES  {
            usdMarkingRulesGroup }
    ::= { usdPolicyManagerMarkingRulesAgent 1 }


-- *****************************************************************************
-- The forward rules Policy Manager agent capabilities.
-- *****************************************************************************
usdPolicyManagerForwardRulesAgent OBJECT-IDENTITY
    STATUS      current
    DESCRIPTION
        "The forward policy rules component of the Policy Manager application.
        MIB support for this specific policy rule type subcomponent requires the
        base component but can run independently of the other subcomponents."
    ::= { usdPolicyManagerAgent 9 }

usdPolicyManagerForwardRulesAgentV1 AGENT-CAPABILITIES
    PRODUCT-RELEASE
        "Version 1 of the forward rules subcomponent of the Policy Manager
        component of the Unisphere Routing Switch SNMP agent.  This version of
        the forward policy rules subcomponent is supported in the Unisphere RX
        3.2 and subsequent system releases."
    STATUS      current
    DESCRIPTION
        "The MIB group supported by the SNMP agent for the forward policy rules
        subcomponent of the Policy Manager application in the Unisphere Routing
        Switch."
    SUPPORTS    Unisphere-Data-POLICY-MIB
        INCLUDES  {
            usdForwardRulesGroup }
    ::= { usdPolicyManagerForwardRulesAgent 1 }


-- *****************************************************************************
-- The color rules Policy Manager agent capabilities.
-- *****************************************************************************
usdPolicyManagerColorRulesAgent OBJECT-IDENTITY
    STATUS      current
    DESCRIPTION
        "The color policy rules component of the Policy Manager application.
        MIB support for this specific policy rule type subcomponent requires the
        base component but can run independently of the other subcomponents."
    ::= { usdPolicyManagerAgent 10 }

usdPolicyManagerColorRulesAgentV1 AGENT-CAPABILITIES
    PRODUCT-RELEASE
        "Version 1 of the color rules subcomponent of the Policy Manager
        component of the Unisphere Routing Switch SNMP agent.  This version of
        the color policy rules subcomponent is supported in the Unisphere RX 3.2
        and subsequent system releases."
    STATUS      current
    DESCRIPTION
        "The MIB group supported by the SNMP agent for the color policy rules
        subcomponent of the Policy Manager application in the Unisphere Routing
        Switch."
    SUPPORTS    Unisphere-Data-POLICY-MIB
        INCLUDES  {
            usdColorRulesGroup }
    ::= { usdPolicyManagerColorRulesAgent 1 }


-- *****************************************************************************
-- The traffic class rules Policy Manager agent capabilities.
-- *****************************************************************************
usdPolicyManagerTrafficClassRulesAgent OBJECT-IDENTITY
    STATUS      current
    DESCRIPTION
        "The traffic class policy rules component of the Policy Manager
        application.  MIB support for this specific policy rule type
        subcomponent requires the base component but can run independently of
        the other subcomponents."
    ::= { usdPolicyManagerAgent 11 }

usdPolicyManagerTrafficClassRulesAgentV1 AGENT-CAPABILITIES
    PRODUCT-RELEASE
        "Version 1 of the traffic class rules subcomponent of the Policy Manager
        component of the Unisphere Routing Switch SNMP agent.  This version of
        the traffic class policy rules subcomponent is supported in the
        Unisphere RX 4.0 and subsequent system releases."
    STATUS      current
    DESCRIPTION
        "The MIB group supported by the SNMP agent for the traffic class policy
        rules subcomponent of the Policy Manager application in the Unisphere
        Routing Switch."
    SUPPORTS    Unisphere-Data-POLICY-MIB
        INCLUDES  {
            usdTrafficClassRulesGroup }
    ::= { usdPolicyManagerTrafficClassRulesAgent 1 }

END
