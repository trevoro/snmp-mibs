STREAMCORE-MIB DEFINITIONS ::= BEGIN

-- ==========================================================================
-- Copyright (c) 2001 StreamCORE
--
-- Auteur: Laurent HOUDARD (LH) - 17 Jul 2001
--
-- Ajouts: Mathias Boivin - 26 nov 2007
--
-- Nom   : STREAMCORE-MIB.txt
--
-- Description :
--
-- $Id: hp-STREAMCORE-MIB.txt,v 1.3 2007/01/10 10:38:59 lh Exp $
--
-- ==========================================================================

IMPORTS
    OBJECT-TYPE, NOTIFICATION-TYPE,
    Integer32, MODULE-IDENTITY, OBJECT-IDENTITY, enterprises  FROM SNMPv2-SMI
    TEXTUAL-CONVENTION                             FROM SNMPv2-TC
    MODULE-COMPLIANCE, NOTIFICATION-GROUP,
    OBJECT-GROUP                                   FROM SNMPv2-CONF
    Unsigned32, Gauge32                            FROM SNMPv2-SMI;

streamcore MODULE-IDENTITY
    LAST-UPDATED "200107170000Z"
    ORGANIZATION "StreamCore"
    CONTACT-INFO
            "        
             Postal: StreamCore
                     Immeuble Avant-Seine
                     11-15, Quai de Dion Bouton
                     92800 Puteaux
                     France

             Phone:  +33 (0)1 47 86 83 10
             Email:  support@streamcore.com"
    DESCRIPTION
            "The top-level MIB module for managing StreamCore equipments."
    REVISION     "200107170000Z"
    DESCRIPTION
            "Initial revision."
    ::= { enterprises 4056 } -- assigned by IANA

--
-- StreamCore Products objects identifiers
--

scProducts OBJECT-IDENTITY
    STATUS  current
    DESCRIPTION
        "scProducts is the root OBJECT IDENTIFIER from
        which sysObjectID values are assigned."
    ::= { streamcore 1 }

--
-- Streamcore products objects identifiers
--

streamGroomerManager OBJECT IDENTIFIER ::= { scProducts 1 }

streamGroomer        OBJECT IDENTIFIER ::= { scProducts 2 }

  sg100              OBJECT IDENTIFIER ::= { streamGroomer 1 }
  sg200              OBJECT IDENTIFIER ::= { streamGroomer 2 }
  sg400              OBJECT IDENTIFIER ::= { streamGroomer 3 }

  sg150              OBJECT IDENTIFIER ::= { streamGroomer 4 }
  sg250              OBJECT IDENTIFIER ::= { streamGroomer 5 }
  sg420              OBJECT IDENTIFIER ::= { streamGroomer 6 }
  sg800              OBJECT IDENTIFIER ::= { streamGroomer 7 }
  sg1600             OBJECT IDENTIFIER ::= { streamGroomer 8 }
  sg3200             OBJECT IDENTIFIER ::= { streamGroomer 9 }

--
-- StreamCore MIB modules
--

scMibs OBJECT-IDENTITY
    STATUS  current
    DESCRIPTION
        "not used"
    ::= { streamcore 2 }

--
-- StreamCore Traps
--


scTraps OBJECT-IDENTITY
    STATUS  current
    DESCRIPTION
        "Streamcore Traps"
    ::= { streamcore 3 }

scTrapsPrefix OBJECT-IDENTITY
    STATUS  current
    DESCRIPTION
        "This level with the 0 sub-identifier is used to make
        this MIB translate to an SNMPv1 format in a reversible way."
    ::= { scTraps 0 }

scGenericTraps OBJECT-IDENTITY
    STATUS  current
    DESCRIPTION
        "generic traps."
    ::= { scTrapsPrefix 1 }

scSGMTraps OBJECT-IDENTITY
    STATUS  current
    DESCRIPTION
        "SGM traps."
    ::= { scTrapsPrefix 2 }

scSGTraps OBJECT-IDENTITY
    STATUS  current
    DESCRIPTION
        "SG traps."
    ::= { scTrapsPrefix 3 }


scMIBConformance
               OBJECT IDENTIFIER ::= { scMibs 3 }

scMIBCompliances
               OBJECT IDENTIFIER ::= { scMIBConformance 1 }
scMIBGroups
               OBJECT IDENTIFIER ::= { scMIBConformance 2 }


scCompliance MODULE-COMPLIANCE
    STATUS  current
    DESCRIPTION
            "The compliance statement for SNMP entities which
            implement this MIB module."
    MODULE  -- this module
        MANDATORY-GROUPS { scNotificationsGroup, scAdvancedTrapGroup }

        GROUP   scTraps
        DESCRIPTION
            "This group is mandatory for SNMP entities which
            support community-based authentication."
        
    ::= { scMIBCompliances 1 }


scNotificationsGroup NOTIFICATION-GROUP
    NOTIFICATIONS { scQosStatusChange, scFreeMemory, scTotalNumberRulesExceeded,
                    scHDPartitionNearlyFull, scLoadTooHigh, scFreeMemoryTooLow, scHDFailure }
    STATUS        current
    DESCRIPTION
       "The basic notifications group defines notifications which are specific to streamcore managed traps."
    ::= { scMIBGroups 1 }


scAdvancedTrapGroup OBJECT-GROUP
    OBJECTS { scQosOperStatus, scFreeStaticMemory, scFreeDynamicMemory }
    STATUS  current
    DESCRIPTION
            "The advanced group defines objects which are used in streamcore managed traps."
    ::= { scMIBGroups 2 }



scLoadTooHigh  NOTIFICATION-TYPE
    STATUS      current
    DESCRIPTION
        "load too high trap"
    ::= { scGenericTraps 1 }


scTotalNumberRulesExceeded  NOTIFICATION-TYPE
    STATUS      current
    DESCRIPTION
        "total number of rules have been exceeded on "
    ::= { scSGMTraps 1 }

scHDPartitionNearlyFull  NOTIFICATION-TYPE
    STATUS      current
    DESCRIPTION
        "partition nearly full trap"
    ::= { scSGMTraps 2 }

scFreeMemoryTooLow  NOTIFICATION-TYPE
    STATUS      current
    DESCRIPTION
        "free memory too low trap"
    ::= { scSGMTraps 3 }

scHDFailure  NOTIFICATION-TYPE
    STATUS      current
    DESCRIPTION
        "HD failure trap"
    ::= { scSGMTraps 4 }

scBackupSGMConnFailed  NOTIFICATION-TYPE
    STATUS      current
    DESCRIPTION
        "can't connect to SGM partner"
    ::= { scSGMTraps 5 }

scBackupSGMConnLost  NOTIFICATION-TYPE
    STATUS      current
    DESCRIPTION
        "connection to SGM partner lost"
    ::= { scSGMTraps 6 }

scBackupSGMConnOk  NOTIFICATION-TYPE
    STATUS      current
    DESCRIPTION
        "connected to SGM partner"
    ::= { scSGMTraps 7 }

scBackupSGMStandby  NOTIFICATION-TYPE
    STATUS      current
    DESCRIPTION
        "SGM is on Standby"
    ::= { scSGMTraps 8 }

scBackupSGM  NOTIFICATION-TYPE
    STATUS      current
    DESCRIPTION
        "backup SGM state"
    ::= { scSGMTraps 9 }

scBackupSGMStatus  NOTIFICATION-TYPE
    STATUS      current
    DESCRIPTION
        "backup SGM status"
    ::= { scSGMTraps 10 }

scBackupSGMSync  NOTIFICATION-TYPE
    STATUS      current
    DESCRIPTION
        "SGM is synchronizing"
    ::= { scSGMTraps 11 }

scBackupSGMSyncStatus  NOTIFICATION-TYPE
    STATUS      current
    DESCRIPTION
        "state of last synchronisation"
    ::= { scSGMTraps 12 }

scBackupSGM  NOTIFICATION-TYPE
    STATUS      current
    DESCRIPTION
        "change of SGM status trap"
    ::= { scSGMTraps 13 }

scFreeMemory NOTIFICATION-TYPE
    OBJECTS { scFreeStaticMemory, scFreeDynamicMemory }
    STATUS  current
    DESCRIPTION
        "This trap is sent whenever one of the four types of memory storage
        monitored in a StreamGroomer goes below a specific threshold."
    ::= { scSGTraps 1 }

scQosStatusChange NOTIFICATION-TYPE
    OBJECTS { scQosOperStatus }
    STATUS  current
    DESCRIPTION
        "This trap is sent whenever the StreamGroomer's QOS status changes.
        The new status is defined by the scQosOperStatus variable."
    ::= { scSGTraps 2 }

scAvgRate NOTIFICATION-TYPE
    STATUS  current
    DESCRIPTION
        "This trap is sent whenever the average rate is too low."
    ::= { scSGTraps 3 }

scRateDistributionN3 NOTIFICATION-TYPE
    STATUS  current
    DESCRIPTION
        "This trap is sent whenever the percent of time with a rate use higher of 50% too high."
    ::= { scSGTraps 4 }

scRateDistributionN4 NOTIFICATION-TYPE
    STATUS  current
    DESCRIPTION
        "This trap is sent whenever the percent of time with a rate use higher of 75% too high."
    ::= { scSGTraps 5 }

scRateDistributionN5 NOTIFICATION-TYPE
    STATUS  current
    DESCRIPTION
        "This trap is sent whenever the percent of time with a rate use higher of 90% too high."
    ::= { scSGTraps 6 }

scAvgActivity NOTIFICATION-TYPE
    STATUS  current
    DESCRIPTION
        "This trap is sent whenever the average QoS activity is too high."
    ::= { scSGTraps 7 }

scAvgStress NOTIFICATION-TYPE
    STATUS  current
    DESCRIPTION
        "This trap is sent whenever the average stress is too high."
    ::= { scSGTraps 8 }

scAvgRtt NOTIFICATION-TYPE
    STATUS  current
    DESCRIPTION
        "This trap is sent whenever the average round-trip time is too high."
    ::= { scSGTraps 9 }

scAvgWanRtt NOTIFICATION-TYPE
    STATUS  current
    DESCRIPTION
        "This trap is sent whenever the average Wan round-trip time is too high."
    ::= { scSGTraps 10 }

scAvgLanRtt NOTIFICATION-TYPE
    STATUS  current
    DESCRIPTION
        "This trap is sent whenever the average Lan round-trip time is too high."
    ::= { scSGTraps 11 }

scAccessLinkDisponibility NOTIFICATION-TYPE
    STATUS  current
    DESCRIPTION
        "This trap is sent whenever the access link availability is too low."
    ::= { scSGTraps 12 }

scJitter NOTIFICATION-TYPE
    STATUS  current
    DESCRIPTION
        "This trap is sent whenever the jitter is too high."
    ::= { scSGTraps 13 }

scGroomingLoss NOTIFICATION-TYPE
    STATUS  current
    DESCRIPTION
        "This trap is sent whenever the grooming link loss ratio is too high."
    ::= { scSGTraps 14 }

scTcpCallsNb NOTIFICATION-TYPE
    STATUS  current
    DESCRIPTION
        "This trap is sent whenever the TCP calls/minute number is too high."
    ::= { scSGTraps 15 }

scAvgCnxNb NOTIFICATION-TYPE
    STATUS  current
    DESCRIPTION
        "This trap is sent whenever the average connections number is too high."
    ::= { scSGTraps 16 }

scRetransmitRatio NOTIFICATION-TYPE
    STATUS  current
    DESCRIPTION
        "This trap is sent whenever the TCP retransmit ratio is too high."
    ::= { scSGTraps 17 }

scAvailableRate NOTIFICATION-TYPE
    STATUS  current
    DESCRIPTION
        "This trap is sent whenever the available rate is too low."
    ::= { scSGTraps 18 }

scTcpDelayTotal NOTIFICATION-TYPE
    STATUS  current
    DESCRIPTION
        "This trap is sent whenever the total delay time is too high."
    ::= { scSGTraps 19 }

scTcpDelayNetwork NOTIFICATION-TYPE
    STATUS  current
    DESCRIPTION
        "This trap is sent whenever the network delay time is too high."
    ::= { scSGTraps 20 }

scTcpDelayServer NOTIFICATION-TYPE
    STATUS  current
    DESCRIPTION
        "This trap is sent whenever the server delay time is too high."
    ::= { scSGTraps 21 }

scTcpDelayDistributionPeriod3 NOTIFICATION-TYPE
    STATUS  current
    DESCRIPTION
        "This trap is sent whenever the % of time with: Application response time > 300 is too high."
    ::= { scSGTraps 22 }

scTcpDelayDistributionPeriod4 NOTIFICATION-TYPE
    STATUS  current
    DESCRIPTION
        "This trap is sent whenever the % of time with: Application response time > 600 is too high."
    ::= { scSGTraps 23 }

scTcpDelayDistributionPeriod5 NOTIFICATION-TYPE
    STATUS  current
    DESCRIPTION
        "This trap is sent whenever the % of time with: Application response time > 1000 is too high."
    ::= { scSGTraps 24 }

scVoipDelay NOTIFICATION-TYPE
    STATUS  current
    DESCRIPTION
        "This trap is sent whenever the VoIP delay is too high."
    ::= { scSGTraps 25 }

scVoipLoss NOTIFICATION-TYPE
    STATUS  current
    DESCRIPTION
        "This trap is sent whenever the VoIP loss is too high."
    ::= { scSGTraps 26 }

scVoipMoslq26 NOTIFICATION-TYPE
    STATUS  current
    DESCRIPTION
        "This trap is sent whenever the VoIP 2.1 quality attain a threshold."
    ::= { scSGTraps 27 }

scVoipMoslq31 NOTIFICATION-TYPE
    STATUS  current
    DESCRIPTION
        "This trap is sent whenever the VoIP 3.1 quality attain a threshold."
    ::= { scSGTraps 28 }

scVoipMoslq36 NOTIFICATION-TYPE
    STATUS  current
    DESCRIPTION
        "This trap is sent whenever the VoIP 3.6 quality attain a threshold."
    ::= { scSGTraps 29 }

scVoipMoslq40 NOTIFICATION-TYPE
    STATUS  current
    DESCRIPTION
        "This trap is sent whenever the VoIP 4.0 quality attain a threshold."
    ::= { scSGTraps 30 }

scVoipMoslq NOTIFICATION-TYPE
    STATUS  current
    DESCRIPTION
        "This trap is sent whenever the VoIP MosLQ is too low."
    ::= { scSGTraps 31 }

scVoipMoscq NOTIFICATION-TYPE
    STATUS  current
    DESCRIPTION
        "This trap is sent whenever the VoIP MosCQ is too low."
    ::= { scSGTraps 32 }

scDualTandemSG NOTIFICATION-TYPE
    STATUS  current
    DESCRIPTION
        "This trap is sent whenever the status up/down of a dual or tandem SG changes."
    ::= { scSGTraps 33 }

scGroomingDisponibility NOTIFICATION-TYPE
    STATUS  current
    DESCRIPTION
        "This trap is sent whenever the disponibility of a grooming fall under a limit."
    ::= { scSGTraps 34 }

scNbConversations NOTIFICATION-TYPE
    STATUS  current
    DESCRIPTION
        "This trap is sent whenever the number of VoIP conversation attain a threshold."
    ::= { scSGTraps 35 }

scQosAskedStatusChange NOTIFICATION-TYPE
    STATUS  current
    DESCRIPTION
        "This trap is sent whenever the customer ask the StreamGroomer's QOS status to change.
        The new status is defined by the scQosOperStatus variable."
    ::= { scSGTraps 36 }

scTrapsObjects OBJECT-IDENTITY
    STATUS  current
    DESCRIPTION
        "Auxiliary objects used in Streamcore traps"
    ::= { scTraps 1 }

scQosOperStatus  OBJECT-TYPE
    SYNTAX      INTEGER {
        boot(1),
        ope-bypass(2),
        ope-monitoring(3),
        ope-optimisation(4),
        ope-tap(6)
    }
    MAX-ACCESS  accessible-for-notify
    STATUS      current
    DESCRIPTION
        "status of SGM"
    ::= { scTrapsObjects 1 }

scFreeStaticMemory  OBJECT-TYPE
    SYNTAX      Integer32
    MAX-ACCESS  accessible-for-notify
    STATUS      current
    DESCRIPTION
        "free static memory trap in percent."
    ::= { scTrapsObjects 2 }

scFreeDynamicMemory  OBJECT-TYPE
    SYNTAX      Integer32
    MAX-ACCESS  accessible-for-notify
    STATUS      current
    DESCRIPTION
        "free dynamic memory trap in percent."
    ::= { scTrapsObjects 3 }

scGetRatioValue  OBJECT-TYPE
    SYNTAX      Integer32 (0..100)
    MAX-ACCESS  accessible-for-notify
    STATUS      current
    DESCRIPTION
        "ratio variable object. Integer between 0 and 100 representing a percent."
    ::= { scTrapsObjects 4 }

scGetRealValue  OBJECT-TYPE
    SYNTAX      TextualNumber
    MAX-ACCESS  accessible-for-notify
    STATUS      current
    DESCRIPTION
        "real/integer/text variable object"
    ::= { scTrapsObjects 5 }

scLeftValue  OBJECT-TYPE
    SYNTAX      TextualNumber
    MAX-ACCESS  accessible-for-notify
    STATUS      current
    DESCRIPTION
        "left real/integer variable object."
    ::= { scTrapsObjects 6 }

scRightValue  OBJECT-TYPE
    SYNTAX      TextualNumber
    MAX-ACCESS  accessible-for-notify
    STATUS      current
    DESCRIPTION
        "right real/integer variable object."
    ::= { scTrapsObjects 7 }

scTypeValue  OBJECT-TYPE
    SYNTAX      OCTET STRING
    MAX-ACCESS  accessible-for-notify
    STATUS      current
    DESCRIPTION
        "string precising the type of the alarm sent variable object"
    ::= { scTrapsObjects 8 }

scStateValue  OBJECT-TYPE
    SYNTAX      INTEGER {
        rearmed(0),
        activated(1)
    }
    MAX-ACCESS  accessible-for-notify
    STATUS      current
    DESCRIPTION
        "integer indicating if the alarm sent is activated or rearmed variable object"
    ::= { scTrapsObjects 9 }

scAlarmIdValue  OBJECT-TYPE
    SYNTAX      Integer32
    MAX-ACCESS  accessible-for-notify
    STATUS      current
    DESCRIPTION
        "this integer indicate the ID of the alarm sent"
    ::= { scTrapsObjects 10 }

--
-- Textual convensions used in MIB modules
--

StreamGroomerId ::= TEXTUAL-CONVENTION
    STATUS current
    DESCRIPTION
        "SG id"
    SYNTAX Unsigned32

ScId ::= TEXTUAL-CONVENTION
    STATUS current
    DESCRIPTION
        "Sc id"
    SYNTAX Unsigned32

ScAdminStatus ::= TEXTUAL-CONVENTION
    STATUS current
    DESCRIPTION
        "Sc admin status"
    SYNTAX INTEGER {
        down(0),
        up(1)
    }

TextualNumber ::= TEXTUAL-CONVENTION
        STATUS      current
        DESCRIPTION
            "Definition of the real number's translation type "
        SYNTAX OCTET STRING

END
