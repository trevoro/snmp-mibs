Nortel-MsCarrier-MscPassport-SnaMIB
DEFINITIONS ::= BEGIN



IMPORTS

      OBJECT-TYPE
   FROM RFC-1212

      mscPassportMIBs
   FROM Nortel-MsCarrier-MscPassport-UsefulDefinitionsMIB

      Counter32,
      RowPointer,
      DisplayString,
      StorageType,
      RowStatus,
      Gauge32,
      Integer32,
      Unsigned32
   FROM Nortel-MsCarrier-MscPassport-StandardTextualConventionsMIB

      DashedHexString,
      NonReplicated,
      HexString
   FROM Nortel-MsCarrier-MscPassport-TextualConventionsMIB

      mscVrIndex,
      mscVrPp,
      mscVrPpIndex,
      mscVr
   FROM Nortel-MsCarrier-MscPassport-VirtualRouterMIB;




-- LAST-UPDATED   "9909010000Z"
-- ORGANIZATION   "Nortel Networks"
-- CONTACT-INFO   "
--         Nortel Carrier Data Network Management
--         
--         Postal:       P.O. Box 3511, Station C 
--                       Ottawa, Ontario 
--                       Canada  K1Y 4H7
--         
--         via the WEB:  http://www.nortelnetworks.com  
--                       select 'Contact Us' from the menu
--          
--         via phone:    1-800-4NORTEL"
-- DESCRIPTION
--    "The module describing the Nortel MsCarrier MscPassport
--     Sna Enterprise MIB."

snaMIB OBJECT IDENTIFIER ::= { mscPassportMIBs 56 }










-- Vr/<string> Pp/<string> SnaPort
-- The SnaPort component contains DLR attributes specific to this 
-- port. A semantic check verifies that an SnaPort component cannot 
-- be added or deleted unless an Sna component under VR is present.

mscVrPpSnaPort OBJECT IDENTIFIER ::= { mscVrPp 15 }



mscVrPpSnaPortRowStatusTable OBJECT-TYPE
   SYNTAX     SEQUENCE OF MscVrPpSnaPortRowStatusEntry
   ACCESS     not-accessible
   STATUS     mandatory
   DESCRIPTION
     "This entry controls the addition and deletion of 
      mscVrPpSnaPort components."
::= { mscVrPpSnaPort 1 }

mscVrPpSnaPortRowStatusEntry OBJECT-TYPE
   SYNTAX     MscVrPpSnaPortRowStatusEntry
   ACCESS     not-accessible
   STATUS     mandatory
   DESCRIPTION
     "A single entry in the table represents a single 
      mscVrPpSnaPort component."
   INDEX {
      mscVrIndex,
      mscVrPpIndex,
      mscVrPpSnaPortIndex }
::= { mscVrPpSnaPortRowStatusTable 1 }

MscVrPpSnaPortRowStatusEntry ::= SEQUENCE {
   mscVrPpSnaPortRowStatus
      RowStatus,
   mscVrPpSnaPortComponentName
      DisplayString,
   mscVrPpSnaPortStorageType
      StorageType,
   mscVrPpSnaPortIndex
      NonReplicated }

mscVrPpSnaPortRowStatus OBJECT-TYPE
   SYNTAX     RowStatus 
   ACCESS     read-write
   STATUS     mandatory
   DESCRIPTION
     "This variable is used as the basis for SNMP naming of
      mscVrPpSnaPort components.
      These components can be added and deleted."
::= { mscVrPpSnaPortRowStatusEntry 1 }

mscVrPpSnaPortComponentName OBJECT-TYPE
   SYNTAX     DisplayString 
   ACCESS     read-only
   STATUS     mandatory
   DESCRIPTION
     "This variable provides the component's string name for
      use with the ASCII Console Interface"
::= { mscVrPpSnaPortRowStatusEntry 2 }

mscVrPpSnaPortStorageType OBJECT-TYPE
   SYNTAX     StorageType 
   ACCESS     read-only
   STATUS     mandatory
   DESCRIPTION
     "This variable represents the storage type value for the
      mscVrPpSnaPort tables."
::= { mscVrPpSnaPortRowStatusEntry 4 }

mscVrPpSnaPortIndex OBJECT-TYPE
   SYNTAX     NonReplicated 
   ACCESS     not-accessible
   STATUS     mandatory
   DESCRIPTION
     "This variable represents the index for the mscVrPpSnaPort tables."
::= { mscVrPpSnaPortRowStatusEntry 10 }

mscVrPpSnaPortAdminControlTable OBJECT-TYPE
   SYNTAX     SEQUENCE OF MscVrPpSnaPortAdminControlEntry
   ACCESS     not-accessible
   STATUS     mandatory
   DESCRIPTION
     "This group includes the Administrative Control attribute. This 
      attribute defines the current administrative state of this component."
::= { mscVrPpSnaPort 100 }

mscVrPpSnaPortAdminControlEntry OBJECT-TYPE
   SYNTAX     MscVrPpSnaPortAdminControlEntry
   ACCESS     not-accessible
   STATUS     mandatory
   DESCRIPTION
     "An entry in the mscVrPpSnaPortAdminControlTable."
   INDEX {
      mscVrIndex,
      mscVrPpIndex,
      mscVrPpSnaPortIndex }
::= { mscVrPpSnaPortAdminControlTable 1 }

MscVrPpSnaPortAdminControlEntry ::= SEQUENCE {
   mscVrPpSnaPortSnmpAdminStatus
      INTEGER }

mscVrPpSnaPortSnmpAdminStatus OBJECT-TYPE
   SYNTAX     INTEGER  {
                 up(1),
                 down(2),
                 testing(3) }
   ACCESS     read-write
   STATUS     mandatory
   DESCRIPTION
     "The desired state of the interface. The up state indicates the 
      interface is operational and packet forwarding is allowed. The down 
      state indicates the interface is not operational and packet forwarding 
      is unavailable. The testing state indicates that no operational 
      packets can be passed."
   DEFVAL     { up }
::= { mscVrPpSnaPortAdminControlEntry 1 }

mscVrPpSnaPortProvTable OBJECT-TYPE
   SYNTAX     SEQUENCE OF MscVrPpSnaPortProvEntry
   ACCESS     not-accessible
   STATUS     mandatory
   DESCRIPTION
     "This group contains provisionable attributes for SNA ports."
::= { mscVrPpSnaPort 101 }

mscVrPpSnaPortProvEntry OBJECT-TYPE
   SYNTAX     MscVrPpSnaPortProvEntry
   ACCESS     not-accessible
   STATUS     mandatory
   DESCRIPTION
     "An entry in the mscVrPpSnaPortProvTable."
   INDEX {
      mscVrIndex,
      mscVrPpIndex,
      mscVrPpSnaPortIndex }
::= { mscVrPpSnaPortProvTable 1 }

MscVrPpSnaPortProvEntry ::= SEQUENCE {
   mscVrPpSnaPortVirtualSegmentLFSize
      Unsigned32 }

mscVrPpSnaPortVirtualSegmentLFSize OBJECT-TYPE
   SYNTAX     Unsigned32 (516 | 635 | 754 | 873 | 993 | 1112 | 1231 | 1350 | 1470 | 1542 | 1615 | 1688 | 1761 | 1833 | 1906 | 1979 | 2052 | 2345 | 5331 | 5798 | 6264 | 6730 | 7197 | 7663 | 8130 | 8539 | 8949 | 9358 | 9768 | 10178 | 10587 | 10997 | 11407 | 12199 | 12992 | 13785 | 14578 | 15370 | 16163 | 16956 | 17749 | 20730 | 23711 | 26693 | 29674 | 32655 | 35637 | 38618 | 41600 | 44591 | 47583 | 50575 | 53567 | 56559 | 59551 | 65535)
   ACCESS     read-write
   STATUS     mandatory
   DESCRIPTION
     "This attribute specifies the largest frame size (including DLC header 
      and info field but not any MAC-level or framing octets) for end-to-
      end connections established through this Sna component. This value 
      is used as the largest frame size for all circuits unless a smaller 
      value is specified in XID signals or by local LAN constraints."
   DEFVAL     { 2345 }
::= { mscVrPpSnaPortProvEntry 1 }

mscVrPpSnaPortStateTable OBJECT-TYPE
   SYNTAX     SEQUENCE OF MscVrPpSnaPortStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { mscVrPpSnaPort 103 }

mscVrPpSnaPortStateEntry OBJECT-TYPE
   SYNTAX     MscVrPpSnaPortStateEntry
   ACCESS     not-accessible
   STATUS     mandatory
   DESCRIPTION
     "An entry in the mscVrPpSnaPortStateTable."
   INDEX {
      mscVrIndex,
      mscVrPpIndex,
      mscVrPpSnaPortIndex }
::= { mscVrPpSnaPortStateTable 1 }

MscVrPpSnaPortStateEntry ::= SEQUENCE {
   mscVrPpSnaPortAdminState
      INTEGER,
   mscVrPpSnaPortOperationalState
      INTEGER,
   mscVrPpSnaPortUsageState
      INTEGER }

mscVrPpSnaPortAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { mscVrPpSnaPortStateEntry 1 }

mscVrPpSnaPortOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { mscVrPpSnaPortStateEntry 2 }

mscVrPpSnaPortUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { mscVrPpSnaPortStateEntry 3 }

mscVrPpSnaPortOperStatusTable OBJECT-TYPE
   SYNTAX     SEQUENCE OF MscVrPpSnaPortOperStatusEntry
   ACCESS     not-accessible
   STATUS     mandatory
   DESCRIPTION
     "This group includes the Operational Status attribute. This attribute 
      defines the current operational state of this component."
::= { mscVrPpSnaPort 104 }

mscVrPpSnaPortOperStatusEntry OBJECT-TYPE
   SYNTAX     MscVrPpSnaPortOperStatusEntry
   ACCESS     not-accessible
   STATUS     mandatory
   DESCRIPTION
     "An entry in the mscVrPpSnaPortOperStatusTable."
   INDEX {
      mscVrIndex,
      mscVrPpIndex,
      mscVrPpSnaPortIndex }
::= { mscVrPpSnaPortOperStatusTable 1 }

MscVrPpSnaPortOperStatusEntry ::= SEQUENCE {
   mscVrPpSnaPortSnmpOperStatus
      INTEGER }

mscVrPpSnaPortSnmpOperStatus OBJECT-TYPE
   SYNTAX     INTEGER  {
                 up(1),
                 down(2),
                 testing(3) }
   ACCESS     read-only
   STATUS     mandatory
   DESCRIPTION
     "The current state of the interface. The up state indicates the 
      interface is operational and capable of forwarding packets. The 
      down state indicates the interface is not operational, thus unable to 
      forward packets. testing state indicates that no operational packets 
      can be passed."
   DEFVAL     { up }
::= { mscVrPpSnaPortOperStatusEntry 1 }

-- 
-- *** THIS SUBTREE CURRENTLY NOT IMPLEMENTED ***
-- 

-- Vr/<string> Pp/<string> SnaPort Circuit/
-- <s1Mac>,<s1Sap>,<s2Mac>,<s2Sap>
-- This table is the circuit representation in the Sna component. There 
-- is a conceptual row associated with each locally attached end 
-- station. End station 1 (S1) and End station 2 (S2) are used to 
-- represent the two end stations of the circuit. S1 is always an end 
-- station which is locally attached. S2 may be locally attached or 
-- remote. If it is locally attached, the circuit will be represented by 
-- two rows indexed by (A, B) and (B, A) where A & B are the 
-- relevant MACs/SAPs. 

mscVrPpSnaPortCircuit OBJECT IDENTIFIER ::= { mscVrPpSnaPort 2 }



mscVrPpSnaPortCircuitRowStatusTable OBJECT-TYPE
   SYNTAX     SEQUENCE OF MscVrPpSnaPortCircuitRowStatusEntry
   ACCESS     not-accessible
   STATUS     mandatory
   DESCRIPTION
     "*** THIS TABLE CURRENTLY NOT IMPLEMENTED ***

      This entry controls the addition and deletion of 
      mscVrPpSnaPortCircuit components."
::= { mscVrPpSnaPortCircuit 1 }

mscVrPpSnaPortCircuitRowStatusEntry OBJECT-TYPE
   SYNTAX     MscVrPpSnaPortCircuitRowStatusEntry
   ACCESS     not-accessible
   STATUS     mandatory
   DESCRIPTION
     "A single entry in the table represents a single 
      mscVrPpSnaPortCircuit component."
   INDEX {
      mscVrIndex,
      mscVrPpIndex,
      mscVrPpSnaPortIndex,
      mscVrPpSnaPortCircuitS1MacIndex,
      mscVrPpSnaPortCircuitS1SapIndex,
      mscVrPpSnaPortCircuitS2MacIndex,
      mscVrPpSnaPortCircuitS2SapIndex }
::= { mscVrPpSnaPortCircuitRowStatusTable 1 }

MscVrPpSnaPortCircuitRowStatusEntry ::= SEQUENCE {
   mscVrPpSnaPortCircuitRowStatus
      RowStatus,
   mscVrPpSnaPortCircuitComponentName
      DisplayString,
   mscVrPpSnaPortCircuitStorageType
      StorageType,
   mscVrPpSnaPortCircuitS1MacIndex
      DashedHexString,
   mscVrPpSnaPortCircuitS1SapIndex
      Integer32,
   mscVrPpSnaPortCircuitS2MacIndex
      DashedHexString,
   mscVrPpSnaPortCircuitS2SapIndex
      Integer32 }

mscVrPpSnaPortCircuitRowStatus OBJECT-TYPE
   SYNTAX     RowStatus 
   ACCESS     read-only
   STATUS     mandatory
   DESCRIPTION
     "This variable is used as the basis for SNMP naming of
      mscVrPpSnaPortCircuit components.
      These components cannot be added nor deleted."
::= { mscVrPpSnaPortCircuitRowStatusEntry 1 }

mscVrPpSnaPortCircuitComponentName OBJECT-TYPE
   SYNTAX     DisplayString 
   ACCESS     read-only
   STATUS     mandatory
   DESCRIPTION
     "This variable provides the component's string name for
      use with the ASCII Console Interface"
::= { mscVrPpSnaPortCircuitRowStatusEntry 2 }

mscVrPpSnaPortCircuitStorageType OBJECT-TYPE
   SYNTAX     StorageType 
   ACCESS     read-only
   STATUS     mandatory
   DESCRIPTION
     "This variable represents the storage type value for the
      mscVrPpSnaPortCircuit tables."
::= { mscVrPpSnaPortCircuitRowStatusEntry 4 }

mscVrPpSnaPortCircuitS1MacIndex OBJECT-TYPE
   SYNTAX     DashedHexString (SIZE (6))
   ACCESS     not-accessible
   STATUS     mandatory
   DESCRIPTION
     "This variable represents an index for the mscVrPpSnaPortCircuit tables."
::= { mscVrPpSnaPortCircuitRowStatusEntry 10 }

mscVrPpSnaPortCircuitS1SapIndex OBJECT-TYPE
   SYNTAX     Integer32 (2..254)
   ACCESS     not-accessible
   STATUS     mandatory
   DESCRIPTION
     "This variable represents an index for the mscVrPpSnaPortCircuit tables."
::= { mscVrPpSnaPortCircuitRowStatusEntry 11 }

mscVrPpSnaPortCircuitS2MacIndex OBJECT-TYPE
   SYNTAX     DashedHexString (SIZE (6))
   ACCESS     not-accessible
   STATUS     mandatory
   DESCRIPTION
     "This variable represents an index for the mscVrPpSnaPortCircuit tables."
::= { mscVrPpSnaPortCircuitRowStatusEntry 12 }

mscVrPpSnaPortCircuitS2SapIndex OBJECT-TYPE
   SYNTAX     Integer32 (2..254)
   ACCESS     not-accessible
   STATUS     mandatory
   DESCRIPTION
     "This variable represents an index for the mscVrPpSnaPortCircuit tables."
::= { mscVrPpSnaPortCircuitRowStatusEntry 13 }

mscVrPpSnaPortCircuitOperTable OBJECT-TYPE
   SYNTAX     SEQUENCE OF MscVrPpSnaPortCircuitOperEntry
   ACCESS     not-accessible
   STATUS     mandatory
   DESCRIPTION
     "*** THIS TABLE CURRENTLY NOT IMPLEMENTED ***

      This group defines an entry in the SnaCircuitEntry Table."
::= { mscVrPpSnaPortCircuit 100 }

mscVrPpSnaPortCircuitOperEntry OBJECT-TYPE
   SYNTAX     MscVrPpSnaPortCircuitOperEntry
   ACCESS     not-accessible
   STATUS     mandatory
   DESCRIPTION
     "An entry in the mscVrPpSnaPortCircuitOperTable."
   INDEX {
      mscVrIndex,
      mscVrPpIndex,
      mscVrPpSnaPortIndex,
      mscVrPpSnaPortCircuitS1MacIndex,
      mscVrPpSnaPortCircuitS1SapIndex,
      mscVrPpSnaPortCircuitS2MacIndex,
      mscVrPpSnaPortCircuitS2SapIndex }
::= { mscVrPpSnaPortCircuitOperTable 1 }

MscVrPpSnaPortCircuitOperEntry ::= SEQUENCE {
   mscVrPpSnaPortCircuitS1DlcType
      INTEGER,
   mscVrPpSnaPortCircuitS1RouteInfo
      HexString,
   mscVrPpSnaPortCircuitS2Location
      INTEGER,
   mscVrPpSnaPortCircuitOrigin
      INTEGER,
   mscVrPpSnaPortCircuitState
      INTEGER,
   mscVrPpSnaPortCircuitPriority
      INTEGER,
   mscVrPpSnaPortCircuitVcId
      RowPointer }

mscVrPpSnaPortCircuitS1DlcType OBJECT-TYPE
   SYNTAX     INTEGER  {
                 other(1),
                 na(2),
                 llc(3),
                 sdlc(4),
                 qllc(5) }
   ACCESS     read-only
   STATUS     mandatory
   DESCRIPTION
     "This attribute indicates the DLC protocol in use between the SNA 
      node and S1."
::= { mscVrPpSnaPortCircuitOperEntry 2 }

mscVrPpSnaPortCircuitS1RouteInfo OBJECT-TYPE
   SYNTAX     HexString (SIZE (0..30))
   ACCESS     read-only
   STATUS     mandatory
   DESCRIPTION
     "If source-route bridging is in use between the SNA node and S1, 
      this is the routing information field describing the path between the 
      two devices. The format of the routing information corresponds to 
      that of the route designator fields of a specifically routed SRB 
      frame. Otherwise the value will be a Hex string of zero length."
::= { mscVrPpSnaPortCircuitOperEntry 3 }

mscVrPpSnaPortCircuitS2Location OBJECT-TYPE
   SYNTAX     INTEGER  {
                 other(1),
                 internal(2),
                 remote(3),
                 local(4) }
   ACCESS     read-only
   STATUS     mandatory
   DESCRIPTION
     "This attribute indicates the location of End Station 2 (S2). If the 
      location of End Station 2 is local, the interface information will be 
      available in the conceptual row whose S1 and S2 are the S2 and the 
      S1 of this conceptual row, respectively."
::= { mscVrPpSnaPortCircuitOperEntry 6 }

mscVrPpSnaPortCircuitOrigin OBJECT-TYPE
   SYNTAX     INTEGER  {
                 s2(0),
                 s1(1) }
   ACCESS     read-only
   STATUS     mandatory
   DESCRIPTION
     "This attribute indicates  which of the two end stations initiated the 
      establishment of this circuit."
::= { mscVrPpSnaPortCircuitOperEntry 10 }

mscVrPpSnaPortCircuitState OBJECT-TYPE
   SYNTAX     INTEGER  {
                 disconnected(1),
                 circuitStart(2),
                 resolvePending(3),
                 circuitPending(4),
                 circuitEstablished(5),
                 connectPending(6),
                 contactPending(7),
                 connected(8),
                 disconnectPending(9),
                 haltPending(10),
                 haltPendingNoack(11),
                 circuitRestart(12),
                 restartPending(13) }
   ACCESS     read-only
   STATUS     mandatory
   DESCRIPTION
     "This attribute indicates the current state of this circuit. Note that this 
      implementation does not keep entries after circuit disconnect. 
      Details regarding the state machine and meaning of individual states 
      may be found in RFC 1795."
::= { mscVrPpSnaPortCircuitOperEntry 13 }

mscVrPpSnaPortCircuitPriority OBJECT-TYPE
   SYNTAX     INTEGER  {
                 unsupported(1),
                 low(2),
                 medium(3),
                 high(4),
                 highest(5) }
   ACCESS     read-only
   STATUS     mandatory
   DESCRIPTION
     "This attribute indicates the transmission priority of this circuit as 
      understood by this SNA node. This value is determined by the two 
      SNA nodes at circuit startup time."
::= { mscVrPpSnaPortCircuitOperEntry 14 }

mscVrPpSnaPortCircuitVcId OBJECT-TYPE
   SYNTAX     RowPointer 
   ACCESS     read-only
   STATUS     mandatory
   DESCRIPTION
     "This attribute indicates the component name of the GvcIf/n Dlci/n 
      which represents this VC connection in the SNA DLR service. This 
      attribute appears only for circuits that are connecting over a Frame 
      Relay DLCI only. For circuits connecting over Qllc VCs or Token 
      Ring interface this attribute does not appear."
::= { mscVrPpSnaPortCircuitOperEntry 26 }


-- Vr/<string> Sna
-- This component defines the overall characteristics of a Data Link 
-- Routing (DLR)  instance which routes SNA traffic through a 
-- Passport network. 

mscVrSna OBJECT IDENTIFIER ::= { mscVr 14 }



mscVrSnaRowStatusTable OBJECT-TYPE
   SYNTAX     SEQUENCE OF MscVrSnaRowStatusEntry
   ACCESS     not-accessible
   STATUS     mandatory
   DESCRIPTION
     "This entry controls the addition and deletion of 
      mscVrSna components."
::= { mscVrSna 1 }

mscVrSnaRowStatusEntry OBJECT-TYPE
   SYNTAX     MscVrSnaRowStatusEntry
   ACCESS     not-accessible
   STATUS     mandatory
   DESCRIPTION
     "A single entry in the table represents a single 
      mscVrSna component."
   INDEX {
      mscVrIndex,
      mscVrSnaIndex }
::= { mscVrSnaRowStatusTable 1 }

MscVrSnaRowStatusEntry ::= SEQUENCE {
   mscVrSnaRowStatus
      RowStatus,
   mscVrSnaComponentName
      DisplayString,
   mscVrSnaStorageType
      StorageType,
   mscVrSnaIndex
      NonReplicated }

mscVrSnaRowStatus OBJECT-TYPE
   SYNTAX     RowStatus 
   ACCESS     read-write
   STATUS     mandatory
   DESCRIPTION
     "This variable is used as the basis for SNMP naming of
      mscVrSna components.
      These components can be added and deleted."
::= { mscVrSnaRowStatusEntry 1 }

mscVrSnaComponentName OBJECT-TYPE
   SYNTAX     DisplayString 
   ACCESS     read-only
   STATUS     mandatory
   DESCRIPTION
     "This variable provides the component's string name for
      use with the ASCII Console Interface"
::= { mscVrSnaRowStatusEntry 2 }

mscVrSnaStorageType OBJECT-TYPE
   SYNTAX     StorageType 
   ACCESS     read-only
   STATUS     mandatory
   DESCRIPTION
     "This variable represents the storage type value for the
      mscVrSna tables."
::= { mscVrSnaRowStatusEntry 4 }

mscVrSnaIndex OBJECT-TYPE
   SYNTAX     NonReplicated 
   ACCESS     not-accessible
   STATUS     mandatory
   DESCRIPTION
     "This variable represents the index for the mscVrSna tables."
::= { mscVrSnaRowStatusEntry 10 }

mscVrSnaAdminControlTable OBJECT-TYPE
   SYNTAX     SEQUENCE OF MscVrSnaAdminControlEntry
   ACCESS     not-accessible
   STATUS     mandatory
   DESCRIPTION
     "This group includes the Administrative Control attribute. This 
      attribute defines the current administrative state of this component."
::= { mscVrSna 100 }

mscVrSnaAdminControlEntry OBJECT-TYPE
   SYNTAX     MscVrSnaAdminControlEntry
   ACCESS     not-accessible
   STATUS     mandatory
   DESCRIPTION
     "An entry in the mscVrSnaAdminControlTable."
   INDEX {
      mscVrIndex,
      mscVrSnaIndex }
::= { mscVrSnaAdminControlTable 1 }

MscVrSnaAdminControlEntry ::= SEQUENCE {
   mscVrSnaSnmpAdminStatus
      INTEGER }

mscVrSnaSnmpAdminStatus OBJECT-TYPE
   SYNTAX     INTEGER  {
                 up(1),
                 down(2),
                 testing(3) }
   ACCESS     read-write
   STATUS     mandatory
   DESCRIPTION
     "The desired state of the interface. The up state indicates the 
      interface is operational and packet forwarding is allowed. The down 
      state indicates the interface is not operational and packet forwarding 
      is unavailable. The testing state indicates that no operational 
      packets can be passed."
   DEFVAL     { up }
::= { mscVrSnaAdminControlEntry 1 }

mscVrSnaStateTable OBJECT-TYPE
   SYNTAX     SEQUENCE OF MscVrSnaStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { mscVrSna 101 }

mscVrSnaStateEntry OBJECT-TYPE
   SYNTAX     MscVrSnaStateEntry
   ACCESS     not-accessible
   STATUS     mandatory
   DESCRIPTION
     "An entry in the mscVrSnaStateTable."
   INDEX {
      mscVrIndex,
      mscVrSnaIndex }
::= { mscVrSnaStateTable 1 }

MscVrSnaStateEntry ::= SEQUENCE {
   mscVrSnaAdminState
      INTEGER,
   mscVrSnaOperationalState
      INTEGER,
   mscVrSnaUsageState
      INTEGER }

mscVrSnaAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { mscVrSnaStateEntry 1 }

mscVrSnaOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { mscVrSnaStateEntry 2 }

mscVrSnaUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { mscVrSnaStateEntry 3 }

mscVrSnaOperStatusTable OBJECT-TYPE
   SYNTAX     SEQUENCE OF MscVrSnaOperStatusEntry
   ACCESS     not-accessible
   STATUS     mandatory
   DESCRIPTION
     "This group includes the Operational Status attribute. This attribute 
      defines the current operational state of this component."
::= { mscVrSna 102 }

mscVrSnaOperStatusEntry OBJECT-TYPE
   SYNTAX     MscVrSnaOperStatusEntry
   ACCESS     not-accessible
   STATUS     mandatory
   DESCRIPTION
     "An entry in the mscVrSnaOperStatusTable."
   INDEX {
      mscVrIndex,
      mscVrSnaIndex }
::= { mscVrSnaOperStatusTable 1 }

MscVrSnaOperStatusEntry ::= SEQUENCE {
   mscVrSnaSnmpOperStatus
      INTEGER }

mscVrSnaSnmpOperStatus OBJECT-TYPE
   SYNTAX     INTEGER  {
                 up(1),
                 down(2),
                 testing(3) }
   ACCESS     read-only
   STATUS     mandatory
   DESCRIPTION
     "The current state of the interface. The up state indicates the 
      interface is operational and capable of forwarding packets. The 
      down state indicates the interface is not operational, thus unable to 
      forward packets. testing state indicates that no operational packets 
      can be passed."
   DEFVAL     { up }
::= { mscVrSnaOperStatusEntry 1 }

mscVrSnaOperTable OBJECT-TYPE
   SYNTAX     SEQUENCE OF MscVrSnaOperEntry
   ACCESS     not-accessible
   STATUS     mandatory
   DESCRIPTION
     "This group contains operational attributes which describe the  
      behavior of the Sna component and associated ports under the 
      Virtual Router (VR)."
::= { mscVrSna 103 }

mscVrSnaOperEntry OBJECT-TYPE
   SYNTAX     MscVrSnaOperEntry
   ACCESS     not-accessible
   STATUS     mandatory
   DESCRIPTION
     "An entry in the mscVrSnaOperTable."
   INDEX {
      mscVrIndex,
      mscVrSnaIndex }
::= { mscVrSnaOperTable 1 }

MscVrSnaOperEntry ::= SEQUENCE {
   mscVrSnaVersion
      HexString }

mscVrSnaVersion OBJECT-TYPE
   SYNTAX     HexString (SIZE (2))
   ACCESS     read-only
   STATUS     mandatory
   DESCRIPTION
     "This attribute indicates the particular version of the SNA standard 
      supported by this Sna.  The first 2 digits  represent the SNA 
      standard Version number of this Sna, the second 2 digits represent 
      the SNA standard Release number."
::= { mscVrSnaOperEntry 2 }

mscVrSnaCircStatsTable OBJECT-TYPE
   SYNTAX     SEQUENCE OF MscVrSnaCircStatsEntry
   ACCESS     not-accessible
   STATUS     mandatory
   DESCRIPTION
     "A circuit is the end-to-end association of two Data Link Routing 
      (DLR) entities through one or two DLR nodes. It is the 
      concatenation of two 'data links', optionally with an intervening 
      transport connection (not initially supported). The origin of the 
      circuit is the end station that initiates the circuit. The target of the 
      circuit is the end station that receives the initiation."
::= { mscVrSna 104 }

mscVrSnaCircStatsEntry OBJECT-TYPE
   SYNTAX     MscVrSnaCircStatsEntry
   ACCESS     not-accessible
   STATUS     mandatory
   DESCRIPTION
     "An entry in the mscVrSnaCircStatsTable."
   INDEX {
      mscVrIndex,
      mscVrSnaIndex }
::= { mscVrSnaCircStatsTable 1 }

MscVrSnaCircStatsEntry ::= SEQUENCE {
   mscVrSnaActives
      Gauge32,
   mscVrSnaCreates
      Counter32 }

mscVrSnaActives OBJECT-TYPE
   SYNTAX     Gauge32 (0..4292967295)
   ACCESS     read-only
   STATUS     mandatory
   DESCRIPTION
     "This attribute indiates the current number of circuits in Circuit table 
      that are not in the disconnected state."
   DEFVAL     { 0 }
::= { mscVrSnaCircStatsEntry 1 }

mscVrSnaCreates OBJECT-TYPE
   SYNTAX     Counter32 
   ACCESS     read-only
   STATUS     mandatory
   DESCRIPTION
     "This attribute indicates the total number of entries ever added to 
      Circuit table, or reactivated upon exiting disconnected state."
::= { mscVrSnaCircStatsEntry 2 }

mscVrSnaDirStatsTable OBJECT-TYPE
   SYNTAX     SEQUENCE OF MscVrSnaDirStatsEntry
   ACCESS     not-accessible
   STATUS     mandatory
   DESCRIPTION
     "MAC Table Directory statistics"
::= { mscVrSna 105 }

mscVrSnaDirStatsEntry OBJECT-TYPE
   SYNTAX     MscVrSnaDirStatsEntry
   ACCESS     not-accessible
   STATUS     mandatory
   DESCRIPTION
     "An entry in the mscVrSnaDirStatsTable."
   INDEX {
      mscVrIndex,
      mscVrSnaIndex }
::= { mscVrSnaDirStatsTable 1 }

MscVrSnaDirStatsEntry ::= SEQUENCE {
   mscVrSnaMacEntries
      Gauge32,
   mscVrSnaMacCacheHits
      Counter32,
   mscVrSnaMacCacheMisses
      Counter32 }

mscVrSnaMacEntries OBJECT-TYPE
   SYNTAX     Gauge32 (0..10000)
   ACCESS     read-only
   STATUS     mandatory
   DESCRIPTION
     "This attribute indicates the current total number of entries in the 
      DirectoryEntry table."
   DEFVAL     { 0 }
::= { mscVrSnaDirStatsEntry 1 }

mscVrSnaMacCacheHits OBJECT-TYPE
   SYNTAX     Counter32 
   ACCESS     read-only
   STATUS     mandatory
   DESCRIPTION
     "This attribute indicates the number of times a cache search for a 
      particular MAC address resulted in success."
::= { mscVrSnaDirStatsEntry 2 }

mscVrSnaMacCacheMisses OBJECT-TYPE
   SYNTAX     Counter32 
   ACCESS     read-only
   STATUS     mandatory
   DESCRIPTION
     "This attribute indicates the number of times a cache search for a 
      particular MAC address resulted in failure."
::= { mscVrSnaDirStatsEntry 3 }




-- 
-- Version and Compliance statements
-- 



-- Object-Group Statement:
-- A list of all current accessible leaf objects.

-- OBJECTS { mscVrSnaUsageState,
--           mscVrSnaMacCacheHits,
--           mscVrPpSnaPortCircuitComponentName,
--           mscVrPpSnaPortCircuitS1DlcType,
--           mscVrPpSnaPortCircuitState,
--           mscVrSnaAdminState,
--           mscVrPpSnaPortAdminState,
--           mscVrPpSnaPortCircuitStorageType,
--           mscVrSnaRowStatus,
--           mscVrPpSnaPortRowStatus,
--           mscVrSnaVersion,
--           mscVrSnaSnmpAdminStatus,
--           mscVrPpSnaPortSnmpAdminStatus,
--           mscVrPpSnaPortCircuitPriority,
--           mscVrSnaSnmpOperStatus,
--           mscVrPpSnaPortSnmpOperStatus,
--           mscVrSnaMacCacheMisses,
--           mscVrSnaCreates,
--           mscVrPpSnaPortVirtualSegmentLFSize,
--           mscVrPpSnaPortCircuitS2Location,
--           mscVrPpSnaPortUsageState,
--           mscVrPpSnaPortCircuitOrigin,
--           mscVrSnaStorageType,
--           mscVrPpSnaPortCircuitRowStatus,
--           mscVrSnaComponentName,
--           mscVrPpSnaPortComponentName,
--           mscVrPpSnaPortCircuitVcId,
--           mscVrPpSnaPortCircuitS1RouteInfo,
--           mscVrPpSnaPortStorageType,
--           mscVrSnaActives,
--           mscVrSnaMacEntries,
--           mscVrSnaOperationalState,
--           mscVrPpSnaPortOperationalState }
-- STATUS  mandatory
-- DESCRIPTION
--   "A list of all current accessible leaf objects."

snaGroup OBJECT IDENTIFIER ::= { snaMIB 1 }
snaGroupCA OBJECT IDENTIFIER ::= { snaGroup 1 }
snaGroupCA02 OBJECT IDENTIFIER ::= { snaGroupCA 3 }
snaGroupCA02DevelopmentLoad OBJECT IDENTIFIER ::= { snaGroupCA02 1 }
snaGroupCA0214 OBJECT IDENTIFIER ::= { snaGroupCA02DevelopmentLoad 14 }
snaGroupCA0214A OBJECT IDENTIFIER ::= { snaGroupCA0214 1 }



-- Agent-Capabilities Statement:

-- PRODUCT-RELEASE "MscPassport Release 1.2 Sna."
-- STATUS          mandatory
-- DESCRIPTION     "Carrier Passport Sna MIB: MIB Version CA0214A,
--                  Software Version CA0214A."
-- SUPPORTS        Nortel-MsCarrier-MscPassport-SnaMIB
--    INCLUDES     { snaGroupCA0214A }

snaCapabilities OBJECT IDENTIFIER ::= { snaMIB 3 }
snaCapabilitiesCA OBJECT IDENTIFIER ::= { snaCapabilities 1 }
snaCapabilitiesCA02 OBJECT IDENTIFIER ::= { snaCapabilitiesCA 3 }
snaCapabilitiesCA02DevelopmentLoad OBJECT IDENTIFIER ::= { snaCapabilitiesCA02 1 }
snaCapabilitiesCA0214 OBJECT IDENTIFIER ::= { snaCapabilitiesCA02DevelopmentLoad 14 }
snaCapabilitiesCA0214A OBJECT IDENTIFIER ::= { snaCapabilitiesCA0214 1 }





END
