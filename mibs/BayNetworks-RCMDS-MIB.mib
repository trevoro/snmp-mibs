BayNetworks-RCMDS-MIB DEFINITIONS ::= BEGIN


    IMPORTS

      Counter, Gauge
        FROM RFC1155-SMI
      OBJECT-TYPE
        FROM RFC-1212
      DisplayString
        FROM RFC1213-MIB
      wfRcmdsGroup
        FROM Wellfleet-COMMON-MIB;


    wfRcmds	OBJECT IDENTIFIER ::= { wfRcmdsGroup 1 }

    wfRcmdsDelete OBJECT-TYPE
        SYNTAX	INTEGER {
    		    created(1),
    		    deleted(2)
    		}
        ACCESS	read-write
        STATUS	mandatory
        DESCRIPTION
                "Create/Delete parameter. Default is created.
                Users perform a set operation on this
                object in order to create/delete Rcmds."
        DEFVAL	{ created }
        ::= { wfRcmds 1 }

    wfRcmdsDisable OBJECT-TYPE
        SYNTAX	INTEGER {
    		    enabled(1),
    		    disabled(2)
    		}
        ACCESS	read-write
        STATUS	mandatory
        DESCRIPTION
                "Enables or Disables Rcmds Subsystem"
        DEFVAL	{ enabled }
        ::= { wfRcmds 2 }

    wfRcmdsReservedPort OBJECT-TYPE
        SYNTAX INTEGER(512..1023)
        ACCESS read-write
        STATUS mandatory
        DESCRIPTION
               "Next Local reserved port available"
        DEFVAL { 1023 }
        ::= { wfRcmds 3 }

    wfRcmdsKerberosDefaultRealmName OBJECT-TYPE
        SYNTAX	DisplayString
        ACCESS	read-write
        STATUS	mandatory
        DESCRIPTION
                "This is the default kerberos realm name for the router"
        ::= { wfRcmds 4 }

    wfRcmdsKerberosKDCName OBJECT-TYPE
        SYNTAX	DisplayString
        ACCESS	read-write
        STATUS	mandatory
        DESCRIPTION
                "This is the default kerberos KDC name to which router sends kerberos
	             ticket requests"
        ::= { wfRcmds 5 }

    wfRcmdsRouterHostName OBJECT-TYPE
        SYNTAX	DisplayString
        ACCESS	read-write
        STATUS	mandatory
        DESCRIPTION
                "This is the DNS host name for the router"
        ::= { wfRcmds 6 }

	wfRcmdsKerberosHostServiceKey OBJECT-TYPE
        SYNTAX	OCTET STRING
        ACCESS	read-write
        STATUS	mandatory
        DESCRIPTION
                "This secret equivalent of the content of V5SRVTAB file
                 which contains the host principal keberos  private key for 
                 the router. This can be manipulated only using the secure shell from
                 the console"
        ::= { wfRcmds 7 }


    wfRcmdsRlogind	OBJECT IDENTIFIER ::= { wfRcmdsGroup 2 }

    wfRcmdsRlogindDelete OBJECT-TYPE
        SYNTAX	INTEGER {
    		    created(1),
    		    deleted(2)
    		}
        ACCESS	read-write
        STATUS	mandatory
        DESCRIPTION
                "Create/Delete parameter. Default is created.
                Users perform a set operation on this
                object in order to create/delete"
        DEFVAL	{ created }
        ::= { wfRcmdsRlogind 1 }

    wfRcmdsRlogindDisable OBJECT-TYPE
        SYNTAX	INTEGER {
    		    enabled(1),
    		    disabled(2)
    		}
        ACCESS	read-write
        STATUS	mandatory
        DESCRIPTION
                "Enables or Disables Rlogind"
        DEFVAL	{ enabled }
        ::= { wfRcmdsRlogind 2 }

    wfRcmdsRlogindState OBJECT-TYPE
        SYNTAX	INTEGER {
    		    up(1),
    		    down(2)
    		}
        ACCESS	read-only
        STATUS	mandatory
        DESCRIPTION
                "State of Rlogind"
        DEFVAL	{ down }
        ::= { wfRcmdsRlogind 3 }

    wfRcmdsRlogindMoreDisable OBJECT-TYPE
        SYNTAX	INTEGER {
    		    enabled(1),
    		    disabled(2)
    		}
        ACCESS	read-write
        STATUS	mandatory
        DESCRIPTION
                "Enable the 'more' feature on the Technician Interface console"
        ::= { wfRcmdsRlogind 4 }

    wfRcmdsRlogindPrompt OBJECT-TYPE
        SYNTAX	DisplayString
        ACCESS	read-write
        STATUS	mandatory
        DESCRIPTION
                "Character string which will be used as the system prompt on
                the Technician Interface console"
        ::= { wfRcmdsRlogind 5 }

    wfRcmdsRlogindLoginTimeOut OBJECT-TYPE
        SYNTAX	INTEGER(1..99)
        ACCESS	read-write
        STATUS	mandatory
        DESCRIPTION
                "Time out in minutes to Disconnect when at the login prompt"
        DEFVAL	{ 1 }
        ::= { wfRcmdsRlogind 6 }

    wfRcmdsRlogindPasswordTimeOut OBJECT-TYPE
        SYNTAX	INTEGER(1..99)
        ACCESS	read-write
        STATUS	mandatory
        DESCRIPTION
                "Timout in minutes on Password entry"
        DEFVAL	{ 1 }
        ::= { wfRcmdsRlogind 7 }

    wfRcmdsRlogindCommandTimeOut OBJECT-TYPE
        SYNTAX	INTEGER(1..99)
        ACCESS	read-write
        STATUS	mandatory
        DESCRIPTION
                "Time out in minutes to Disconnect when at the command prompt"
        DEFVAL	{ 15 }
        ::= { wfRcmdsRlogind 8 }

    wfRcmdsRlogindLoginRetries OBJECT-TYPE
        SYNTAX	INTEGER(1..99)
        ACCESS	read-write
        STATUS	mandatory
        DESCRIPTION
                "Limit # of login attempts then Disconnect"
        DEFVAL	{ 3 }
        ::= { wfRcmdsRlogind 9 }

    wfRcmdsRlogindTotalLogins OBJECT-TYPE
        SYNTAX	Counter
        ACCESS	read-only
        STATUS	mandatory
        DESCRIPTION
                "Total number of Rlogind TI login attempts"
        ::= { wfRcmdsRlogind 10 }

    wfRcmdsRlogindUserLoginErrors OBJECT-TYPE
        SYNTAX	Counter
        ACCESS	read-only
        STATUS	mandatory
        DESCRIPTION
                "Total number of FAILED User login attempts"
        ::= { wfRcmdsRlogind 11 }

    wfRcmdsRlogindManagerLoginErrors OBJECT-TYPE
        SYNTAX	Counter
        ACCESS	read-only
        STATUS	mandatory
        DESCRIPTION
                "Total number of FAILED Manager login attempts"
        ::= { wfRcmdsRlogind 12 }

    wfRcmdsRlogindOtherLoginErrors OBJECT-TYPE
        SYNTAX	Counter
        ACCESS	read-only
        STATUS	mandatory
        DESCRIPTION
                "Total number of FAILED Other login attempts"
        ::= { wfRcmdsRlogind 13 }

    wfRcmdsRlogindActiveSessions OBJECT-TYPE
        SYNTAX	Gauge
        ACCESS	read-only
        STATUS	mandatory
        DESCRIPTION
                "Total number of Rlogind TI Sessions"
        ::= { wfRcmdsRlogind 14 }

    wfRcmdsRlogindManagerAutoScript OBJECT-TYPE
        SYNTAX	DisplayString
        ACCESS	read-write
        STATUS	mandatory
        DESCRIPTION
                "for each login."
        ::= { wfRcmdsRlogind 15 }

    wfRcmdsRlogindUserAutoScript OBJECT-TYPE
        SYNTAX	DisplayString
        ACCESS	read-write
        STATUS	mandatory
        DESCRIPTION
                "for each login."
        ::= { wfRcmdsRlogind 16 }

    wfRcmdsRlogindUserAbortLogoutDisable OBJECT-TYPE
        SYNTAX	INTEGER {
    		    enabled(1),
    		    disabled(2)
    		}
        ACCESS	read-write
        STATUS	mandatory
        DESCRIPTION
                "a USER from escaping out of the User Autoscript"
        DEFVAL	{ disabled }
        ::= { wfRcmdsRlogind 17 }

    wfRcmdsRlogindHistoryDepth OBJECT-TYPE
        SYNTAX	INTEGER(1..40)
        ACCESS	read-write
        STATUS	mandatory
        DESCRIPTION
                "TI command history table size"
        DEFVAL	{ 20 }
        ::= { wfRcmdsRlogind 18 }

    wfRcmdsRlogindTcpPort OBJECT-TYPE
        SYNTAX	INTEGER
        ACCESS	read-write
        STATUS	mandatory
        DESCRIPTION
		"The TCP port on which rlogind listens. by default this is set 
                 543, which supports kerberized rlogin"
	    DEFVAL { 543 }
	    ::= { wfRcmdsRlogind 19 }

    wfRcmdsRlogindTrustedHostAuthentication OBJECT-TYPE
        SYNTAX	INTEGER {
    		    enabled(1),
    		    disabled(2)
    		}
        ACCESS	read-write
        STATUS	mandatory
        DESCRIPTION
                "Enables/Disables Unix trusted host authentication"
        DEFVAL	{ disabled }
        ::= { wfRcmdsRlogind 20 }

    wfRcmdsRlogindKerberosAuthentication OBJECT-TYPE
        SYNTAX	INTEGER {
    		    enabled(1),
    		    disabled(2)
    		}
        ACCESS	read-write
        STATUS	mandatory
        DESCRIPTION
                "Enables/Disables Kerberos Authentication"
        DEFVAL	{ enabled }
        ::= { wfRcmdsRlogind 21 }

    wfRcmdsRlogindKerberosSessionTypeAllowed OBJECT-TYPE   
        SYNTAX	INTEGER {
    		    both(1),
    		    encrypted(2),
		    unencrypted(3),
		    none(4)
    		}
        ACCESS	read-write
        STATUS	mandatory
        DESCRIPTION
                "Encrypted/unencrypted session allowed or not"
        DEFVAL	{ both }
        ::= { wfRcmdsRlogind 22 }
	
    wfRcmdsRshd	OBJECT IDENTIFIER ::= { wfRcmdsGroup 3 }

    wfRcmdsRshdDelete OBJECT-TYPE
        SYNTAX	INTEGER {
    		    created(1),
    		    deleted(2)
    		}
        ACCESS	read-write
        STATUS	mandatory
        DESCRIPTION
                "Create/Delete parameter. Default is created.
                Users perform a set operation on this
                object in order to create/delete"
        DEFVAL	{ created }
        ::= { wfRcmdsRshd 1 }

    wfRcmdsRshdDisable OBJECT-TYPE
        SYNTAX	INTEGER {
    		    enabled(1),
    		    disabled(2)
    		}
        ACCESS	read-write
        STATUS	mandatory
        DESCRIPTION
                "Enables or Disables Rlogind"
        DEFVAL	{ enabled }
        ::= { wfRcmdsRshd 2 }

    wfRcmdsRshdState OBJECT-TYPE
        SYNTAX	INTEGER {
    		    up(1),
    		    down(2)
    		}
        ACCESS	read-only
        STATUS	mandatory
        DESCRIPTION
                "State of Rshd"
        DEFVAL	{ down }
        ::= { wfRcmdsRshd 3 }

    wfRcmdsRshdTotalSessions OBJECT-TYPE
        SYNTAX	Counter
        ACCESS	read-only
        STATUS	mandatory
        DESCRIPTION
                "Total number of Rshd command sessions executed"
        ::= { wfRcmdsRshd 4 }

    wfRcmdsRshdTcpPort OBJECT-TYPE
        SYNTAX	INTEGER
        ACCESS	read-write
        STATUS	mandatory
        DESCRIPTION
		"The TCP port on which rshd listens. by default this is set 
                 544, which supports kerberized rlogin"
	    DEFVAL { 544 }
	    ::= { wfRcmdsRshd 5 }

    wfRcmdsRshdTrustedHostAuthentication OBJECT-TYPE
        SYNTAX	INTEGER {
    		    enabled(1),
    		    disabled(2)
    		}
        ACCESS	read-write
        STATUS	mandatory
        DESCRIPTION
                "Enables/Disables Unix trusted host authentication"
        DEFVAL	{ disabled }
        ::= { wfRcmdsRshd 6 }

    wfRcmdsRshdKerberosAuthentication OBJECT-TYPE
        SYNTAX	INTEGER {
    		    enabled(1),
    		    disabled(2)
    		}
        ACCESS	read-write
        STATUS	mandatory
        DESCRIPTION
                "Enables/Disables Kerberos Authentication"
        DEFVAL	{ enabled }
        ::= { wfRcmdsRshd 7 }

    wfRcmdsRshdKerberosSessionTypeAllowed OBJECT-TYPE
        SYNTAX	INTEGER {
    		    both(1),
    		    encrypted(2),
		    unencrypted(3),
		    none(4)
    		}
        ACCESS	read-write
        STATUS	mandatory
        DESCRIPTION
                "Encrypted/unencrypted session allowed or not"
        DEFVAL	{ both }
        ::= { wfRcmdsRshd 8 }

    wfRcmdsRshdRcpDefaultVolume OBJECT-TYPE
        SYNTAX	INTEGER {
    		    volume1(1),
    		    volume2(2),
    		    volume3(3),
    		    volume4(4),
    		    volume5(5),
    		    volume6(6),
                    volume7(7),
    		    volume8(8),
    		    volume9(9),
    		    volume10(10),
    		    volume11(11),
    		    volume12(12),
    		    volume13(13),
    		    volume14(14),
                    volumea(65)
		}
        ACCESS	read-write
        STATUS	mandatory
        DESCRIPTION
                "The file system volume number to which transferred files will
                be written and from which they will be retrieved. The volume
                number corresponds to the slot number on which the volume
                resides. On systems with a floppy disk, the value 65 represents
                volume 'A'."
        DEFVAL	{ volume2 }
        ::= { wfRcmdsRshd 9 }

    END  -- BayNetworks-RCMDS-MIB
