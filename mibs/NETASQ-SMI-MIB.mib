-- MODULE-IDENTITY
--  OrgName
--    Netasq
--  ContactInfo
--     Customer Support
--     
--     3, rue Arichème
--     59650 Villeneuve d'Ascq
--     FRANCE
--    
--     Tel: +33 03 20 61 96 30
--     E-mail: support@netasq.com
--     Http://www.netasq.com

--
--  Last modified date: 08/08/2002
--    

NETASQ-SMI-MIB DEFINITIONS ::= BEGIN
IMPORTS
    enterprises FROM RFC1155-SMI;
--	DisplayString FROM RFC1213-MIB;
    
netasq OBJECT IDENTIFIER ::= { enterprises 11256 }

netasqMIB OBJECT IDENTIFIER ::= { netasq 1 }
-- netasq Product Property
ntqProductProperty OBJECT IDENTIFIER ::= { netasqMIB 0 }
-- netasq VPN MIBS
ntqVPN OBJECT IDENTIFIER ::= { netasqMIB 1 }
-- netasq users MIBS
ntqUsers OBJECT IDENTIFIER ::= { netasqMIB 2 }
-- netasq hosts MIBS
ntqHosts OBJECT IDENTIFIER ::= { netasqMIB 3 }
-- netasq Interface MIBS
ntqif OBJECT IDENTIFIER ::= { netasqMIB 4 }
-- netasq alarm MIBS
ntqAlarm OBJECT IDENTIFIER ::= { netasqMIB 5 }
-- netasq notification
ntqNotifications OBJECT IDENTIFIER ::= { netasqMIB 6 }
END
