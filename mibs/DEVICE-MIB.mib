DEVICE-MIB 

          DEFINITIONS ::= BEGIN

          -- This file contains the defintion of the device mib for Coriolis Networks.
          -- The device mib describes the attributes of a network element as a whole.

          IMPORTS
                  IpAddress 
                      FROM RFC1155-SMI
                  OBJECT-TYPE, MODULE-IDENTITY, Counter32, Integer32, Unsigned32
                      FROM SNMPv2-SMI
                  DisplayString
		      FROM RFC1213-MIB
                  device, coriolisMibs
                      FROM CORIOLIS-MIB
                  TruthValue
                      FROM SNMPv2-TC
                  TRAP-TYPE
                      FROM RFC-1215;

          deviceMIB MODULE-IDENTITY
              LAST-UPDATED "0007270000Z"
              ORGANIZATION "Coriolis Networks"
              CONTACT-INFO
                      "        Shubhra Garg

                       Postal: 330 Codman Hill Road,
                               Boxboro MA, 01719.

                          Tel: +1 978 264 1904
                          Fax: +1 978 264 1929

                       E-mail: shubhra@coriolisnet.com"
              DESCRIPTION
                      "The MIB module for chassis level information for coriolis boxes"
              ::= { device 1 }


          chassis   OBJECT IDENTIFIER ::= { device 2 }
          systime   OBJECT IDENTIFIER ::= { device 3 }
		  
          chassisAutoConfig OBJECT-TYPE
          SYNTAX TruthValue
          MAX-ACCESS read-write
          STATUS current
          DESCRIPTION
          "Configuration of the element - is it automatic?"
          ::= { chassis 1 }
                  
          chassisIpAddr OBJECT-TYPE
	      SYNTAX IpAddress
	      MAX-ACCESS read-write
	      STATUS current 
	      DESCRIPTION
	      "The ip address of the element." 
         ::= { chassis 2 }

          chassisId OBJECT-TYPE
	      SYNTAX INTEGER {
	      optiFlow5500(1),
	      optiFlow5000(2),
	      optiFlow3500(3),
	      optiFlow3000(4),
	      optiFlow3500thirteen(5),
	      optiFlow3000thirteen(6),
              optiFlow1010(21),
	      optiFlow1020(25)
      -- DO NOT CHANGE THIS VALUE 21 FOR 1010.
      -- IT IS DIRECTLY MAPPED TO THE CARD TYPE 
      -- CM_CARD_TYPE_OAU_ETH16_GIG1_FX
	      }
	      MAX-ACCESS read-only
	      STATUS current 
	      DESCRIPTION
	      "The chassis identifier of the element"
         ::= { chassis 3 }

         chassisCharacter OBJECT-TYPE
    	  SYNTAX INTEGER {
	       gne(1),
	       ne(2),
	       sne(3)	
           }
	     MAX-ACCESS read-write
	     STATUS current
	     DESCRIPTION 
	     "The character of the element that is saved in non volatile 
	     storage. This will take affect after next cold/warm start of 
	     the node."
         ::= { chassis 4 }

         chassisElemReachStatus OBJECT-TYPE
    	     SYNTAX INTEGER {
               reachable(1),
               unreachable(2)
             }
	     MAX-ACCESS not-accessible
	     STATUS  current
	     DESCRIPTION
	     "Whether GNE is reachable from this NE"
         ::= { chassis 5 }

         chassisNumElemReachable OBJECT-TYPE
    	     SYNTAX INTEGER 
	     MAX-ACCESS read-only
	     STATUS  current
	     DESCRIPTION
	     "Number of elements reachable from this element"
         ::= { chassis 6 }

         chassisCurrentCharacter OBJECT-TYPE
    	     SYNTAX INTEGER {
               gne(1),
               ne(2),
	       sne(3)
             }
	     MAX-ACCESS read-only
	     STATUS current
	     DESCRIPTION 
	     "The character of the element that is currently being active."
         ::= { chassis 8 }

         chassisFanStatus OBJECT-TYPE
    	     SYNTAX INTEGER {
			     fail (1),
			     good (2)
	             }
	     MAX-ACCESS accessible-for-notify
	     STATUS  current
	     DESCRIPTION
	     "Indicates the status of the Chassis Fan."
         ::= { chassis 9 }

         chassisPowerSupplyTable  OBJECT-TYPE
	     SYNTAX SEQUENCE OF ChassisPowerSupplyEntry
	     MAX-ACCESS not-accessible
	     STATUS current
	     DESCRIPTION
		 "The table for chassis power supply."
	     ::= {chassis 10}

	     chassisPowerSupplyEntry  OBJECT-TYPE
	     SYNTAX  ChassisPowerSupplyEntry
	     MAX-ACCESS not-accessible
	     STATUS  current
	     DESCRIPTION
		 "Entry containing information on power supply."
	     INDEX {chassisPowerSupplyNumber}
	     ::= { chassisPowerSupplyTable 1}

         ChassisPowerSupplyEntry ::= SEQUENCE {
	      chassisPowerSupplyNumber
	       INTEGER,
	      chassisPowerSupplyStatus
	       INTEGER
	     }      

	     chassisPowerSupplyNumber  OBJECT-TYPE
	     SYNTAX  INTEGER
	     MAX-ACCESS not-accessible
	     STATUS	current
	     DESCRIPTION
		 "The index for the chassis power supply table."
	     ::= {chassisPowerSupplyEntry 1 }    
    
	     chassisPowerSupplyStatus OBJECT-TYPE
    	 SYNTAX INTEGER {
	        present (1),
			absent (2),
			tempHot (3),
			tempNorm (4),
			fault (5),
			noFault (6),
			fail (7),
			noFail (8)
	      }
	     MAX-ACCESS accessible-for-notify
	     STATUS  current
	     DESCRIPTION
	     "Indicates the status of the Chassis power supply."
         ::= { chassisPowerSupplyEntry 2 }

         chassisFWStatus	OBJECT-TYPE
	     SYNTAX  INTEGER {
               ok 			         (0),		
               bad-host	       	   (1),
               net-drv		         (2),	
			      file-not-found		   (3),	
			      task-not-found		   (4),	
			      read-error		      (5),	   
			      unknown-image-type	(6),    
			      out-of-memory		   (7),		
			      write-error		      (8),		
			      busy			         (9),			
			      spawn-failed		   (10),		
			      in-progress		      (11),		
			      state-error		      (12),		
			      bad-ip-addr		      (13),		
			      bad-msg		         (14),		
			      unknown-msg		      (15),		
			      retries-expired	   (16),		
			      reg-ipc		         (17),		
			      fault			         (18),                  
			      lock-failure		   (19),           
			      locked			      (20),                 
			      invalid-image-header	(21),   
			      crc-mismatch		   (22),           
			      not-a-gne		      (23),              
			      signature-mismatch	(24),     
			      last-instance		   (25),          
			      init-not-complete	   (26),      
			      abort			         (27),                  
			      pending		         (28) 
}         
	     MAX-ACCESS accessible-for-notify
	     STATUS	current
	     DESCRIPTION
		 " The statuses for chassis firmware update or rollback."
	     ::= {chassis 11 }	    

     ringFWStatus	OBJECT-TYPE
	     SYNTAX  INTEGER {
               ok 			         (0),		
               bad-host	       	   (1),
               net-drv		         (2),	
			      file-not-found		   (3),	
			      task-not-found		   (4),	
			      read-error		      (5),	   
			      unknown-image-type	(6),    
			      out-of-memory		   (7),		
			      write-error		      (8),		
			      busy			         (9),			
			      spawn-failed		   (10),		
			      in-progress		      (11),		
			      state-error		      (12),		
			      bad-ip-addr		      (13),		
			      bad-msg		         (14),		
			      unknown-msg		      (15),		
			      retries-expired	   (16),		
			      reg-ipc		         (17),		
			      fault			         (18),                  
			      lock-failure		   (19),           
			      locked			      (20),                 
			      invalid-image-header	(21),   
			      crc-mismatch		   (22),           
			      not-a-gne		      (23),              
			      signature-mismatch	(24),     
			      last-instance		   (25),          
			      init-not-complete	   (26),      
			      abort			         (27),                  
			      pending		         (28)	    
}         
	     MAX-ACCESS accessible-for-notify
	     STATUS	current
	     DESCRIPTION
		 " The statuses for ring firmware update or rollback "
	     ::= { chassis 12 } 

	 ftpServerIP OBJECT-TYPE
	     SYNTAX IpAddress
	     MAX-ACCESS accessible-for-notify
	     STATUS  current
	     DESCRIPTION
	     "Where the firmware was located"
         ::= { chassis 13 }

	 controlFilePath OBJECT-TYPE
	     SYNTAX OCTET STRING
	     MAX-ACCESS accessible-for-notify
	     STATUS  current
	     DESCRIPTION
	     "Path to the new control file"
         ::= { chassis 14 }

	 versionString	 OBJECT-TYPE
	     SYNTAX OCTET STRING
	     MAX-ACCESS accessible-for-notify
	     STATUS  current
	     DESCRIPTION
	     "control file version string"
         ::= { chassis 15 }

	 syslogUnknownEvent OBJECT-TYPE
	     SYNTAX INTEGER
	     MAX-ACCESS accessible-for-notify
	     STATUS  current
	     DESCRIPTION
	     "An unknown event occurs when the event Manager gets 
         an event-type which it doesn't know about. This is an 
         almost impossible event to occur..as all event-types 
         are first defined and made known to the event-manager."
         ::= { chassis 16 }

	 syslogUnknownVersion	 OBJECT-TYPE
	     SYNTAX INTEGER
	     MAX-ACCESS accessible-for-notify
	     STATUS  current
	     DESCRIPTION
	     "For any given image, all events will have a constant 
         version number. All events are preceded by a 'common_header' 
         which will have a version. Again, if the event-manager 
         doesn't recognize the version, it generates 'unknownVersion' 
         event. But again, this is very unlikely to happen as for any 
         given image, all events will have  the same common_hdr version."
         ::= { chassis 17 }      
		 
	 chassisRoutingProt OBJECT-TYPE
	     SYNTAX INTEGER {
               none(1),
               rip(2)
             }
	     MAX-ACCESS read-write
	     STATUS current
	     DESCRIPTION
	     " This variable is used to dynamically initiate RIP or OSPF on the switch.
             Setting this variable to none causes RIP or OSPF to be shutdown if they
             have been enabled "
	 ::= { chassis 18 }   
	

		 chassisSubnetIp OBJECT-TYPE
		 SYNTAX IpAddress
		 MAX-ACCESS read-write
		 STATUS current
		 DESCRIPTION
		 " This object gives the subnet IP Address of the chassis."
		 ::= { chassis 19 }

		 chassisSubnetMask OBJECT-TYPE
		 SYNTAX IpAddress
		 MAX-ACCESS read-write
		 STATUS current
		 DESCRIPTION
		 " This object provides the subnet mask of the chassis."
		 ::= { chassis 20 }

		 chassisRingsOnMaster OBJECT-TYPE
		 SYNTAX OCTET STRING
		 MAX-ACCESS read-write
		 STATUS current
		 DESCRIPTION
		 " This object gives a comma separated list of ring IDs for
         which this SNE acts as a master. This object is valid
         only for an SNE."
		 ::= { chassis 21 }

		 chassisCurrentRingsOnMaster OBJECT-TYPE
		 SYNTAX OCTET STRING
		 MAX-ACCESS read-only
		 STATUS current
		 DESCRIPTION
		 " This object gives the current list of ring IDs which
         this master (SNE) controls. If rings are added or taken-off,
         the system has to be rebooted to provide the correct list. 
         This is valid only for an SNE."
		 ::= { chassis 22 }

	 chassisFailoverPreserveRings OBJECT-TYPE
	        SYNTAX OCTET STRING
		MAX-ACCESS read-write
		STATUS current
		DESCRIPTION
		" This object gives a comma separated list of ring IDs that
		  are to be preserved across module failures. "
		::= { chassis 23 }


         systimeTimingMode OBJECT-TYPE
              SYNTAX INTEGER {
                tmExt(1),
                tmLine(2),
                tmFreerun(3)
               }
              MAX-ACCESS read-write
              STATUS current
              DESCRIPTION
              "The type of timing used by the device.

		         External    (default for OptiFlow 5000) 
                           -	Primary Clock Source is always BITS1.
                           -	Secondary Clock Source is always BITS2.

               Line	      (default for OptiFlow 3000/3500)
                           -	Primary Clock Source may be a switch module 
                              or an I/O module.
                           -	Secondary Clock Source may be a switch module, 
                              an I/O module or the internal oscillator.

		         Freerun
                           -	Clock source is the internal oscillator (Primary Clock 
                              Source and Secondary Clock Source not used)."   
              ::= { systime 1 }

         systimePriBITSFraming OBJECT-TYPE 
              SYNTAX INTEGER {
                t1SF(1),
                t1ESF4K(2),
                t1T1DM(3),
                t1T1DMAlt(4),
                t1SLC96(5),
                e1(6)
               }
              MAX-ACCESS read-write
              STATUS current
              DESCRIPTION
              " This is the Primary BITS basic line framing. Default is T1-ESF-4K.

               t1SF -   Super Frame framing method used on T1 circuits. SF consists of 
                        12 frames of 192 bits each, with the 193rd bit providing error 
                        checking and other functions. SF is superseded by ESF, but is
                        still widely used. Also called D4 framing.

               t1ESF4K -   The default method. Extended Super Frame framing method used
                           on T1 circuits that consists of 24 frames of 192 bits each, 
                           with the 193rd bit providing timing and other functions. ESF
                           is an enhanced version of SF.

               t1T1DM    - Data Mode.

               t1T1DMAlt - Data MOde A.

               t1SLC96   - Subscriber Lopp Carrier, 96 lines.

               e1        - Wide-area digital transmission scheme used predominantly
                           in Europe that carries data at a arate of 2.048 Mbps."   
              ::= { systime 2 }   

            systimeSecBITSFraming OBJECT-TYPE 
              SYNTAX INTEGER {
                t1SF(1),
                t1ESF4K(2),
                t1T1DM(3),
                t1T1DMAlt(4),
                t1SLC96(5),
                e1(6)
               }
              MAX-ACCESS read-write
              STATUS current
              DESCRIPTION
              " This is the Secondary BITS basic line framing. Default is T1-ESF-4K.

               t1SF -   Super Frame framing method used on T1 circuits. SF consists of 
                        12 frames of 192 bits each, with the 193rd bit providing error 
                        checking and other functions. SF is superseded by ESF, but is
                        still widely used. Also called D4 framing.

               t1ESF4K -   The default method. Extended Super Frame framing method used
                           on T1 circuits that consists of 24 frames of 192 bits each, 
                           with the 193rd bit providing timing and other functions. ESF
                           is an enhanced version of SF.

               t1T1DM    - Data Mode.

               t1T1DMAlt - Data MOde A.

               t1SLC96   - Subscriber Lopp Carrier, 96 lines.

               e1        - Wide-area digital transmission scheme used predominantly
                           in Europe that carries data at a arate of 2.048 Mbps."   
              ::= { systime 3 }        

            systimePriBITSCoding OBJECT-TYPE
            SYNTAX INTEGER {
              ami(1),
              b8zs(2),
              hdb3(3)
            }
            MAX-ACCESS read-write
            STATUS current
            DESCRIPTION 
            " This is the primary BITS line coding. Default is B8ZS. Valid when 
               timing_mode is EXT.
               AMI  -   Alternate Mask Inversion (valid when PrimaryBITSFraming = T1).
               B8ZS -   Bianry 8 Zero Substitution (the default). Valid when
                        PrimaryBITSFraming = T1).
               HDB3 -   High Density Bipolar 3 (valid when PrimaryBITSFraming = E1)."
            ::= { systime 4 }

            systimeSecBITSCoding OBJECT-TYPE
            SYNTAX INTEGER {
              ami(1),
              b8zs(2),
              hdb3(3)
            }
            MAX-ACCESS read-write
            STATUS current
            DESCRIPTION 
            " This is the seconday BITS line coding. Default is B8ZS. Valid when
               timing mode is EXT.
               AMI  -   Alternate Mask Inversion (valid when PrimaryBITSFraming = T1).
               B8ZS -   Bianry 8 Zero Substitution (the default). Valid when
                        PrimaryBITSFraming = T1).
               HDB3 -   High Density Bipolar 3 (valid when PrimaryBITSFraming = E1)."
            ::= { systime 5 }

            systimePriClkSrcId OBJECT-TYPE
            SYNTAX OCTET STRING
            MAX-ACCESS read-write
            STATUS current
            DESCRIPTION 
            " This is the primary timing interface clock.
   
            bits1 - Valid when the timing mode is EXT.
            bits2 - Valid when the timing mode is EXT.
            iosc  - Internal Oscillator (valid when the timing mode is LINE. "
            ::= { systime 6 }

          
            systimeSecClkSrcId OBJECT-TYPE
            SYNTAX OCTET STRING
            MAX-ACCESS read-write
            STATUS current
            DESCRIPTION 
            " This is the secondary timing interface clock

            bits1 - Valid when the timing mode is EXT.
            bits2 - Valid when the timing mode is EXT.
            iosc  - Internal Oscillator (valid when the timing mode is LINE."
            ::= { systime 7 }

          systimeClkReference OBJECT-TYPE
          SYNTAX INTEGER {
            crAuto(1),
            crPri(2),
            crSec(3),
            crHoldover(4),
            crStandby(5),
            crStandbypri(6),
            crStandbysec(7),
            crFreerun(8)
           }
          MAX-ACCESS read-write
          STATUS current
          DESCRIPTION
		     "Automatic(default) -	This automatically selects a Stratum 3 or better 
               clock from the Primary Clock Source, Secondary Clock Source, Holdover 
               Clock, Standby Clock or internal oscillator.

		      Primary -	This is the permanent selection of the Primary Clock Source 
               if the Primary Clock Source is valid at the time of request.

            Secondary -	This is the permanent selection of the Secondary Clock Source 
               if the Secondary Clock Source is valid at the time of request.

		      Standby -	This is the permanent selection of the Standby Clock Source 
               if the Standby Clock Source is valid at the time of request.

		      Standby / Primary -	This is the permanent selection of the Standby / 
               Primary Clock Source if the Standby / Primary Clock Source is valid at 
               the time of request.

		      Standby / Secondary -	This is the permanent selection of the Standby / 
               Secondary Clock Source if the Standby / Secondary Clock Source is valid 
               at the time of request.

		      Freerun -	This is the permanent selection of the internal oscillator."
          ::= { systime 8 }

          systimeClkRevertive OBJECT-TYPE
          SYNTAX INTEGER {
            enable(1),
            disable(2)
          }
          MAX-ACCESS read-write
          STATUS current
          DESCRIPTION
          " Sets the method by which the device (equipment) returns to using the 
            Primary Clock Source after the Primary Clock Source has failed. Options:

            Enable  - enables attempting to return to the Primary Clock Source at any time.

            Disable - disables 'attempting at any time' and forces return to the Primary 
                      Clock Source as defined by pri_cs_use_limit and 
                      pri_cs_use_interval. This is the default setting. This setting 
                      avoids excessive switching between clock sources."

          ::= { systime 9 }

          systimeStandbyClkEnable OBJECT-TYPE
          SYNTAX INTEGER {
            enable(1),
            disable(2)
          }
          MAX-ACCESS read-write
          STATUS current
          DESCRIPTION
          " This enables use of standby management module clock reference.
            It enables using the primary clock source, secondary clock source
            or holdover on the standby management module when those on the 
            active management module are not acceptable. The default state
            is Enabled."
          ::= { systime 10 }

          systimePriCSNVTime OBJECT-TYPE
          SYNTAX INTEGER(1..30) 
          MAX-ACCESS read-write
          STATUS current
          DESCRIPTION
          " Primary Clock Source Normal Validation Time. This is the amount of 
            time required to validate the primary clock source when not in the 
            holdover state. Default is 3 seconds."
          ::= { systime 11 }

          systimeSecCSNVTime OBJECT-TYPE
          SYNTAX INTEGER(1..30)
          MAX-ACCESS read-write
          STATUS current
          DESCRIPTION
          " Secondary Clock Source Normal Validation Time. This is the amount of 
            time required to validate the secondary clock source when not in the 
            holdover state. Default is 3 seconds."
          ::= { systime 12 }

          systimePriCSHVTime OBJECT-TYPE
          SYNTAX INTEGER(1..60)
          MAX-ACCESS read-write
          STATUS current
          DESCRIPTION
          " Primary Clock Source Holdover Validation Time. This is the amount of 
            time required to validate the primary clock source when in the holdover 
            state. Default is 10 seconds."
          ::= { systime 13 }

          systimeSecCSHVTime OBJECT-TYPE
          SYNTAX INTEGER(1..60)
          MAX-ACCESS read-write
          STATUS current
          DESCRIPTION
          " Secondary Clock Source Holdover Validation Time. This is the amount of 
            time required to validate the secondary clock source when in the holdover 
            state. Default is 10 seconds."
          ::= { systime 14 }

          systimePriCSUseLimit OBJECT-TYPE
          SYNTAX INTEGER(1..999) 
          MAX-ACCESS read-write
          STATUS current
          DESCRIPTION
          " This is the number of times the primary clock source may be
            used over the time interval primary clock source use interval
            (systimeSecCSUseInterval). It permits several attempts at using 
            the primary clock source when prior attempts did not pass the 
            Stratum 3 requirement. The default is 3 times."
          ::= { systime 15 }

          systimeSecCSUseLimit OBJECT-TYPE
          SYNTAX INTEGER(1..999)
          MAX-ACCESS read-write
          STATUS current
          DESCRIPTION
          " This is the number of times the secondary clock source may be
            used over the time interval Secondary clock source use interval
            (systimeSecCSUseInterval). It permits several attempts at using 
            the secondary clock source when prior attempts did not pass the 
            Stratum 3 requirement. The default is 3 times."
          ::= { systime 16 }

          systimeStandbyCSUseLimit OBJECT-TYPE
          SYNTAX INTEGER(1..999)
          MAX-ACCESS read-write
          STATUS current
          DESCRIPTION
          " This is the number of times the standby clock source may be
            used over the time interval standby clock source use interval
            (systimeStandbyCSUseInterval).It permits several attempts at 
            using the standby clock source   when prior attempts did not 
            pass the Stratum 3 requirement. The default is 3 times."
          ::= { systime 17 }

          systimePriCSUseInterval OBJECT-TYPE
          SYNTAX INTEGER(1..96)
          MAX-ACCESS read-write
          STATUS current
          DESCRIPTION
          " This is the time interval used to reset the Primary Clock Source used
            count. Ranges from 1 to 96 hours. Default is 1 hour."
          ::= { systime 18 }

          systimeSecCSUseInterval OBJECT-TYPE
          SYNTAX INTEGER(1..96)
          MAX-ACCESS read-write
          STATUS current
          DESCRIPTION
          " This is the time interval used to reset the Secondary Clock Source used
            count. Ranges from 1 to 96 hours. Default is 1 hour."
          ::= { systime 19 }

          systimeStandbyCSUseInterval OBJECT-TYPE
          SYNTAX INTEGER(1..96)
          MAX-ACCESS read-write
          STATUS current
          DESCRIPTION
          " This is the time interval used to reset the Standby Clock Source used
            count. Ranges from 1 to 96 hours. Default is 1 hour."
          ::= { systime 20}

          systimeCREventEnable OBJECT-TYPE
          SYNTAX INTEGER {
            enable(1),
            disable(2)
          }
          MAX-ACCESS read-write
          STATUS current
          DESCRIPTION
          " This generates an alarm when the clock reference used changes from either
            the primary or the secondary. Default is Enable."
          ::= { systime 21 }

          systimeCRInUse OBJECT-TYPE
          SYNTAX INTEGER {
            crAuto(1),
            crPri(2),
            crSec(3),
            crHoldover(4),
            crStandby(5),
            crStandbypri(6),
            crStandbysec(7),
            crFreerun(8)
          }
          MAX-ACCESS read-only
          STATUS current
          DESCRIPTION
          " This indicates the current clock reference.
		      Automatic(default) -	This automatically selects a Stratum 3 or better 
               clock from the Primary Clock Source, Secondary Clock Source, Holdover 
               Clock, Standby Clock or internal oscillator.

		      Primary -	This is the permanent selection of the Primary Clock Source 
               if the Primary Clock Source is valid at the time of request.

            Secondary -	This is the permanent selection of the Secondary Clock Source 
               if the Secondary Clock Source is valid at the time of request.

		      Standby -	This is the permanent selection of the Standby Clock Source 
               if the Standby Clock Source is valid at the time of request.

		      Standby / Primary -	This is the permanent selection of the Standby / 
               Primary Clock Source if the Standby / Primary Clock Source is valid at 
               the time of request.

		      Standby / Secondary -	This is the permanent selection of the Standby / 
               Secondary Clock Source if the Standby / Secondary Clock Source is valid 
               at the time of request.

		      Freerun -	This is the permanent selection of the internal oscillator."
          ::= { systime 22 }

          systimeCRUsedCount OBJECT-TYPE
          SYNTAX	Counter32
          MAX-ACCESS read-only
          STATUS current
          DESCRIPTION
          " This indicates the number of times this clock had been used."
          ::= { systime 23 }            

         deviceNMSTable OBJECT-TYPE
              SYNTAX  SEQUENCE OF DeviceNMSEntry
              MAX-ACCESS  not-accessible
              STATUS  current
              DESCRIPTION
              "A table that contains information about the set of
               network management stations that are allowed to 
               manage this device"
              ::= { device 4 }

          deviceNMSEntry OBJECT-TYPE
              SYNTAX  DeviceNMSEntry
              MAX-ACCESS  not-accessible
              STATUS  current
              DESCRIPTION
              "A list of information for each NMS allowed to manage this device"
              INDEX  { deviceNMSIndex }
              ::= { deviceNMSTable 1 }


          DeviceNMSEntry ::=
              SEQUENCE {
                  deviceNMSIndex
                      INTEGER,
                  deviceNMSIpAddress
                      IpAddress,
                  deviceNMSAccessType
                      INTEGER,
                  deviceNMSMIBIITrapList
                      OCTET STRING,
                  deviceNMSEnterpriseTrapList
                      OCTET STRING,
                  deviceNMSTrapSevAllowed
                      INTEGER
              }

          deviceNMSIndex OBJECT-TYPE
              SYNTAX INTEGER
              MAX-ACCESS not-accessible
              STATUS current
              DESCRIPTION
              " The index of the Network Management Station "
              ::= { deviceNMSEntry 1 } 

          deviceNMSIpAddress OBJECT-TYPE
              SYNTAX IpAddress
              MAX-ACCESS read-write
              STATUS current
              DESCRIPTION
              " The IP address of the Network Management Station"
              ::= { deviceNMSEntry 2 } 

          deviceNMSAccessType OBJECT-TYPE
              SYNTAX INTEGER {
                accessTypeTrapEnabled(1),
                accessTypeTrapDisabled(2)
              }
              MAX-ACCESS read-write
              STATUS current
              DESCRIPTION
              " This determines whether the NMS can receive traps or not"
              ::= { deviceNMSEntry 3 } 

          deviceNMSMIBIITrapList OBJECT-TYPE
              SYNTAX OCTET STRING (SIZE (1))
              MAX-ACCESS read-write
              STATUS current
              DESCRIPTION
              " The bitmask describing the MIB II traps that this NMS can receive. The
               MIBII traps are the following:
               0 = coldStart
               1 = warmStart
               2 = linkDown
               3 = linkUp
               4 = authenticationFailure
               5 = egpNeighborLoss 

               This is a 1 byte bit-mask. If only the least significant bit is set, it means
               'coldStart' traps are allowed to be received by the device. If the bit-mask
               is '00100101', it means that the device is enabled to receive the traps
               coldStart, linkDown and egpNeighborLoss."
              ::= { deviceNMSEntry 4 } 

          deviceNMSEnterpriseTrapList OBJECT-TYPE
              SYNTAX OCTET STRING (SIZE (20))
              MAX-ACCESS read-write
              STATUS current
              DESCRIPTION
              " The bitmask describing the enterprise specific traps that this NMS can receive.
                These kinds of traps begin at the value 7 (values 0-6 are taken by the MIBII
                traps). The bit-mask is handled in the way this example shows for a specific
                trapType of (say) 55: 

                specificTrapType/8 = 55/8 = 6.
                specificTrapType % 8 = 7.

                There are 20 bytes in this mask and the 7th bit in the 6th byte is set."
              ::= { deviceNMSEntry 5 } 

          deviceNMSTrapSevAllowed OBJECT-TYPE
              SYNTAX INTEGER {
                trapSevClear(1),
                trapSevInfo(2),
                trapSevWarning(3),
                trapSevMinor(4),
                trapSevMajor(5),
                trapSevCritical(6)
              }
              MAX-ACCESS read-write
              STATUS current
              DESCRIPTION
              " This determines the trap severities the NMS can receive"
              ::= { deviceNMSEntry 6 } 

          sysMemory	OBJECT IDENTIFIER ::= { device 5 } 

          --	Memory Group

          --	This group provides the memory usage information on the target.
          --	All variables in this group are read only.


          numBytesFree		OBJECT-TYPE
	      SYNTAX		Integer32
	      MAX-ACCESS	read-only
		  STATUS		current
	      DESCRIPTION
		  " The number of bytes free in the system memory "	      
	      ::= { sysMemory 1 }

          numBlocksFree		OBJECT-TYPE
	      SYNTAX		Integer32
	      MAX-ACCESS	read-only
	      STATUS		current
	      DESCRIPTION
		  " The number of blocks free in the system memory "
	      ::= { sysMemory 2 }

          avgBlockSizeFree	OBJECT-TYPE
	      SYNTAX		Integer32
	      MAX-ACCESS	read-only
	      STATUS		current
	      DESCRIPTION
		  " The average block size that is free in the system memory "
	      ::= { sysMemory 3 }

          maxBlockSizeFree	OBJECT-TYPE
	      SYNTAX		Integer32
	      MAX-ACCESS	read-only
	      STATUS		current
	      DESCRIPTION
		  " The largest block size that is free in the memory "
	      ::= { sysMemory 4 }

          numBytesAlloc		OBJECT-TYPE
	      SYNTAX		Integer32
	      MAX-ACCESS	read-only
	      STATUS		current
	      DESCRIPTION
		  " The number of bytes of system memory that have been allocated by 
            tasks and system services "
	      ::= { sysMemory 5 }

          numBlocksAlloc		OBJECT-TYPE
	      SYNTAX		Integer32
	      MAX-ACCESS	read-only
	      STATUS		current
	      DESCRIPTION
	  	  " The number of blocks of system memory that have been allocated in 
            the system "
	      ::= { sysMemory 6 }

          avgBlockSizeAlloc	OBJECT-TYPE
	      SYNTAX		Integer32
	      MAX-ACCESS	read-only
	      STATUS		current
	      DESCRIPTION
		  " The average memory block size that has been allocated in the 
            system "
	      ::= { sysMemory 7 }

		  memUtilization OBJECT-TYPE
		  SYNTAX         Integer32
		  MAX-ACCESS     read-only
		  STATUS         current
		  DESCRIPTION
		  " This gives the memory utilization in terms of percentage "
		  ::= { sysMemory 8 }

	      sysTask OBJECT IDENTIFIER ::= { device 6 }


--      Task Group

--      This group provides access to the target's task table.
--      Tasks can be suspended, created, resumed and deleted.
--      Individual parameters can also be changed. While changing
--      task information, it should be remembered that the information
--      from this group is only a snapshot of the task table entries.
--      VxWorks tasks can be created by creating an entry in the
--      tasktable. An entry should be created with an index of zero.
--      The other parameters that must be specified are: name, priority,
--       stacksize, entry point and other options.


          taskTable               OBJECT-TYPE
          SYNTAX          SEQUENCE OF TaskEntry
          MAX-ACCESS      not-accessible
          STATUS          current
          DESCRIPTION
                "Represents the target's task table. Each entry in this table 
                 represents a task"
          ::= { sysTask 1 }

          taskEntry               OBJECT-TYPE
          SYNTAX          TaskEntry
          MAX-ACCESS      not-accessible
          STATUS          current
          DESCRIPTION
                " Each entry contains information with regards to a task in the 
                  system "
          INDEX           { taskId }
          ::= { taskTable 1 }

          TaskEntry ::=
          SEQUENCE {
          taskId
          Integer32,
          taskName
          DisplayString,
          taskPriority
          Integer32,
          taskStatus
          INTEGER,
          taskOptions
          Integer32,
          taskMain
          DisplayString,
          taskStackPtr
          Unsigned32,
          taskStackBase
          Unsigned32,
          taskStackPos
          Unsigned32,
          taskStackEnd
          Unsigned32,
          taskStackSize
          Unsigned32,
          taskStackSizeUsage
          Unsigned32,
          taskStackMaxUsed
          Unsigned32,
          taskStackFree
          Unsigned32,
          taskErrorStatus
          Integer32
           }

          taskId          OBJECT-TYPE
          SYNTAX          Integer32
          MAX-ACCESS      read-only
          STATUS          current
          DESCRIPTION
                " This is the task ID assigned by VxWorks to a task in the
                  system. A taskId of zero specifies a new task."
          ::= { taskEntry 1 }

          taskName                OBJECT-TYPE
          SYNTAX          DisplayString
          MAX-ACCESS      read-write
          STATUS          current
          DESCRIPTION
                " This is the name of the VxWorks task.  This value can
                 only be specified (set) at task creation."
          ::= { taskEntry 2 }

          taskPriority            OBJECT-TYPE
          SYNTAX          Integer32
          MAX-ACCESS      read-write
          STATUS          current
          DESCRIPTION
                "The priority of the VxWorks task.  This value can be
                 in the range from 0, the highest priority,
                 to 255, the lowest priority."
          ::= { taskEntry 3 }

          taskStatus              OBJECT-TYPE
          SYNTAX          INTEGER {
                                task-ready(1),      -- Task is ready to run.
                                task-suspended(2),  -- Task is suspended.
                                task-delay(3),      -- Task is delayed.
                                task-deleted(4)     -- Task is to be deleted.
                        }
          MAX-ACCESS      read-write
          STATUS          current
          DESCRIPTION
                "This field specifies the current task status.  It
                 can be used to change the current task state.
                 For example, to suspend a task, the value of
                 taskStatus is changed to task-suspended,
                 to delete a task the value is changed to
                 task-deleted, etc..."
          ::= { taskEntry 4 }

          taskOptions             OBJECT-TYPE
          SYNTAX          Integer32
          MAX-ACCESS      read-write
          STATUS          current
          DESCRIPTION
                "This value represents the sum of the following
                 options:

                        value      option
                         1        VX_SUPERVISOR_MODE(read-only)
                         2        VX_UNBREAKABLE    (break points ignored)
                         4        VX_DEALLOC_STACK  (deallocate stack)
                         8        VX_FP_TASK        (floating point support)
                        16        VX_STDIO          (read-only)
                        128        VX_PRIVATE_ENV    (private env. variables)
                        256        VX_NO_STACK_FILL  (don't fill stack)

                 All the options above can be set at task creation time.
                 However, once the task is executing the only option
                 that can be changed is VX_UNBREAKABLE.  The option is
                 toggled based on the current setting."
          ::= { taskEntry 5 }

          taskMain                OBJECT-TYPE
          SYNTAX          DisplayString
          MAX-ACCESS      read-write
          STATUS          current
          DESCRIPTION
                "This is the name of the entry function for the VxWorks
                 task.  This name can only be specified when a task
                 is created (entry added in the table).  The symbol
                 must exist in the VxWorks target."
          ::= { taskEntry 6 }

          taskStackPtr            OBJECT-TYPE
          SYNTAX          Unsigned32
          MAX-ACCESS      read-only
          STATUS          current
          DESCRIPTION
                "This is the saved stack pointer for the task."
          ::= { taskEntry 7 }


          taskStackBase           OBJECT-TYPE
          SYNTAX          Unsigned32
          MAX-ACCESS      read-only
          STATUS          current
          DESCRIPTION
                "This is the address of the bottom of the stack of
                 the VxWorks task."
          ::= { taskEntry 8 }

          taskStackPos            OBJECT-TYPE
          SYNTAX          Unsigned32
          MAX-ACCESS      read-only
          STATUS          current
          DESCRIPTION
                "This is the effective top of the stack in the current
                 task state."
          ::= { taskEntry 9 }

          taskStackEnd            OBJECT-TYPE
          SYNTAX          Unsigned32
          MAX-ACCESS      read-only
          STATUS          current
          DESCRIPTION
                "This is the address of the top of the stack of the
                 VxWorks task."
          ::= { taskEntry 10 }

          taskStackSize           OBJECT-TYPE
          SYNTAX          Unsigned32
          MAX-ACCESS      read-write
          STATUS          current
          DESCRIPTION
                "This is the actual size of the stack in bytes.  The
                 size of the stack can only be specified at task
                 creation (adding an entry to the table)."
          ::= { taskEntry 11 }

          taskStackSizeUsage      OBJECT-TYPE
          SYNTAX          Unsigned32
          MAX-ACCESS      read-only
          STATUS          current
          DESCRIPTION
                "The number of bytes currently in use by the task from
                 the stack."
          ::= { taskEntry 12 }

          taskStackMaxUsed        OBJECT-TYPE
          SYNTAX          Unsigned32
          MAX-ACCESS      read-only
          STATUS          current
          DESCRIPTION
                "This is the maximum number of bytes that have been used
                 by the task from the stack."
          ::= { taskEntry 13 }

          taskStackFree           OBJECT-TYPE
          SYNTAX          Unsigned32
          MAX-ACCESS      read-only
          STATUS          current
          DESCRIPTION
                "This is the number of bytes that are free currently in
                 the task stack."
          ::= { taskEntry 14 }

          taskErrorStatus         OBJECT-TYPE
          SYNTAX          Integer32
          MAX-ACCESS      read-only
          STATUS          current
          DESCRIPTION
                "This is the most recent error status for this task."
          ::= { taskEntry 15 }

          emSysLogCorrupt TRAP-TYPE
          ENTERPRISE coriolisMibs
          DESCRIPTION
          " Event log entries got corrupted "
          ::= 8        

          emSysLogCapacity TRAP-TYPE
          ENTERPRISE coriolisMibs
          DESCRIPTION
          " Event logs nearing capacity "
          ::= 9        

          emSysLogBackUpDelete TRAP-TYPE
          ENTERPRISE coriolisMibs
          DESCRIPTION
          " Event backup log file deleted "
          ::= 10

          emSysLogEvIdWrap TRAP-TYPE
          ENTERPRISE coriolisMibs
          DESCRIPTION
          " Event Id wrapped"
          ::= 11

		  emErrLogCorrupt TRAP-TYPE
          ENTERPRISE coriolisMibs
          DESCRIPTION
          " Corrupt error log file "
          ::= 14

		  emErrLogCapacity TRAP-TYPE
          ENTERPRISE coriolisMibs
          DESCRIPTION
          " Error logs nearing capacity "
          ::= 15

		  emErrLogBackUpDelete TRAP-TYPE
          ENTERPRISE coriolisMibs
          DESCRIPTION
          " Backup error log deleted "
          ::= 16

		  emErrLogEvIdWrap TRAP-TYPE
          ENTERPRISE coriolisMibs
          DESCRIPTION
          " Error event id wrapped "
          ::= 17

		  emSysLogsCleared TRAP-TYPE
          ENTERPRISE coriolisMibs
          DESCRIPTION
          " System logs cleared "
          ::= 18

		  emErrLogsCleared TRAP-TYPE
          ENTERPRISE coriolisMibs
          DESCRIPTION
          " Error logs cleared "
          ::= 19

	      systimeClkReferenceChange	TRAP-TYPE
	      ENTERPRISE  coriolisMibs
		  VARIABLES { systimeClkReference }
	      DESCRIPTION
		  "Change in the systiming clk reference to primary, secondary, 
         holdover or freerun"
	      ::= 23

	      powerSupplyStatusChange	TRAP-TYPE
		  ENTERPRISE	coriolisMibs
		  VARIABLES	{chassisPowerSupplyNumber, chassisPowerSupplyStatus}
		  DESCRIPTION
		      "Indicates the change in power supply status of the chassis."
	      ::= 42

	      fanStatusChange	TRAP-TYPE
		  ENTERPRISE	coriolisMibs
		  VARIABLES	{chassisFanStatus}
		  DESCRIPTION
		      "Indicates the change in fan status of the chassis."
	      ::= 43

	      chassisFWUpdate	TRAP-TYPE
		  ENTERPRISE	coriolisMibs
		  VARIABLES	{chassisFWStatus, chassisIpAddr, ftpServerIP, controlFilePath }
		  DESCRIPTION
		      "Chassis FirmWare update event."
	      ::= 54	 

	      chassisFWActivate	TRAP-TYPE
		  ENTERPRISE	coriolisMibs
		  VARIABLES	{chassisFWStatus, chassisIpAddr, versionString }
		  DESCRIPTION
		      "Chassis FirmWare activate event."
	      ::= 52

	      ringFWUpdate	TRAP-TYPE
		  ENTERPRISE	coriolisMibs
		  VARIABLES	{ringFWStatus, chassisIpAddr, ftpServerIP, controlFilePath }
		  DESCRIPTION
		      "Ring FirmWare update event."
	      ::= 53	 

	      ringFWActivate	TRAP-TYPE
		  ENTERPRISE	coriolisMibs
		  VARIABLES	{ringFWStatus, chassisIpAddr, versionString }
		  DESCRIPTION
		      "Ring FirmWare activate event."
	      ::= 51
     
	      sysLogUnknownEvent  TRAP-TYPE
		  ENTERPRISE	coriolisMibs
		  VARIABLES	{syslogUnknownEvent }
		  DESCRIPTION
		      "Unknown Event."
	      ::= 57

	      sysLogUnknownVersion  TRAP-TYPE
		  ENTERPRISE	coriolisMibs
		  VARIABLES	{syslogUnknownVersion }
		  DESCRIPTION
		      "Unknown Version."
	      ::= 58		  

          END
