Nortel-Magellan-Passport-TextualConventionsMIB
DEFINITIONS ::= BEGIN

IMPORTS

      Gauge, Counter
   FROM RFC1155-SMI

      Unsigned32, Integer32
   FROM  Nortel-Magellan-Passport-StandardTextualConventionsMIB
    
    passportMIBs	
   FROM Nortel-Magellan-Passport-UsefulDefinitionsMIB;

--    LAST-UPDATED   "9603010000Z"
--    ORGANIZATION   "Nortel"
--    CONTACT-INFO   "
--         Nortel Magellan Network Management
--
--         Postal: P.O. Box 5080, Station F
--                 Ottawa, Ontario
--                 Canada  K2C 3T1
--
--         Email:  nm_plm@nt.com"
--    DESCRIPTION 
--       "The MIB module describing the Nortel Magellan Passport 
--       Textual Conventions.
--
--       A detailed description of how these conventions work is 
--       provided in Appendix B of the Passport Enterprise MIB 
--       User Guide."

textualConventionsMIB   OBJECT IDENTIFIER  ::= { passportMIBs 2 }

--
-- General Conventions:
--

Hex          ::= Unsigned32
--    " Represents an Unsigned32 value that should be displayed
--     in Hexadecimal format."

Gauge64      ::= OCTET STRING (SIZE (8))
--    " Represents a 64-bit integer value that has the semantics of 
--    a gauge. This value is encoded as eight octets where the first
--    octet is the most significant (big-endian encoding)."

Unsigned64   ::= OCTET STRING (SIZE (8))
--    " Represents a 64-bit integer value that has no particular 
--    semantics (that is, is not a Counter or a Gauge). This 
--    value is encoded as eight octets where the first octet
--    is the most significant (big-endian encoding)."

DigitString  ::= OCTET STRING (SIZE(0..1024))
--    " Represents a string of decimal digits, that is 0..9.
--    Each OCTET contains the ASCII representation of a single digit."

WildcardedDigitString  ::= OCTET STRING (SIZE(0..1024))
--    " Represents a string of decimal digits, that is 0..9,
--    or the question mark character '?' that acts as a wildcard
--    character for any single digit.
--    Each OCTET contains the ASCII representation of a single digit
--    or the ASCII representation of the wild card character."

HexString    ::= OCTET STRING (SIZE(0..1024))
--    " Represents an OCTET STRING that should be displayed in hex."

AsciiString  ::= OCTET STRING (SIZE(0..1024))
--    " Represents a string of printable Ascii characters in the range
--    32 to 127. Newlines may appear in read-only variables."

ExtendedAsciiString ::= OCTET STRING (SIZE(0..1024))
--    " Represents an OCTET STRING that should be displayed as ASCII 
--    where there is a correspondence to AsciiString and as `\xx` 
--    otherwise."

DashedHexString ::= OCTET STRING (SIZE(0..1024))
--    " Represents an OCTET STRING that should be displayed in hex 
--    with dash seperators."

EnterpriseDateAndTime 
    ::= OCTET STRING (SIZE ( 0 | 2 | 5 | 8 | 10 | 13 | 16 | 19 ))
--    "A date-time specification.
--
--        Octets      Contents     Range
--       ==================================
--         1-4          year     0000..9999
--         5            '-'          na
--         6-7         month       01..12
--         8            '-'          na
--         9-10         day        01..31
--         11       ' ' (space)      na
--         12-13       hour        00..23
--         14           ':'          na
--         15-16       minutes     00..59
--         17           ':'          na
--         18-19       seconds     00..60
--
--    Only those fields applicable will be present. An invocation
--    of this textual convention will include the size limitation
--    appropriate for the corresponding time precision . The correspondence
--    between the length of the OCTET STRING and the time precision is:
--             2 - corresponds to H (Octets 12-13 present)
--             5 - corresponds to HM (Octets 12-16 present)
--             8 - corresponds to HMS (Octets 12-19 present)
--            10 - corresponds to D (Octets 1-10 present)
--            13 - corresponds to DH (Octets 1-13 present)
--            16 - corresponds to DHM (Octets 1-16 present)
--            19 - corresponds to DHMS (Octets 1-19 present)
--    For example, Tuesday May 26, 1992 at 1:30:15 PM EDT might be
--    encoded using the DHM option as:
--                    1992-05-26 13:30:15 "


Link         ::= OBJECT IDENTIFIER
--    " Similar to the RowPointer textual convention which points to
--    to the RowStatus variable of a component having a relationship
--    to the present component. For example, a service-user
--    service-provider relationship is modelled using bidirectional Links."

IntegerSequence ::= OCTET STRING
--    " Represents an ASCII encoded integer sequence with dot '.' 
--    seperators. For example: 1.156.5.63 would be encoded as: 
--                   49 46 49 53 54 46 53 46 54 51 "

FixedPoint1 ::= Unsigned32
--    " Represents a fixed point value with one decimal place. For 
--    example, the value 123456789 should be displayed, and otherwise treated, 
--    as the decimal value: 12345678.9 "

FixedPoint2 ::= Unsigned32
--    " Represents a fixed point value with two decimal places. For 
--    example, the value 123456789 should be displayed, and otherwise treated, 
--    as the decimal value: 1234567.89 "

FixedPoint3 ::= Unsigned32
--    " Represents a fixed point value with three decimal places. For 
--    example, the value 123456789 should be displayed, and otherwise treated, 
--    as the decimal value: 123456.789 "

FixedPoint4 ::= Unsigned32
--    " Represents a fixed point value with four decimal places. For 
--    example, the value 123456789 should be displayed, and otherwise treated, 
--    as the decimal value: 12345.6789 "

FixedPoint5 ::= Unsigned32
--    " Represents a fixed point value with five decimal places. For 
--    example, the value 123456789 should be displayed, and otherwise treated, 
--    as the decimal value: 1234.56789 "

FixedPoint6 ::= Unsigned32
--    " Represents a fixed point value with six decimal places. For 
--    example, the value 123456789 should be displayed, and otherwise treated, 
--    as the decimal value: 123.456789 "

FixedPoint7 ::= Unsigned32
--    " Represents a fixed point value with seven decimal places. For 
--    example, the value 123456789 should be displayed, and otherwise treated, 
--    as the decimal value: 12.3456789 "

FixedPoint8 ::= Unsigned32
--    " Represents a fixed point value with eight decimal places. For 
--    example, the value 123456789 should be displayed, and otherwise treated, 
--    as the decimal value: 1.23456789 "

FixedPoint9 ::= Unsigned32
--    " Represents a fixed point value with eight decimal places. For 
--    example, the value 123456789 should be displayed, and otherwise 
--    treated, as the decimal value: 0.123456789 "

--
-- Conventions specific to component indexing:
--

AsciiStringIndex ::= OCTET STRING
--    " Represents a string of printable Ascii characters, excluding
--    whitespace, lower case letters, the double quote character and
--    the <>/:* characters. " 

NonReplicated ::= INTEGER {present(1)}
--    " Represents a type used to index a table containing 0 or 1 rows."


--
-- Version and Compliance statements
--
 
 
-- Object-Group Statement: 

--    OBJECTS   { }
--    STATUS    current
--    DESCRIPTION
--       "A list of all current accessible leaf objects."

textualConventionsGroup OBJECT IDENTIFIER ::= { textualConventionsMIB 1 }
textualConventionsGroupBC OBJECT IDENTIFIER ::= { textualConventionsGroup 3 }
textualConventionsGroupBC02 OBJECT IDENTIFIER ::= { textualConventionsGroupBC 2 }
textualConventionsGroupBC02A OBJECT IDENTIFIER ::= { textualConventionsGroupBC02 2 }


-- Agent-Capabilities Statement:

--    PRODUCT-RELEASE "Passport Release 3.2 Textual Conventions."
--    STATUS          current
--    DESCRIPTION
--       "Textual Conventions MIB: MIB Version BC02A."
--    SUPPORTS        Nortel-Magellan-Passport-TextualConventionsMIB
--    INCLUDES        { textualConventionsGroupBC02A }

textualConventionsCapabilities OBJECT IDENTIFIER ::= { textualConventionsMIB 3 }
textualConventionsCapabilitiesBC OBJECT IDENTIFIER ::= { textualConventionsCapabilities 3 }
textualConventionsCapabilitiesBC02 OBJECT IDENTIFIER ::= { textualConventionsCapabilitiesBC 2 }
textualConventionsCapabilitiesBC02A OBJECT IDENTIFIER ::= { textualConventionsCapabilitiesBC02 2 }


END
