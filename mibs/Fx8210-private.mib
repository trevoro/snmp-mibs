------------------------------------------------------------------------
-- @(#)fib-priv.mib
-- Copyright (c) 1992 Fibronics International
------------------------------------------------------------------------
-- Title:         Fibronics' MIB  
-- MIB Module :   Private MIB for  fx8210
-- Version    :   V1.0
-- Date       :   Nov 23, 1992
-- By         :   Adi Fischer
-- Contact    :   Edna Ganon
-- Email:     :   edna@fibronics.co.il 
-- 
-- Description:   SNMP Agent MIB Definitions - for the Fibronics
--                                             fx8210 private MIB
-- 

------------------------------------------------------------------------

          Fx8210-private DEFINITIONS ::= BEGIN

          IMPORTS
	TRAP-TYPE FROM RFC-1215
                  mgmt, NetworkAddress, IpAddress, Counter, Gauge,
                          TimeTicks, internet
                      FROM RFC1155-SMI
                  OBJECT-TYPE
                          FROM RFC-1212;




          -- *****************************************
          --       F I N E X       M I B
          -- ****************************************
	   


          private    OBJECT IDENTIFIER ::= { internet 4 }
          enterprises OBJECT IDENTIFIER ::= { private 1 }


                  fibronics  OBJECT IDENTIFIER ::= { enterprises 22 }
                  trap          OBJECT IDENTIFIER ::= { fibronics 3 }
                  traprun         OBJECT IDENTIFIER ::= { trap 1 }
                  traperm         OBJECT IDENTIFIER ::= { trap 2 }
                  trapvar         OBJECT IDENTIFIER ::= { trap 3 }
                  fxm8000         OBJECT IDENTIFIER ::= { fibronics 10 }
                  finexsystem     OBJECT IDENTIFIER ::= { fxm8000 1 }
                  fxmsystemrun    OBJECT IDENTIFIER ::= { finexsystem 1 }
                  fxmsystemperm   OBJECT IDENTIFIER ::= { finexsystem 2 }


          
          --------------------------------------------
          --
          --          T R A P     T A B L E
          --
          --------------------------------------------
          

          
          --   Trap runtime objects

-- The objects in the run-time group reside in RAM and therefore
-- are of volatile nature. After the system has been reset the 
-- objects in this group will be an exact copy of the permanent
-- group of objects (traperm). If the permanent group of object 
-- does not exist for some reason (for instance, the EEPROM is 
-- not burnt yet) the objects will initialize by a known set of 
-- default values.
          
          rTrapAddrTbl    OBJECT-TYPE
                  SYNTAX  SEQUENCE OF RTrapAddrEntry
                  ACCESS  not-accessible
                  STATUS  mandatory
                  DESCRIPTION "Table of managers to which traps
                               must be sent. Up to 10
                               entries in table.
                               Some (up to 5) entries in table
                               are copied from the permanent trap
	                       table at reset time. The other entries
	                       are learned from SNMP requests coming 
	                       to the target station."
                  ::= { traprun 1 }
          
          rTrapAddrEntry  OBJECT-TYPE
                  SYNTAX  RTrapAddrEntry
                  ACCESS  not-accessible
                  STATUS  mandatory
                  INDEX   { rTrapAddrAddr }
                  ::= { rTrapAddrTbl 1 }
          
          RTrapAddrEntry ::= SEQUENCE {
                  rTrapAddrAddr
                          IpAddress,
                  rTrapAddrComm
                          OCTET STRING,
                  rTrapAddrVer
                          INTEGER,
                  rTrapAddrType
                          OCTET STRING,
                  rTrapAddrState
                          INTEGER,
                  rTrapAddrFlag
                          INTEGER,
                  rTrapAddrAge
                          INTEGER
                  }
          
          rTrapAddrAddr   OBJECT-TYPE
                  SYNTAX  IpAddress
                  ACCESS  read-only
                  STATUS  mandatory
                  DESCRIPTION "IP address of entity
                               requesting event notification"
                  ::= { rTrapAddrEntry 1 }
          
          rTrapAddrComm   OBJECT-TYPE
                  SYNTAX  OCTET STRING
                  ACCESS  read-only
                  STATUS  mandatory
                  DESCRIPTION "Community name the receiving
                               entity will expect"
                  ::= { rTrapAddrEntry 2 }
          
          rTrapAddrVer    OBJECT-TYPE
                  SYNTAX  INTEGER
                  ACCESS  read-only
                  STATUS  mandatory
                  DESCRIPTION "Version number supported by
                               destination node"
                  ::= { rTrapAddrEntry 3 }
          
          rTrapAddrType   OBJECT-TYPE
                  SYNTAX  OCTET STRING
                  ACCESS  read-only
                  STATUS  mandatory
                  DESCRIPTION "Type of event that should be
                               reported to this address,
                               bit 0 - authentication trap
                               bit 1 - other SNMP traps
                               bit 2 - Error Traps
                               bit 3 - Diagnostic Traps
                               bit 4 - Debug Traps"
                  ::= { rTrapAddrEntry 4 }
          
          rTrapAddrState  OBJECT-TYPE
                  SYNTAX  INTEGER {
                          active(1),
                          inactive(2)
                          }
                  ACCESS  read-only
                  STATUS  mandatory
                  DESCRIPTION "Determines status of this entry"
                  ::= { rTrapAddrEntry 5 }
          
          rTrapAddrFlag   OBJECT-TYPE
                  SYNTAX  INTEGER {
                          removable(1),
                          fixed(2)
                          }
                  ACCESS  read-only
                  STATUS  mandatory
                  DESCRIPTION "If the entry is fixed, it can not
                          be deleted because of aging, which means
	                  it was copied from the permanent trap table."
                  ::= { rTrapAddrEntry 6 }
          
          
          rTrapAddrAge    OBJECT-TYPE
                  SYNTAX  INTEGER
                  ACCESS  read-only
                  STATUS  mandatory
                  DESCRIPTION "A time stamp of the last time the 
	                       Manager sent SNMP request to the target
	                       agent ( in 50 msec units )."
                  ::= { rTrapAddrEntry 7 }
          
          rTrapLearning   OBJECT-TYPE
                  SYNTAX  INTEGER {
                          enable(1),
                          disable(2)
                          }
                  ACCESS  read-only
                  STATUS  mandatory
                  DESCRIPTION "Learn the addresses of the managers
                          automatically."
                  ::= { traprun 2 }
          
          rTrapAging      OBJECT-TYPE
                  SYNTAX  INTEGER
                  ACCESS  read-only
                  STATUS  mandatory
                  DESCRIPTION "Time in sec. until a trap entry
	                       is erased from the table."
                  ::= { traprun 3 }
          
          --   Trap permanent objects

-- The objects in the permanent group are saved in EEPROM and
-- therefore are of non-volatile nature.
          
          pTrapAddrTbl    OBJECT-TYPE
                  SYNTAX  SEQUENCE OF PTrapAddrEntry
                  ACCESS  not-accessible
                  STATUS  mandatory
                  DESCRIPTION "Table of managers to which traps
                               must be sent. Up to 5
                               entries in table"
                  ::= { traperm 1 }
          
          pTrapAddrEntry  OBJECT-TYPE
                  SYNTAX  PTrapAddrEntry
                  ACCESS  not-accessible
                  STATUS  mandatory
                  INDEX   { pTrapAddrAddr }
                  ::= { pTrapAddrTbl 1 }
          
          PTrapAddrEntry ::= SEQUENCE {
                  pTrapAddrAddr
                          IpAddress,
                  pTrapAddrComm
                          OCTET STRING,
                  pTrapAddrVer
                          INTEGER,
                  pTrapAddrType
                          OCTET STRING,
                  pTrapAddrState
                          INTEGER
                  }
          
          pTrapAddrAddr   OBJECT-TYPE
                  SYNTAX  IpAddress
                  ACCESS  read-write
                  STATUS  mandatory
                  DESCRIPTION "IP address of entity
                               requesting event notification"
                  ::= { pTrapAddrEntry 1 }
          
          pTrapAddrComm   OBJECT-TYPE
                  SYNTAX  OCTET STRING
                  ACCESS  read-write
                  STATUS  mandatory
                  DESCRIPTION "Community name the receiving
                               entity will expect"
                  ::= { pTrapAddrEntry 2 }
          
          pTrapAddrVer    OBJECT-TYPE
                  SYNTAX  INTEGER
                  ACCESS  read-write
                  STATUS  mandatory
                  DESCRIPTION "Version number supported by
                               destination node"
                  ::= { pTrapAddrEntry 3 }
          
          pTrapAddrType   OBJECT-TYPE
                  SYNTAX  OCTET STRING
                  ACCESS  read-write
                  STATUS  mandatory
                  DESCRIPTION "Type of event that should be
                               reported to this address,
                               bit 0 - authentication trap
                               bit 1 - other SNMP traps
                               bit 2 - Error Traps
                               bit 3 - Diagnostic Traps
                               bit 4 - Debug Traps"
                  ::= { pTrapAddrEntry 4 }
          
          pTrapAddrState  OBJECT-TYPE
                  SYNTAX  INTEGER {
                          active(1),
                          inactive(2)
                          }
                  ACCESS  read-write
                  STATUS  mandatory
                  DESCRIPTION "Determines status of this entry"
                  ::= { pTrapAddrEntry 5 }
          
          pTrapLearning   OBJECT-TYPE
                  SYNTAX  INTEGER {
                          enable(1),
                          disable(2)
                          }
                  ACCESS  read-write
                  STATUS  mandatory
                  DESCRIPTION "Learn the addresses of the managers
                          automatically."
                  ::= { traperm 2 }
          
          pTrapAging      OBJECT-TYPE
                  SYNTAX  INTEGER
                  ACCESS  read-write
                  STATUS  mandatory
                  DESCRIPTION "Time in sec. until a trap entry
	                       is erased from the table."
                  ::= { traperm 3 }
          
          
         --  System Group RunTime
          
-- The objects in the run-time group reside in RAM and therefore
-- are of volatile nature. After the system has been reset the 
-- objects in this group will be an exact copy of the permanent
-- group of objects (fxmsystemperm). If the permanent group of object 
-- does not exist for some reason (for instance, the EEPROM is 
-- not burnt yet) the objects will initialize by a known set of 
-- default values.
          
          fxmSystemIpAddr  OBJECT-TYPE
                  SYNTAX   IpAddress
                  ACCESS   read-only
                  STATUS   mandatory
                	DESCRIPTION "IP address of the agent"
                  ::= { fxmsystemrun 1 }
          
          fxmSystemIPNetMask   OBJECT-TYPE
                  SYNTAX      IpAddress
                  ACCESS      read-only
                  STATUS      mandatory
                	DESCRIPTION "IP Network Mask"
                  ::= { fxmsystemrun 2 }
          
          fxmSystemIPDefGway  OBJECT-TYPE
                  SYNTAX      IpAddress
                  ACCESS      read-only
                  STATUS      mandatory
                	DESCRIPTION "Default Gateway Address"
                  ::= { fxmsystemrun 3 }
          
          fxmSystemBroadcastOpt OBJECT-TYPE
                  SYNTAX        IpAddress
                  ACCESS        read-only
                  STATUS        mandatory
                	DESCRIPTION "Default Broadcast option:
                		     all zeros or all ones"
                  ::= { fxmsystemrun 4 }
          
          fxmSystemBootServer  OBJECT-TYPE
                  SYNTAX       IpAddress
                  ACCESS       read-only
                  STATUS        mandatory
                  DESCRIPTION "IP address to which a TFTP for boot is sent."
                  ::= { fxmsystemrun 5 }
          
          fxmSystemBootGenName  OBJECT-TYPE
                  SYNTAX        OCTET STRING
                  ACCESS        read-only
                  STATUS        mandatory
                 	DESCRIPTION "Path and file name that is 
                 		   sent as a TFTP request"
                  ::= { fxmsystemrun 6 }
          
          fxmSystemBootMode  OBJECT-TYPE
                  SYNTAX     INTEGER {
                             internal-memory(1),
                             bootp(2)
                             }
                  ACCESS     read-only
                  STATUS     mandatory
                	DESCRIPTION "Method for booting"
                  ::= { fxmsystemrun 7 }
          
          fxmSystemSelfTestLevel  OBJECT-TYPE
                  SYNTAX          INTEGER {
                                  none(1),
                                  full(2),
                                  partial(3),
                                  extended(4)
                                  }
                  ACCESS          read-only
                  STATUS          mandatory
                	DESCRIPTION "Type of self test to be
                		     executed upon cold-reset"
                  ::= { fxmsystemrun 8 }
          
          fxmSystemReset  OBJECT-TYPE
                  SYNTAX  INTEGER {
                          warm-reset(1),
                          cold-reset(2)
                          }
                  ACCESS  read-write
                  STATUS  mandatory
                	DESCRIPTION "Resetting the target station.
				     When reading the instance of this
				     object the value has no meaning."
                  ::= { fxmsystemrun 9 }
          
          
          
          --  System Group Permanent

-- The objects in the permanent group are saved in EEPROM and
-- therefore are of non-volatile nature.
          
          pfxmSystemIpAddr  OBJECT-TYPE
                  SYNTAX    IpAddress
                  ACCESS    read-write
                  STATUS     mandatory
                	DESCRIPTION "IP address of the agent"
                  ::= { fxmsystemperm 1 }
          
          pfxmSystemIPNetMask  OBJECT-TYPE
                  SYNTAX       IpAddress
                  ACCESS       read-write
                  STATUS       mandatory
                 	DESCRIPTION "IP Network Mask"
                  ::= { fxmsystemperm 2 }
          
          pfxmSystemIPDefGway  OBJECT-TYPE
                  SYNTAX       IpAddress
                  ACCESS       read-write
                  STATUS       mandatory
                 	DESCRIPTION "Default Gateway Address"
                  ::= { fxmsystemperm 3 }
          
          pfxmSystemBroadcastOpt  OBJECT-TYPE
                  SYNTAX          IpAddress
                  ACCESS          read-write
                  STATUS          mandatory
                 	DESCRIPTION "Default Broadcast option:
                 	 	     all zeros or all ones"
                  ::= { fxmsystemperm 4 }
          
          pfxmSystemBootServer  OBJECT-TYPE
                  SYNTAX       IpAddress
                  ACCESS       read-write
                  STATUS       mandatory
                 	DESCRIPTION "IP address to which a TFTP for boot is sent."
                  ::= { fxmsystemperm 5 }
          
          pfxmSystemBootGenName  OBJECT-TYPE
                  SYNTAX        OCTET STRING
                  ACCESS        read-write
                  STATUS        mandatory
                	DESCRIPTION "Path and file name that is 
                		   sent as a TFTP request"
                  ::= { fxmsystemperm 6 }
          
          pfxmSystemBootMode  OBJECT-TYPE
                  SYNTAX      INTEGER {
                              internal-memory(1),
                              bootp(2)
                              }
                  ACCESS      read-write
                  STATUS      mandatory
                	DESCRIPTION "Method for booting"
                  ::= { fxmsystemperm 7 }
          
          pfxmSystemSelfTestLevel	OBJECT-TYPE
                  SYNTAX          INTEGER {
                                  none(1),
                                  full(2),
                                  partial(3),
                                  extended(4)
                                  }
                  ACCESS          read-write
                  STATUS          mandatory
                	DESCRIPTION "Type of self test to be
                		     executed upon cold-reset"
                  ::= { fxmsystemperm 8 }
          
         pfxmSpanMode   	OBJECT-TYPE
	         SYNTAX  INTEGER {
		         enable(1),
		         disable(2)
		         }
	         ACCESS  read-write
	         STATUS  mandatory
	                 DESCRIPTION "Enable/Disable of the 
	                 spanning tree Algorithm"
	::= { fxmsystemperm 9 }

          pfxmSystemCommunity1  OBJECT-TYPE
                  SYNTAX        OCTET STRING
                  ACCESS        write-only
                  STATUS        mandatory
                 	DESCRIPTION "Community string number 1"
                  ::= { fxmsystemperm 10 }
          
          pfxmSystemCommunity2  OBJECT-TYPE
                  SYNTAX        OCTET STRING
                  ACCESS        write-only
                  STATUS        mandatory
                 	DESCRIPTION "Community string number 2"
                  ::= { fxmsystemperm 11 }
          
          pfxmSystemCommunity3  OBJECT-TYPE
                  SYNTAX        OCTET STRING
                  ACCESS        write-only
                  STATUS        mandatory
                 	DESCRIPTION "Community string number 3"
                  ::= { fxmsystemperm 12 }
          
          pfxmSystemCommunity4  OBJECT-TYPE
                  SYNTAX        OCTET STRING
                  ACCESS        write-only
                  STATUS        mandatory
                 	DESCRIPTION "Community string number 4"
                  ::= { fxmsystemperm 13 }
          
          pfxmSystemCommunity5  OBJECT-TYPE
                  SYNTAX        OCTET STRING
                  ACCESS        write-only
                  STATUS        mandatory
                 	DESCRIPTION "Community string number 5"
                  ::= { fxmsystemperm 14 }
          
          pfxmSystemCommunity6  OBJECT-TYPE
                  SYNTAX        OCTET STRING
                  ACCESS        write-only
                  STATUS        mandatory
                 	DESCRIPTION "Community string number 6"
                  ::= { fxmsystemperm 15 }
          
          pfxmSystemCommunity7  OBJECT-TYPE
                  SYNTAX        OCTET STRING
                  ACCESS        write-only
                  STATUS        mandatory
                 	DESCRIPTION "Community string number 7"
                  ::= { fxmsystemperm 16 }
          
          pfxmSystemCommunity8  OBJECT-TYPE
                  SYNTAX        OCTET STRING
                  ACCESS        write-only
                  STATUS        mandatory
                 	DESCRIPTION "Community string number 8"
                  ::= { fxmsystemperm 17 }
          
          

           -- Trap variables objects

eventTrap    	OBJECT-TYPE
	SYNTAX  OCTET STRING
	ACCESS	not-accessible
	STATUS  mandatory
	DESCRIPTION "Octet string used to send events to
		NMS. String description:
                     1'st octet         : severity code (ASCII decimal)
		     2'nd octet         : space
		     3'rd - 5'th octet  : diu number (ASCII decimal) 
		     6'th octet         : space
		     7'th - 12'th octet : message code (ASCII decimal)  
				          e.g: BR0345
                     13'th octet        : space
		     14'th and up       : extra message string (ASCII)"

	::= { trapvar 1 }

  -- *********************************************************
  -- **                                                     **
  -- **                                                     **
  -- **        T R A P          D E F I N I T I O N S       **
  -- **                                                     **
  -- **                                                     **
  -- *********************************************************

sendGenericEvent        TRAP-TYPE	
	ENTERPRISE finexsystem    
	VARIABLES { eventTrap }
        DESCRIPTION 
                "This trap message is generated by any 
		software module in the FINEX software.
		Any type of event can be sent."
	::= 1

END
