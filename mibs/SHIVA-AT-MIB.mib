-- 	$Id: shiva-at.asn,v 1.5 1996/01/16 16:31:43 dfox Exp $

--
-- 	Copyright 1992, 1993, 1994, 1995, 1996 Shiva Corporation
--

--	Supplementary AppleTalk-related variables.

SHIVA-AT-MIB DEFINITIONS ::= BEGIN

IMPORTS
	OBJECT-TYPE
		FROM RFC-1212		-- Concise MIB Definitions
	tATalk
		FROM SHIVA-MIB;


    tRTMPEntryTimeouts OBJECT-TYPE
	SYNTAX	INTEGER			-- should be Counter
	ACCESS  read-only
	STATUS  mandatory
	DESCRIPTION
		"The number of entries which were removed from 
		routing table because the aging algorithm
		indicated that they were invalid."
	::= { tATalk 1 }

    tRTMPEntryDeletes OBJECT-TYPE
	SYNTAX	INTEGER			-- should be Counter
	ACCESS  read-only
	STATUS  mandatory
	DESCRIPTION
		"The number of entries which were removed from the
		routing table for any reason other than aging, for
		instance, due to a command from a Network
		Management station."
	::= { tATalk 2 }

    tRTMPEntryEqualReplaces OBJECT-TYPE
	SYNTAX	INTEGER			-- should be Counter
	ACCESS  read-only
	STATUS  mandatory
	DESCRIPTION
		"The number of entries whose route was replaced by
		another route with the same hop count."
	::= { tATalk 3 }

    tRTMPEntryBetterReplaces OBJECT-TYPE
	SYNTAX	INTEGER			-- should be Counter
	ACCESS  read-only
	STATUS  mandatory
	DESCRIPTION
		"The number of entries whose route was replaced by
		another route with a lower hop count."
	::= { tATalk 4 }

    tRTMPEntryAdds OBJECT-TYPE
	SYNTAX	INTEGER			-- should be Counter
	ACCESS  read-only
	STATUS  mandatory
	DESCRIPTION
		"The number of new entries which have been added to
		the table."
	::= { tATalk 5 }

    tRTMPZeroCounters OBJECT-TYPE
	SYNTAX	INTEGER { zero(1) }
	ACCESS  read-write
	STATUS  mandatory
	DESCRIPTION
		"Writing this variable causes all the RTMP variables
		in this group to be set to zero."
	::= { tATalk 6 }

    tZIPDeletes OBJECT-TYPE
	SYNTAX	INTEGER			-- Should be Counter
	ACCESS  read-only
	STATUS  mandatory
	DESCRIPTION
		"The number of Zones which have been deleted from the
		Zone Table."
	::= { tATalk 7 }

    tZIPAdds OBJECT-TYPE
	SYNTAX	INTEGER			-- Should be Counter
	ACCESS  read-only
	STATUS  mandatory
	DESCRIPTION
		"The number of Zones which have been added to the
		Zone Table."
	::= { tATalk 8 }

    tZIPZeroCounters OBJECT-TYPE
	SYNTAX	INTEGER { zero(1) }
	ACCESS  read-write
	STATUS  mandatory
	DESCRIPTION
		"Writing this variable causes all the ZIP variables
		in this group to be set to zero."
	::= { tATalk 9 }

    tAARPClearCache OBJECT-TYPE
	SYNTAX	INTEGER { clear(1) }
	ACCESS  read-write
	STATUS  mandatory
	DESCRIPTION
		"Writing this variable clears the AARP Cache."
	::= { tATalk 10 }

    tKIPRoutesValid OBJECT-TYPE
	SYNTAX  INTEGER { valid(1), invalid(2) }
	ACCESS  read-write
	STATUS  mandatory
	DESCRIPTION
		"This variable can be used to force KIP to reacquire its
		configuration information."
	::= { tATalk 11 }

-- LanRover/E 3.0

-- The following variables should really be per interface rather than
-- box-wide: tNBPDeviceObject, tNBPDeviceType, tNBPDeviceZone,
-- tNBPDeviceSocket, and tATRoutingMode.  This could accommodate
-- instances of multiple designated home ports (especially multiple
-- LAN ports).

-- Some information provided here could be derived using the nbpTable
-- and atportTable from RFC1243, and may be superceded by information
-- in the new version of the AppleTalk MIB (still an Internet-Draft).
-- The information is provided for convenience as an analogue to
-- current LanRover AppleTalk configuration parameters.

    tNBPDeviceObject OBJECT-TYPE
	SYNTAX  OCTET STRING
	ACCESS  read-only
	STATUS  mandatory
	DESCRIPTION
		"The NBP name used to advertise this device's primary
		 NVE on the LAN interface."
	::= { tATalk 12 }

    tNBPDeviceType OBJECT-TYPE
	SYNTAX  OCTET STRING
	ACCESS  read-only
	STATUS  mandatory
	DESCRIPTION
		"The NBP type used to advertise this device's primary
		 NVE on the LAN interface."
	::= { tATalk 13 }

    tNBPDeviceZone OBJECT-TYPE
	SYNTAX  OCTET STRING
	ACCESS  read-only
	STATUS  mandatory
	DESCRIPTION
		"The zone in which this device registers its primary
		 NVE on the LAN interface."
	::= { tATalk 14 }

    tNBPDeviceSocket OBJECT-TYPE
	SYNTAX  INTEGER
	ACCESS  read-only
	STATUS  mandatory
	DESCRIPTION
		"The DDP socket number used by the device in NBP
		 Responses for its primary NVE registered on the LAN
		 interface."
	::= { tATalk 15 }

    tATDialinNetwork OBJECT-TYPE
	SYNTAX  OCTET STRING (SIZE(2))
	ACCESS  read-only
	STATUS  mandatory
	DESCRIPTION
		"The AppleTalk network number in which AppleTalk
		 dialin users appear.  When
		 tATDialInPacketDeliveryMode is routing(1) this value
		 corresponds to the configured dialin network number.
		 When tATDialInPacketDeliveryMode is
		 endNodeForwarding(2) this value corresponds to the
		 network number of the LAN interface.  Note that when
		 endNodeForwarding(2) it is possible that not all
		 dialin clients have addresses on this network because
		 there may not have been enough available node ids to
		 obtain addresses for all of the clients.  In this
		 case another network in the extended range of the LAN
		 interface may be used for the remaining clients'
		 addresses.  Ideally this should be a table of clients
		 with their dialin addresses."
	::= { tATalk 16 }

    tATDialinZone OBJECT-TYPE
	SYNTAX  OCTET STRING (SIZE(2))
	ACCESS  read-only
	STATUS  mandatory
	DESCRIPTION
		"The zone with which tATDialinNetwork is associated."
	::= { tATalk 17 }

    tATRoutingMode OBJECT-TYPE
	SYNTAX  INTEGER {
		conformingRouter(1),
		seedRouter(2),
		endNode(3),
		other(4)
	}
	ACCESS  read-only
	STATUS  mandatory
	DESCRIPTION
		"The routing behavior of this device for AppleTalk.  

		 If the device is configured as conformingRouter(1) or
		 seedRouter(2) then it will behave as an AppleTalk
		 router on the LAN interface, and will route packets to
		 all interfaces.  If it is a conformingRouter(1) then
		 it will learn its configuration for the LAN interface
		 from other routers on that interface's
		 directly-connected network.  If it is a seedRouter(2)
		 then it will use the configured LAN interface
		 parameters.

		 If the device is configured as endNode(3) it will
		 behave as an AppleTalk endnode on the LAN interface.

		 other(4) is provided in the event a value is returned
		 which does not match any of the other enumerated
		 values.  It is not expected that this will happen."
	::= { tATalk 18 }

    tATDialinPacketDeliveryMode OBJECT-TYPE
	SYNTAX  INTEGER {
		routing(1),
		endNodeForwarding(2),
		other(3)
	}
	ACCESS  read-only
	STATUS  mandatory
	DESCRIPTION
		"The method used to deliver packets to and from
		 Appletalk dialin clients.

		 If the device is configured as routing(1) it will use
		 routing tables to deliver packets to and from dialin
		 clients, which will be homed on an internal virtual
		 interface (port).  Technically, the value routing(1)
		 is only valid if the device is acting as a router
		 (the value of tATRoutingMode is conformingRouter(1)
		 or seedRouter(2)).

	 	 If the device is configured to use
		 endNodeForwarding(2) then it will obtain addresses
		 for dialin users in the LAN network range, and will
		 defend those addresses.  Packets to and from dialin
		 clients will be forwarded.  Technically the device
		 may be configured as endNodeForwarding(2) when
		 tATRoutingMode is any of: conformingRouter(1),
		 seedRouter(2), or endNode(3).

	  	 other(3) is provided in the event a value is returned
		 which does not match any of the other enumerated
		 values.  It is not expected that this will happen."
	::= { tATalk 19 }

    tRTMPEntryTotal OBJECT-TYPE
	SYNTAX  INTEGER 
	ACCESS  read-only
	STATUS  mandatory
	DESCRIPTION
		"The number of network (range) entries in the
		 device's RTMP Table.  This value is not cleared by 
                 the tRTMPZeroCounters switch."
	::= { tATalk 20 }

    tZoneTotal OBJECT-TYPE
	SYNTAX  INTEGER 
	ACCESS  read-only
	STATUS  mandatory
	DESCRIPTION
		"The number of AppleTalk zones for which the device
		 has learned one or more associated nets or net
		 ranges.  This value is not cleared by
                 the tZIPZeroCounters switch."
	::= { tATalk 21 }

END
