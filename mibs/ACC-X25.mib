ACC-X25 DEFINITIONS ::= BEGIN

    IMPORTS
		NetworkAddress, OBJECT-TYPE, IpAddress, TimeTicks, Gauge, Counter FROM RFC1155-SMI
		TRAP-TYPE FROM RFC-1215
         accTrapLogSeqNum FROM ACC-SYSTEM
	 accBRG, DisplayString, RowStatus, IfIndex, SmdsAddress
             FROM ACC-MIB;

-- X.25 Group
-- X.25 addresses are represented as variable-length 
-- ASCII strings (length is between 0 and 15, inclusive).
      accX25      OBJECT IDENTIFIER  ::= { accBRG 17 }
	accX25AtTable	OBJECT-TYPE
			SYNTAX	SEQUENCE OF AccX25AtEntry
			ACCESS	not-accessible
			STATUS	mandatory
			DESCRIPTION
			 " Address translation table for X.25 interfaces.
			   This is a superset of the standard address
			   translation table.
			   Entries are added/deleted via management action."
			::= { accX25 1	}
	  accX25AtEntry OBJECT-TYPE
			SYNTAX	AccX25AtEntry
			ACCESS	not-accessible
			STATUS	mandatory
			DESCRIPTION
			 " Address translation entry for X.25 interfaces."
                        INDEX { accX25AtIfIndex, 
                                accX25AtIpAddress }
			::= { accX25AtTable 1 }
		AccX25AtEntry ::= SEQUENCE {
			    accX25AtIfIndex	INTEGER,
			    accX25AtIpAddress	NetworkAddress,
			    accX25AtNetInOutAddr	DisplayString,
			    accX25AtNetInAddr	DisplayString,
			    accX25AtNetFacIndex INTEGER
			    }
	  accX25AtIfIndex	OBJECT-TYPE   
			SYNTAX	INTEGER
			ACCESS	read-write
			STATUS	mandatory
			DESCRIPTION
			 " Interface number (ifIndex) for which this 
			   translation entry is valid."
			::= { accX25AtEntry 1 }
	  accX25AtIpAddress OBJECT-TYPE	  
			SYNTAX	NetworkAddress
			ACCESS	read-write
			STATUS	mandatory
			DESCRIPTION
                         " IP Address of this entry
			   Set this object to NULL to delete entry."
			::= { accX25AtEntry 2 }
	  accX25AtNetInOutAddr OBJECT-TYPE   
			SYNTAX  DisplayString	
			ACCESS	read-write
			STATUS	mandatory
			DESCRIPTION
			 " X.25 address to use when calling this destination.
			   (both X.25 addresses are checked when mapping an
			   X.25 address to an IP address)
			   Object required in entry-adding SET PDU."
			::= { accX25AtEntry 3 }
	  accX25AtNetInAddr OBJECT-TYPE   
			SYNTAX  DisplayString	
			ACCESS	read-write
			STATUS	mandatory
			DESCRIPTION
			 " Alternate X.25 address to check when mapping an
			   X.25 address to an IP address
			   Object will be set to default value if not present
			       in entry-adding SET PDU."
			::= { accX25AtEntry 4 }
        accX25AtNetFacIndex OBJECT-TYPE
                      SYNTAX  INTEGER (0..255)
                      ACCESS  read-write
                      STATUS  mandatory
                      DESCRIPTION
                           " Index of optional facility string or 0."
                      DEFVAL  { 0 }
                      ::= { accX25AtEntry 5 }
	accX25SubnetParmTable	OBJECT-TYPE
			SYNTAX	SEQUENCE OF AccX25SubnetParmEntry
			ACCESS	not-accessible
			STATUS	mandatory
			DESCRIPTION
			 " Per-network parameters for IP networks attached
			   via X.25 interface.
			   Entries added/deleted via management action."
			::= { accX25 2 }
	  accX25SubnetParmEntry OBJECT-TYPE
			SYNTAX	AccX25SubnetParmEntry
			ACCESS	not-accessible
			STATUS	mandatory
			DESCRIPTION
			 " X.25-specific parameters for this IP network"
                        INDEX { accX25SubnetAddr }
			::= { accX25SubnetParmTable 1 }
		AccX25SubnetParmEntry ::= SEQUENCE {
			    accX25SubnetAddr	IpAddress,
			    accX25Facility	INTEGER,
			    accX25PktNegot	INTEGER,
			    accX25WindowNegot	INTEGER
			    }
	    accX25SubnetAddr	OBJECT-TYPE   
			SYNTAX	IpAddress
			ACCESS	read-write
			STATUS	mandatory
			DESCRIPTION
			 " Network/subnet number of IP network
			   Set this object to NULL to delete entry."
			::= { accX25SubnetParmEntry 1 }
	    accX25Facility	OBJECT-TYPE   
			SYNTAX	INTEGER {
				none(1),
				std(2)
				}
			ACCESS	read-write
			STATUS	mandatory
			DESCRIPTION
			 " selects whether DDN Standard Mode facility is
			   included in call requests. "
                        DEFVAL { none }
			::= { accX25SubnetParmEntry 2 }
	    accX25PktNegot	OBJECT-TYPE   
			SYNTAX	INTEGER
			ACCESS	read-write
			STATUS	mandatory
			DESCRIPTION
			 " specifies value for Packet Size Negotiation Facility
			   (power of 2 between 16 and 1024), or zero if Packet
			   Size Negotiation Facility is not to be used."
                        DEFVAL { 0 }
			::= { accX25SubnetParmEntry 3 }
	    accX25WindowNegot	OBJECT-TYPE   
			SYNTAX	INTEGER
			ACCESS	read-write
			STATUS	mandatory
			DESCRIPTION
			 " specifies value for Window Size Negotiation Facility
			   (between 1 and 127 inclusive), or zero if Window
			   Size Negotiation Facility is not to be used."
                        DEFVAL { 0 }
			::= { accX25SubnetParmEntry 4 }
	accX25PortParmTable	OBJECT-TYPE
			SYNTAX	SEQUENCE OF AccX25PortParmEntry
			ACCESS	not-accessible
			STATUS	mandatory
			DESCRIPTION
			 " Per-port parameters for X.25 interfaces."
			::= { accX25 3 }
          accX25PortParmEntry   OBJECT-TYPE
                        SYNTAX  AccX25PortParmEntry
                        ACCESS  not-accessible
                        STATUS  mandatory
                        DESCRIPTION
                         " X25 parameters of a specific port."
                        INDEX { accX25PortParmIndex }
                        ::= { accX25PortParmTable 1 }
			AccX25PortParmEntry ::= SEQUENCE {
			    accX25PortParmIndex INTEGER,
			    accX25AddrMode	INTEGER,
			    accX25PktSize	INTEGER,
			    accX25PktWind	INTEGER,
			    accX25SvcNumber	INTEGER,
			    accX25SvcBase	INTEGER,
			    accX25ExtendClr	INTEGER,
			    accX25ExtendSeq	INTEGER,
			    accX25IdleMin	TimeTicks,
			    accX25IdleMax	TimeTicks,
			    accX25IdleScale	TimeTicks,
			    accX25SvcMax	INTEGER,
			    accX25SvcLimit	INTEGER,
			    accX25OpenThresh 	INTEGER,
			    accX25SvcMin	INTEGER,
			    accX25SvcDelay	INTEGER,
			    accX25InitBackoff	INTEGER,
			    accX25MaxBackoff	INTEGER,
			    accX25OurAddress	DisplayString,
			    accX25PvcBase	INTEGER,
			    accX25PvcNumber	INTEGER,
			    accX25Tx0Timer	TimeTicks,
			    accX25Tx1Timer	TimeTicks,
			    accX25Tx2Timer	TimeTicks,
			    accX25Tx3Timer	TimeTicks,
			    accX25PortEventSeverityLevel	INTEGER
			    }
	    accX25PortParmIndex		OBJECT-TYPE   
			SYNTAX	INTEGER
			ACCESS	read-only
			STATUS	mandatory
			DESCRIPTION
			 " Port number"
			::= { accX25PortParmEntry 1 }
	    accX25AddrMode	OBJECT-TYPE   
			SYNTAX	INTEGER {
				table(1),	-- use translation table
						-- (accX25AtTable)
				ddn(2),		-- use DDN mapping algorithm
				bfe(3)		-- use Blacker algorithm
				}
			ACCESS	read-write
			STATUS	mandatory
			DESCRIPTION
			 " specifies address translation technique."
                        DEFVAL { table }
			::= { accX25PortParmEntry 2 }
	    accX25PktSize	OBJECT-TYPE   
			SYNTAX	INTEGER
			ACCESS	read-write
			STATUS	mandatory
			DESCRIPTION
			 " specifies default data packet size for this port."
                        DEFVAL { 128 }
			::= { accX25PortParmEntry 3 }
	    accX25PktWind	OBJECT-TYPE   
			SYNTAX	INTEGER
			ACCESS	read-write
			STATUS	mandatory
			DESCRIPTION
			 " specifies default packet window size for this port."
                        DEFVAL { 2 }
			::= { accX25PortParmEntry 4 }
	    accX25SvcNumber	OBJECT-TYPE   
			SYNTAX	INTEGER
			ACCESS	read-write
			STATUS	mandatory
			DESCRIPTION
			 " specifies maximum number of switched virtual
			   circuits to be used on this port."
                        DEFVAL { 256 }
			::= { accX25PortParmEntry 5 }
	    accX25SvcBase	OBJECT-TYPE   
			SYNTAX	INTEGER
			ACCESS	read-write
			STATUS	mandatory
			DESCRIPTION
			 " specifies lowest Logical Channel Identifier
			   to be used for switched virtual circuits."
                        DEFVAL { 1 }
			::= { accX25PortParmEntry 6 }
	    accX25ExtendClr	OBJECT-TYPE   
			SYNTAX	INTEGER {
				on(1),	-- use/accept extended clear format
				off(2)	-- disallow extended clear format
				}
			ACCESS	read-write
			STATUS	mandatory
			DESCRIPTION
			 " specifies whether extended format for call clearing
			   packets (as defined by X.25-1984) is permitted"
                        DEFVAL { off }
			::= { accX25PortParmEntry 7 }
	    accX25ExtendSeq	OBJECT-TYPE   
			SYNTAX	INTEGER {
				normal(1),	-- modulo-8 sequence numbers
				extended(2)	-- modulo-128 sequence numbers
				}
			ACCESS	read-write
			STATUS	mandatory
			DESCRIPTION
			 " Use of extended sequence numbers"
                        DEFVAL { normal }
			::= { accX25PortParmEntry 8 }
	    accX25IdleMin	OBJECT-TYPE   
			SYNTAX	TimeTicks
			ACCESS	read-write
			STATUS	mandatory
			DESCRIPTION
			 " minimum idle time for closing circuits; a circuit
			   will not be cleared until it has been idle (no data
			   has been sent or received) for at least this amount
			   of time."
                        DEFVAL { 30000 }
			::= { accX25PortParmEntry 9 }
	    accX25IdleMax	OBJECT-TYPE   
			SYNTAX	TimeTicks
			ACCESS	read-write
			STATUS	mandatory
			DESCRIPTION
			 " maximum idle time for closing circuits; a circuit
			   will be cleared when its idle time exceeds this
			   value."
                        DEFVAL { 180000 }
			::= { accX25PortParmEntry 10 }
	    accX25IdleScale	OBJECT-TYPE   
			SYNTAX	TimeTicks
			ACCESS	read-write
			STATUS	mandatory
			DESCRIPTION
			 " scale factor for idle timeout: a circuit will
			   be cleared when it has been idle for accX25IdleMin
			   plus accX25IdleScale times the number of available
			   circuits."
                        DEFVAL { 1000 }
			::= { accX25PortParmEntry 11 }
	    accX25SvcMax	OBJECT-TYPE
			SYNTAX	INTEGER
			ACCESS	read-write
			STATUS	mandatory
			DESCRIPTION
			 " Maximum number of virtual circuits which can be 
			   opened to a single destination."
                        DEFVAL { 1 }
			::= { accX25PortParmEntry 12 }
	    accX25SvcLimit	OBJECT-TYPE
			SYNTAX	INTEGER
			ACCESS	read-write
			STATUS	mandatory
			DESCRIPTION
			 " Maximum number of switched virtual circuits that
			   IP can use.  The value must not exceed the total
			   number of logical channels available on this
			   trunk."
                        DEFVAL { 256 }
			::= { accX25PortParmEntry 13 }
	    accX25OpenThresh	OBJECT-TYPE
			SYNTAX	INTEGER
			ACCESS	read-write
			STATUS	mandatory
			DESCRIPTION
			 " Threshold (number of IP datagrams queued per circuit)
			   at which an additional virtual circuit will be
			   opened."
                        DEFVAL { 3 }
			::= { accX25PortParmEntry 14 }
	    accX25SvcMin	OBJECT-TYPE
			SYNTAX	INTEGER
			ACCESS	read-write
			STATUS	mandatory
			DESCRIPTION
			 " The minimum number of virtual circuits which IP
			   will leave available for first circuits
			   to other destinations"
                        DEFVAL { 0 }
			::= { accX25PortParmEntry 15 }
	    accX25SvcDelay	OBJECT-TYPE
			SYNTAX	INTEGER
			ACCESS	read-write
			STATUS	mandatory
			DESCRIPTION
			 " Delay (seconds) between opening of 
			   successive virtual circuits to same destination."
                        DEFVAL { 5 }
			::= { accX25PortParmEntry 16 }
	    accX25InitBackoff	OBJECT-TYPE
			SYNTAX	INTEGER
			ACCESS	read-write
			STATUS	mandatory
			DESCRIPTION
			 " Initial backoff time (seconds) to delay before 
			   next attempt to open an additional virtual circuit
			   to the same destination when an attempt to do so
			   has failed.  "
                        DEFVAL { 15 }
			::= { accX25PortParmEntry 17 }
	    accX25MaxBackoff	OBJECT-TYPE
			SYNTAX	INTEGER
			ACCESS	read-write
			STATUS	mandatory
			DESCRIPTION
			 " Maximum backoff time (seconds) to delay between
			   subsequent attempts to open additional virtual
			   circuits to the same destination.  The actual
			   delay is varied exponentially from 
			   accX25InitBackoff up to this value."
                        DEFVAL { 86400 }
			::= { accX25PortParmEntry 18 }
	    accX25OurAddress	OBJECT-TYPE
			SYNTAX  DisplayString --(SIZE(15))	
			ACCESS	read-write
			STATUS	mandatory
			DESCRIPTION
			 " Our X25 address (put in outbound packets)"
                        DEFVAL { '0'h }
			::= { accX25PortParmEntry 19 }
        accX25PvcBase       OBJECT-TYPE
                 SYNTAX  INTEGER
                 ACCESS  read-write
                 STATUS  mandatory
                 DESCRIPTION
                     " Lowest LCID to be used for PVCs."
                 DEFVAL  { 0 }
                 ::= { accX25PortParmEntry 20 }
        accX25PvcNumber     OBJECT-TYPE
                  SYNTAX  INTEGER
                  ACCESS  read-write
                  STATUS  mandatory
                  DESCRIPTION
                      " Maximum number of PVCs."
                  DEFVAL  { 0 }
                  ::= { accX25PortParmEntry 21 }
        accX25Tx0Timer      OBJECT-TYPE
                   SYNTAX  TimeTicks
                   ACCESS  read-write
                   STATUS  mandatory
                   DESCRIPTION
                       " Value for T10 (DCE) or T20 (DTE) timer."
                   DEFVAL  { 18000 } -- 180 sec (DTE)
                   ::= { accX25PortParmEntry 22 }
        accX25Tx1Timer      OBJECT-TYPE
                   SYNTAX  TimeTicks
                   ACCESS  read-write
                   STATUS  mandatory
                   DESCRIPTION
                       " Value for T11 (DCE) or T21 (DTE) timer."
                   DEFVAL  { 20000 } -- 200 sec (DTE)
                   ::= { accX25PortParmEntry 23 }
        accX25Tx2Timer      OBJECT-TYPE
                   SYNTAX  TimeTicks
                   ACCESS  read-write
                   STATUS  mandatory
                   DESCRIPTION
                       " Value for T12 (DCE) or T22 (DTE) timer."
                   DEFVAL  { 18000 } -- 180 sec (DTE)
                   ::= { accX25PortParmEntry 24 }
        accX25Tx3Timer      OBJECT-TYPE
                   SYNTAX  TimeTicks
                   ACCESS  read-write
                   STATUS  mandatory
                   DESCRIPTION
                       " Value for T13 (DCE) or T23 (DTE) timer."
                   DEFVAL  { 18000 } -- 180 sec (DTE)
		   ::= { accX25PortParmEntry 25 }
    accX25PortEventSeverityLevel    OBJECT-TYPE
                SYNTAX  INTEGER (1..7)
                ACCESS  read-write
                STATUS  mandatory
                DESCRIPTION
                   " The base severity level which events are recorded. "
                ::= { accX25PortParmEntry 26 }
	accX25PktStatTable	OBJECT-TYPE
			SYNTAX	SEQUENCE OF AccX25PktStatEntry
			ACCESS	not-accessible
			STATUS	mandatory
			DESCRIPTION
			 " Per-port packet statistics for X.25 interfaces."
			::= { accX25 4 }
          accX25PktStatEntry    OBJECT-TYPE
                        SYNTAX  AccX25PktStatEntry
                        ACCESS  not-accessible
                        STATUS  mandatory
                        DESCRIPTION
                         " X.25 packet level statistics for an X.25 interface."
                        INDEX { accX25PktIndex }
                        ::= { accX25PktStatTable 1 }
			AccX25PktStatEntry ::= SEQUENCE {
			    accX25PktIndex	INTEGER,
			    accX25RcvDiags	Counter,
			    accX25RcvRestartReqs Counter,
			    accX25RcvRestartConfs Counter,
			    accX25RcvCallReqs	Counter,
			    accX25RcvCallAccs	Counter,
			    accX25RcvClrReqs	Counter,
			    accX25RcvClrConfs	Counter,
			    accX25RcvResetReqs	Counter,
			    accX25RcvResetConfs	Counter,
			    accX25RcvInts	Counter,
			    accX25RcvIntConfs	Counter,
			    accX25RcvRRs		Counter,
			    accX25RcvRNRs	Counter,
			    accX25RcvDatas	Counter,
			    accX25XmtDiags	Counter,
			    accX25XmtRestartReqs Counter,
			    accX25XmtRestartConfs Counter,
			    accX25XmtCallReqs	Counter,
			    accX25XmtCallAccs	Counter,
			    accX25XmtClrReqs	Counter,
			    accX25XmtClrConfs	Counter,
			    accX25XmtResetReqs	Counter,
			    accX25XmtResetConfs	Counter,
			    accX25XmtInts	Counter,
			    accX25XmtIntConfs	Counter,
			    accX25XmtRRs	Counter,
			    accX25XmtRNRs	Counter,
			    accX25XmtDatas	Counter,
			    accX25OpenSvcCounts	Counter
			    }
	    accX25PktIndex	OBJECT-TYPE   
			SYNTAX	INTEGER
			ACCESS	read-only
			STATUS	mandatory
			DESCRIPTION
			 " Port number of this X.25 interface."
			::= { accX25PktStatEntry 1 }
	    accX25RcvDiags	OBJECT-TYPE   
			SYNTAX	Counter
			ACCESS	read-only
			STATUS	mandatory
			DESCRIPTION
			 " Number of Diagnostic packets received on this port."
			::= { accX25PktStatEntry 2 }
	    accX25RcvRestartReqs		OBJECT-TYPE   
			SYNTAX	Counter
			ACCESS	read-only
			STATUS	mandatory
			DESCRIPTION
			 " Number of Restart Request (Restart Indication)
			   packets received on this port."
			::= { accX25PktStatEntry 3 }
	    accX25RcvRestartConfs	OBJECT-TYPE   
			SYNTAX	Counter
			ACCESS	read-only
			STATUS	mandatory
			DESCRIPTION
			 " Number of Restart Confirmation packets received
			   on this port."
			::= { accX25PktStatEntry 4 }
	    accX25RcvCallReqs	OBJECT-TYPE   
			SYNTAX	Counter
			ACCESS	read-only
			STATUS	mandatory
			DESCRIPTION
			 " Number of Call Request (Incoming Call) packets
			   received on this port."
			::= { accX25PktStatEntry 5 }
	    accX25RcvCallAccs	OBJECT-TYPE   
			SYNTAX	Counter
			ACCESS	read-only
			STATUS	mandatory
			DESCRIPTION
			 " Number of Call Accepted (Call Connected) packets
			   received on this port."
			::= { accX25PktStatEntry 6 }
	    accX25RcvClrReqs	OBJECT-TYPE   
			SYNTAX	Counter
			ACCESS	read-only
			STATUS	mandatory
			DESCRIPTION
			 " Number of Clear Request (Clear Indication) packets
			   received on this port."
			::= { accX25PktStatEntry 7 }
	    accX25RcvClrConfs	OBJECT-TYPE   
			SYNTAX	Counter
			ACCESS	read-only
			STATUS	mandatory
			DESCRIPTION
			 " Number of Clear Confirmation packets received on
			   this port."
			::= { accX25PktStatEntry 8 }
	    accX25RcvResetReqs	OBJECT-TYPE   
			SYNTAX	Counter
			ACCESS	read-only
			STATUS	mandatory
			DESCRIPTION
			 " Number of Reset Request (Reset Indication) packets
			   received on this port."
			::= { accX25PktStatEntry 9 }
	    accX25RcvResetConfs	OBJECT-TYPE   
			SYNTAX	Counter
			ACCESS	read-only
			STATUS	mandatory
			DESCRIPTION
			 " Number of Reset Confirmation packets received on
			   this port."
			::= { accX25PktStatEntry 10 }
	    accX25RcvInts	OBJECT-TYPE   
			SYNTAX	Counter
			ACCESS	read-only
			STATUS	mandatory
			DESCRIPTION
			 " Number of Interrupt packets received on this port."
			::= { accX25PktStatEntry 11 }
	    accX25RcvIntConfs	OBJECT-TYPE   
			SYNTAX	Counter
			ACCESS	read-only
			STATUS	mandatory
			DESCRIPTION
			 " Number of Interrupt Confirmation packets received
			   on this port."
			::= { accX25PktStatEntry 12 }
	    accX25RcvRRs		OBJECT-TYPE   
			SYNTAX	Counter
			ACCESS	read-only
			STATUS	mandatory
			DESCRIPTION
			 " Number of RR [Receive Ready] packets received on
			   this port."
			::= { accX25PktStatEntry 13 }
	    accX25RcvRNRs	OBJECT-TYPE   
			SYNTAX	Counter
			ACCESS	read-only
			STATUS	mandatory
			DESCRIPTION
			 " Number of RNR [Receive Not Ready] packets received
			   on this port."
			::= { accX25PktStatEntry 14 }
	    accX25RcvDatas	OBJECT-TYPE   
			SYNTAX	Counter
			ACCESS	read-only
			STATUS	mandatory
			DESCRIPTION
			 " Number of Data packets received on this port."
			::= { accX25PktStatEntry 15 }
	    accX25XmtDiags	OBJECT-TYPE   
			SYNTAX	Counter
			ACCESS	read-only
			STATUS	mandatory
			DESCRIPTION
			 " Number of Diagnostic packets transmitted on this
			   port."
			::= { accX25PktStatEntry 16 }
	    accX25XmtRestartReqs		OBJECT-TYPE   
			SYNTAX	Counter
			ACCESS	read-only
			STATUS	mandatory
			DESCRIPTION
			 " Number of Restart Request (Restart Indication)
			   packets transmitted on this port."
			::= { accX25PktStatEntry 17 }
	    accX25XmtRestartConfs	OBJECT-TYPE   
			SYNTAX	Counter
			ACCESS	read-only
			STATUS	mandatory
			DESCRIPTION
			 " Number of Restart Confirmation packets transmitted
			   on this port."
			::= { accX25PktStatEntry 18 }
	    accX25XmtCallReqs	OBJECT-TYPE   
			SYNTAX	Counter
			ACCESS	read-only
			STATUS	mandatory
			DESCRIPTION
			 " Number of Call Request (Incoming Call) packets
			   transmitted on this port."
			::= { accX25PktStatEntry 19 }
	    accX25XmtCallAccs	OBJECT-TYPE   
			SYNTAX	Counter
			ACCESS	read-only
			STATUS	mandatory
			DESCRIPTION
			 " Number of Call Accepted (Call Connected) packets
			   transmitted on this port."
			::= { accX25PktStatEntry 20 }
	    accX25XmtClrReqs	OBJECT-TYPE   
			SYNTAX	Counter
			ACCESS	read-only
			STATUS	mandatory
			DESCRIPTION
			 " Number of Clear Request (Clear Indication) packets
			   transmitted on this port."
			::= { accX25PktStatEntry 21 }
	    accX25XmtClrConfs	OBJECT-TYPE   
			SYNTAX	Counter
			ACCESS	read-only
			STATUS	mandatory
			DESCRIPTION
			 " Number of Clear Confirmation packets transmitted
			   on this port."
			::= { accX25PktStatEntry 22 }
	    accX25XmtResetReqs	OBJECT-TYPE   
			SYNTAX	Counter
			ACCESS	read-only
			STATUS	mandatory
			DESCRIPTION
			 " Number of Reset Request (Reset Indication) packets
			   transmitted on this port."
			::= { accX25PktStatEntry 23 }
	    accX25XmtResetConfs	OBJECT-TYPE   
			SYNTAX	Counter
			ACCESS	read-only
			STATUS	mandatory
			DESCRIPTION
			 " Number of Reset Confirmation packets transmitted
			   on this port."
			::= { accX25PktStatEntry 24 }
	    accX25XmtInts	OBJECT-TYPE   
			SYNTAX	Counter
			ACCESS	read-only
			STATUS	mandatory
			DESCRIPTION
			 " Number of Interrupt packets transmitted on this
			   port."
			::= { accX25PktStatEntry 25 }
	    accX25XmtIntConfs	OBJECT-TYPE   
			SYNTAX	Counter
			ACCESS	read-only
			STATUS	mandatory
			DESCRIPTION
			 " Number of Interrupt Confirmation packets
			   transmitted on this port."
			::= { accX25PktStatEntry 26 }
	    accX25XmtRRs		OBJECT-TYPE   
			SYNTAX	Counter
			ACCESS	read-only
			STATUS	mandatory
			DESCRIPTION
			 " Number of RR [Receive Ready] packets transmitted
			   on this port."
			::= { accX25PktStatEntry 27 }
	    accX25XmtRNRs	OBJECT-TYPE   
			SYNTAX	Counter
			ACCESS	read-only
			STATUS	mandatory
			DESCRIPTION
			 " Number of RNR [Receive Not Ready] packets
			   transmitted on this port."
			::= { accX25PktStatEntry 28 }
	    accX25XmtDatas	OBJECT-TYPE   
			SYNTAX	Counter
			ACCESS	read-only
			STATUS	mandatory
			DESCRIPTION
			 " Number of Data packets transmitted on this port."
			::= { accX25PktStatEntry 29 }
	accX25OpenSvcCounts  OBJECT-TYPE
	            SYNTAX  Counter
	            ACCESS  read-only
	            STATUS  mandatory
	            DESCRIPTION
	                  " Count of SVCs open on this port."
	            ::= { accX25PktStatEntry 30 }
-- X25 XOT Group
--	X25 XOT Group
	accX25Xot OBJECT IDENTIFIER ::= { accX25 12 }
--
--	X.25 XOT Parameters definition
--
		accX25XotParmTable	OBJECT-TYPE
			SYNTAX SEQUENCE OF AccX25XotParmEntry
			ACCESS	not-accessible
			STATUS	mandatory
			DESCRIPTION
				" XOT parameter table."
			::= { accX25Xot 1 }
		accX25XotParmEntry OBJECT-TYPE
			SYNTAX	AccX25XotParmEntry
			ACCESS	not-accessible
			STATUS	mandatory
			DESCRIPTION
				" The entry part of accX25XotParmEntry."
			INDEX	{ accX25XotParmLine
				}
			::= { accX25XotParmTable 1 }
		AccX25XotParmEntry ::= SEQUENCE {
			accX25XotParmLine	INTEGER,
			accX25XotParmIpAddress	IpAddress,
			accX25XotParmMsgLevel	INTEGER
			}
		accX25XotParmLine OBJECT-TYPE
			SYNTAX	INTEGER
			ACCESS	read-write
			STATUS	mandatory
			DESCRIPTION
				" Virtual port for which this entry applies."
			::= { accX25XotParmEntry 1 }
		accX25XotParmIpAddress	OBJECT-TYPE
			SYNTAX	IpAddress
			ACCESS	read-write
			STATUS	mandatory
			DESCRIPTION
				" IP Address for virtual port."
			::= { accX25XotParmEntry 2 }
		accX25XotParmMsgLevel	OBJECT-TYPE
			SYNTAX	INTEGER
			ACCESS	read-write
			STATUS	mandatory
			DESCRIPTION
				" Debug message level for virtual port."
			::= { accX25XotParmEntry 3 }
--
--	XOT Connection Table
--
		accX25XotConnTable	OBJECT-TYPE
			SYNTAX SEQUENCE OF AccX25XotConnEntry
			ACCESS	not-accessible
			STATUS	mandatory
			DESCRIPTION
				" This Table contains objects which report 
		 		information about the X.25 XOT calls currently 
				being switched through this router."
			::= { accX25Xot 2 }
		accX25XotConnEntry OBJECT-TYPE
			SYNTAX	AccX25XotConnEntry
			ACCESS	not-accessible
			STATUS	mandatory
			DESCRIPTION
				" The entry part of accX25XotConnEntry."
			INDEX	{ accX25XotConnLine,
				accX25XotConnLcn
				}
			::= { accX25XotConnTable 1 }
		AccX25XotConnEntry ::= SEQUENCE {
			accX25XotConnLine	INTEGER,
			accX25XotConnLcn	INTEGER,
			accX25XotConnState	INTEGER,
			accX25XotConnType	INTEGER,
			accX25XotConnIpAddress	NetworkAddress,
			accX25XotConnTcpPortNumber	INTEGER,
			accX25XotConnRemoteIpAddress	NetworkAddress,
			accX25XotConnRemoteTCPPortNumber	INTEGER,
			accX25XotConnRcvEncaps	Counter,
			accX25XotConnXmtEncaps	Counter
			}
		accX25XotConnLine OBJECT-TYPE
			SYNTAX	INTEGER
			ACCESS	read-only
			STATUS	mandatory
			DESCRIPTION
				" Virtual port for which this entry applies."
			::= { accX25XotConnEntry 1 }
		accX25XotConnLcn	OBJECT-TYPE
			SYNTAX	INTEGER
			ACCESS	read-only
			STATUS	mandatory
			DESCRIPTION
				" The LCN of the virtual circuit for the 
				initiating interface."
			::= { accX25XotConnEntry 2 }
		accX25XotConnState	OBJECT-TYPE
			SYNTAX	INTEGER	{
				waitCallConfirm(1),
				clearProcActive(2),
				clearProcComplete(3),
				tcpCongested(4),
				tcpConnRefused(9),
				tcpConnInProgress(16),
				waitPvcSetupConfirm(17),
				connected(18),
				noDestInterface(19),
				destInterfaceNotUp(20),
				destInterfaceNotX25(21),
				noDestPvc(22),
				destPvcCfgMismatch(23),
				flowControlMismatch(24),
				flowControlValuesNotSupported(25),
				pvcSetupProtocolError(26)
				}
			ACCESS	read-only
			STATUS	mandatory
			DESCRIPTION
				" An integer that indicates the state of the
				circuit."
			::= { accX25XotConnEntry 3 }
		accX25XotConnType	OBJECT-TYPE
			SYNTAX	INTEGER {
				incoming(1),
				outgoing(2),
				pvc(3)
				}
			ACCESS	read-only
			STATUS	mandatory
			DESCRIPTION
				" An integer that indicates the circuit type."
			::= { accX25XotConnEntry 4 }
		accX25XotConnIpAddress	OBJECT-TYPE
			SYNTAX	NetworkAddress
			ACCESS	read-only
			STATUS	mandatory
			DESCRIPTION
				" IP Address for this XOT."
			::= { accX25XotConnEntry 5 }
		accX25XotConnTcpPortNumber	OBJECT-TYPE
			SYNTAX	INTEGER
			ACCESS	read-only
			STATUS	mandatory
			DESCRIPTION
				" TCP port number for this connection."
			::= { accX25XotConnEntry 6 }
		accX25XotConnRemoteIpAddress	OBJECT-TYPE
			SYNTAX	NetworkAddress
			ACCESS	read-write
			STATUS	mandatory
			DESCRIPTION
				" IP Address for the remote XOT."
			::= { accX25XotConnEntry 7 }
		accX25XotConnRemoteTCPPortNumber	OBJECT-TYPE
			SYNTAX	INTEGER
			ACCESS	read-only
			STATUS	mandatory
			DESCRIPTION
				" remote TCP port number for this connection."
			::= { accX25XotConnEntry 8 }
		accX25XotConnRcvEncaps	OBJECT-TYPE
			SYNTAX	Counter 
			ACCESS	read-only
			STATUS	mandatory
			DESCRIPTION
				" The total number of encapsulated packets 
				received by the XOT for this connection."
			::= { accX25XotConnEntry 9 }
		accX25XotConnXmtEncaps	OBJECT-TYPE
			SYNTAX	Counter 
			ACCESS	read-only
			STATUS	mandatory
			DESCRIPTION
				" The total number of encapsulated packets 
				transmitted by the XOT for this connection."
			::= { accX25XotConnEntry 10 }
--
--	XOT Statistics
--
		accX25XotStatsTable	OBJECT-TYPE
			SYNTAX	SEQUENCE OF AccX25XotStatsEntry
			ACCESS	not-accessible
			STATUS	mandatory
			DESCRIPTION
				" This Table contains objexts which report 
				the accumulated counts for X.25 packet 
				activity and TCP connections for an XOT
				virtual port."
			::= { accX25Xot 4 }
		accX25XotStatsEntry	OBJECT-TYPE
			SYNTAX	AccX25XotStatsEntry
			ACCESS	not-accessible
			STATUS	mandatory
			DESCRIPTION
				" The entry part of accX25XotStatsEntry."
			INDEX	{ accX25XotStatsLine
				}
			::= { accX25XotStatsTable 1 }
		AccX25XotStatsEntry ::= SEQUENCE {
			accX25XotStatsLine		INTEGER,
			accX25XotStatsTotalConnections	Counter,
			accX25XotStatsActiveConnections	Gauge,
			accX25XotStatsRcvInvalids	Counter,
			accX25XotStatsGenClearReqs	Counter,
			accX25XotStatsGenResetReqs	Counter,
			accX25XotStatsGenPvcSetups	Counter,
			accX25XotStatsRcvValids		Counter,
			accX25XotStatsXmtTotals		Counter
			}
		accX25XotStatsLine	OBJECT-TYPE
			SYNTAX	INTEGER
			ACCESS	read-only
			STATUS	mandatory
			DESCRIPTION
				" Virtual port for which this entry applies."
			::= { accX25XotStatsEntry 1 }
		accX25XotStatsTotalConnections	OBJECT-TYPE
			SYNTAX	Counter 
			ACCESS	read-only
			STATUS	mandatory
			DESCRIPTION
				" The total number of 
				TCP connections for the XOT on this 
				router."
			::= { accX25XotStatsEntry 2 }
		accX25XotStatsActiveConnections	OBJECT-TYPE
			SYNTAX	Gauge 
			ACCESS	read-only
			STATUS	mandatory
			DESCRIPTION
				" The current number of 
				active TCP connections for the XOT on this 
				router."
			::= { accX25XotStatsEntry 3 }
		accX25XotStatsRcvInvalids	OBJECT-TYPE
			SYNTAX	Counter 
			ACCESS	read-only
			STATUS	mandatory
			DESCRIPTION
				" The total number of 
				invalid packets received by the XOT 
				from TCP connections on this router."
			::= { accX25XotStatsEntry 4 }
		accX25XotStatsGenClearReqs	OBJECT-TYPE
			SYNTAX	Counter 
			ACCESS	read-only
			STATUS	mandatory
			DESCRIPTION
				" The total number of 
				clear packets generated by the XOT."
			::= { accX25XotStatsEntry 5 }
		accX25XotStatsGenResetReqs	OBJECT-TYPE
			SYNTAX	Counter 
			ACCESS	read-only
			STATUS	mandatory
			DESCRIPTION
				" The total number of 
				reset packets generated by the XOT."
			::= { accX25XotStatsEntry 6 }
                accX25XotStatsGenPvcSetups OBJECT-TYPE
                        SYNTAX  Counter
                        ACCESS  read-only
                        STATUS  mandatory
                        DESCRIPTION
                                " The total number of PVC setup 
                                packets generated by the XOT on
                                this virtual port"
                        ::= { accX25XotStatsEntry 7 }
		accX25XotStatsRcvValids	OBJECT-TYPE
			SYNTAX	Counter 
			ACCESS	read-only
			STATUS	mandatory
			DESCRIPTION
				" The total number of 
				valid packets received by the XOT 
				from TCP connections on this router."
			::= { accX25XotStatsEntry 8 }
		accX25XotStatsXmtTotals	OBJECT-TYPE
			SYNTAX	Counter 
			ACCESS	read-only
			STATUS	mandatory
			DESCRIPTION
				" The total number of 
				packets transmitted by the XOT 
				over TCP connections on this router."
			::= { accX25XotStatsEntry 9 }
-- X25 Enhanced Group
       accX25OptFacTable       OBJECT-TYPE
                    SYNTAX  SEQUENCE OF AccX25OptFacEntry
                    ACCESS  not-accessible
                    STATUS  mandatory
                    DESCRIPTION
                      " Optional facility string table."
                    ::= { accX25 5 }
       accX25OptFacEntry     OBJECT-TYPE
                    SYNTAX  AccX25OptFacEntry
                    ACCESS  not-accessible
                    STATUS  mandatory
                    DESCRIPTION
                      " A single optional facility entry."
                    INDEX { accX25OptFacIndex }
                    ::= { accX25OptFacTable 1 }
       AccX25OptFacEntry ::= SEQUENCE {
                    accX25OptFacIndex   INTEGER,
                    accX25OptFacString  OCTET STRING
                    }
       accX25OptFacIndex   OBJECT-TYPE
                    SYNTAX  INTEGER
                    ACCESS  read-write
                    STATUS  mandatory
                    DESCRIPTION
                       " Index of this entry in table [1..n]."
                    ::= { accX25OptFacEntry 1 }
       accX25OptFacString  OBJECT-TYPE
                    SYNTAX  OCTET STRING
                    ACCESS  read-write
                    STATUS  mandatory
                    DESCRIPTION
                      " facility string to be added when placing calls."
                    ::= { accX25OptFacEntry 2 }
        accX25PvcAddrTable      OBJECT-TYPE
                    SYNTAX  SEQUENCE OF AccX25PvcAddrEntry
                    ACCESS  not-accessible
                    STATUS  mandatory
                    DESCRIPTION
                       " PVC to X.25 address mapping table."
                    ::= { accX25 6 }
        accX25PvcAddrEntry    OBJECT-TYPE
                     SYNTAX  AccX25PvcAddrEntry
                     ACCESS  not-accessible
                     STATUS  mandatory
                     DESCRIPTION
                       " A single PVC to X.25 address mapping entry."
                     INDEX { accX25PvcLine,
                             accX25PvcAddrLcid
                           }
                     ::= { accX25PvcAddrTable 1 }
	AccX25PvcAddrEntry ::= SEQUENCE {
                     accX25PvcLine       INTEGER,
                     accX25PvcAddrLcid   INTEGER,
                     accX25PvcAddrString DisplayString,
                     accX25PvcProtocol   INTEGER
                     }
        accX25PvcLine       OBJECT-TYPE
                     SYNTAX  INTEGER
                     ACCESS  read-write
                     STATUS  mandatory
                     DESCRIPTION
                        " Physical port for which this entry applies.
			Same is ifIndex."
                     ::= { accX25PvcAddrEntry 1 }
	accX25PvcAddrLcid       OBJECT-TYPE
                     SYNTAX  INTEGER
                     ACCESS  read-write
                     STATUS  mandatory
                     DESCRIPTION
                       " PVC logical channel ID ."
                     ::= { accX25PvcAddrEntry 2 }
        accX25PvcAddrString    OBJECT-TYPE
                     SYNTAX  DisplayString 
                     ACCESS  read-write
                     STATUS  mandatory
                     DESCRIPTION
                        " X.25 address to associate with this PVC."
                     ::= { accX25PvcAddrEntry 3 }
	accX25PvcProtocol       OBJECT-TYPE
                     SYNTAX  INTEGER {
			     ip(1),
			     appletalk(2),
			     decnet(3),
			     idp(4),
			     ipx(5),
			     bridging(6),
			     sourcerouting(7)
			     }
                     ACCESS  read-write
                     STATUS  mandatory
                     DESCRIPTION
                       " PVC Protocol Associated with this line and the LCID ."
                     ::= { accX25PvcAddrEntry 4 }
    accX25EventLogSize    OBJECT-TYPE
                SYNTAX  INTEGER
                ACCESS  read-write
                STATUS  mandatory
                DESCRIPTION
                "The number of entries to maintain in the event table"
                ::= { accX25 9 }
-- X25 Event Table
   accX25EventTable        OBJECT-TYPE
                SYNTAX  SEQUENCE OF AccX25EventEntry
                ACCESS  not-accessible
                STATUS  mandatory
                DESCRIPTION
                   " Event and exception logging table."
                ::= { accX25 10 }
   AccX25EventEntry ::= SEQUENCE {
                accX25EventSeq      INTEGER,
                accX25EventLine     INTEGER,
                accX25EventLCID     INTEGER,
                accX25EventUpTime   TimeTicks,
                accX25EventCode     OCTET STRING,
                accX25EventCause    INTEGER,
                accX25EventProtocol INTEGER,
                accX25EventDiag     INTEGER,
                accX25EventPacket   OCTET STRING
                }
    accX25EventEntry      OBJECT-TYPE
                SYNTAX  AccX25EventEntry
                ACCESS  not-accessible
                STATUS  mandatory
                DESCRIPTION
                  " A single event or exception record."
                INDEX { accX25EventSeq }
                ::= { accX25EventTable 1 }
    accX25EventSeq      OBJECT-TYPE
                SYNTAX  INTEGER
                ACCESS  read-only
                STATUS  mandatory
                DESCRIPTION
                   " A unique sequential number for the logged event."
                ::= { accX25EventEntry 1 }
    accX25EventLine     OBJECT-TYPE
                SYNTAX  INTEGER
                ACCESS  read-only
                STATUS  mandatory
                DESCRIPTION
                   " Physical port which encountered the event."
                ::= { accX25EventEntry 2 }
    accX25EventLCID     OBJECT-TYPE
                SYNTAX  INTEGER
                ACCESS  read-only
                STATUS  mandatory
                DESCRIPTION
                   " The logical circuit id for the circuit which
                     encountered the event."
                ::= { accX25EventEntry 3 }
    accX25EventUpTime   OBJECT-TYPE
                SYNTAX  TimeTicks
                ACCESS  read-only
                STATUS  mandatory
                DESCRIPTION
                  " SysUpTime when event occurred."
                ::= { accX25EventEntry 4 }
    accX25EventCode    OBJECT-TYPE
                SYNTAX  OCTET STRING
                ACCESS  read-write
                STATUS  mandatory
                DESCRIPTION
                   " Code indicating the type of event being logged. "
                ::= { accX25EventEntry 5 }
    accX25EventCause    OBJECT-TYPE
                SYNTAX  INTEGER
                ACCESS  read-only
                STATUS  mandatory
                DESCRIPTION
                  " Cause octet from close packet."
                ::= { accX25EventEntry 6 }
    accX25EventDiag     OBJECT-TYPE
                SYNTAX  INTEGER
                ACCESS  read-only
                STATUS  mandatory
                DESCRIPTION
                   " Diagnostic octet from close packet."
                ::= { accX25EventEntry 7 }
    accX25EventProtocol OBJECT-TYPE
                SYNTAX  INTEGER
                ACCESS  read-only
                STATUS  mandatory
                DESCRIPTION
                  " Protocol which encountered the event."
                ::= { accX25EventEntry 8 }
    accX25EventPacket   OBJECT-TYPE
                SYNTAX  OCTET STRING
                ACCESS  read-only
                STATUS  mandatory
                DESCRIPTION
                    " Packet that triggered the log entry
                      (if available)."
                ::= { accX25EventEntry 9 }
   accX25CircuitTable        OBJECT-TYPE
                SYNTAX  SEQUENCE OF AccX25CircuitEntry
                ACCESS  not-accessible
                STATUS  mandatory
                DESCRIPTION
                   " The X.25 Circuit information table."
                ::= { accX25 11 }
   AccX25CircuitEntry ::= SEQUENCE {
                accX25CircuitLine      INTEGER,
                accX25CircuitLCID      INTEGER,
                accX25CircuitType      INTEGER,
		accX25CircuitRemoteAddr	OCTET STRING,
		accX25CircuitLocalAddr	OCTET STRING,
                accX25CircuitState     INTEGER,
                accX25CircuitPktTimer     INTEGER,
                accX25CircuitPktRetry     INTEGER
                }
    accX25CircuitEntry      OBJECT-TYPE
                SYNTAX  AccX25CircuitEntry
                ACCESS  not-accessible
                STATUS  mandatory
                DESCRIPTION
                  " A single Circuit information record."
                INDEX { accX25CircuitLine,
                        accX25CircuitLCID
                      }
                ::= { accX25CircuitTable 1 }
    accX25CircuitLine     OBJECT-TYPE
                SYNTAX  INTEGER
                ACCESS  read-only
                STATUS  mandatory
                DESCRIPTION
                   " Physical port on which the circuit is established."
                ::= { accX25CircuitEntry 1 }
    accX25CircuitLCID     OBJECT-TYPE
                SYNTAX  INTEGER (0..4095)
                ACCESS  read-only
                STATUS  mandatory
                DESCRIPTION
                   " The logical circuit ID also called the logical
                     channel number (LCN)."
                ::= { accX25CircuitEntry 2 }
    accX25CircuitType     OBJECT-TYPE
                SYNTAX  INTEGER {
			incoming	(1),
			outgoing	(2),
			pvc		(3)
		}
                ACCESS  read-only
                STATUS  mandatory
                DESCRIPTION
                   " The type of circuit."
                ::= { accX25CircuitEntry 3 }
    accX25CircuitRemoteAddr     OBJECT-TYPE
                SYNTAX  OCTET STRING
                ACCESS  read-only
                STATUS  mandatory
                DESCRIPTION
                   " X.25 remote address associated with this circuit."
                ::= { accX25CircuitEntry 4 }
    accX25CircuitLocalAddr     OBJECT-TYPE
                SYNTAX  OCTET STRING
                ACCESS  read-only
                STATUS  mandatory
                DESCRIPTION
                   " X.25 local address associated with this circuit."
                ::= { accX25CircuitEntry 5 }
    accX25CircuitState     OBJECT-TYPE
                SYNTAX  INTEGER {
			p1-ready (1),
			p2-dte-call-req (2),
			p3-dxe-inc-call (3),
			d1-flow-ctl-rdy (4),
			d2-dte-reset-req (5),
			d3-dxe-reset-ind (6),
			p5-call-collision (7),
			p6-dte-clr-req (8),
			p7-dxe-clr-ind (9),
			r2-dte-restart-req (10),
			r3-dxe-restart-ind (11),
			pvc (12)
			}
                ACCESS  read-only
                STATUS  mandatory
                DESCRIPTION
                   " Current state of the circuit."
                ::= { accX25CircuitEntry 6 }
    accX25CircuitPktTimer     OBJECT-TYPE
                SYNTAX  INTEGER
                ACCESS  read-only
                STATUS  mandatory
                DESCRIPTION
                   " Packet level timeout value for this circuit."
                ::= { accX25CircuitEntry 7 }
    accX25CircuitPktRetry     OBJECT-TYPE
                SYNTAX  INTEGER
                ACCESS  read-only
                STATUS  mandatory
                DESCRIPTION
                   " Packet level retry count for this circuit."
                ::= { accX25CircuitEntry 8 }
-- X25 Switch Group
	accX25Switch    OBJECT IDENTIFIER  ::= { accX25 8  }
		accX25SwitchStatus  OBJECT-TYPE
			SYNTAX INTEGER {
			       enabled(1),
			       disabled(2)
			       }
			ACCESS read-write
			STATUS mandatory
			DESCRIPTION
				" This Object controls whether X.25 switching 
			is enabled or disabled."
			::= { accX25Switch 1 }
		accX25SwitchConnections  OBJECT-TYPE
			SYNTAX Gauge 
         		ACCESS read-only       
			STATUS mandatory        
			DESCRIPTION
				" This Object indicates the current number of
			X.25 connections that are being switched through this 
			router."
			::= { accX25Switch 2 }
		accX25SwitchCallSucceeds  OBJECT-TYPE
			SYNTAX Counter 
         		ACCESS read-only       
			STATUS mandatory        
			DESCRIPTION
				" This Object indicates the total number of
			X.25 calls that have been switched by this router."
			::= { accX25Switch 3 }
		accX25SwitchCallFails  OBJECT-TYPE
			SYNTAX Counter 
         		ACCESS read-only       
			STATUS mandatory        
			DESCRIPTION
				" This Object indicates the total number of
			X.25 calls that this router has been unable to switch."
			::= { accX25Switch 4 }
		accX25SwitchConnTable OBJECT-TYPE
			SYNTAX SEQUENCE OF AccX25SwitchConnEntry
			ACCESS not-accessible
			STATUS mandatory
			DESCRIPTION
				" This Table contains objects which report
		 	information about the X.25 calls currently being
			switched through this router."
			::= { accX25Switch 5 }
		accX25SwitchConnEntry OBJECT-TYPE
			SYNTAX AccX25SwitchConnEntry
			ACCESS not-accessible
			STATUS mandatory
			DESCRIPTION
				" The entry part of accX25SwitchConnTable."
			INDEX { accX25SwitchConnCallingIfIndex,
				accX25SwitchConnCallingIndex }
			::= { accX25SwitchConnTable 1 }
		AccX25SwitchConnEntry ::= SEQUENCE {
			accX25SwitchConnCallingIfIndex	INTEGER,
			accX25SwitchConnCallingIndex	INTEGER,
			accX25SwitchConnCallingType     INTEGER,
			accX25SwitchConnCallingX121Addr	OCTET STRING,
			accX25SwitchConnCallingPkts	Counter,
			accX25SwitchConnCallingOctets	Counter,
			accX25SwitchConnCalledIfIndex	INTEGER,
			accX25SwitchConnCalledIndex	INTEGER,
			accX25SwitchConnCalledType      INTEGER,
			accX25SwitchConnCalledX121Addr	OCTET STRING,
			accX25SwitchConnCalledPkts	Counter,
			accX25SwitchConnCalledOctets	Counter,
			accX25SwitchConnState		INTEGER
			}
		accX25SwitchConnCallingIfIndex OBJECT-TYPE
			SYNTAX INTEGER
			ACCESS read-only
			STATUS mandatory
			DESCRIPTION
				" An Integer that identifies the row of the
			system wide interfaces table associated with the X.25
			interface which initiated the connection."
			::= { accX25SwitchConnEntry 1 }
		accX25SwitchConnCallingIndex OBJECT-TYPE
			SYNTAX INTEGER
			ACCESS read-only
			STATUS mandatory
			DESCRIPTION
				" An Integer that uniquely identifies the 
			virtual circuit for the initiating interface. For
			X.25 ports, this will be the LCN. For the TCP ports,
			this will be the remote port number."
			::= { accX25SwitchConnEntry 2 }
		accX25SwitchConnCallingType OBJECT-TYPE
			SYNTAX INTEGER {
			       other(1),
			       x25(2),
			       tcp(3)
			       }
			ACCESS read-only
			STATUS mandatory
			DESCRIPTION
				" An integer that indicates the calling type."
			::= { accX25SwitchConnEntry 3 }
		accX25SwitchConnCallingX121Addr OBJECT-TYPE
			SYNTAX OCTET STRING
			ACCESS read-only
			STATUS mandatory
			DESCRIPTION
				" A string that contains the Calling X.121
			address that initiated the connection."
			::= { accX25SwitchConnEntry 4 }
		accX25SwitchConnCallingPkts OBJECT-TYPE
			SYNTAX Counter
			ACCESS read-only
			STATUS mandatory
			DESCRIPTION
				" A counter which keeps track of the number of
			packets sent from the calling to the called port."
			::= { accX25SwitchConnEntry 5 }
		accX25SwitchConnCallingOctets OBJECT-TYPE
			SYNTAX Counter
			ACCESS read-only
			STATUS mandatory
			DESCRIPTION
				" A counter which keeps track of the number of
			octets sent from the calling to the called port."
			::= { accX25SwitchConnEntry 6 }
		accX25SwitchConnCalledIfIndex OBJECT-TYPE
			SYNTAX INTEGER
			ACCESS read-only
			STATUS mandatory
			DESCRIPTION
				" An Integer that identifies the row of the
			system wide interfaces table associated with the X.25
			interface which propagated the connection."
			::= { accX25SwitchConnEntry 7 }
		accX25SwitchConnCalledIndex OBJECT-TYPE
			SYNTAX INTEGER
			ACCESS read-only
			STATUS mandatory
			DESCRIPTION
				" An Integer that uniquely identifies the 
			virtual circuit for the outgoing interface. For
			X.25 ports, this will be the LCN. For the TCP ports,
			this will be the local port number."
			::= { accX25SwitchConnEntry 8 }
		accX25SwitchConnCalledType OBJECT-TYPE
			SYNTAX INTEGER {
			       other(1),
			       x25(2),
			       tcp(3)
			       }
			ACCESS read-only
			STATUS mandatory
			DESCRIPTION
				" An integer that indicates the called type."
			::= { accX25SwitchConnEntry 9 }
		accX25SwitchConnCalledX121Addr OBJECT-TYPE
			SYNTAX OCTET STRING
			ACCESS read-only
			STATUS mandatory
			DESCRIPTION
				" A string that contains the Called X.121
			address that initiated the connection."
			::= { accX25SwitchConnEntry 10 }
		accX25SwitchConnCalledPkts OBJECT-TYPE
			SYNTAX Counter
			ACCESS read-only
			STATUS mandatory
			DESCRIPTION
				" A counter which keeps track of the number of
			packets sent from the calling to the called port."
			::= { accX25SwitchConnEntry 11 }
		accX25SwitchConnCalledOctets OBJECT-TYPE
			SYNTAX Counter
			ACCESS read-only
			STATUS mandatory
			DESCRIPTION
				" A counter which keeps track of the number of
			octets sent from the calling to the called port."
			::= { accX25SwitchConnEntry 12 }
		accX25SwitchConnState OBJECT-TYPE
			SYNTAX INTEGER {
			       open(1),
			       calling(2),
			       clearing(3),
			       resetting(4)
			       }
			ACCESS read-only
			STATUS mandatory
			DESCRIPTION
				" An integer that indicates the state of the
			switched X.25 circuit."
			::= { accX25SwitchConnEntry 13 }
		accX25SwitchAddrTransTable OBJECT-TYPE
			SYNTAX SEQUENCE OF AccX25SwitchAddrTransEntry
			ACCESS not-accessible
			STATUS mandatory
			DESCRIPTION
				" This Table contains objects which control
			the translation of X.121 addresses."
			::= { accX25Switch 6 }
		accX25SwitchAddrTransEntry OBJECT-TYPE
			SYNTAX AccX25SwitchAddrTransEntry
			ACCESS not-accessible
			STATUS mandatory
			DESCRIPTION
				" The entry part for the AddrTrans Table."
			INDEX { accX25SwitchAddrTransIfIndex,
				accX25SwitchAddrTransDir,
				accX25SwitchAddrTransType,
				accX25SwitchAddrTransPattern
			      }
			::= { accX25SwitchAddrTransTable 1 }
		AccX25SwitchAddrTransEntry ::= SEQUENCE {
			accX25SwitchAddrTransIfIndex	INTEGER,      
			accX25SwitchAddrTransDir	INTEGER, 
			accX25SwitchAddrTransType	INTEGER,
			accX25SwitchAddrTransPattern	DisplayString,
			accX25SwitchAddrTransReplace	DisplayString,
			accX25SwitchAddrTransStatus	INTEGER
			}
		accX25SwitchAddrTransIfIndex OBJECT-TYPE
		SYNTAX INTEGER
		ACCESS read-write
		STATUS mandatory
		DESCRIPTION
			" An Integer that identifies the row of the system
		wide interfaces table associated with the X.25 interface
		that receives the call request."
		::= { accX25SwitchAddrTransEntry 1 }
		accX25SwitchAddrTransDir OBJECT-TYPE
		SYNTAX INTEGER {
		       inbound(1),
		       outbound(2)
		       }
		ACCESS read-write
		STATUS mandatory
		DESCRIPTION
			" An Integer that identifies whether this entry applies
		to inbound or to outbound switched X.25 calls."
		::= { accX25SwitchAddrTransEntry 2 }
		accX25SwitchAddrTransType OBJECT-TYPE
		SYNTAX INTEGER {
		       called(1),
		       calling(2)
		       }
		ACCESS read-write
		STATUS mandatory
		DESCRIPTION
			" An Integer that identifies whether this entry applies
		to called or to calling X.121 addresses."
		::= { accX25SwitchAddrTransEntry 3 }
		accX25SwitchAddrTransPattern OBJECT-TYPE
		SYNTAX DisplayString
		ACCESS read-write
		STATUS mandatory
		DESCRIPTION
			" A character string which defines the matching pattern
		for incoming called X.121 addresses."	
		::= { accX25SwitchAddrTransEntry 4 }
		accX25SwitchAddrTransReplace OBJECT-TYPE
		SYNTAX DisplayString
		ACCESS read-write
		STATUS mandatory
		DESCRIPTION
			" A character string which defines the replacement
		pattern for incoming called X.121 addresses."	
		::= { accX25SwitchAddrTransEntry 5 }
		accX25SwitchAddrTransStatus OBJECT-TYPE
		SYNTAX INTEGER {
		       valid(1),
		       invalid(2)
		       }
		ACCESS read-write
		STATUS mandatory
		DESCRIPTION
			" An Integer that defines the status of the table row."
		::= { accX25SwitchAddrTransEntry 6 }
		accX25SwitchRouteTable OBJECT-TYPE
			SYNTAX SEQUENCE OF AccX25SwitchRouteEntry
			ACCESS not-accessible
			STATUS mandatory
			DESCRIPTION
				" This Table contains objects which determine
			the switching of incoming X.25 calls."
			::= { accX25Switch 7 }
		accX25SwitchRouteEntry OBJECT-TYPE
			SYNTAX AccX25SwitchRouteEntry
			ACCESS not-accessible
			STATUS mandatory
			DESCRIPTION
				" The entry part for the Route Table."
			INDEX { accX25SwitchRoutePattern}
			::= { accX25SwitchRouteTable 1 }
		AccX25SwitchRouteEntry ::= SEQUENCE {
			accX25SwitchRoutePattern	OCTET STRING,
			accX25SwitchRouteIfIndex	INTEGER,
			accX25SwitchRouteStatus		INTEGER
			}
		accX25SwitchRoutePattern OBJECT-TYPE
			SYNTAX OCTET STRING
			ACCESS read-write
			STATUS mandatory
			DESCRIPTION
				" A character string which defines the
			matching pattern for the incoming called X.121
			addresses."
			::= { accX25SwitchRouteEntry 1 }
		accX25SwitchRouteIfIndex OBJECT-TYPE
			SYNTAX INTEGER
			ACCESS read-write
			STATUS mandatory
			DESCRIPTION
				" An Integer that identifies the row of the
			system wide interfaces table associated with the X.25
			interface which receives the call request."
			::= { accX25SwitchRouteEntry 2 }
		accX25SwitchRouteStatus OBJECT-TYPE
		SYNTAX INTEGER {
		       valid(1),
		       invalid(2)
		       }
		ACCESS read-write
		STATUS mandatory
		DESCRIPTION
			" An Integer that defines the status of the table row."
		::= { accX25SwitchRouteEntry 3 }
		accX25SwitchExtRtTable OBJECT-TYPE
			SYNTAX SEQUENCE OF AccX25SwitchExtRtEntry
			ACCESS not-accessible
			STATUS mandatory
			DESCRIPTION
				" This Table contains an extended set
			of objects which determine the switching of
			incoming X.25 calls."
			::= { accX25Switch 8 }
		accX25SwitchExtRtEntry OBJECT-TYPE
			SYNTAX AccX25SwitchExtRtEntry
			ACCESS not-accessible
			STATUS mandatory
			DESCRIPTION
				" The entry part for the Extended Route Table."
			INDEX { accX25SwitchExtRtIndex}
			::= { accX25SwitchExtRtTable 1 }
		AccX25SwitchExtRtEntry ::= SEQUENCE {
			accX25SwitchExtRtIndex		INTEGER,
			accX25SwitchExtRtIfIn		INTEGER,
			accX25SwitchExtRtAddr		OCTET STRING,
			accX25SwitchExtRtCUD		OCTET STRING,
			accX25SwitchExtRtDisp		INTEGER,
			accX25SwitchExtRtIfOut		INTEGER,
			accX25SwitchExtRtStatus		INTEGER
			}
		accX25SwitchExtRtIndex OBJECT-TYPE
			SYNTAX INTEGER
			ACCESS read-write
			STATUS mandatory
			DESCRIPTION
				" An Integer that uniquely identifies
			this row of the Extended Switching Table."
			::= { accX25SwitchExtRtEntry 1 }
		accX25SwitchExtRtIfIn OBJECT-TYPE
			SYNTAX INTEGER
			ACCESS read-write
			STATUS mandatory
			DESCRIPTION
				" An Integer that identifies the row of the
			system wide interfaces table associated with the X.25
			interface which receives the call request.  This column
			must match the interface that the call is received on
			before a match can be made.  A value of zero will match
			calls received from any interface."
			::= { accX25SwitchExtRtEntry 2 }
		accX25SwitchExtRtAddr OBJECT-TYPE
			SYNTAX OCTET STRING
			ACCESS read-write
			STATUS mandatory
			DESCRIPTION
				" A character string which defines the
			matching pattern for the incoming called X.121
			addresses."
			::= { accX25SwitchExtRtEntry 3 }
		accX25SwitchExtRtCUD OBJECT-TYPE
			SYNTAX OCTET STRING
			ACCESS read-write
			STATUS mandatory
			DESCRIPTION
				" A octet string which defines the matching
				pattern for the incoming Call User Data.  A
				zero length octet string matches any Call
				User Data contents (including none)."
			::= { accX25SwitchExtRtEntry 4 }
		accX25SwitchExtRtDisp OBJECT-TYPE
			SYNTAX INTEGER {
				switch(1),
				local(2),
				reject(3)
				}
			ACCESS read-write
			STATUS mandatory
			DESCRIPTION
				" An Integer that specifies the disposition
			of incoming calls that match this table entry.  A
			value of 'switch' causes matching calls to be switched
			out the interface specified by accX25SwitchExtRtIfOut.
			A value of 'local' causes the call to be processed for
			local call termination.  A value of 'reject' causes the
			call to be cleared."
			::= { accX25SwitchExtRtEntry 5 }
		accX25SwitchExtRtIfOut OBJECT-TYPE
			SYNTAX INTEGER
			ACCESS read-write
			STATUS mandatory
			DESCRIPTION
				" An Integer that identifies the row of the
			system wide interfaces table associated with the X.25
			interface to which the call will be switched.  This
			column is only significant when the disposition is
			'switch'."
			::= { accX25SwitchExtRtEntry 6 }
		accX25SwitchExtRtStatus OBJECT-TYPE
		SYNTAX INTEGER {
		       valid(1),
		       invalid(2)
		       }
		ACCESS read-write
		STATUS mandatory
		DESCRIPTION
			" An Integer that defines the status of the table row."
		::= { accX25SwitchExtRtEntry 7 }

END
