-- *****************************************************************
-- CISCO-L4L7MODULE-RESOURCE-LIMIT-CAPABILITY.my:
-- Cisco CISCO-L4L7MODULE-RESOURCE-LIMIT-MIB AGENT-CAPABILITIES
--
-- April 2006, Roopeshakumar N. Shalgar
--
-- Copyright (c) 2006 by Cisco Systems, Inc.
-- All rights reserved.
-- *****************************************************************

CISCO-L4L7MODULE-RESOURCE-LIMIT-CAPABILITY DEFINITIONS ::= BEGIN

IMPORTS
        MODULE-IDENTITY
                FROM SNMPv2-SMI
        AGENT-CAPABILITIES
                FROM SNMPv2-CONF
        ciscoAgentCapability
                FROM CISCO-SMI;

ciscoL4L7ModRsrcLimCap MODULE-IDENTITY
        LAST-UPDATED    "200604190000Z"
        ORGANIZATION    "Cisco Systems, Inc."
        CONTACT-INFO
                "       Cisco Systems
                        Customer Service

                Postal: 170 West Tasman Drive
                        San Jose, CA  95134
                        USA

                   Tel: +1 800 553-NETS

        E-mail: cs-l47security@cisco.com"

        DESCRIPTION
                "The capabilities description for 
                 CISCO-L4L7MODULE-RESOURCE-LIMIT-MIB."
        REVISION        "200604190000Z"
        DESCRIPTION
                "Added capability statement 
                 cL4L7ModRsrcLimCapACSWV03R000 
                 for Application Control Engine (ACE)."
        ::= { ciscoAgentCapability 499 }

cL4L7ModRsrcLimCapACSWV03R000 AGENT-CAPABILITIES

PRODUCT-RELEASE "ACSW (Application Control Software) 3.0"
STATUS          current
DESCRIPTION     "CISCO-L4L7MODULE-RESOURCE-LIMIT-MIB capabilities."

SUPPORTS        CISCO-L4L7MODULE-RESOURCE-LIMIT-MIB

     INCLUDES   { ciscoL4L7ResourceClassGroup, 
                  ciscoL4L7ResourceLimitGroup,
                  ciscoL4L7ResourceRateLimitGroup }

     VARIATION       crlResourceClassStorageType
     ACCESS          read-only
     DESCRIPTION     "Create operation not allowed."

     VARIATION       crlResourceClassRowStatus
     ACCESS          read-only
     DESCRIPTION     "Create operation not allowed."

     VARIATION       crlResourceLimitMin
     ACCESS          read-only
     DESCRIPTION     "Create operation not allowed."

     VARIATION       crlResourceLimitMax
     ACCESS          read-only
     DESCRIPTION     "Create operation not allowed."

     VARIATION       crlResourceLimitStorageType
     ACCESS          read-only
     DESCRIPTION     "Create operation not allowed."

     VARIATION       crlResourceLimitRowStatus
     ACCESS          read-only
     DESCRIPTION     "Create operation not allowed."

     VARIATION       crlRateLimitResourceMax
     ACCESS          read-only
     DESCRIPTION     "Create operation not allowed."

     VARIATION       crlRateLimitResourceStorageType
     ACCESS          read-only
     DESCRIPTION     "Create operation not allowed."

     VARIATION       crlRateLimitResourceRowStatus
     ACCESS          read-only
     DESCRIPTION     "Create operation not allowed."

    ::= { ciscoL4L7ModRsrcLimCap 1 }

END
