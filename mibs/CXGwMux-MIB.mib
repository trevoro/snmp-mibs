CXGwMux-MIB DEFINITIONS ::= BEGIN

-- rev.2.22

IMPORTS
	Counter     FROM RFC1155-SMI
	OBJECT-TYPE FROM RFC-1212

-- Proprietary definitions:
	cxGwMux, Alias FROM CXProduct-SMI;

-- Proprietary Data Types
SubRef   ::=   INTEGER (0..255)

--  GMF GENERAL CONFIGURATION and STATISTICS GROUP.

gmfConfig   OBJECT IDENTIFIER ::= { cxGwMux 1}

gmfMuxInterPassPeriodInMs OBJECT-TYPE
	SYNTAX   INTEGER (1..500)
	ACCESS   read-write
	STATUS   mandatory
	DESCRIPTION
"Determines the minimum period in milliseconds between the muxing of 
queued frames.

Range of Values: 1-500

Default Value: 10

Configuration Changed: operative "
	DEFVAL { 10 }
	::= { gmfConfig 1 }

gmfVoiceOverDataPriorityFactor OBJECT-TYPE
	SYNTAX   INTEGER (1..1000)
	ACCESS   read-write
	STATUS   mandatory
	DESCRIPTION
"Determines the maximum number of compressed voice-type frames that can be 
muxed in sequence before a compressed data-type frame must be muxed.

Range of Values: 1 - 1,000

Default Value: 1,000

Configuration Changed: operative "
	DEFVAL { 1000 }
	::= { gmfConfig 2 }

gmfStatSamplingPeriod OBJECT-TYPE
	SYNTAX   INTEGER (0..3600)
	ACCESS   read-write
	STATUS   mandatory
	DESCRIPTION
"Determines the maximum duration in seconds for statistical sampling. 
Resetting this sampling window to a different value zeroes the objects
gmfLinkUtilizationTx, gmfLinkUtilizationRx and gmfLinkErrorRate to 
begin a fresh sample.

Range of Values: 0 - 3,600

Default Value: 3,600

Configuration Changed: operative "
	DEFVAL { 3600 }
	::= { gmfConfig 3 }

gmfNoOfLinkSupported OBJECT-TYPE
	SYNTAX   INTEGER (0..1024)
	ACCESS   read-write
	STATUS   mandatory
	DESCRIPTION
"Determines the number of virtual circuits that the GMF software layer 
currently supports for compressed voice/data traffic. If '0', voice/data 
traffic is disabled. If '1', then that one voice/data link will be 
numbered Link Number 1. If '5', then voice/data links one through five 
will be numbered Link Number 1, Link Number 2, Link Number 3, Link Number 
4 and Link Number 5, respectively. 'gmfLink' uses the numbers assigned to 
these virtual circuits.

Range of Values: 0 - 1,024

Default Value: 0

Configuration Changed: administrative "
	DEFVAL { 0 }
	::= { gmfConfig 4 }

gmfNoOfEntryPerFiFo OBJECT-TYPE
	SYNTAX   INTEGER (32..10000)
	ACCESS   read-write
	STATUS   mandatory
	DESCRIPTION
"Determines the maximum number of voice/data entries that the queueing 
controller (FIFO) in system memory can handle.

Range of Values: 32 - 10,000

Default Value: 256

Configuration Changed: administrative "
	DEFVAL { 256 }
	::= { gmfConfig 5 }

gmfToFrCouplingLevel OBJECT-TYPE
	SYNTAX   INTEGER (1..2)
	ACCESS   read-write
	STATUS   mandatory
	DESCRIPTION
"Not currently used."
	DEFVAL { 1 }
	::= { gmfConfig 6 }

gmfOutputFlowControlFactor OBJECT-TYPE
	SYNTAX   INTEGER (1..10)
	ACCESS   read-write
	STATUS   mandatory
	DESCRIPTION
"Determines the extent to which the GMF software layer slows down 
compressed data (but not compressed voice) traffic from a Data Compression 
module (if present) after being notified of congestion by the Frame Relay 
software layer.

Range of Values: 1 - 10 (10 = slowest)

Default Value: 1

Configuration Changed: operative "
	DEFVAL { 1 }
	::= { gmfConfig 7 }

gmfState OBJECT-TYPE
	SYNTAX   INTEGER {
			dead (1),
			gmf-task-conf (2),
			general-conf (3),
			sap-conf (4),
			route-conf (5),
			init-gmf-completed (6),
			init-appl-completed (7),   
			mci-only (8),
			reg-to-iam(9)
		}
	ACCESS   read-only
	STATUS   mandatory
	DESCRIPTION
"Indicates the state of the GMF software layer at initialization. Report 
abnormal value to Memotec Service Department.

Options:
dead (1): CX900/CX1000 abnormal

gmf-task-conf (2): CX900/CX1000 abnormal

general-conf (3): CX900/CX1000 abnormal

sap-conf (4): CX900/CX1000 abnormal

route-conf (5): CX900/CX1000 abnormal

init-gmf-completed (6): CX900/CX1000
abnormal

init-appl-completed (7): CX900 normal/CX1000 abnormal

mci-only (8): CX900 abnormal/CX1000 CCM only

reg-to-iam (9): CX900 abnormal/CX1000 normal

Default Value: none"
	::= { gmfConfig 8 }

gmfCntInfoMsgRelFromBus OBJECT-TYPE
	SYNTAX   Counter 
	ACCESS   read-only
	STATUS   mandatory
	DESCRIPTION
"Indicates the number of information messages (including Management 
Console Interface traffic) received from the Token Bus software layer.

Range of Values: 0 - 4, 294, 967, 295

Default Value: none"
	::= { gmfConfig 9 }

gmfCntInfoMsgRelFromWan OBJECT-TYPE
	SYNTAX   Counter 
	ACCESS   read-only
	STATUS   mandatory
	DESCRIPTION
"Indicates the number of compressed voice/data messages received from the 
Frame Relay software layer.

Range of Values: 0 - 4, 294, 967, 295

Default Value: none"
	::= { gmfConfig 10 }

gmfCntTxAckToWan  OBJECT-TYPE
	SYNTAX   Counter 
	ACCESS   read-only
	STATUS   mandatory
	DESCRIPTION
"Indicates the number of ACKs sent to the Frame Relay software layer.

Range of Values: 0 - 4, 294, 967, 295

Default Value: none"
	::= { gmfConfig 11 }

gmfCntUnexpLinkNoFromWan OBJECT-TYPE
	SYNTAX   Counter 
	ACCESS   read-only
	STATUS   mandatory
	DESCRIPTION
"Indicates the number of unexpected DLCIs in message headers received from 
the Frame Relay software layer.

Range of Values: 0-4, 294, 967, 295

Default Value: none"
	::= { gmfConfig 12 }

gmfCntFrmTooShortFromWan OBJECT-TYPE
	SYNTAX   Counter 
	ACCESS   read-only
	STATUS   mandatory
	DESCRIPTION
"Indicates the number of short frames received from the Frame Relay 
software layer and then discarded.

Range of Values: 0 - 4, 294, 967, 295

Default Value: none"
	::= { gmfConfig 13 }

gmfCntFrmTooLongFromWan OBJECT-TYPE
	SYNTAX   Counter 
	ACCESS   read-only
	STATUS   mandatory
	DESCRIPTION
"Indicates the number of long frames received from the Frame Relay 
software layer and then discarded.

Range of Values: 0 - 4, 294, 967, 295

Default Value: none"
	::= { gmfConfig 14 }

gmfLongestTimeToMux OBJECT-TYPE
	SYNTAX   Counter
	ACCESS   read-only
	STATUS   mandatory
	DESCRIPTION
"Indicates the duration in milliseconds for the longest mux pass.

Range of Values: 0 - 4, 294, 967, 295

Default Value: none"
	::= { gmfConfig 15 }

gmfCntSilentConnections OBJECT-TYPE
	SYNTAX   Counter
	ACCESS   read-only
	STATUS   mandatory
	DESCRIPTION
"Indicates the number of connections with the Voice Module (CX 900 only) 
or with a local AC 600/MC 600/HC 600 (CX 1000 only) that have been dropped 
by the GMF software layer due to inactivity.

Range of Values: 0 - 4, 294, 967, 295

Default Value: none"
	::= { gmfConfig 16 }

-- The next object is obsolete.

gmfCntMuxPassTimeExceeded OBJECT-TYPE
	SYNTAX   Counter
	ACCESS   read-only
	STATUS   obsolete
	DESCRIPTION
"Not currently used."
	::= { gmfConfig 17 }

-- The next object is obsolete.

gmfMciCurrentConnection OBJECT-TYPE
	SYNTAX   INTEGER
	ACCESS   read-only
	STATUS   obsolete
	DESCRIPTION
"Not currently used."
	::= { gmfConfig 18 }

gmfCntInfoMsgRelFromVce OBJECT-TYPE
	SYNTAX   Counter 
	ACCESS   read-only
	STATUS   mandatory
	DESCRIPTION
"Indicates the number of information messages received from the Voice 
module (if present).

Range of Values: 0 - 4, 294, 967, 295

Default Value: none"
	::= { gmfConfig 19 }

gmfCntGlobalFlowCtlCond OBJECT-TYPE
	SYNTAX   Counter 
	ACCESS   read-only
	STATUS   mandatory
	DESCRIPTION
"Indicates the number of times that voice/data entries nearly exceeded 
what the queuing controller (FIFO) in system memory could handle as 
defined in 'gmfNoOfEntryPerFifo'.

Range of Values: 0 - 4, 294, 967, 295

Default Value: none"
	::= { gmfConfig 20 }

gmfNoOfVoicePacketQueued OBJECT-TYPE
	SYNTAX   INTEGER (0..8)
	ACCESS   read-write
	STATUS   mandatory
	DESCRIPTION
"Determines the maximum number of voice packets that can be buffered 
before being muxed.

Range of Values: 0-8

Default Value: 4

Configuration Changed: operative "
	DEFVAL { 4 }
	::= { gmfConfig 21 }

gmfControlStats OBJECT-TYPE
	SYNTAX   INTEGER {
				clearStats (1)
			}
	ACCESS   write-only
	STATUS   mandatory
	DESCRIPTION
"Clears GMF statistics not related to sampling period.

Options:
clearStats (1): clear statistics

Default Value: none

Configuration Changed: operative "
	::= { gmfConfig 22 }







--  GMF ROUTING DEFINITION GROUP.

gmfRouteTable  OBJECT-TYPE
	SYNTAX   SEQUENCE  OF GmfRouteEntry
	ACCESS   not-accessible
	STATUS   mandatory
	DESCRIPTION
"GMF routing table. The table maintains a row per slot source (i.e. 16 
possible rows for the CX 1000 chassis) and GMF link number. This table is 
has no meaning for voice stations that use the voice switching option."
	::= { cxGwMux 2 }

	gmfRouteEntry  OBJECT-TYPE -- This defines a row in the table.
		SYNTAX   GmfRouteEntry
		ACCESS   not-accessible
		STATUS   mandatory
		DESCRIPTION
"Each row associates a slot destination number for each possible route 
number with a specific <source slot number>.<GMF link number to use> 
combination."

		INDEX { gmfOrigin, gmfLink }
		::= { gmfRouteTable 1 }

	GmfRouteEntry ::=    -- This defines a column in the table.
		SEQUENCE {
			gmfOrigin      INTEGER,
			gmfLink     INTEGER,
			gmfDest     INTEGER,
			gmfRouteRowStatus INTEGER
		}

	gmfOrigin   OBJECT-TYPE
		SYNTAX   INTEGER (1..16)
		ACCESS   read-only
		STATUS   mandatory
		DESCRIPTION
"Indicates the slot in the chassis occupied by a CPU card sending 
compressed voice/data packets.

Range of Values: 1-16

Default Value: none

Configuration Changed: administrative "
		::= { gmfRouteEntry 1 }

	gmfLink     OBJECT-TYPE
		SYNTAX   INTEGER (1..48)
		ACCESS   read-only
		STATUS   mandatory
		DESCRIPTION
"Indicates a valid route number established in 'gmfNoOfLinkSupported' that 
is used by the Voice/Data Compression module to send compressed voice/data 
packets to the Frame Relay software layer.

Range of Values: 1-48

Default Value: none

Configuration Changed: administrative "
		::= { gmfRouteEntry 2 }

	gmfDest     OBJECT-TYPE
		SYNTAX   INTEGER (1..16)
		ACCESS   read-write
		STATUS   mandatory
		DESCRIPTION
"Determines the slot in an equivalent chassis across the network occupied 
by a CPU card receiving compressed voice/data packets.

Range of Values: 1-16

Default Value: undefined

Configuration Changed: operative "
		::= { gmfRouteEntry 3 }

	gmfRouteRowStatus OBJECT-TYPE
		SYNTAX   INTEGER { invalid (1), valid (2) }
		ACCESS   read-write
		STATUS   mandatory
		DESCRIPTION
"Determines whether this slot/route combination is to be deleted from the 
GMF software layer.

Options:
invalid (1): Row is deleted from the table immediately, however values are 
still in effect until the next reset. 

valid (2): Use this value to add a new row to the table, or modify an 
existing row.

Default Value: none

Configuration Changed: administrative "
		::= { gmfRouteEntry 4 }




-- GMF LINKS STATISTICS and CONTROL

gmfLinkStatTable  OBJECT-TYPE
	SYNTAX   SEQUENCE  OF GmfLinkStatEntry
	ACCESS   not-accessible
	STATUS   mandatory
	DESCRIPTION
	"GMF links statistics table.  The table maintains a row per link."
	::= { cxGwMux 3 }

	gmfLinkStatEntry  OBJECT-TYPE -- This defines a row in the table.
		SYNTAX   GmfLinkStatEntry
		ACCESS   not-accessible
		STATUS   mandatory
		DESCRIPTION
"Each row contains the state variables and general counters associated 
with a particular link."
		INDEX { gmfLinkIndex }
		::= { gmfLinkStatTable 1 }

	GmfLinkStatEntry ::= -- This defines columns in the table; each 
			     -- column gives the statistics related to a    
		SEQUENCE {   -- specific LinkIndex.   
			gmfLinkIndex               INTEGER,
			gmfLinkStatus              INTEGER,
			gmfLinkType                INTEGER,
			gmfCntDataFrmMx            Counter,
			gmfCntDataFrmDmx           Counter,
			gmfCntVoiceFrmMx           Counter,
			gmfCntVoiceFrmDmx          Counter,
			gmfCntLinkDown             Counter,
			gmfLinkUtilizationTx       Counter,
			gmfLinkUtilizationRx       Counter,
			gmfLinkErrorRate           Counter,
			gmfCntInFlowCtrlMuxSide    Counter,
			gmfCntOutFlowCtrlWanSide   Counter,
			gmfCntSeqErrorFromMux      Counter,
			gmfCntSeqErrorFromWan      Counter,
			gmfCntSilentLink           Counter,
			gmfCntSeqErrorForced       Counter,
			gmfCntUnexpLoopBack        Counter,
			gmfCntRemoteRestarted      Counter,
			gmfCntVoiceMuxInterrupted  Counter,
			gmfCntDataQueueFull        Counter,
			gmfCntVoiceQueueFull       Counter,
			gmfCntUnexpSliceType       Counter,
			gmfCntRouteChange          Counter,
			gmfCntTooManyCodes         Counter,
			gmfCntPosValidation        Counter,
			gmfCntNegValidation        Counter,
			gmfControlLink             INTEGER,
			gmfDataOutWindowWidth      INTEGER,
			gmfDataOutPriority         INTEGER
		}

	gmfLinkIndex   OBJECT-TYPE
		SYNTAX   INTEGER 
		ACCESS   read-only
		STATUS   mandatory
		DESCRIPTION
"Indicates the row containing objects for monitoring the virtual circuit.

Range of Values: 1 - 48

Default Value: none"
		::= { gmfLinkStatEntry 1 }

	gmfLinkStatus  OBJECT-TYPE
		SYNTAX   INTEGER {down(1), init(2), up(3)}
		ACCESS   read-only
		STATUS   mandatory
		DESCRIPTION
"Indicates the virtual circuit's current state.

Options:
down (1): circuit is down

init (2): circuit is initializing

up (3): circuit is up

Default Value: none"
		::= { gmfLinkStatEntry 2 }

	gmfLinkType OBJECT-TYPE
	SYNTAX   INTEGER {bound-to-FR(1), routed-to-IAM(2), in-loopback(3)}
	ACCESS   read-only
	STATUS   mandatory
	DESCRIPTION
"Indicates routing of virtual circuit from GMF software layer.

Options:
bound-to-FR (1): direct to Frame Relay module

routed-to-IAM (2): direct to Inter-Application module

in-loopback (3): looped back to Token Bus module or Voice module (if 
present)

Default Value: none"
		::= { gmfLinkStatEntry 3 }

	gmfCntDataFrmMx OBJECT-TYPE
		SYNTAX   Counter
		ACCESS   read-only
		STATUS   mandatory
		DESCRIPTION
"Indicates the number of data frames that have been muxed since the last 
power up or since 'gmfControlStats' was set to 'clearStats'.

Range of Values: 0 - 4, 294, 967, 295

Default Value: none"
		::= { gmfLinkStatEntry 4 }

	gmfCntDataFrmDmx OBJECT-TYPE
		SYNTAX   Counter
		ACCESS   read-only
		STATUS   mandatory
		DESCRIPTION
"Indicates the number of data frames that have been demuxed since the last 
power up or since 'gmfControlStats' was set to 'clearStats'.

Range of Values: 0 - 4, 294, 967, 295

Default Value: none"
		::= { gmfLinkStatEntry 5 }

	gmfCntVoiceFrmMx OBJECT-TYPE
		SYNTAX   Counter
		ACCESS   read-only
		STATUS   mandatory
		DESCRIPTION
"Indicates the number of voice frames that have been muxed since the last 
power up or since 'gmfControlStats' was set to 'clearStats'.

Range of Values: 0 - 4, 294, 967, 295

Default Value: none"
		::= { gmfLinkStatEntry 6 }

	gmfCntVoiceFrmDmx OBJECT-TYPE
		SYNTAX   Counter
		ACCESS   read-only
		STATUS   mandatory
		DESCRIPTION
"Indicates the number of compressed voice frames that have been demuxed 
since the last power up or since 'gmfControlStats' was set to 
'clearStats'.

Range of Values: 0 - 4, 294, 967, 295

Default Value: none"
		::= { gmfLinkStatEntry 7 }

	gmfCntLinkDown OBJECT-TYPE
		SYNTAX   Counter
		ACCESS   read-only
		STATUS   mandatory
		DESCRIPTION
"Indicates the number of notifications received from the Frame Relay 
software layer that the PVC has been down since the last power up or since 
'gmfControlStats' was set to 'clearStats'.

Range of Values: 0 - 4, 294, 967, 295

Default Value: none"
		::= { gmfLinkStatEntry 8 }

	gmfLinkUtilizationTx  OBJECT-TYPE
		SYNTAX   Counter
		ACCESS   read-only
		STATUS   mandatory
		DESCRIPTION
"Indicates the transfer rate in bits per second of data moving from the 
local Voice/Data Compression module to the Frame Relay module within the 
last sampling period.

Range of Values: 0 - 4, 294, 967, 295

Default Value: none"
		::= { gmfLinkStatEntry 9 }

	gmfLinkUtilizationRx  OBJECT-TYPE
		SYNTAX   Counter
		ACCESS   read-only
		STATUS   mandatory
		DESCRIPTION
"Indicates the transfer rate in bits per second of data moving from the 
Frame Relay module to the local Voice/Data Compression module within the 
last sampling period.

Range of Values: 0 - 4, 294, 967, 295

Default Value: none"
		::= { gmfLinkStatEntry 10 }

	gmfLinkErrorRate  OBJECT-TYPE
		SYNTAX   Counter
		ACCESS   read-only
		STATUS   mandatory
		DESCRIPTION
"Indicates the number of sequence errors occurring within the last 
sampling period on the virtual circuit between the GMF and the Frame Relay 
software layers.

Range of Values: 0 - 4, 294, 967, 295

Default Value: none"
		::= { gmfLinkStatEntry 11 }

	gmfCntInFlowCtrlMuxSide OBJECT-TYPE
		SYNTAX   Counter
		ACCESS   read-only
		STATUS   mandatory
		DESCRIPTION
"Indicates the number of times the GMF software layer has notified the 
Voice/Data Compression module to slow its traffic. This value is zeroed 
when 'gmfControlStats' is set to 'clearStats'.

Range of Values: 0 - 4, 294, 967, 295

Default Value: none"
		::= { gmfLinkStatEntry 12 }

	gmfCntOutFlowCtrlWanSide OBJECT-TYPE
		SYNTAX   Counter
		ACCESS   read-only
		STATUS   mandatory
		DESCRIPTION
"Indicates the number of times the GMF software layer has slowed its 
muxing of data traffic due to messages received from the Frame Relay 
software layer with the BECN bit set. This value is zeroed when 
'gmfControlStats' is set to 'clearStats'.

Range of Values: 0 - 4, 294, 967, 295

Default Value: none"
		::= { gmfLinkStatEntry 13 }

	gmfCntSeqErrorFromMux OBJECT-TYPE
		SYNTAX   Counter
		ACCESS   read-only
		STATUS   mandatory
		DESCRIPTION
"Indicates the number of times the GMF software layer detected sequence 
errors in the data stream coming from the Voice/Data Compression module 
since the last power up or since 'gmfControlStats' was set to 
'clearStats'.

Range of Values: 0 - 4, 294, 967, 295

Default Value: none"
		::= { gmfLinkStatEntry 14 }

	gmfCntSeqErrorFromWan   OBJECT-TYPE
		SYNTAX   Counter
		ACCESS   read-only
		STATUS   mandatory
		DESCRIPTION
"Indicates the number of times the GMF software layer detected sequence 
errors in the data stream coming from the Frame Relay software layer since 
the last power up or since 'gmfControlStats' was set to 'clearStats'.

Range of Values: 0 - 4, 294, 967, 295

Default Value: none"
		::= { gmfLinkStatEntry 15 }

	gmfCntSilentLink OBJECT-TYPE
		SYNTAX   Counter
		ACCESS   read-only
		STATUS   mandatory
		DESCRIPTION

"Indicates whether the GMF software layer detected a silence on the 
virtual circuit between the GMF and Frame Relay software layer since the 
last power up or since 'gmfControlStats' was set to 'clearStats'.

Options:
false: silence not detected

true: silence detected

Default Value: false"
		::= { gmfLinkStatEntry 16 }

	gmfCntSeqErrorForced OBJECT-TYPE
		SYNTAX   Counter
		ACCESS   read-only
		STATUS   mandatory
		DESCRIPTION
"Indicates the number of times the GMF software layer forced a sequence 
error in a message to the Frame Relay software layer since the last power 
up or since 'gmfControlStats' was set to 'clearStats'.

Range of Values: 0 - 4, 294, 967, 295

Default Value: none"
		::= { gmfLinkStatEntry 17 }

	gmfCntUnexpLoopBack OBJECT-TYPE
		SYNTAX   Counter
		ACCESS   read-only
		STATUS   mandatory
		DESCRIPTION
"Not currently used."
		::= { gmfLinkStatEntry 18 }

	gmfCntRemoteRestarted OBJECT-TYPE
		SYNTAX   Counter
		ACCESS   read-only
		STATUS   mandatory
		DESCRIPTION
"Not currently used."
		::= { gmfLinkStatEntry 19 }

	gmfCntVoiceMuxInterrupted OBJECT-TYPE
		SYNTAX   Counter
		ACCESS   read-only
		STATUS   mandatory
		DESCRIPTION
"Indicates the number of times the GMF software layer stopped muxing 
current voice traffic to allow for muxing of data traffic in accordance 
with the 'gmfVoiceOverDataPriorityFactor' since the last power up or since 
'gmfControlStats' was set to 'clearStats'.

Range of Values: 0 - 4, 294, 967, 295

Default Value: none"
		::= { gmfLinkStatEntry 20 }

	gmfCntDataQueueFull OBJECT-TYPE
		SYNTAX   Counter
		ACCESS   read-only
		STATUS   mandatory
		DESCRIPTION
"Indicates the number of times that data entries exceeded the capacity of 
the queueing controller (FIFO) in system memory since the last power up or 
since 'gmfControlStats' was set to 'clearStats'.

Range of Values: 0 - 4, 294, 967, 295

Default Value: none"
		::= { gmfLinkStatEntry 21 }

	gmfCntVoiceQueueFull OBJECT-TYPE
		SYNTAX   Counter
		ACCESS   read-only
		STATUS   mandatory
		DESCRIPTION
"Indicates the number of times that voice entries exceeded the capacity of 
the queueing controller (FIFO) in system memory since the last power up or 
since 'gmfControlStats' was set to 'clearStats'.

Range of Values: 0 - 4, 294, 967, 295

Default Value: none"
		::= { gmfLinkStatEntry 22 }

	gmfCntUnexpSliceType OBJECT-TYPE
		SYNTAX   Counter
		ACCESS   read-only
		STATUS   mandatory
		DESCRIPTION
"Indicates the number of times the GMF software layer detected a message 
of an unexpected type from a Voice/Data Compression module since the last 
power up or since 'gmfControlStats' was set to 'clearStats'.

Range of Values: 0 - 4, 294, 967, 295

Default Value: none"
		::= { gmfLinkStatEntry 23 }

	gmfCntRouteChange OBJECT-TYPE
		SYNTAX   Counter
		ACCESS   read-only
		STATUS   mandatory
		DESCRIPTION
"Indicates the number of times an active routing entry using this virtual 
circuit has been killed through on-the-fly route changes with 
'gmfRouteEntry' since the last power up or since 'gmfControlStats' was set 
to 'clearStats'.

Range of Values: 0 - 4, 294, 967, 295

Default Value: none"
		::= { gmfLinkStatEntry 24 }

	gmfCntTooManyCodes OBJECT-TYPE
		SYNTAX   Counter
		ACCESS   read-only
		STATUS   mandatory
		DESCRIPTION
"Indicates the number of times the GMF software layer received a 
compressed voice/data packet containing too many codes from the Voice/Data 
Compression module since the last power up or since 'gmfControlStats' was 
set to 'clearStats'.

Range of Values: 0 - 4, 294,967, 295

Default Value: none"
		::= { gmfLinkStatEntry 25 }

	gmfCntPosValidation OBJECT-TYPE
		SYNTAX   Counter
		ACCESS   read-only
		STATUS   mandatory
		DESCRIPTION
"Indicates the number of positive validations the GMF software layer has 
sent the Voice/Data Compression module since the last power up or since 
'gmfControlStats' was set to 'clearStats'.

Range of Values: 0 - 4, 294, 967,295

Default Value: none"
		::= { gmfLinkStatEntry 26 }

	gmfCntNegValidation OBJECT-TYPE
		SYNTAX   Counter
		ACCESS   read-only
		STATUS   mandatory
		DESCRIPTION
"Indicates the number of negative validations the GMF software layer has 
sent the Voice/Data Compression module since the last power up or since 
'gmfControlStats' was set to 'clearStats'.

Range of Values: 0 - 4, 294, 967, 295

Default Value: none"
		::= { gmfLinkStatEntry 27 }

-- There is a hole at the position 28

	gmfControlLink OBJECT-TYPE
		SYNTAX   INTEGER {
					forceNormal     (1),
					forceLoopback (2)
				}
		ACCESS   write-only
		STATUS   mandatory
		DESCRIPTION
"Determines whether the GMF software layer puts link in normal mode or in 
loopback mode.

Options:
forceNormal (1): puts link in normal mode

forceLoopback (2): puts link in loopback mode

Default Value: none

Configuration Changed: operative "
		::= { gmfLinkStatEntry 29 }

	gmfDataOutWindowWidth OBJECT-TYPE
		SYNTAX   INTEGER (1..16)
		ACCESS   read-write
		STATUS   mandatory
		DESCRIPTION
"Determines the width in the transmit window given to data traffic in 
relation to voice traffic. The lower this value, the more restricted will 
be the flow of data traffic.

Range of Values: 1-16

Default Value: 6

Configuration Changed: operative "
		DEFVAL { 6 }
		::= { gmfLinkStatEntry 30 }

	gmfDataOutPriority OBJECT-TYPE
		SYNTAX   INTEGER (1..4)
		ACCESS   read-write
		STATUS   mandatory
		DESCRIPTION
"Determines the priority given to outbound data traffic routed through the 
FRIM software layer. Priority for traffic routed directly through the 
Frame Relay software layer is controlled with 'frCircuitPriorityLevel'.

Range of Values: 1 - 4 (4 is the lowest)

Default Value: 1

Configuration Changed: operative "
		DEFVAL { 1 }
		::= { gmfLinkStatEntry 31 }




--  GMF SYSTEM ROUTING DEFINITION GROUP.

gmfSRTable OBJECT-TYPE
	SYNTAX   SEQUENCE OF GmfSREntry
	ACCESS   not-accessible
	STATUS   mandatory
	DESCRIPTION
"GMF system routing table. The table may contain a row per GMF link i.e. up 
to 48 rows (currently)."
	::= {  cxGwMux 4  }


	gmfSREntry OBJECT-TYPE
	SYNTAX   GmfSREntry
	ACCESS   not-accessible
	STATUS   mandatory
	DESCRIPTION
"Each row associates an alias and a subref field to a GMF's link."
	INDEX {  gmfSRLink  }
	::= { gmfSRTable 1 }


	GmfSREntry ::=
		SEQUENCE {
			gmfSRLink               INTEGER,
			gmfSRDestCircuitAlias   Alias,
			gmfSRSubRef             SubRef,
			gmfSRConStatus          INTEGER,
			gmfSRFailStatus         INTEGER,
			gmfSRRowStatus          INTEGER
		}




	gmfSRLink OBJECT-TYPE
		SYNTAX   INTEGER (1..1024)
		ACCESS   read-only
		STATUS   mandatory
		DESCRIPTION
"Indicates a valid route number established in 'gmfNoOfLinkSupported' used 
by the Voice/Data Compression module to send compressed voice/data packets 
to the Frame Relay software layer.

Range of Values: 1 - 1,024

Default Value: none"
		::= { gmfSREntry 1 }


	gmfSRDestCircuitAlias OBJECT-TYPE
		SYNTAX   Alias
		ACCESS   read-write
		STATUS   mandatory
		DESCRIPTION
"Determines the alias of a circuit specified in the Frame Relay software 
layer that will link with the GMF route.

Range of Values:
(CX 1000) 0 - 35 alphanumeric characters beginning
with a non-numeric character

(CX 900) 0 - 16 alphanumeric characters beginning
with a non-numeric character 

Default Value: none

Configuration Changed: operative "
		::= { gmfSREntry 2 }


	gmfSRSubRef OBJECT-TYPE
		SYNTAX   SubRef
		ACCESS   read-write
		STATUS   mandatory
		DESCRIPTION
"Determines the reference that one user's segment of traffic will be 
assigned on the outbound PVC to distinguish it from traffic segments of 
other users of the same outbound PVC.

Range of Values: 1 - 255

Default Value: 1

Configuration Changed: operative "
		DEFVAL {1}
		::= { gmfSREntry 3 }


	gmfSRConStatus OBJECT-TYPE
		SYNTAX   INTEGER
				{
					not-init    (1),
					closed         (2),
					waitForQueryConf  (3),
					waitForOpenConf   (4),
					opened         (5)
				}
		ACCESS   read-only
		STATUS   mandatory
		DESCRIPTION
"Indicates status of connection on the system route.

Options:
not-init (1): system route not initialized

closed (2): system route closed

waitForQueryConf (3): in progress (query confirmed?)

waitForOpenConf (4): in progress (opening confirmed?)

opened (5): system route opened

Default Value: none"


		::= { gmfSREntry 4 }


	gmfSRFailStatus OBJECT-TYPE
		SYNTAX   INTEGER
				{
					noFailure         (1),
					internalError        (2),
					localMemAllocFailure    (3),
					remoteMemAllocFailure      (4),
					remoteNoAccess    (5),
					remotePvcDown     (6),
					remotePvcBusy     (7),
					localFcnFailure      (8),
					remoteFcnFailure     (9),
					localDsnFailure      (10),
					remoteAliasNotFound     (11),
					remoteNoPvcService      (12),
					openReqTimeout    (13),
					adjaCardReset        (14),
					linkNotSupported     (15)
				}
		ACCESS   read-only
		STATUS   mandatory
		DESCRIPTION
"Indicates the reason for a connection failure on a system route prior to 
the next attempt to establish a connection on that route.

Default Value: none

Options:
noFailure (1): did not fail

internalError (2): system error

localMemAllocFailure (3): GMF memory allocation error

remoteMemAllocFailure (4): FRIM memory allocation error

remoteNoAccess (5): FRIM not configured

remotePvcDown (6): FRIM reported down

remotevcBusy (7): FRIM busy

localFcnFailure (8): flow control type unknown to GMF

remoteFcnFailure (9): flow control type unknown to FRIM

localDsnFailure (10): GMF could not negotiate data size

remoteAliasNotFound (11): no PVC for destination alias

remoteNoPvcService (12): FRIM not supporting PVC protocol

openReqTimeout (13): timeout of open connection request

adjaCardReset (14): adjacent CPU reset (CX 1000 only)

linkNotSupported (15): system route number not supported"
		::= { gmfSREntry 5 }


	gmfSRRowStatus OBJECT-TYPE
		SYNTAX   INTEGER { invalid(1), valid(2) }
		ACCESS   read-write
		STATUS   mandatory
		DESCRIPTION
"Determines whether this system route is in service or is to be deleted 
from the GMF software layer.

Options:
invalid (1): Row is deleted from the table immediately, however values are 
still in effect until the next reset. 

valid (2): Use this value to add a new row to the table, or modify an 
existing row.

Default Value: none

Configuration Changed: operative "
		::= { gmfSREntry 6 }


END
