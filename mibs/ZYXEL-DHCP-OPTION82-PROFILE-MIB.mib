-- ZyXEL Communications Corporation
-- Private Enterprise MIB definition 
  
-- This file describes the ZyXEL Communications Corporation Enterprise MIB.
-- It contains ZyXEL products OIDs, and common managed objects.

-- $Log: ZYXEL-DHCP-OPTION82-PROFILE-MIB.mib $ 
-- Revision 1.3  2012/09/19 07:30:35  Kevin 
-- if it's leaf node, revise the vender name from zyxel to zy 
-- Revision 1.2  2012/07/05 06:22:26  Kevin 
-- 1. upgrade from SNMP to SNMPv2  
-- 2. clean warning 
-- Revision 1.1  2012/05/30 07:48:43  Kevin 
-- Initial revision 

ZYXEL-DHCP-OPTION82-PROFILE-MIB DEFINITIONS ::= BEGIN

    IMPORTS
	enterprises		FROM RFC1155-SMI                                
	
	OBJECT-TYPE
		FROM SNMPv2-SMI			-- RFC2578	
	RowStatus, DateAndTime, TruthValue, StorageType, MacAddress ,TDomain, TAddress
		FROM SNMPv2-TC			-- RFC2579
	DisplayString                                          
	  	FROM RFC1213-MIB
	EnabledStatus
		FROM  P-BRIDGE-MIB
	PortList
		FROM  Q-BRIDGE-MIB
	dot1dBasePort
       	FROM BRIDGE-MIB
	InterfaceIndexOrZero			-- RFC2863
		FROM IF-MIB
	SnmpAdminString
		FROM SNMP-FRAMEWORK-MIB		-- RFC2571
	InetAddressType, InetAddress
		FROM INET-ADDRESS-MIB		-- RFC2851
	OperationResponseStatus
		FROM DISMAN-PING-MIB
    Counter, TimeTicks
        FROM RFC1155-SMI
    BridgeId, Timeout
        FROM BRIDGE-MIB  
    dot1agCfmMdIndex 
		FROM IEEE8021-CFM-MIB
	dot1agCfmMaIndex
		FROM IEEE8021-CFM-MIB	
	dot1agCfmMepIdentifier
		FROM IEEE8021-CFM-MIB   	
    IpAddress
        FROM SNMPv2-SMI
    ifIndex
    	FROM IF-MIB					-- RFC2863
    NOTIFICATION-TYPE
        FROM SNMPv2-SMI
    sysObjectID 
        FROM RFC1213-MIB 
	ospfIfIpAddress, ospfAddressLessIf, ospfAreaId, ospfNbrIpAddr, ospfNbrAddressLessIndex,
	ospfLsdbAreaId, ospfLsdbType, ospfLsdbLsid, ospfLsdbRouterId, ospfVirtIfAreaId, ospfVirtIfNeighbor
		FROM OSPF-MIB
	esMgmt			
		FROM ZYXEL-ES-SMI;

	zyxelDhcpOption82Profile MODULE-IDENTITY
		LAST-UPDATED	"201207010000Z"    
		ORGANIZATION "Enterprise Solution ZyXEL"     
		CONTACT-INFO
			""	   
		DESCRIPTION
			"The subtree for dhcp option 82 profile"
		::= { esMgmt 17 }

	zyxelDhcpOption82ProfileSetup 	OBJECT IDENTIFIER ::= { zyxelDhcpOption82Profile 1 }		


		zyDhcpOption82ProfileMaxNumberOfProfiles OBJECT-TYPE
        SYNTAX  	INTEGER
        MAX-ACCESS  read-only
        STATUS  	current
        DESCRIPTION
		"The maximum number of DHCP option 82 entries that can be created."
		::= { zyxelDhcpOption82ProfileSetup 1 }


		zyxelDhcpOption82ProfileTable OBJECT-TYPE
        SYNTAX	SEQUENCE OF ZyxelDhcpOption82ProfileEntry
        MAX-ACCESS  not-accessible
        STATUS  current
        DESCRIPTION
        "The table contains DHCP option 82 profile configuration."
        ::= { zyxelDhcpOption82ProfileSetup 2 }
        
		zyxelDhcpOption82ProfileEntry OBJECT-TYPE
        SYNTAX	ZyxelDhcpOption82ProfileEntry
        MAX-ACCESS	not-accessible
        STATUS	current
        DESCRIPTION    	
		"An entry contains DHCP option 82 profile configuration. "
        INDEX          	{ zyDhcpOption82ProfileName }
        ::= { zyxelDhcpOption82ProfileTable 1 }              

      	ZyxelDhcpOption82ProfileEntry ::=
		SEQUENCE {
        	zyDhcpOption82ProfileName						DisplayString,
        	zyDhcpOption82ProfileCircuitIdState				EnabledStatus,
        	zyDhcpOption82ProfileCircuitIdSlotPortState		EnabledStatus,
        	zyDhcpOption82ProfileCircuitIdVidState			EnabledStatus,
        	zyDhcpOption82ProfileCircuitIdHostnameState		EnabledStatus,
        	zyDhcpOption82ProfileCircuitIdString			DisplayString,
        	zyDhcpOption82ProfileRemoteIdState				EnabledStatus,
        	zyDhcpOption82ProfileRemoteIdMacAddressState	EnabledStatus,
			zyDhcpOption82ProfileRemoteIdString				DisplayString,
        	zyDhcpOption82ProfileRowstatus 					RowStatus
           }

        zyDhcpOption82ProfileName OBJECT-TYPE
        SYNTAX  DisplayString
        MAX-ACCESS  not-accessible
        STATUS  current
        DESCRIPTION
        "DHCP option 82 profile Name."
        ::= { zyxelDhcpOption82ProfileEntry 1 }

        zyDhcpOption82ProfileCircuitIdState OBJECT-TYPE
        SYNTAX  EnabledStatus
        MAX-ACCESS  read-write
        STATUS  current
        DESCRIPTION
        "Enable/Disable DHCP option 82 circuit-ID."
        ::= { zyxelDhcpOption82ProfileEntry 2 }                        

        zyDhcpOption82ProfileCircuitIdSlotPortState OBJECT-TYPE
        SYNTAX  EnabledStatus
        MAX-ACCESS  read-write
        STATUS  current
        DESCRIPTION
        "Add DHCP option 82 circuit-ID with slot-port."
        ::= { zyxelDhcpOption82ProfileEntry 3 }                        

        zyDhcpOption82ProfileCircuitIdVidState OBJECT-TYPE
        SYNTAX  EnabledStatus
        MAX-ACCESS  read-write
        STATUS  current
        DESCRIPTION
        "Add DHCP option 82 circuit-ID with VLAN."
        ::= { zyxelDhcpOption82ProfileEntry 4 }                        

        zyDhcpOption82ProfileCircuitIdHostnameState OBJECT-TYPE
        SYNTAX  EnabledStatus
        MAX-ACCESS  read-write
        STATUS  current
        DESCRIPTION
        "Add DHCP option 82 circuit-ID with hostname."
        ::= { zyxelDhcpOption82ProfileEntry 5 }

        zyDhcpOption82ProfileCircuitIdString OBJECT-TYPE
        SYNTAX  DisplayString
        MAX-ACCESS  read-write
        STATUS  current
        DESCRIPTION
        "Add DHCP option 82 circuit-ID with string."
        ::= { zyxelDhcpOption82ProfileEntry 6 }

        zyDhcpOption82ProfileRemoteIdState OBJECT-TYPE
        SYNTAX  EnabledStatus
        MAX-ACCESS  read-write
        STATUS  current
        DESCRIPTION
        "Enable/Disable DHCP option 82 remote-ID."
        ::= { zyxelDhcpOption82ProfileEntry 7 }

        zyDhcpOption82ProfileRemoteIdMacAddressState OBJECT-TYPE
        SYNTAX  EnabledStatus
        MAX-ACCESS  read-write
        STATUS  current
        DESCRIPTION
        "Add DHCP option 82 remote-ID with MAC address."
        ::= { zyxelDhcpOption82ProfileEntry 8 }
                        
        zyDhcpOption82ProfileRemoteIdString OBJECT-TYPE
        SYNTAX  DisplayString
        MAX-ACCESS  read-write
        STATUS  current
        DESCRIPTION
        "Add DHCP option 82 remote-ID with string."
        ::= { zyxelDhcpOption82ProfileEntry 9 }

        zyDhcpOption82ProfileRowstatus OBJECT-TYPE
        SYNTAX  RowStatus
        MAX-ACCESS  read-write
        STATUS  current
        DESCRIPTION
        "This object allows a DHCP option 82 profile entry to be created and deleted."
        ::= { zyxelDhcpOption82ProfileEntry 10 }
                          
END
