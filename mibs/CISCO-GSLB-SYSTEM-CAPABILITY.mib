-- *****************************************************************
-- CISCO-GSLB-SYSTEM-CAPABILITY.my:
-- CISCO-GSLB-SYSTEM-MIB AGENT-CAPABILITIES
--   
-- Feb 2007, Pawan N
--   
-- Copyright (c) 2006-2007 by Cisco Systems Inc.
-- All rights reserved.
-- ****************************************************************

CISCO-GSLB-SYSTEM-CAPABILITY DEFINITIONS ::= BEGIN

IMPORTS
    MODULE-IDENTITY
        FROM SNMPv2-SMI
    AGENT-CAPABILITIES
        FROM SNMPv2-CONF
    ciscoAgentCapability
        FROM CISCO-SMI;


ciscoGslbSystemCapability MODULE-IDENTITY
    LAST-UPDATED    "200702230000Z"
    ORGANIZATION    "Cisco Systems, Inc."
    CONTACT-INFO
            "Cisco Systems
            Customer Service

            Postal:  170 W Tasman Drive
            San Jose, CA  95134
            USA

            Tel:  +1 800 553-NETS

            E-mail:  cs-slb@cisco.com"
    DESCRIPTION
        "The capabilities description
        of CISCO-GSLB-SYSTEM-MIB."
    REVISION        "200702230000Z"
    DESCRIPTION
        "Initial version of this MIB module."
    ::= { ciscoAgentCapability 534 }



ciscoGslbSystemCapabilityV02R00 AGENT-CAPABILITIES
    PRODUCT-RELEASE "GSS 2.0"
    STATUS          current
    DESCRIPTION
        "GSS 2.0 Cisco GSLB SYSTEM MIB capabilities"

    SUPPORTS        CISCO-GSLB-SYSTEM-MIB
    INCLUDES        {
                        ciscoGslbSystemNotifObjectsGroup,
                        ciscoGslbSystemNotifGroup
                    }
    ::= { ciscoGslbSystemCapability 1 }

END
