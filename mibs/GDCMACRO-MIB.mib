-- Copyright 1993 General DataComm Ind., Inc. All Rights Reserved.
--
-- Reproduction of this document is authorized on condition that the
-- foregoing copyright notice is included. This General DataComm, GDC,
-- SNMP Management Information Base Specification embodies GDCs'
-- confidential and proprietary intellectual property. GDC retains all
-- title and ownership in the Specification, including any revisions.
--
-- It is GDCs intent to encourage the widespread use of this Specification
-- in connection with the management of GDC's products. GDC grants vendors,
-- end-users, and other interested parties a non-exclusive licence to use
-- this Specification in connection with the management of GDC's products.
--
-- This Specification is supplied "AS IS," and GDC makes no warranty,
-- either expressed or implied, as to the use operation, condition, or
-- performance of the Specification.
--
-- gdcmacro.mib
--
-- Revision 1.1  1995/05/31  18:34:35  shankar
-- initial ci for cvs
--
--Revision 1.3  1994/08/19  15:22:49  haggerty
--Changed MIBS for Release 2.0 of Vfast.
--NOTE: Most of these changes were problems with the comment of CVS REvisions
--      The only Real changes were in gdcvfast.mib
--
--  Revision 1.2  1994/06/29  21:56:07  haggerty
--  Moved MIBS from OVDEVEL area to here, also updated lasted scm
--  and vfast mibs...
--
-- 
--
-- Revision History
-- Version   Date	Name		Description


GDCMACRO-MIB DEFINITIONS     ::=     BEGIN

IMPORTS

	Counter, Gauge, enterprises			FROM RFC1155-SMI
	DisplayString			FROM RFC1213-MIB
	OBJECT-TYPE			FROM RFC-1212;

gdc     OBJECT IDENTIFIER ::= { enterprises 498 }

SCinstance ::= INTEGER {
			slot1(16842752),
			slot2(33619968),
			slot3(50397184),
			slot4(67174400),
			slot5(83951616),
			slot6(100728832),
			slot7(117506048),
			slot8(134283264),
			slot9(151060480),
			slot10(167837696),
			slot11(184614912),
			slot12(201392128),
			slot13(218169344),
			slot14(234946560),
			slot15(251723776),
			slot16(258500992),
			slot17(285278208),
			slot18(302055424),
			slot19(318832640),
			slot20(335609856),
			slot21(352387072),
			slot22(369164288),
			slot23(385941504),
			slot24(402718720),
			slot25(419495936),
			slot26(436273152),
			slot27(453050368),
			slot28(469827584),
			slot29(486604800),
			slot30(503382016),
			slot31(520159232),
			slot32(536936448)
}

END
