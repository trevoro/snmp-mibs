Nortel-MsCarrier-MscPassport-DisdnETSIMIB
DEFINITIONS ::= BEGIN



IMPORTS

      OBJECT-TYPE
   FROM RFC-1212

      mscPassportMIBs
   FROM Nortel-MsCarrier-MscPassport-UsefulDefinitionsMIB

      DisplayString,
      StorageType,
      RowStatus,
      Unsigned32
   FROM Nortel-MsCarrier-MscPassport-StandardTextualConventionsMIB

      NonReplicated,
      Link
   FROM Nortel-MsCarrier-MscPassport-TextualConventionsMIB

      mscDataSigChanIndex,
      mscDataSigChan
   FROM Nortel-MsCarrier-MscPassport-DataIsdnMIB;




-- LAST-UPDATED   "9909010000Z"
-- ORGANIZATION   "Nortel Networks"
-- CONTACT-INFO   "
--         Nortel Carrier Data Network Management
--         
--         Postal:       P.O. Box 3511, Station C 
--                       Ottawa, Ontario 
--                       Canada  K1Y 4H7
--         
--         via the WEB:  http://www.nortelnetworks.com  
--                       select 'Contact Us' from the menu
--          
--         via phone:    1-800-4NORTEL"
-- DESCRIPTION
--    "The module describing the Nortel MsCarrier MscPassport
--     DisdnETSI Enterprise MIB."

disdnETSIMIB OBJECT IDENTIFIER ::= { mscPassportMIBs 117 }










-- DataSigChan/n ETSI
-- The ETSI component defines the operational characteristics of the 
-- signalling channel's connection to the external equipment.

mscDataSigChanEtsi OBJECT IDENTIFIER ::= { mscDataSigChan 10 }



mscDataSigChanEtsiRowStatusTable OBJECT-TYPE
   SYNTAX     SEQUENCE OF MscDataSigChanEtsiRowStatusEntry
   ACCESS     not-accessible
   STATUS     mandatory
   DESCRIPTION
     "This entry controls the addition and deletion of 
      mscDataSigChanEtsi components."
::= { mscDataSigChanEtsi 1 }

mscDataSigChanEtsiRowStatusEntry OBJECT-TYPE
   SYNTAX     MscDataSigChanEtsiRowStatusEntry
   ACCESS     not-accessible
   STATUS     mandatory
   DESCRIPTION
     "A single entry in the table represents a single 
      mscDataSigChanEtsi component."
   INDEX {
      mscDataSigChanIndex,
      mscDataSigChanEtsiIndex }
::= { mscDataSigChanEtsiRowStatusTable 1 }

MscDataSigChanEtsiRowStatusEntry ::= SEQUENCE {
   mscDataSigChanEtsiRowStatus
      RowStatus,
   mscDataSigChanEtsiComponentName
      DisplayString,
   mscDataSigChanEtsiStorageType
      StorageType,
   mscDataSigChanEtsiIndex
      NonReplicated }

mscDataSigChanEtsiRowStatus OBJECT-TYPE
   SYNTAX     RowStatus 
   ACCESS     read-write
   STATUS     mandatory
   DESCRIPTION
     "This variable is used as the basis for SNMP naming of
      mscDataSigChanEtsi components.
      These components can be added and deleted."
::= { mscDataSigChanEtsiRowStatusEntry 1 }

mscDataSigChanEtsiComponentName OBJECT-TYPE
   SYNTAX     DisplayString 
   ACCESS     read-only
   STATUS     mandatory
   DESCRIPTION
     "This variable provides the component's string name for
      use with the ASCII Console Interface"
::= { mscDataSigChanEtsiRowStatusEntry 2 }

mscDataSigChanEtsiStorageType OBJECT-TYPE
   SYNTAX     StorageType 
   ACCESS     read-only
   STATUS     mandatory
   DESCRIPTION
     "This variable represents the storage type value for the
      mscDataSigChanEtsi tables."
::= { mscDataSigChanEtsiRowStatusEntry 4 }

mscDataSigChanEtsiIndex OBJECT-TYPE
   SYNTAX     NonReplicated 
   ACCESS     not-accessible
   STATUS     mandatory
   DESCRIPTION
     "This variable represents the index for the mscDataSigChanEtsi tables."
::= { mscDataSigChanEtsiRowStatusEntry 10 }

mscDataSigChanEtsiL2Table OBJECT-TYPE
   SYNTAX     SEQUENCE OF MscDataSigChanEtsiL2Entry
   ACCESS     not-accessible
   STATUS     mandatory
   DESCRIPTION
     "This group represents the provisionable Layer 2 attributes of the 
      Q931 CCITT protocol."
::= { mscDataSigChanEtsi 11 }

mscDataSigChanEtsiL2Entry OBJECT-TYPE
   SYNTAX     MscDataSigChanEtsiL2Entry
   ACCESS     not-accessible
   STATUS     mandatory
   DESCRIPTION
     "An entry in the mscDataSigChanEtsiL2Table."
   INDEX {
      mscDataSigChanIndex,
      mscDataSigChanEtsiIndex }
::= { mscDataSigChanEtsiL2Table 1 }

MscDataSigChanEtsiL2Entry ::= SEQUENCE {
   mscDataSigChanEtsiT23
      Unsigned32,
   mscDataSigChanEtsiT200
      Unsigned32,
   mscDataSigChanEtsiN200
      Unsigned32,
   mscDataSigChanEtsiT203
      Unsigned32,
   mscDataSigChanEtsiN201
      Unsigned32,
   mscDataSigChanEtsiCircuitSwitchedK
      Unsigned32 }

mscDataSigChanEtsiT23 OBJECT-TYPE
   SYNTAX     Unsigned32 (1..15)
   ACCESS     read-write
   STATUS     mandatory
   DESCRIPTION
     "This attribute specifies the layer2 enable request timer."
   DEFVAL     { 10 }
::= { mscDataSigChanEtsiL2Entry 1 }

mscDataSigChanEtsiT200 OBJECT-TYPE
   SYNTAX     Unsigned32 (1..20)
   ACCESS     read-write
   STATUS     mandatory
   DESCRIPTION
     "This attribute specifies the maximum time between a layer 2 frame 
      and its acknowledgement"
   DEFVAL     { 2 }
::= { mscDataSigChanEtsiL2Entry 2 }

mscDataSigChanEtsiN200 OBJECT-TYPE
   SYNTAX     Unsigned32 (1..8)
   ACCESS     read-write
   STATUS     mandatory
   DESCRIPTION
     "This attribute specifies the maximum number of re-transmissions of 
      a layer2 frame."
   DEFVAL     { 3 }
::= { mscDataSigChanEtsiL2Entry 3 }

mscDataSigChanEtsiT203 OBJECT-TYPE
   SYNTAX     Unsigned32 (2..40)
   ACCESS     read-write
   STATUS     mandatory
   DESCRIPTION
     "This attribute specifies the maximum time that a no layer 2 traffic 
      situation can last. Expiry triggers a check on whether the far end is 
      a live."
   DEFVAL     { 10 }
::= { mscDataSigChanEtsiL2Entry 4 }

mscDataSigChanEtsiN201 OBJECT-TYPE
   SYNTAX     Unsigned32 (4..260)
   ACCESS     read-write
   STATUS     mandatory
   DESCRIPTION
     "This attribute specifies the maximum number of octets in an 
      information field."
   DEFVAL     { 260 }
::= { mscDataSigChanEtsiL2Entry 5 }

mscDataSigChanEtsiCircuitSwitchedK OBJECT-TYPE
   SYNTAX     Unsigned32 (1..632)
   ACCESS     read-write
   STATUS     mandatory
   DESCRIPTION
     "This attribute specifies the maximum number of frames for B 
      channel use."
   DEFVAL     { 7 }
::= { mscDataSigChanEtsiL2Entry 6 }

mscDataSigChanEtsiProvTable OBJECT-TYPE
   SYNTAX     SEQUENCE OF MscDataSigChanEtsiProvEntry
   ACCESS     not-accessible
   STATUS     mandatory
   DESCRIPTION
     "This group defines the general options of the d-channel signalling 
      link."
::= { mscDataSigChanEtsi 13 }

mscDataSigChanEtsiProvEntry OBJECT-TYPE
   SYNTAX     MscDataSigChanEtsiProvEntry
   ACCESS     not-accessible
   STATUS     mandatory
   DESCRIPTION
     "An entry in the mscDataSigChanEtsiProvTable."
   INDEX {
      mscDataSigChanIndex,
      mscDataSigChanEtsiIndex }
::= { mscDataSigChanEtsiProvTable 1 }

MscDataSigChanEtsiProvEntry ::= SEQUENCE {
   mscDataSigChanEtsiSide
      INTEGER }

mscDataSigChanEtsiSide OBJECT-TYPE
   SYNTAX     INTEGER  {
                 network(1),
                 user(2) }
   ACCESS     read-write
   STATUS     mandatory
   DESCRIPTION
     "This attribute specifies whether the layer 2 HDLC interface is the 
      network or user side of the connection."
   DEFVAL     { user }
::= { mscDataSigChanEtsiProvEntry 1 }

mscDataSigChanEtsiOperTable OBJECT-TYPE
   SYNTAX     SEQUENCE OF MscDataSigChanEtsiOperEntry
   ACCESS     not-accessible
   STATUS     mandatory
   DESCRIPTION
     "This group provides the operational attributes for the signalling 
      protocol."
::= { mscDataSigChanEtsi 15 }

mscDataSigChanEtsiOperEntry OBJECT-TYPE
   SYNTAX     MscDataSigChanEtsiOperEntry
   ACCESS     not-accessible
   STATUS     mandatory
   DESCRIPTION
     "An entry in the mscDataSigChanEtsiOperTable."
   INDEX {
      mscDataSigChanIndex,
      mscDataSigChanEtsiIndex }
::= { mscDataSigChanEtsiOperTable 1 }

MscDataSigChanEtsiOperEntry ::= SEQUENCE {
   mscDataSigChanEtsiActiveChannels
      Unsigned32,
   mscDataSigChanEtsiPeakActiveChannels
      Unsigned32,
   mscDataSigChanEtsiDChanStatus
      INTEGER }

mscDataSigChanEtsiActiveChannels OBJECT-TYPE
   SYNTAX     Unsigned32 (0..128)
   ACCESS     read-only
   STATUS     mandatory
   DESCRIPTION
     "This attribute indicates the number of currently active channels. 
      This includes data and voice channels."
   DEFVAL     { 0 }
::= { mscDataSigChanEtsiOperEntry 1 }

mscDataSigChanEtsiPeakActiveChannels OBJECT-TYPE
   SYNTAX     Unsigned32 (0..128)
   ACCESS     read-only
   STATUS     mandatory
   DESCRIPTION
     "This attribute indicates the maximum number of channels that have 
      been active on this signalling channel during the last polling period."
   DEFVAL     { 0 }
::= { mscDataSigChanEtsiOperEntry 4 }

mscDataSigChanEtsiDChanStatus OBJECT-TYPE
   SYNTAX     INTEGER  {
                 outOfService(0),
                 establishing(1),
                 established(2),
                 enabling(3),
                 inService(4),
                 restarting(5) }
   ACCESS     read-only
   STATUS     mandatory
   DESCRIPTION
     "This attribute indicates the state of the D-channel. 
      outOfService means that there is no layer 2 or layer 3 connectivity 
      to the PBX.
      establishing means that the signalling channel is attempting to stage 
      the layer 2.
      established means that the layer 2 is enabled. If the signalling 
      channel stays in the established state, then it is waiting for a restart 
      from the PBX.
      enabling means that the resources for processing calls are being 
      initialized. If the signalling channel stays in the enabling state then 
      it is waiting for a restart acknowledgement from the PBX. 
      inService means that the resources for processing calls are 
      available. 
      restarting means that the resources for call processing are being rei-
      initialized."
::= { mscDataSigChanEtsiOperEntry 7 }

mscDataSigChanEtsiToolsTable OBJECT-TYPE
   SYNTAX     SEQUENCE OF MscDataSigChanEtsiToolsEntry
   ACCESS     not-accessible
   STATUS     mandatory
   DESCRIPTION
     "This group contains a series of operational attributes which turn on 
      and off several kinds of tracing."
::= { mscDataSigChanEtsi 16 }

mscDataSigChanEtsiToolsEntry OBJECT-TYPE
   SYNTAX     MscDataSigChanEtsiToolsEntry
   ACCESS     not-accessible
   STATUS     mandatory
   DESCRIPTION
     "An entry in the mscDataSigChanEtsiToolsTable."
   INDEX {
      mscDataSigChanIndex,
      mscDataSigChanEtsiIndex }
::= { mscDataSigChanEtsiToolsTable 1 }

MscDataSigChanEtsiToolsEntry ::= SEQUENCE {
   mscDataSigChanEtsiTracing
      OCTET STRING }

mscDataSigChanEtsiTracing OBJECT-TYPE
   SYNTAX     OCTET STRING (SIZE (1))
   ACCESS     read-write
   STATUS     mandatory
   DESCRIPTION
     "This attribute defines which types of tracing are active for this 
      signalling channel.  The tracing messages are sent to the debug 
      stream. To see the messages the agentQueue attribute in Col/debug 
      must be greater than 0 and a Telnet NMIS session must list the 
      debug stream in in its data streams (ex. set nmis telnet session/1 
      dataStreams debug). Different types of tracing can be enabled 
      simultaneously. 
      Note that tracing consumes additional CPU resources and will slow 
      down call processing on a heavily loaded card.  If there is message 
      block exhaustion tracing will be suspended for a period and then 
      automatically reenabled.  An alarm is generated on tracing 
      suspension and resumption.  This mechanism protects the function 
      processor against excessive numbers of tracing messages.
      
      Types of tracing include: 
      protocolErrors - get details of any protocol errors which are 
      occuring. Protocol errors are also reported in summary form as 
      alarms. 
      q931Summary - Summary of the Q.931 messages on the signalling 
      link, including certain call details (calling number, called number, 
      release codes). 
      q931Hex - Q.931 messages displayed in hex format.  Useful to 
      determine protocol compliance in case of errors reported on local or 
      remote ends.
      q931Symbolic - Q.931 messages parsed to give maximum detail.  
      Useful for understanding content of messages flowing on the link.
      portHex - Messages in hex format being sent and received on the 
      link.

      Description of bits:
      protocolErrors(0)
      q931Summary(1)
      q931Hex(2)
      q931Symbolic(3)
      portHex(4)"
::= { mscDataSigChanEtsiToolsEntry 1 }


-- 
-- DataSigChan/n ts014 Framer
-- 
-- The Framer component controls link layer framing for application 
-- components sending and receiving data on a link interface. It is also 
-- through Framer, that an application component is associated with a 
-- specific hardware link interface.
-- 
-- The Framer component provides provisionable attributes related to 
-- datapath aspects of the hardware interface (such as crc and frame 
-- length). The Framer component also provides a provisionable 
-- attribute which binds the application component to a specific 
-- hardware component.
-- 
-- The Framer component contains operational attributes for link 
-- interface datapath statistics (such as frame counts and aborts).
-- 

mscDataSigChanEtsiFramer OBJECT IDENTIFIER ::= { mscDataSigChanEtsi 2 }



mscDataSigChanEtsiFramerRowStatusTable OBJECT-TYPE
   SYNTAX     SEQUENCE OF MscDataSigChanEtsiFramerRowStatusEntry
   ACCESS     not-accessible
   STATUS     mandatory
   DESCRIPTION
     "This entry controls the addition and deletion of 
      mscDataSigChanEtsiFramer components."
::= { mscDataSigChanEtsiFramer 1 }

mscDataSigChanEtsiFramerRowStatusEntry OBJECT-TYPE
   SYNTAX     MscDataSigChanEtsiFramerRowStatusEntry
   ACCESS     not-accessible
   STATUS     mandatory
   DESCRIPTION
     "A single entry in the table represents a single 
      mscDataSigChanEtsiFramer component."
   INDEX {
      mscDataSigChanIndex,
      mscDataSigChanEtsiIndex,
      mscDataSigChanEtsiFramerIndex }
::= { mscDataSigChanEtsiFramerRowStatusTable 1 }

MscDataSigChanEtsiFramerRowStatusEntry ::= SEQUENCE {
   mscDataSigChanEtsiFramerRowStatus
      RowStatus,
   mscDataSigChanEtsiFramerComponentName
      DisplayString,
   mscDataSigChanEtsiFramerStorageType
      StorageType,
   mscDataSigChanEtsiFramerIndex
      NonReplicated }

mscDataSigChanEtsiFramerRowStatus OBJECT-TYPE
   SYNTAX     RowStatus 
   ACCESS     read-only
   STATUS     mandatory
   DESCRIPTION
     "This variable is used as the basis for SNMP naming of
      mscDataSigChanEtsiFramer components.
      These components cannot be added nor deleted."
::= { mscDataSigChanEtsiFramerRowStatusEntry 1 }

mscDataSigChanEtsiFramerComponentName OBJECT-TYPE
   SYNTAX     DisplayString 
   ACCESS     read-only
   STATUS     mandatory
   DESCRIPTION
     "This variable provides the component's string name for
      use with the ASCII Console Interface"
::= { mscDataSigChanEtsiFramerRowStatusEntry 2 }

mscDataSigChanEtsiFramerStorageType OBJECT-TYPE
   SYNTAX     StorageType 
   ACCESS     read-only
   STATUS     mandatory
   DESCRIPTION
     "This variable represents the storage type value for the
      mscDataSigChanEtsiFramer tables."
::= { mscDataSigChanEtsiFramerRowStatusEntry 4 }

mscDataSigChanEtsiFramerIndex OBJECT-TYPE
   SYNTAX     NonReplicated 
   ACCESS     not-accessible
   STATUS     mandatory
   DESCRIPTION
     "This variable represents the index for the mscDataSigChanEtsiFramer tables."
::= { mscDataSigChanEtsiFramerRowStatusEntry 10 }

mscDataSigChanEtsiFramerProvTable OBJECT-TYPE
   SYNTAX     SEQUENCE OF MscDataSigChanEtsiFramerProvEntry
   ACCESS     not-accessible
   STATUS     mandatory
   DESCRIPTION
     "This group contains the base provisioning data for the Framer 
      component. Application or hardware interface specific provisioning 
      data is contained in other provisionable Framer groups."
::= { mscDataSigChanEtsiFramer 10 }

mscDataSigChanEtsiFramerProvEntry OBJECT-TYPE
   SYNTAX     MscDataSigChanEtsiFramerProvEntry
   ACCESS     not-accessible
   STATUS     mandatory
   DESCRIPTION
     "An entry in the mscDataSigChanEtsiFramerProvTable."
   INDEX {
      mscDataSigChanIndex,
      mscDataSigChanEtsiIndex,
      mscDataSigChanEtsiFramerIndex }
::= { mscDataSigChanEtsiFramerProvTable 1 }

MscDataSigChanEtsiFramerProvEntry ::= SEQUENCE {
   mscDataSigChanEtsiFramerInterfaceName
      Link }

mscDataSigChanEtsiFramerInterfaceName OBJECT-TYPE
   SYNTAX     Link 
   ACCESS     read-write
   STATUS     mandatory
   DESCRIPTION
     "This attribute contains a hardware component name.
      
      The attribute associates the application with a specific link. This 
      defines the module processor on which Framer's parent component 
      (as well as Framer itself) will run."
::= { mscDataSigChanEtsiFramerProvEntry 1 }

mscDataSigChanEtsiFramerStateTable OBJECT-TYPE
   SYNTAX     SEQUENCE OF MscDataSigChanEtsiFramerStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { mscDataSigChanEtsiFramer 12 }

mscDataSigChanEtsiFramerStateEntry OBJECT-TYPE
   SYNTAX     MscDataSigChanEtsiFramerStateEntry
   ACCESS     not-accessible
   STATUS     mandatory
   DESCRIPTION
     "An entry in the mscDataSigChanEtsiFramerStateTable."
   INDEX {
      mscDataSigChanIndex,
      mscDataSigChanEtsiIndex,
      mscDataSigChanEtsiFramerIndex }
::= { mscDataSigChanEtsiFramerStateTable 1 }

MscDataSigChanEtsiFramerStateEntry ::= SEQUENCE {
   mscDataSigChanEtsiFramerAdminState
      INTEGER,
   mscDataSigChanEtsiFramerOperationalState
      INTEGER,
   mscDataSigChanEtsiFramerUsageState
      INTEGER }

mscDataSigChanEtsiFramerAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { mscDataSigChanEtsiFramerStateEntry 1 }

mscDataSigChanEtsiFramerOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { mscDataSigChanEtsiFramerStateEntry 2 }

mscDataSigChanEtsiFramerUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { mscDataSigChanEtsiFramerStateEntry 3 }

mscDataSigChanEtsiFramerStatsTable OBJECT-TYPE
   SYNTAX     SEQUENCE OF MscDataSigChanEtsiFramerStatsEntry
   ACCESS     not-accessible
   STATUS     mandatory
   DESCRIPTION
     "This group contains the operational statistics data for a Framer 
      component."
::= { mscDataSigChanEtsiFramer 13 }

mscDataSigChanEtsiFramerStatsEntry OBJECT-TYPE
   SYNTAX     MscDataSigChanEtsiFramerStatsEntry
   ACCESS     not-accessible
   STATUS     mandatory
   DESCRIPTION
     "An entry in the mscDataSigChanEtsiFramerStatsTable."
   INDEX {
      mscDataSigChanIndex,
      mscDataSigChanEtsiIndex,
      mscDataSigChanEtsiFramerIndex }
::= { mscDataSigChanEtsiFramerStatsTable 1 }

MscDataSigChanEtsiFramerStatsEntry ::= SEQUENCE {
   mscDataSigChanEtsiFramerFrmToIf
      Unsigned32,
   mscDataSigChanEtsiFramerFrmFromIf
      Unsigned32,
   mscDataSigChanEtsiFramerOctetFromIf
      Unsigned32,
   mscDataSigChanEtsiFramerAborts
      Unsigned32,
   mscDataSigChanEtsiFramerCrcErrors
      Unsigned32,
   mscDataSigChanEtsiFramerLrcErrors
      Unsigned32,
   mscDataSigChanEtsiFramerNonOctetErrors
      Unsigned32,
   mscDataSigChanEtsiFramerOverruns
      Unsigned32,
   mscDataSigChanEtsiFramerUnderruns
      Unsigned32,
   mscDataSigChanEtsiFramerLargeFrmErrors
      Unsigned32 }

mscDataSigChanEtsiFramerFrmToIf OBJECT-TYPE
   SYNTAX     Unsigned32 (0..4294967295)
   ACCESS     read-only
   STATUS     mandatory
   DESCRIPTION
     "This attribute counts the number of frames transmitted to the link 
      interface by Framer.
      This count wraps to zero after reaching its maximum value."
   DEFVAL     { 0 }
::= { mscDataSigChanEtsiFramerStatsEntry 1 }

mscDataSigChanEtsiFramerFrmFromIf OBJECT-TYPE
   SYNTAX     Unsigned32 (0..4294967295)
   ACCESS     read-only
   STATUS     mandatory
   DESCRIPTION
     "This attribute counts the number of frames received from the link 
      interface by Framer.
      This count wraps to zero after reaching its maximum value."
   DEFVAL     { 0 }
::= { mscDataSigChanEtsiFramerStatsEntry 2 }

mscDataSigChanEtsiFramerOctetFromIf OBJECT-TYPE
   SYNTAX     Unsigned32 (0..4294967295)
   ACCESS     read-only
   STATUS     mandatory
   DESCRIPTION
     "The number of bytes received from the link interface by Framer."
   DEFVAL     { 0 }
::= { mscDataSigChanEtsiFramerStatsEntry 3 }

mscDataSigChanEtsiFramerAborts OBJECT-TYPE
   SYNTAX     Unsigned32 (0..4294967295)
   ACCESS     read-only
   STATUS     mandatory
   DESCRIPTION
     "This attribute counts the total number of aborts received.
      This count wraps to zero after reaching its maximum value."
   DEFVAL     { 0 }
::= { mscDataSigChanEtsiFramerStatsEntry 4 }

mscDataSigChanEtsiFramerCrcErrors OBJECT-TYPE
   SYNTAX     Unsigned32 (0..4294967295)
   ACCESS     read-only
   STATUS     mandatory
   DESCRIPTION
     "This attribute counts the total number of frames with CRC errors.
      This count wraps to zero after reaching its maximum value."
   DEFVAL     { 0 }
::= { mscDataSigChanEtsiFramerStatsEntry 5 }

mscDataSigChanEtsiFramerLrcErrors OBJECT-TYPE
   SYNTAX     Unsigned32 (0..4294967295)
   ACCESS     read-only
   STATUS     mandatory
   DESCRIPTION
     "This attribute counts the total number of frames with LRC errors.
      This count wraps to zero after reaching its maximum value."
   DEFVAL     { 0 }
::= { mscDataSigChanEtsiFramerStatsEntry 6 }

mscDataSigChanEtsiFramerNonOctetErrors OBJECT-TYPE
   SYNTAX     Unsigned32 (0..4294967295)
   ACCESS     read-only
   STATUS     mandatory
   DESCRIPTION
     "This attribute counts the total number of frames that were non octet 
      aligned.
      This count wraps to zero after reaching its maximum value."
   DEFVAL     { 0 }
::= { mscDataSigChanEtsiFramerStatsEntry 7 }

mscDataSigChanEtsiFramerOverruns OBJECT-TYPE
   SYNTAX     Unsigned32 (0..4294967295)
   ACCESS     read-only
   STATUS     mandatory
   DESCRIPTION
     "This attribute counts the total number of frames received from the 
      link for which overruns occurred.
      This count wraps to zero after reaching its maximum value."
   DEFVAL     { 0 }
::= { mscDataSigChanEtsiFramerStatsEntry 8 }

mscDataSigChanEtsiFramerUnderruns OBJECT-TYPE
   SYNTAX     Unsigned32 (0..4294967295)
   ACCESS     read-only
   STATUS     mandatory
   DESCRIPTION
     "This attribute counts the total number of frames transmitted to the 
      link for which underruns occurred.
      This count wraps to zero after reaching its maximum value."
   DEFVAL     { 0 }
::= { mscDataSigChanEtsiFramerStatsEntry 9 }

mscDataSigChanEtsiFramerLargeFrmErrors OBJECT-TYPE
   SYNTAX     Unsigned32 (0..4294967295)
   ACCESS     read-only
   STATUS     mandatory
   DESCRIPTION
     "This attribute counts the total number of frames received which 
      were too large. The frame was longer than 500 bytes.
      This count wraps to zero after reaching its maximum value."
   DEFVAL     { 0 }
::= { mscDataSigChanEtsiFramerStatsEntry 10 }




-- 
-- Version and Compliance statements
-- 



-- Object-Group Statement:
-- A list of all current accessible leaf objects.

-- OBJECTS { mscDataSigChanEtsiFramerComponentName,
--           mscDataSigChanEtsiN200,
--           mscDataSigChanEtsiSide,
--           mscDataSigChanEtsiFramerInterfaceName,
--           mscDataSigChanEtsiComponentName,
--           mscDataSigChanEtsiT23,
--           mscDataSigChanEtsiFramerOverruns,
--           mscDataSigChanEtsiFramerUnderruns,
--           mscDataSigChanEtsiFramerCrcErrors,
--           mscDataSigChanEtsiStorageType,
--           mscDataSigChanEtsiFramerRowStatus,
--           mscDataSigChanEtsiTracing,
--           mscDataSigChanEtsiT200,
--           mscDataSigChanEtsiFramerStorageType,
--           mscDataSigChanEtsiFramerOctetFromIf,
--           mscDataSigChanEtsiT203,
--           mscDataSigChanEtsiFramerFrmFromIf,
--           mscDataSigChanEtsiDChanStatus,
--           mscDataSigChanEtsiFramerAdminState,
--           mscDataSigChanEtsiFramerLrcErrors,
--           mscDataSigChanEtsiFramerLargeFrmErrors,
--           mscDataSigChanEtsiActiveChannels,
--           mscDataSigChanEtsiFramerAborts,
--           mscDataSigChanEtsiRowStatus,
--           mscDataSigChanEtsiN201,
--           mscDataSigChanEtsiFramerFrmToIf,
--           mscDataSigChanEtsiFramerNonOctetErrors,
--           mscDataSigChanEtsiPeakActiveChannels,
--           mscDataSigChanEtsiCircuitSwitchedK,
--           mscDataSigChanEtsiFramerUsageState,
--           mscDataSigChanEtsiFramerOperationalState }
-- STATUS  mandatory
-- DESCRIPTION
--   "A list of all current accessible leaf objects."

disdnETSIGroup OBJECT IDENTIFIER ::= { disdnETSIMIB 1 }
disdnETSIGroupCA OBJECT IDENTIFIER ::= { disdnETSIGroup 1 }
disdnETSIGroupCA02 OBJECT IDENTIFIER ::= { disdnETSIGroupCA 3 }
disdnETSIGroupCA02A OBJECT IDENTIFIER ::= { disdnETSIGroupCA02 2 }



-- Agent-Capabilities Statement:

-- PRODUCT-RELEASE "MscPassport Release 1.2 DisdnETSI."
-- STATUS          mandatory
-- DESCRIPTION     "Carrier Passport DisdnETSI MIB: MIB Version CA02A,
--                  Software Version CA02S9C."
-- SUPPORTS        Nortel-MsCarrier-MscPassport-DisdnETSIMIB
--    INCLUDES     { disdnETSIGroupCA02A }

disdnETSICapabilities OBJECT IDENTIFIER ::= { disdnETSIMIB 3 }
disdnETSICapabilitiesCA OBJECT IDENTIFIER ::= { disdnETSICapabilities 1 }
disdnETSICapabilitiesCA02 OBJECT IDENTIFIER ::= { disdnETSICapabilitiesCA 3 }
disdnETSICapabilitiesCA02A OBJECT IDENTIFIER ::= { disdnETSICapabilitiesCA02 2 }





END
