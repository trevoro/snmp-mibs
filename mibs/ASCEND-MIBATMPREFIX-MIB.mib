--			Ascend mibatmprefix MIB
--
--			Ascend Communications, Inc
--			1275 Harbor Bay Pkwy
--			Alameda, CA 94502
--			+1 510 769 6001
--			info@ascend.com
--
-- Copyright (c) 1993-1999 Ascend Communications, Inc.
-- All rights reserved.
--
-- Do not edit this file directly.
-- It is generated automatically by mibgen for use with
-- TAOS version 10.0.1 or newer.
--

ASCEND-MIBATMPREFIX-MIB DEFINITIONS ::= BEGIN

    IMPORTS

        configuration
            FROM ASCEND-MIB
	IpAddress
	    FROM RFC1155-SMI
	OBJECT-TYPE
	    FROM RFC-1212;

	-- If any of the MIB compilers have problems with the DisplayString
	-- or PhysAddress, uncomment the next two lines.

    DisplayString	::=	OCTET STRING
    -- PhysAddress	::=	OCTET STRING

    mibatmPrefixProfile  OBJECT IDENTIFIER ::= { configuration 22}

	-- The mibatmPrefixProfile table
	--
	-- This table contains parameters for the mibatmPrefixProfile profile
	--

    mibatmPrefixProfileTable	OBJECT-TYPE
	SYNTAX		SEQUENCE OF MibatmPrefixProfileEntry
	ACCESS		not-accessible
	STATUS		mandatory
	DESCRIPTION	"A list of mibatmPrefixProfile profile entries."
	::= { mibatmPrefixProfile 1 }

    mibatmPrefixProfileEntry	OBJECT-TYPE
	SYNTAX		MibatmPrefixProfileEntry
	ACCESS		not-accessible
	STATUS		mandatory
	DESCRIPTION	"A mibatmPrefixProfile entry containing objects that
			 maps to the parameters of mibatmPrefixProfile profile."
	INDEX		{ atmPrefixProfile-PrefixName }
	::= { mibatmPrefixProfileTable 1 }

    MibatmPrefixProfileEntry ::=
	SEQUENCE {
	    atmPrefixProfile-PrefixName
		DisplayString,
	    atmPrefixProfile-UseShortAddress
		INTEGER,
	    atmPrefixProfile-PnniNodePrefix-Length
		INTEGER,
	    atmPrefixProfile-PnniNodePrefix-Address
		DisplayString,
	    atmPrefixProfile-SpvcAddressPrefix-Length
		INTEGER,
	    atmPrefixProfile-SpvcAddressPrefix-Address
		DisplayString,
	    atmPrefixProfile-SvcAddressPrefix-Length
		INTEGER,
	    atmPrefixProfile-SvcAddressPrefix-Address
		DisplayString,
	    atmPrefixProfile-Action-o
		INTEGER
	}

    atmPrefixProfile-PrefixName	OBJECT-TYPE
	SYNTAX	DisplayString
	ACCESS	read-only
	STATUS	mandatory
	DESCRIPTION	"The name of the ATM Address Prefix Profile."
	::= { mibatmPrefixProfileEntry 1 }

    atmPrefixProfile-UseShortAddress	OBJECT-TYPE
	SYNTAX	INTEGER {
		    no (1),
		    yes (2)
		}
	ACCESS	read-write
	STATUS	mandatory
	DESCRIPTION	"Applies to default address generated using this profile's prefix. Flag == NO (default) value means, default address generated will always be 20 byte long. FLAG == YES value means, default address generated could be less than 20 byte. Also algorithm used to generate is different based on this flag's value. use-short-address == FALSE, in NSAP structure, ESI byte is coded as follows. FF MSB MSB-1 MSB-2 LSB PortNumber. In case short-flag == TRUE, in NSAP structure, immediately after Prefix length, following 8 bits are used for the slot number and subsequent 8 bits are used for the port number."
	::= { mibatmPrefixProfileEntry 2 }

    atmPrefixProfile-PnniNodePrefix-Length	OBJECT-TYPE
	SYNTAX	INTEGER
	ACCESS	read-write
	STATUS	mandatory
	DESCRIPTION	"Length of the prefix in number of bytes."
	::= { mibatmPrefixProfileEntry 3 }

    atmPrefixProfile-PnniNodePrefix-Address	OBJECT-TYPE
	SYNTAX	DisplayString
	ACCESS	read-write
	STATUS	mandatory
	DESCRIPTION	"The prefix value."
	::= { mibatmPrefixProfileEntry 4 }

    atmPrefixProfile-SpvcAddressPrefix-Length	OBJECT-TYPE
	SYNTAX	INTEGER
	ACCESS	read-write
	STATUS	mandatory
	DESCRIPTION	"Length of the prefix in number of bytes."
	::= { mibatmPrefixProfileEntry 5 }

    atmPrefixProfile-SpvcAddressPrefix-Address	OBJECT-TYPE
	SYNTAX	DisplayString
	ACCESS	read-write
	STATUS	mandatory
	DESCRIPTION	"The prefix value."
	::= { mibatmPrefixProfileEntry 6 }

    atmPrefixProfile-SvcAddressPrefix-Length	OBJECT-TYPE
	SYNTAX	INTEGER
	ACCESS	read-write
	STATUS	mandatory
	DESCRIPTION	"Length of the prefix in number of bytes."
	::= { mibatmPrefixProfileEntry 7 }

    atmPrefixProfile-SvcAddressPrefix-Address	OBJECT-TYPE
	SYNTAX	DisplayString
	ACCESS	read-write
	STATUS	mandatory
	DESCRIPTION	"The prefix value."
	::= { mibatmPrefixProfileEntry 8 }

    atmPrefixProfile-Action-o	OBJECT-TYPE
	SYNTAX	INTEGER {
		    noAction (1),
		    createProfile (2),
		    deleteProfile (3)
		}
	ACCESS	read-write
	STATUS	mandatory
	DESCRIPTION	""
	::= { mibatmPrefixProfileEntry 9 }

END
