-- ----------------------------------------------------------------------------
--                  HUAWEI MUSA Enterprise MIB   
--                                       MusaSys MIB 
--      Copyright (c) 1999-2002 HUA WEI TECH CO.,LTD,SHENZHEN.
--      All rights reserved.
--  Create date: 02-03-08
-- ----------------------------------------------------------------------------

HUAWEI-MUSA-MA5100-CONFMIB DEFINITIONS ::= BEGIN
IMPORTS
        IpAddress,Counter
                        FROM RFC1155-SMI
        OBJECT-TYPE
                        FROM RFC-1212                
        musa
                        FROM HUAWEI-MIB;
    
    DisplayString ::= OCTET STRING                  
    
    hwMa5100Mib     OBJECT IDENTIFIER ::= { musa 5 }
    hwMusaSysMib    OBJECT IDENTIFIER ::= { hwMa5100Mib 1 } 
    hwMusaEndOfMib  OBJECT IDENTIFIER ::= { hwMa5100Mib 100 } 



    -- -------------------------------------------------------------------------
    --  机架、框、槽描述表
    -- ------------------------------------------------------------------------- 
    hwMusaSlotGroup OBJECT IDENTIFIER ::= { hwMusaSysMib  6 }
    hwMusaFrame     OBJECT IDENTIFIER ::= { hwMusaSlotGroup 2 }
    hwMusaSlot      OBJECT IDENTIFIER ::= { hwMusaSlotGroup 3 }
    
    
   -- ----------------------------------------------------------------------------
   -- 机框信息表
   -- ----------------------------------------------------------------------------
   hwMusaFrameNumber    OBJECT-TYPE
        SYNTAX      INTEGER
        ACCESS      read-only
        STATUS      mandatory
    DESCRIPTION  
    "Musa frame numbers."
    ::= { hwMusaFrame 1 }
    
    hwMusaFrameConfTable    OBJECT-TYPE
        SYNTAX      SEQUENCE OF HwMusaFrameConfEntry
        ACCESS      not-accessible
        STATUS      mandatory
    DESCRIPTION  
    "This table contains Musa Frame configuration parameters."
    ::= { hwMusaFrame 2 }

    hwMusaFrameConfEntry    OBJECT-TYPE
        SYNTAX         HwMusaFrameConfEntry
        ACCESS         not-accessible
        STATUS         mandatory
    DESCRIPTION
    "This list contains Musa Frame configuration parameters and status variables.
    MUSA设备机框配置描述表."
    INDEX { hwMusaShelfIndex,
            hwMusaFrameIndex }
    ::= { hwMusaFrameConfTable  1}
    
   HwMusaFrameConfEntry    ::= SEQUENCE  {
            hwMusaFrameIndex                    INTEGER
            }
            
   hwMusaFrameIndex OBJECT-TYPE
        SYNTAX     INTEGER
        ACCESS     not-accessible
        STATUS     mandatory
    DESCRIPTION
    "the Musa Frame number. 
    框号索引"
    ::= { hwMusaFrameConfEntry 1}
    
    hwMusaSlotConfTable    OBJECT-TYPE
        SYNTAX      SEQUENCE OF HwMusaSlotConfEntry
        ACCESS      not-accessible
        STATUS      mandatory
    DESCRIPTION  
    "This table contains Musa slot configuration
     parameters, one entry per Musa slot."
    ::= { hwMusaSlot 2 }

   hwMusaSlotConfEntry    OBJECT-TYPE
        SYNTAX         HwMusaSlotConfEntry
        ACCESS         not-accessible
        STATUS         mandatory
    DESCRIPTION
    "This list contains Musa slot configuration parameters and status variables.
    MUSA设备槽位配置描述表."
    INDEX { 
            hwMusaFrameIndex,
            hwMusaSlotIndex }
    ::= { hwMusaSlotConfTable  1}
    
    HwMusaSlotConfEntry    ::= SEQUENCE  {
            hwMusaSlotIndex             INTEGER
            				}
            				
    hwMusaSlotIndex  OBJECT-TYPE
        SYNTAX     INTEGER(0..15)
        ACCESS     not-accessible
        STATUS     mandatory
    DESCRIPTION
    "the Musa slot number. 槽位号"
    ::= { hwMusaSlotConfEntry 1 }            				
    
    -- ------------------------------------------------------------------------
    -- 小区PVC表 (adl-lan)
    -- ------------------------------------------------------------------------
    hwMusaRegionPvcConfTable    OBJECT-TYPE
        SYNTAX      SEQUENCE OF HwMusaRegionPvcConfEntry
        ACCESS      not-accessible
        STATUS      mandatory
    DESCRIPTION
    "Musa region pvc configuration table."
    ::= { hwMusaSysMib 15 }

   hwMusaRegionPvcConfEntry    OBJECT-TYPE
        SYNTAX         HwMusaRegionPvcConfEntry
        ACCESS         not-accessible
        STATUS         mandatory
    DESCRIPTION
    "This list contains Musa region pvc Configuration
     parameters and variables."
    INDEX       { 
                hwMusaFrameIndex, 
                hwMusaSlotIndex,
                hwMusaVlanId,
                hwMusaVlanIciIndex
                }
    ::= { hwMusaRegionPvcConfTable  1 }

   HwMusaRegionPvcConfEntry    ::= SEQUENCE  {
            hwMusaVlanId                INTEGER,
            hwMusaVlanIciIndex          INTEGER,
            hwMusaAdlFrameId            INTEGER,
            hwMusaAdlSlotId             INTEGER,
            hwMusaAdlPortId             INTEGER,
            hwMusaAdlVpi                INTEGER,
            hwMusaAdlVci                INTEGER,
            hwMusaToLanTrafficId        INTEGER,
            hwMusaFromLanTrafficId      INTEGER,
            hwMusaAdlPortOperat         INTEGER
          }

    hwMusaVlanId    OBJECT-TYPE
        SYNTAX          INTEGER(1..63)
        ACCESS          read-only
        STATUS          mandatory
    DESCRIPTION
    "Musa region VLan Id.
    本小区VLAN ID。"
    ::= { hwMusaRegionPvcConfEntry  1 }   
    
    hwMusaVlanIciIndex    OBJECT-TYPE
        SYNTAX          INTEGER
        ACCESS          read-only
        STATUS          mandatory
    DESCRIPTION
    "Musa region VLanIciIndex.
    本小区VLAN 内部索引。"
    ::= { hwMusaRegionPvcConfEntry  2 }   
    
    hwMusaAdlFrameId    OBJECT-TYPE
        SYNTAX          INTEGER(0..4)
        ACCESS          read-write
        STATUS          mandatory
    DESCRIPTION
    "Musa region ADL frame ID.
    小区PVC的ADL框号"
    ::= { hwMusaRegionPvcConfEntry  4 }       
    
    hwMusaAdlSlotId    OBJECT-TYPE
        SYNTAX          INTEGER(1..15)
        ACCESS          read-write
        STATUS          mandatory
    DESCRIPTION
    "Musa region ADL slot ID.
    小区PVC的ADL槽号"
    ::= { hwMusaRegionPvcConfEntry  5 }
    
    hwMusaAdlPortId    OBJECT-TYPE
        SYNTAX          INTEGER(0..15)
        ACCESS          read-write
        STATUS          mandatory
    DESCRIPTION
    "Musa region ADL port ID.
    小区PVC的ADL端口号"
    ::= { hwMusaRegionPvcConfEntry  6 }                           

    hwMusaAdlVpi    OBJECT-TYPE
        SYNTAX          INTEGER(0..127)
        ACCESS          read-only
        STATUS          mandatory
    DESCRIPTION
    "Musa region VPI.
    小区PVC的VPI"
    ::= { hwMusaRegionPvcConfEntry  7 }       

    hwMusaAdlVci    OBJECT-TYPE
        SYNTAX          INTEGER(32..127)
        ACCESS          read-only
        STATUS          mandatory
    DESCRIPTION
    "Musa region VCI.
    小区PVC的VCI"
    ::= { hwMusaRegionPvcConfEntry  8 }       

    hwMusaToLanTrafficId    OBJECT-TYPE
        SYNTAX          INTEGER
        ACCESS          read-write
        STATUS          mandatory
    DESCRIPTION
    "Musa region to lan board traffic index.
    往LAN板的流量表号"
    ::= { hwMusaRegionPvcConfEntry  9 }       

    hwMusaFromLanTrafficId    OBJECT-TYPE
        SYNTAX          INTEGER
        ACCESS          read-write
        STATUS          mandatory
    DESCRIPTION
    "Musa region from lan board traffic index.
    来自LAN板的流量表号"
    ::= { hwMusaRegionPvcConfEntry  10 }  

    hwMusaAdlPortOperat    OBJECT-TYPE
        SYNTAX          INTEGER
                        {
                        add(0),
                        del(1)
                        }
        ACCESS          read-write
        STATUS          mandatory
    DESCRIPTION
    "Musa region ADL Operat.
    小区模式ADL端口的操作。"
    ::= { hwMusaRegionPvcConfEntry  11 }   
    
   -- ******************************************************************
   -- 总PVC表
   -- ******************************************************************

   hwMusaAllPvcConfTable   OBJECT-TYPE
       SYNTAX      SEQUENCE OF HwMusaAllPvcConfEntry
       ACCESS      not-accessible
       STATUS      mandatory
   DESCRIPTION
    "The  config talbe of all kinds of PVC."
   ::= { hwMusaSysMib 22 }
   
   hwMusaAllPvcConfEntry   OBJECT-TYPE
       SYNTAX      HwMusaAllPvcConfEntry
       ACCESS      not-accessible
       STATUS      mandatory
   DESCRIPTION
    "This lists config variables of all kinds of PVC."
   INDEX {  hwMusaTypeOfPvcPvpindex,
            hwMusaCidIndex }
   ::= { hwMusaAllPvcConfTable 1 }
   
   HwMusaAllPvcConfEntry   ::= SEQUENCE  {
             hwMusaCidIndex                  Counter,
             hwMusaSrcFrameId                INTEGER,
             hwMuasSrcSlotId                 INTEGER,
             hwMusaSrcPortVlanVccId          INTEGER,
             hwMusaSrcBoardVpi               INTEGER,
             hwMusaSrcBoardVci               INTEGER,
             hwMusaSrcUpcEpdPpd              INTEGER,
             hwMusaDestFrameId               INTEGER,
             hwMusaDestSlotId                INTEGER,
             hwMusaDestPortVlanVccId         INTEGER,
             hwMusaDestBoardVpi              INTEGER,
             hwMusaDestBoardVci              INTEGER,
             hwMusaDestUpcEpdPpd             INTEGER,
             hwMusaSrcToDestTraffic          INTEGER,
             hwMusaDestToSrcTraffic          INTEGER,
             hwMusaAllPvcOperater            INTEGER,
             hwMusaTypeOfPvcPvpindex         INTEGER,
             hwMusaPvcPvpState               INTEGER
             }
   
    hwMusaCidIndex    OBJECT-TYPE
        SYNTAX          Counter
        ACCESS          read-only
        STATUS          mandatory
    DESCRIPTION
    "The CID index."
    ::= { hwMusaAllPvcConfEntry  1 }
    
    hwMusaSrcFrameId    OBJECT-TYPE
        SYNTAX          INTEGER
        ACCESS          read-write
        STATUS          mandatory
    DESCRIPTION
    "The Frame id of source board."
    ::= { hwMusaAllPvcConfEntry  2 }
    
    hwMuasSrcSlotId    OBJECT-TYPE
        SYNTAX          INTEGER
        ACCESS          read-write
        STATUS          mandatory
    DESCRIPTION
    "The slot id of source board."
    ::= { hwMusaAllPvcConfEntry  3 }
    
    hwMusaSrcPortVlanVccId    OBJECT-TYPE
        SYNTAX          INTEGER
        ACCESS          read-write
        STATUS          mandatory
    DESCRIPTION
    "The Port/VlanID/VCC Index of source board."
    ::= { hwMusaAllPvcConfEntry  4 }
    
    hwMusaSrcBoardVpi    OBJECT-TYPE
        SYNTAX          INTEGER
        ACCESS          read-write
        STATUS          mandatory
    DESCRIPTION
    "Src board Port vpi Index."
    ::= { hwMusaAllPvcConfEntry  6 }   

    hwMusaSrcBoardVci    OBJECT-TYPE
        SYNTAX          INTEGER
        ACCESS          read-write
        STATUS          mandatory
    DESCRIPTION
    "Src board VCI Index."
    ::= { hwMusaAllPvcConfEntry  7 }
        
   hwMusaSrcUpcEpdPpd  OBJECT-TYPE
        SYNTAX  INTEGER
        ACCESS  read-write
        STATUS  mandatory
        DESCRIPTION
        "The flow control parameter of connection."
    ::= { hwMusaAllPvcConfEntry 16 } 
    
   hwMusaDestFrameId    OBJECT-TYPE
        SYNTAX          INTEGER
        ACCESS          read-write
        STATUS          mandatory
    DESCRIPTION
    "Destination frame Index."
    ::= { hwMusaAllPvcConfEntry  20 }
   
   hwMusaDestSlotId    OBJECT-TYPE
        SYNTAX          INTEGER
        ACCESS          read-write
        STATUS          mandatory
    DESCRIPTION
    "Destination slot Index."
    ::= { hwMusaAllPvcConfEntry  21 }
    
   hwMusaDestPortVlanVccId    OBJECT-TYPE
        SYNTAX          INTEGER
        ACCESS          read-write
        STATUS          mandatory
    DESCRIPTION
    "Destination port Index."
    ::= { hwMusaAllPvcConfEntry  22 }
    
    hwMusaDestBoardVpi    OBJECT-TYPE
        SYNTAX          INTEGER
        ACCESS          read-write
        STATUS          mandatory
    DESCRIPTION
    "Destination Port vpi Index."
    ::= { hwMusaAllPvcConfEntry  24 }   

    hwMusaDestBoardVci    OBJECT-TYPE
        SYNTAX          INTEGER
        ACCESS          read-write
        STATUS          mandatory
    DESCRIPTION
    "Destination VCI Index."
    ::= { hwMusaAllPvcConfEntry  25 }
    
   hwMusaDestUpcEpdPpd    OBJECT-TYPE
        SYNTAX          INTEGER
        ACCESS          read-write
        STATUS          mandatory
    DESCRIPTION
    "The flow control parameter of connection."
   ::= { hwMusaAllPvcConfEntry  34 }
   
   hwMusaSrcToDestTraffic  OBJECT-TYPE
        SYNTAX  INTEGER
        ACCESS  read-write
        STATUS  mandatory
        DESCRIPTION
        "The source board to destination traffic."
    ::= { hwMusaAllPvcConfEntry 38 }
    
   hwMusaDestToSrcTraffic  OBJECT-TYPE
        SYNTAX  INTEGER
        ACCESS  read-write
        STATUS  mandatory
        DESCRIPTION
        "The destination to source board traffic."
    ::= { hwMusaAllPvcConfEntry 39 }
       
   hwMusaAllPvcOperater    OBJECT-TYPE
        SYNTAX          INTEGER
                        {
                        add(0),
                        del(1)
                        }
        ACCESS          read-write
        STATUS          mandatory
    DESCRIPTION
    "Add or delete PVC."
    ::= { hwMusaAllPvcConfEntry  40}

   hwMusaTypeOfPvcPvpindex    OBJECT-TYPE
       SYNTAX          INTEGER
                        {
                        pvc(0),
                        pvp(1)
                        }
        ACCESS          read-write
        STATUS          mandatory
    DESCRIPTION
    "Identified type of Pvc or Pvp"
    ::= { hwMusaAllPvcConfEntry  41}
    
    hwMusaPvcPvpState  OBJECT-TYPE
       SYNTAX          INTEGER
                        {
                        normal(1),
                        invalid(2),
                        delete(3) 
                        }
        ACCESS          read-only
        STATUS          mandatory
    DESCRIPTION
    "Pvc or Pvp  state "
    ::= { hwMusaAllPvcConfEntry  42}
    
    
-- ADLB板
    hwMusaAdlb             OBJECT IDENTIFIER ::= { hwMa5100Mib 6 }
-- ADLB板描述组 Adlb Board
    hwMusaAdlbBoard        OBJECT IDENTIFIER ::= { hwMusaAdlb 1 }
-- ADLB套片管理组 Adlb Chipset
    hwMusaAdlbChipset      OBJECT IDENTIFIER ::= { hwMusaAdlb 2 }
-- ADLB端口配置管理组 Adlb Port Config
    hwMusaAdlbConf         OBJECT IDENTIFIER ::= { hwMusaAdlb 3 }
-- ADLB端口性能管理组 Adlb Port Performance
    hwMusaAdlbPfm          OBJECT IDENTIFIER ::= { hwMusaAdlb 4 }
-- ADLB维测管理组 Adlb Port Maintenance
    hwMusaAdlbTest         OBJECT IDENTIFIER ::= { hwMusaAdlb 5 }

    
    
-- ***************************************************************
--     |    |－ ADLB板描述组
--     |    |   |－板与套片（MODEM）描述表
--     |    |   |   |－#框号
--     |    |   |   |－#槽位号
--     |    |   |   |－产品代号ID（R）
--     |    |   |   |－用户线类型:(0:未知类型 1:ISDN 2:POTS)（R）
--     |    |   |   |－MODEM固化软件的版本（R）
--     |    |   |   |－MODEM固化软件的生成日期（R）       
--     |    |   |   |－OAM软件模块的版本（R）
--     |    |   |   |－OAM软件模块的生成日期（R）
--     |    |   |   |－DIAG CODE软件模块的版本（R）
--     |    |   |   |－MODEM CODE软件模块的版本（R）
--     |    |   |   |－供应商ID，只有在T1.413方式下才有（R）
--     |    |   |   |－供应商的版本号，在T.1413和G.HS方式下用（R）
--     |    |   |   |－ITU-T标准的国家代码号，在G.HS方式用（R）
--     |    |   |   |－ITU-T标准的供应商代码号，在G.HS方式用（R）
-- ***************************************************************       
     
    -- 板与套片（MODEM）描述表
    hwMusaAdlbBoardInfoTable    OBJECT-TYPE
        SYNTAX      SEQUENCE OF HwMusaAdlbBoardInfoEntry
        ACCESS      not-accessible
        STATUS      mandatory
    DESCRIPTION
    "Musa adlb board description table."
    ::= { hwMusaAdlbBoard 1 }

   hwMusaAdlbBoardInfoEntry    OBJECT-TYPE
        SYNTAX         HwMusaAdlbBoardInfoEntry
        ACCESS         not-accessible
        STATUS         mandatory
    DESCRIPTION
    "This list contains Musa adlb board description variables."
    INDEX { hwMusaFrameIndex,
            hwMusaSlotIndex }
    ::= { hwMusaAdlbBoardInfoTable  1 }

   HwMusaAdlbBoardInfoEntry    ::= SEQUENCE  {
            adlbProductId      		INTEGER,
            adlbCustomId      		INTEGER,
            adlbAtucRomSwVer   		DisplayString,
            adlbAtucRomSwBuildDate  DisplayString,
            adlbAtucOamSwVer  		DisplayString,
            adlbAtucOamSwBuildDate	DisplayString,
  			adlbByDiagCodeVer 		DisplayString,
    		adlbByModemCodeVer		DisplayString,
            adlbAtucVendorId        INTEGER,
            adlbAtucVersionNo       INTEGER,
            adlbItuCountryCode     	INTEGER,
            adlbItuProviderCode    	DisplayString
            }            
        
    adlbProductId  			OBJECT-TYPE
        SYNTAX  INTEGER
        ACCESS  read-only
        STATUS  mandatory
        DESCRIPTION
        " 产品代号ID "
    ::= { hwMusaAdlbBoardInfoEntry 1 }

    adlbCustomId      		OBJECT-TYPE
        SYNTAX  INTEGER		{
                            unknown(0), 
                            isdn(1),
                            pots(2)
                       }
        ACCESS  read-only
        STATUS  mandatory
        DESCRIPTION
        " 用户线类型(0:未知类型 1:ISDN 2:POTS) "
    ::= { hwMusaAdlbBoardInfoEntry 2 }
    
    adlbAtucRomSwVer   		OBJECT-TYPE
        SYNTAX  DisplayString
        ACCESS  read-only
        STATUS  mandatory
        DESCRIPTION
        " MODEM固化软件的版本 "
    ::= { hwMusaAdlbBoardInfoEntry 3 }
    
    adlbAtucRomSwBuildDate  OBJECT-TYPE
        SYNTAX  DisplayString
        ACCESS  read-only
        STATUS  mandatory
        DESCRIPTION
        " MODEM固化软件的生成日期 "
    ::= { hwMusaAdlbBoardInfoEntry 4 }
    
    adlbAtucOamSwVer  		OBJECT-TYPE
        SYNTAX  DisplayString
        ACCESS  read-only
        STATUS  mandatory
        DESCRIPTION
        " OAM软件模块的版本 "
    ::= { hwMusaAdlbBoardInfoEntry 5 }
    
    adlbAtucOamSwBuildDate	OBJECT-TYPE
        SYNTAX  DisplayString
        ACCESS  read-only
        STATUS  mandatory
        DESCRIPTION
        " OAM软件模块的生成日期 "
    ::= { hwMusaAdlbBoardInfoEntry 6 }
    
	adlbByDiagCodeVer 		OBJECT-TYPE
        SYNTAX  DisplayString
        ACCESS  read-only
        STATUS  mandatory
        DESCRIPTION
        " DIAG CODE软件模块的版本 "
    ::= { hwMusaAdlbBoardInfoEntry 7 }
    
	adlbByModemCodeVer		OBJECT-TYPE
        SYNTAX  DisplayString
        ACCESS  read-only
        STATUS  mandatory
        DESCRIPTION
        " MODEM CODE软件模块的版本 "
    ::= { hwMusaAdlbBoardInfoEntry 8 }
    
    adlbAtucVendorId        OBJECT-TYPE
        SYNTAX  INTEGER
        ACCESS  read-only
        STATUS  mandatory
        DESCRIPTION
        " 供应商ID ,只有在T1.413方式下才有 "
    ::= { hwMusaAdlbBoardInfoEntry 9 }
    
    adlbAtucVersionNo       OBJECT-TYPE
        SYNTAX  INTEGER
        ACCESS  read-only
        STATUS  mandatory
        DESCRIPTION
        " 供应商的版本号，在T.1413和G.HS方式下用 "
    ::= { hwMusaAdlbBoardInfoEntry 10 }
    
    adlbItuCountryCode     	OBJECT-TYPE
        SYNTAX  INTEGER
        ACCESS  read-only
        STATUS  mandatory
        DESCRIPTION
        " ITU-T标准的国家代码号，在G.HS方式用 "
    ::= { hwMusaAdlbBoardInfoEntry 11 }
    
    adlbItuProviderCode        	OBJECT-TYPE
        SYNTAX  DisplayString
        ACCESS  read-only
        STATUS  mandatory
        DESCRIPTION
        " ITU-T标准的供应商代码号，在G.HS方式用 "
    ::= { hwMusaAdlbBoardInfoEntry 12 }
    
-- ***************************************************************       
--      |    |－ ADLB套片管理组
--      |    |   |－套片维护表
--      |    |   |   |－#框号
--      |    |   |   |－#槽位号
--      |    |   |   |－#套片索引号 
--      |    |   |   |－套片操作（复位）（W）
-- ***************************************************************       

    -- 套片维护表
    hwMusaAdlbChipsetMtTable    OBJECT-TYPE
        SYNTAX      SEQUENCE OF HwMusaAdlbChipsetMtEntry
        ACCESS      not-accessible
        STATUS      mandatory
    DESCRIPTION
    "Musa adlb board description table."
    ::= { hwMusaAdlbChipset 1 }

   hwMusaAdlbChipsetMtEntry    OBJECT-TYPE
        SYNTAX         HwMusaAdlbChipsetMtEntry
        ACCESS         not-accessible
        STATUS         mandatory
    DESCRIPTION
    "This list contains Musa chipset maintenance variables."
    INDEX { hwMusaFrameIndex,
            hwMusaSlotIndex,
            adlbChipsetIndex }
    ::= { hwMusaAdlbChipsetMtTable  1 }

   HwMusaAdlbChipsetMtEntry    ::= SEQUENCE  {
            adlbChipsetIndex	INTEGER,
            adlbChipsetOper     INTEGER
            }            
        
    adlbChipsetIndex			OBJECT-TYPE
        SYNTAX  INTEGER ( 0..3 )
        ACCESS  not-accessible
        STATUS  mandatory
        DESCRIPTION
        " Adlb套片号 "
    ::= { hwMusaAdlbChipsetMtEntry 1 }
	
	adlbChipsetOper				OBJECT-TYPE
        SYNTAX  INTEGER
        ACCESS  write-only
        STATUS  mandatory
        DESCRIPTION
        " reset chipset 复位套片. "
    ::= { hwMusaAdlbChipsetMtEntry 2 }

-- ***************************************************************       
--     |    |－ ADLB端口配置管理组
--     |    |   |－端口远端设备描述表
--     |    |   |   |－#框号
--     |    |   |   |－#槽位号
--     |    |   |   |－#端口索引号 
--     |    |   |   |－ATUR的供应商ID号（R）
--     |    |   |   |－ATUR的版本号（R）
--     |    |   |   |－ATUR的国家代码（R）	     
--     |    |   |   |－ATUR的供应商代码（R）	 
--     |    |   |   |－ATUR的ADSL能力（R）	 
-- ***************************************************************       

    -- 端口远端设备描述表表
    hwMusaAdlbPortDeviceTable    OBJECT-TYPE
        SYNTAX      SEQUENCE OF HwMusaAdlbPortDeviceEntry
        ACCESS      not-accessible
        STATUS      mandatory
    DESCRIPTION
    "Musa adlb port remote device table."
    ::= { hwMusaAdlbConf 1 }

   hwMusaAdlbPortDeviceEntry    OBJECT-TYPE
        SYNTAX         HwMusaAdlbPortDeviceEntry
        ACCESS         not-accessible
        STATUS         mandatory
    DESCRIPTION
    "This list contains Musa adlb port remote device variables."
    INDEX { hwMusaFrameIndex,
            hwMusaSlotIndex,
            adlbPortIndex }
    ::= { hwMusaAdlbPortDeviceTable  1 }

   HwMusaAdlbPortDeviceEntry    ::= SEQUENCE  {
            adlbPortIndex			INTEGER,
            adlbAturVendorId   		INTEGER,
            adlbAturVersion			INTEGER,
            adlbAturCountryCode		INTEGER,
	    	adlbAturProviderCode	INTEGER,
    		adlbAturAdslCapability	INTEGER
            }            
        
    adlbPortIndex			OBJECT-TYPE
        SYNTAX  INTEGER ( 0..15 )
        ACCESS  not-accessible
        STATUS  mandatory
        DESCRIPTION
        " Adlb端口号 "
    ::= { hwMusaAdlbPortDeviceEntry 1 }
	
    adlbAturVendorId   		OBJECT-TYPE
        SYNTAX  INTEGER
        ACCESS  read-only
        STATUS  mandatory
        DESCRIPTION
        " ATUR的供应商ID号 "
    ::= { hwMusaAdlbPortDeviceEntry 2 }
    
    adlbAturVersion			OBJECT-TYPE
        SYNTAX  INTEGER
        ACCESS  read-only
        STATUS  mandatory
        DESCRIPTION
        " ATUR的版本号 "
    ::= { hwMusaAdlbPortDeviceEntry 3 }
    
    adlbAturCountryCode		OBJECT-TYPE
        SYNTAX  INTEGER
        ACCESS  read-only
        STATUS  mandatory
        DESCRIPTION
        " ATUR供应商的国家代码 "
    ::= { hwMusaAdlbPortDeviceEntry 4 }
    
	adlbAturProviderCode	OBJECT-TYPE
        SYNTAX  INTEGER
        ACCESS  read-only
        STATUS  mandatory
        DESCRIPTION
        " ATUR的供应商代码 "
    ::= { hwMusaAdlbPortDeviceEntry 5 }
    
	adlbAturAdslCapability	OBJECT-TYPE
        SYNTAX  INTEGER
        ACCESS  read-only
        STATUS  mandatory
        DESCRIPTION
        " ATUR的ADSL能力 
           0:not support，1:support;
	       bit0--T1.413 issue2
	       bit2--g992.1 POTS non-overlapped spectrum
	       bit3--g992.1 POTS overlapped specturm
	       bit4--g992.1 ISDN non-overlapped spectrum
	       bit5--g992.1 ISDN overlapped spectrum
	       bit6--g992.1 operation in conjunction with TCM-ISDN non-overlapped spectrum
	       bit7--g992.1 operation in conjunction with TCM-ISDN overlapped spectrum
	       bit8--g992.2 POTS non-overlapped spectrum
	       bit9--g992.2 POTS overlapped specturm
	       bit10--g992.2 operation in conjunction with TCM-ISDN non-overlapped spectrum
	       bit11--g992.2 operation in conjunction with TCM-ISDN overlapped spectrum "
    ::= { hwMusaAdlbPortDeviceEntry 6 }
    
   
-- ***************************************************************       
--     |    |－ ADLB端口配置管理组
--     |    |   |－端口状态表
--     |    |   |   |－#框号
--     |    |   |   |－#槽位号
--     |    |   |   |－#端口索引号 
--     |    |   |   |－端口状态（R） 
--     |    |   |   |	(0:active 1:deactive 2:bad 3:activating 4:deactivating 5:block)  
--     |    |   |   |－端口训练过程所遵循的标准（R）( 0:none 1:G.DMT 2:G.LITE 3:T1.413 )
--     |    |   |   |－端口操作（0:关闭/去激活 1:block 2:unblock）（W）
--     |    |   |   |－使用的模板号（RW）[使用模板激活端口]
-- ***************************************************************       

    -- 端口状态表
    hwMusaAdlbPortTable    OBJECT-TYPE
        SYNTAX      SEQUENCE OF HwMusaAdlbPortEntry
        ACCESS      not-accessible
        STATUS      mandatory
    DESCRIPTION
    "Musa adlb port table."
    ::= { hwMusaAdlbConf 2 }

   hwMusaAdlbPortEntry    OBJECT-TYPE
        SYNTAX         HwMusaAdlbPortEntry
        ACCESS         not-accessible
        STATUS         mandatory
    DESCRIPTION
    "This list contains Musa adlb port query and operation variables."
    INDEX { hwMusaFrameIndex,
            hwMusaSlotIndex,
            adlbPortIndex }
    ::= { hwMusaAdlbPortTable  1 }

   HwMusaAdlbPortEntry    ::= SEQUENCE  {
            adlbPortState   		INTEGER,
            adlbPortTrainStandard  	INTEGER,
            adlbPortOper	   		INTEGER,
            adlbPortTemplateId      INTEGER,
            adlbPortTxCell      INTEGER,
            adlbPortRxCell      INTEGER
            }            
        
    adlbPortState   		OBJECT-TYPE
        SYNTAX  INTEGER     {
                            active(0), 
                            deactive(1),
                            bad(2), 
                            activating(3),
                            deactivating(4),
                            block(5),
                            unblock(6),     --  只是用来给网管显示用，实际中没有的状态
                            other(255)
                       }

        ACCESS  read-only
        STATUS  mandatory
        DESCRIPTION
        " 端口状态 (0:active 1:deactive 2:bad 3:activating 4:deactivating 5:block 255:other) "
    ::= { hwMusaAdlbPortEntry 1 }
	
    adlbPortTrainStandard  	OBJECT-TYPE
        SYNTAX  INTEGER	{ none(0), dmt(1), glite(2), t1413(3) }
        ACCESS  read-only
        STATUS  mandatory
        DESCRIPTION
        " 端口训练过程所遵循的标准 ( 0:none 1:G.DMT 2:G.LITE 3:T1.413 ) "
    ::= { hwMusaAdlbPortEntry 2 }
    
    adlbPortOper	   		OBJECT-TYPE
        SYNTAX  INTEGER		{
                            deact(0), 
                            block(1),
                            unblock(2),
                            clearCellStat(3)
                       }
        ACCESS  write-only
        STATUS  mandatory
        DESCRIPTION
        " 端口操作（0:关闭/去激活 1:阻塞 2:解阻塞） "
    ::= { hwMusaAdlbPortEntry 3 }

    adlbPortTemplateId	   		OBJECT-TYPE
        SYNTAX  INTEGER(1..99)
        ACCESS  read-write
        STATUS  mandatory
        DESCRIPTION
        " activate ADL port by one template. 激活端口 "
    ::= { hwMusaAdlbPortEntry 4 }

    adlbPortTxCell	   		OBJECT-TYPE
        SYNTAX  INTEGER
        ACCESS  read-only
        STATUS  mandatory
        DESCRIPTION
        " ADL port Transfer cells. "
    ::= { hwMusaAdlbPortEntry 5 }

    adlbPortRxCell	   		OBJECT-TYPE
        SYNTAX  INTEGER
        ACCESS  read-only
        STATUS  mandatory
        DESCRIPTION
        " ADL port Receive cells. "
    ::= { hwMusaAdlbPortEntry 6 }
-- ***************************************************************
--     |    |－ ADLB端口配置管理组
--     |    |   |－配置ADSL套片参数并激活（或训练）（R／W）
--     |    |   |   |－#框号
--     |    |   |   |－#槽位号
--     |    |   |   |－#端口索引号
--     |    |   |   |－所有线路配置参数是否采用缺省值（R／W） (1:采用 0:不采用)
--     |    |   |   |－ADSL服务类型（R／W）   (0:All (G992.1, G992.2, T1.413)(Default)
--     |    |   |   |                      		1:Full rate(G992.1 or T1.413)
--     |    |   |   |                      		2:G992.2(g.lite) only
--     |    |   |   |                      		3:T1.413 only
--     |    |   |   |                      		4:G992.1(g.dmt) only
--     |    |   |   |                      		5:g.hs (G992.1 and G992.2 with priority to G992.1))
--     |    |   |   |－延迟设置（R／W） (0:手工配置(Default) 1:由套片自动计算)
--     |    |   |   |－延迟单位（R／W） (0:DMT符号即深度(Default) 1:毫秒)
--     |    |   |   |－帧模式（R／W）	(0-Framing mode 0, Full overhead asynchronous mode
--     |    |   |   |                    1-Framing mode 1, Full overhead synchronous mode
--     |    |   |   |                    2-Framing mode 2, Dual latency with reduced overhead
--     |    |   |   |                    3-Framing mode 3(Default), Single latency with reduced overhead)
--     |    |   |   |－NTR网络时钟参考（R／W） (0:disabled(Default) 1:enabled)
--     |    |   |   |－格栅编码（R／W） (0:disable 1:enable(Default))
--     |    |   |   |－嵌入操作通道EOC模式（R／W） (0:transparent mode(Default) 1:HDLC framing mode)    
--     |    |   |   |－下行通道Single或Dual的选择
--     |    |   |   |						   (1-single DS channel(AS0) (Default)
--     |    |   |   |							3-dual DS channel(AS0 and AS1/LS0ds))
--     |    |   |   |－上行通道Single或Dual的选择
--     |    |   |   |						   (1-single US channel(LS0us) (Default)
--     |    |   |   |							3-dual US channel(LS0us and LS1))
--     |    |   |   |－通道工作方式，在g.lite时强制为interleave
--     |    |   |   |						   (2-Interleaved(default)
--     |    |   |   |							3-Fast)
--     |    |   |   |－下行目标噪声容限（R／W） (0-15dB) Default=6dB
--     |    |   |   |－下行最小噪声容限（R／W） Default=0dB 训练时如低于该值，MODEM自动重训练
--     |    |   |   |－上行目标噪声容限（R／W） (0-15dB) Default=6dB
--     |    |   |   |－上行最小噪声容限（R／W） Default=0dB 训练时如低于该值，MODEM自动重训练    
--     |    |   |   |－/* 如果想指定固定的速率值，则将最大值与最小值设置成相同 */
--     |    |   |   |－/* Lite方式在进行速率设置时，仅使用下列四个总速率 */
--     |    |   |   |－channel0最大下行总速率（R／W） (单位:32kbits/sec 
--     |    |   |   |               对single channel,full rate, Default=255 -> 8.160Mbps 
--     |    |   |   |               对single channel,lite rate, Default=48 -> 1.536Mbps
--     |    |   |   |               对dual channel,full rate,Default=235 -> 7.520Mbps)
--     |    |   |   |－channel0最小下行总速率（R／W） (单位:32kbits/sec
--     |    |   |   |               对single channel,full rate, Default=1 -> 32Kbps 
--     |    |   |   |               对single channel,lite rate, Default=2 -> 64Kbps
--     |    |   |   |               对dual channel,full rate,Default=1 -> 32Kbps)
--     |    |   |   |－channel0最大上行总速率（R／W） (单位:32kbits/sec
--     |    |   |   |                对Full rate, Default=28 -> 896Kbps 
--     |    |   |   |                对Lite     , Default=16 -> 512Kbps 
--     |    |   |   |                对single channel,full rate, Default=28 -> 896Kbps 
--     |    |   |   |                对single channel,lite rate, Default=16 -> 512Kbps 
--     |    |   |   |                对dual channel, Default=24 -> 768Kbps)
--     |    |   |   |－channel0最小上行总速率（R／W） (单位:32kbits/sec
--     |    |   |   |                对single channel,full rate, Default=1 -> 32Kbps 
--     |    |   |   |                对single channel,lite rate, Default=1 -> 32Kbps
--     |    |   |   |                对dual channel, Default=1 -> 32Kbps)
--     |    |   |   |－上行最大线路延迟（R／W）(当延迟单位以毫秒表示，(5-255ms) Default=24ms,
--     |    |   |   |        			 当延迟单位以DMT符号个数即深度表示,(2,4,8,16,32,64,128) Default=64)
--     |    |   |   |－下行最大线路延迟（R／W）(当延迟单位以毫秒表示，(5-255ms) Default=24ms,
--     |    |   |   |        			 当延迟单位以DMT符号个数即深度表示,(2,4,8,16,32,64,128) Default=64)
--     |    |   |   |－上行超出速率分配比率（R／W） (Single channel default=100
--     |    |   |   |								 Dual channel default=50)
--     |    |   |   |－下行超出速率分配比率（R／W） (Single channel default=100
--     |    |   |   |								 Dual channel default=50)
--     |    |   |   |－/* 对Lite方式，下列四个速率寄存器被忽略 */
--     |    |   |   |－/* 对single channel operation方式，下列四个速率寄存器被忽略 */
--     |    |   |   |－/* 下列四个速率寄存器仅在dual channel operation方式使用 */
--     |    |   |   |－Channel1最大下行速率（R／W） (单位:32kbits/sec
--     |    |   |   |                   对dual channel default=20 -> 640Kbps)
--     |    |   |   |－Channel1最小下行速率（R／W） (单位:32kbits/sec
--     |    |   |   |                   对dual channel default=20 -> 640Kbps)
--     |    |   |   |－Channel1最大上行速率（R／W） (单位:32kbits/sec
--     |    |   |   |                   对dual channel default=4 -> 128Kbps)
--     |    |   |   |－Channel1最小上行速率（R／W） (单位:32kbits/sec
--     |    |   |   |                   对dual channel default=4 -> 128Kbps)
--     |    |   |   |－模板操作[0-add, 1-del]
-- ***************************************************************

    -- 配置ADSL套片参数并激活（或训练）
    hwMusaAdlbPortActTable    OBJECT-TYPE
        SYNTAX      SEQUENCE OF HwMusaAdlbPortActEntry
        ACCESS      not-accessible
        STATUS      mandatory
    DESCRIPTION
    "Musa adlb activate port table."
    ::= { hwMusaAdlbConf 3 }

   hwMusaAdlbPortActEntry    OBJECT-TYPE
        SYNTAX         HwMusaAdlbPortActEntry
        ACCESS         not-accessible
        STATUS         mandatory
    DESCRIPTION
    "This list contains activate adlb port variables."
    INDEX { adlbPortTemplateId }
    ::= { hwMusaAdlbPortActTable  1 }

   HwMusaAdlbPortActEntry    ::= SEQUENCE  {
		    adlbIfConfigSetToDefault	INTEGER, 
		    adlbServiceType 			INTEGER,
		    adlbConfigOrAutoDelay   	INTEGER,
		    adlbDelayOrDepth   			INTEGER,
		    adlbFrameMode   			INTEGER,
		    adlbNTROptionEnable    		INTEGER,
		    adlbTrellisModeEnable     	INTEGER,
		    adlbEocClearChannelMode    	INTEGER,
			adlbDsSingleOrDual			INTEGER,
			adlbUsSingleOrDual			INTEGER,
			adlbFastOrInterleave		INTEGER,
		    adlbDsTargetMargin 			INTEGER,
		    adlbDsMinMargin 			INTEGER,
		    adlbUsTargetMargin  		INTEGER,
		    adlbUsMinMargin     		INTEGER,
		    adlbMaxDsRateC0     		INTEGER,
		    adlbMinDsRateC0     		INTEGER,
		    adlbMaxUsRateC0     		INTEGER,
		    adlbMinUsRateC0     		INTEGER,
		    adlbUsMsOrDmtNumber			INTEGER,
		    adlbDsMsOrDmtNumber  		INTEGER,
		    adlbUsExcessRatio  			INTEGER,
		    adlbDsExcessRatio  			INTEGER,
		    adlbMaxDsRateC1  			INTEGER,
		    adlbMinDsRateC1  			INTEGER,
		    adlbMaxUsRateC1  			INTEGER,
		    adlbMinUsRateC1   			INTEGER,
		    adlbTemplateOperate			INTEGER
            }
        
    adlbIfConfigSetToDefault	OBJECT-TYPE
        SYNTAX  INTEGER	{ manual(0), 
                          default(1) }
        ACCESS  read-write
        STATUS  mandatory
        DESCRIPTION
        " 所有线路配置参数是否采用缺省值 (1:采用 0:不采用) "
    ::= { hwMusaAdlbPortActEntry 1 }
                
    adlbServiceType 			OBJECT-TYPE
        SYNTAX  INTEGER	{ all(0), 
                          fullrate(1),
                          glite(2),
                          t1413(3),
                          g9922(4),
                          ghs(5) }
        ACCESS  read-write
        STATUS  mandatory
        DESCRIPTION
        " ADSL服务类型 
       	  ( 0:All (G992.1, G992.2, T1.413)(Default)
      		1:Full rate(G992.1 or T1.413)
      		2:G992.2(g.lite) only
      		3:T1.413 only
      		4:G992.2(g.dmt) only
      		5:g.hs (G992.1 and G992.2 with priority to G992.1) ) "
    ::= { hwMusaAdlbPortActEntry 2 }
                
    adlbConfigOrAutoDelay   	OBJECT-TYPE
        SYNTAX  INTEGER	{ manual(0), 
                          auto(1) }
        ACCESS  read-write
        STATUS  mandatory
        DESCRIPTION
        " 延迟设置 (0:手工配置(Default) 1:由套片自动计算) "
    ::= { hwMusaAdlbPortActEntry 3 }
                
    adlbDelayOrDepth   			OBJECT-TYPE
        SYNTAX  INTEGER	{ depth(0), 
                          ms(1) }
        ACCESS  read-write
        STATUS  mandatory
        DESCRIPTION
        " 延迟单位 (0:DMT符号即深度(Default) 1:毫秒) "
    ::= { hwMusaAdlbPortActEntry 4 }
    
    adlbFrameMode   			OBJECT-TYPE
        SYNTAX  INTEGER	{ mode0(0), 
                          mode1(1),
                          mode2(2),
                          mode3(3) }
        ACCESS  read-write
        STATUS  mandatory
        DESCRIPTION
        " 帧模式
		  ( 0-Framing mode 0, Full overhead asynchronous mode
            1-Framing mode 1, Full overhead synchronous mode
            2-Framing mode 2, Dual latency with reduced overhead
            3-Framing mode 3(Default), Single latency with reduced overhead ) "
    ::= { hwMusaAdlbPortActEntry 5 }
                
    adlbNTROptionEnable    		OBJECT-TYPE
        SYNTAX  INTEGER	{ disable(0), 
                          enable(1) }
        ACCESS  read-write
        STATUS  mandatory
        DESCRIPTION
        " NTR网络时钟参考 (0:disabled(Default) 1:enabled) "
    ::= { hwMusaAdlbPortActEntry 6 }
                
    adlbTrellisModeEnable     	OBJECT-TYPE
        SYNTAX  INTEGER	{ disable(0), 
                          enable(1) }
        ACCESS  read-write
        STATUS  mandatory
        DESCRIPTION
        " 格栅编码 (0:disable 1:enable(Default)) "
    ::= { hwMusaAdlbPortActEntry 7 }
                
    adlbEocClearChannelMode    	OBJECT-TYPE
        SYNTAX  INTEGER	{ transparent(0), 
                          hdlcframing(1) }
        ACCESS  read-write
        STATUS  mandatory
        DESCRIPTION
        " 嵌入操作通道EOC模式 (0:transparent mode(Default) 1:HDLC framing mode) "
    ::= { hwMusaAdlbPortActEntry 8 }
                
	adlbDsSingleOrDual			OBJECT-TYPE
        SYNTAX  INTEGER	{ single(1), 
                          dual(3) }
        ACCESS  read-write
        STATUS  mandatory
        DESCRIPTION
        " 下行通道Single或Dual的选择
		  ( 1-single DS channel(AS0) (Default)
			3-dual DS channel(AS0 and AS1/LS0ds) ) "
    ::= { hwMusaAdlbPortActEntry 9 }
    
	adlbUsSingleOrDual			OBJECT-TYPE
        SYNTAX  INTEGER	{ single(1), 
                          dual(3) }
        ACCESS  read-write
        STATUS  mandatory
        DESCRIPTION
        " 上行通道Single或Dual的选择
    	  ( 1-single US channel(LS0us) (Default)
			3-dual US channel(LS0us and LS1) ) "
    ::= { hwMusaAdlbPortActEntry 10 }
    
	adlbFastOrInterleave		OBJECT-TYPE
        SYNTAX  INTEGER	{ interleaved(2), 
                          fast(3) }
        ACCESS  read-write
        STATUS  mandatory
        DESCRIPTION
        " 通道工作方式，在g.lite时强制为interleave
			( 2-Interleaved(default), 3-Fast) "
    ::= { hwMusaAdlbPortActEntry 11 }
    
	adlbDsTargetMargin 			OBJECT-TYPE
        SYNTAX  INTEGER	( 0..15 )
        ACCESS  read-write
        STATUS  mandatory
        DESCRIPTION
        " 下行目标噪声容限 (0-15dB) Default=6dB "
    ::= { hwMusaAdlbPortActEntry 13 }
                
    adlbDsMinMargin 			OBJECT-TYPE
        SYNTAX  INTEGER	
        ACCESS  read-write
        STATUS  mandatory
        DESCRIPTION
        " 下行最小噪声容限 Default=0dB 训练时如低于该值，MODEM自动重训练 "
    ::= { hwMusaAdlbPortActEntry 14 }
                
    adlbUsTargetMargin  		OBJECT-TYPE
        SYNTAX  INTEGER	( 0..15 )
        ACCESS  read-write
        STATUS  mandatory
        DESCRIPTION
        " 上行目标噪声容限 (0-15dB) Default=6dB "
    ::= { hwMusaAdlbPortActEntry 15 }
                
    adlbUsMinMargin     		OBJECT-TYPE
        SYNTAX  INTEGER	
        ACCESS  read-write
        STATUS  mandatory
        DESCRIPTION
        " 上行最小噪声容限 Default=0dB 训练时如低于该值，MODEM自动重训练 "
    ::= { hwMusaAdlbPortActEntry 16 }

    adlbMaxDsRateC0     		OBJECT-TYPE
        SYNTAX  INTEGER	
        ACCESS  read-write
        STATUS  mandatory
        DESCRIPTION
        " channel0最大下行总速率
          ( 单位:32kbits/sec 
            对single channel,full rate, Default=255 -> 8.160Mbps 
            对single channel,lite rate, Default=48 -> 1.536Mbps
            对dual channel,full rate,Default=235 -> 7.520Mbps ) "
    ::= { hwMusaAdlbPortActEntry 17 }
                
    adlbMinDsRateC0     		OBJECT-TYPE
        SYNTAX  INTEGER	
        ACCESS  read-write
        STATUS  mandatory
        DESCRIPTION
        " channel0最小下行总速率
          ( 单位:32kbits/sec
            对single channel,full rate, Default=1 -> 32Kbps 
            对single channel,lite rate, Default=2 -> 64Kbps
            对dual channel,full rate,Default=1 -> 32Kbps ) "
    ::= { hwMusaAdlbPortActEntry 18 }
                
    adlbMaxUsRateC0     		OBJECT-TYPE
        SYNTAX  INTEGER	
        ACCESS  read-write
        STATUS  mandatory
        DESCRIPTION
        " channel0最大上行总速率
          ( 单位:32kbits/sec
            对Full rate, Default=28 -> 896Kbps 
            对Lite     , Default=16 -> 512Kbps 
            对single channel,full rate, Default=28 -> 896Kbps 
            对single channel,lite rate, Default=16 -> 512Kbps 
            对dual channel, Default=24 -> 768Kbps ) "
	::= { hwMusaAdlbPortActEntry 19 }
                
    adlbMinUsRateC0     		OBJECT-TYPE
        SYNTAX  INTEGER	
        ACCESS  read-write
        STATUS  mandatory
        DESCRIPTION
        " channel0最小上行总速率
          ( 单位:32kbits/sec
            对single channel,full rate, Default=1 -> 32Kbps 
            对single channel,lite rate, Default=1 -> 32Kbps
            对dual channel, Default=1 -> 32Kbps ) "
	::= { hwMusaAdlbPortActEntry 20 }
                
    adlbUsMsOrDmtNumber			OBJECT-TYPE
        SYNTAX  INTEGER	
        ACCESS  read-write
        STATUS  mandatory
        DESCRIPTION
        " 上行最大线路延迟 (当延迟单位以毫秒表示，(5-255ms) Default=16ms,
          当延迟单位以DMT符号个数即深度表示,(2,4,8,16,32,64,128) Default=64) "
    ::= { hwMusaAdlbPortActEntry 21 }
                
    adlbDsMsOrDmtNumber  		OBJECT-TYPE
        SYNTAX  INTEGER	
        ACCESS  read-write
        STATUS  mandatory
        DESCRIPTION
        " 下行最大线路延迟（R／W）(当延迟单位以毫秒表示，(5-255ms) Default=16ms,
          当延迟单位以DMT符号个数即深度表示,(2,4,8,16,32,64,128) Default=64) "
    ::= { hwMusaAdlbPortActEntry 22 }
                
    adlbUsExcessRatio  			OBJECT-TYPE
        SYNTAX  INTEGER	
        ACCESS  read-write
        STATUS  mandatory
        DESCRIPTION
        " 上行超出速率分配比率
          ( Single channel default=100
    		Dual channel default=50) "
    ::= { hwMusaAdlbPortActEntry 23 }
                
    adlbDsExcessRatio  			OBJECT-TYPE
        SYNTAX  INTEGER	
        ACCESS  read-write
        STATUS  mandatory
        DESCRIPTION
        " 下行超出速率分配比率
          ( Single channel default=100
    		Dual channel default=50) "
    ::= { hwMusaAdlbPortActEntry 24 }
                
    adlbMaxDsRateC1  			OBJECT-TYPE
        SYNTAX  INTEGER	
        ACCESS  read-write
        STATUS  mandatory
        DESCRIPTION
        "  	Channel0最大下行速率，仅在dual channel operation方式使用
        	单位:32kbits/sec
			对dual channel default=20 -> 640Kbps "
    ::= { hwMusaAdlbPortActEntry 25 }
                
    adlbMinDsRateC1  			OBJECT-TYPE
        SYNTAX  INTEGER	
        ACCESS  read-write
        STATUS  mandatory
        DESCRIPTION
        "  	Channel0最小下行速率，仅在dual channel operation方式使用
        	单位:32kbits/sec
			对dual channel default=20 -> 640Kbps "
    ::= { hwMusaAdlbPortActEntry 26 }
                
    adlbMaxUsRateC1  			OBJECT-TYPE
        SYNTAX  INTEGER	
        ACCESS  read-write
        STATUS  mandatory
        DESCRIPTION
        "  	Channel0最大上行速率，仅在dual channel operation方式使用
        	单位:32kbits/sec
			对dual channel default=4 -> 128Kbps "
    ::= { hwMusaAdlbPortActEntry 27 }
                
    adlbMinUsRateC1   			OBJECT-TYPE
        SYNTAX  INTEGER	
        ACCESS  read-write
        STATUS  mandatory
        DESCRIPTION
        "  	Channel0最小上行速率，仅在dual channel operation方式使用
        	单位:32kbits/sec
			对dual channel default=4 -> 128Kbps "
    ::= { hwMusaAdlbPortActEntry 28 }

    adlbTemplateOperate   			OBJECT-TYPE
        SYNTAX  INTEGER{add(0),
                        del(1)
                       }	
        ACCESS  read-write
        STATUS  mandatory
        DESCRIPTION
        "  	template add/del operate. "
    ::= { hwMusaAdlbPortActEntry 29 }

-- ***************************************************************
--     |    |－ ADLB端口配置管理组
--     |    |   |－端口性能统计门限表（R／W）
--     |    |   |   |－#框号
--     |    |   |   |－#槽位号
--     |    |   |   |－#端口索引号 
--     |    |   |   |－门限ID1（R／W） (default=远端误码秒门限值)
--     |    |   |   |－门限值1（R／W） (default=0)
--     |    |   |   |－门限ID2（R／W） (default=近端误码秒门限值)
--     |    |   |   |－门限值2（R／W） (default=0)
--     |    |   |   |－门限ID3（R／W） (default=远端严重误码秒门限值)
--     |    |   |   |－门限值3（R／W） (default=0)
--     |    |   |   |－门限ID4（R／W） (default=近端严重误码秒门限值)
--     |    |   |   |－门限值4（R／W） (default=0)
--     |    |   |   |－门限ID5（R／W） (default=远端不可用时间门限值)
--     |    |   |   |－门限值5（R／W） (default=0)
--     |    |   |   |－门限ID6（R／W） (default=近端不可用时间门限值)
--     |    |   |   |－门限值6（R／W） (default=0)
--     |    |   |   |－门限ID7（R／W） (default=远端丢失秒门限值)
--     |    |   |   |－门限值7（R／W） (default=0)
--     |    |   |   |－门限ID8（R／W） (default=近端丢失秒门限值)
--     |    |   |   |－门限值8（R／W） (default=0)
-- ***************************************************************

    -- 端口性能统计门限表
    hwMusaAdlbPortPfmThresTable    OBJECT-TYPE
        SYNTAX      SEQUENCE OF HwMusaAdlbPortPfmThresEntry
        ACCESS      not-accessible
        STATUS      mandatory
    DESCRIPTION
    "Musa adlb port performance statistic threshold table."
    ::= { hwMusaAdlbConf 4 }

   hwMusaAdlbPortPfmThresEntry    OBJECT-TYPE
        SYNTAX         HwMusaAdlbPortPfmThresEntry
        ACCESS         not-accessible
        STATUS         mandatory
    DESCRIPTION
    "This list contains adlb port performance statistic threshold variables."
    INDEX { hwMusaFrameIndex,
            hwMusaSlotIndex,
            adlbPortIndex }
    ::= { hwMusaAdlbPortPfmThresTable  1 }

   HwMusaAdlbPortPfmThresEntry    ::= SEQUENCE  {
		    adlbPortPfmThresId1			INTEGER, 
		    adlbPortPfmThresValue1		INTEGER,
		    adlbPortPfmThresId2			INTEGER, 
		    adlbPortPfmThresValue2		INTEGER,
		    adlbPortPfmThresId3			INTEGER, 
		    adlbPortPfmThresValue3		INTEGER,
		    adlbPortPfmThresId4			INTEGER, 
		    adlbPortPfmThresValue4		INTEGER,
		    adlbPortPfmThresId5			INTEGER, 
		    adlbPortPfmThresValue5		INTEGER,
		    adlbPortPfmThresId6			INTEGER, 
		    adlbPortPfmThresValue6		INTEGER,
		    adlbPortPfmThresId7			INTEGER, 
		    adlbPortPfmThresValue7		INTEGER,
		    adlbPortPfmThresId8			INTEGER, 
		    adlbPortPfmThresValue8		INTEGER
            }
        
    adlbPortPfmThresId1					OBJECT-TYPE
        SYNTAX  INTEGER	(0..30)
        ACCESS  read-write
        STATUS  mandatory
        DESCRIPTION
        " 性能统计门限ID1 (default=远端误码秒门限值) "
    ::= { hwMusaAdlbPortPfmThresEntry 1 }

	adlbPortPfmThresValue1				OBJECT-TYPE
        SYNTAX  INTEGER
        ACCESS  read-write
        STATUS  mandatory
        DESCRIPTION
        " 性能统计门限值1 (default=0) "
    ::= { hwMusaAdlbPortPfmThresEntry 2 }
    
    adlbPortPfmThresId2					OBJECT-TYPE
        SYNTAX  INTEGER	(0..30)
        ACCESS  read-write
        STATUS  mandatory
        DESCRIPTION
        " 性能统计门限ID2(default=近端误码秒门限值)"
    ::= { hwMusaAdlbPortPfmThresEntry 3 }

	adlbPortPfmThresValue2				OBJECT-TYPE
        SYNTAX  INTEGER
        ACCESS  read-write
        STATUS  mandatory
        DESCRIPTION
        " 性能统计门限值2 (default=0) "
    ::= { hwMusaAdlbPortPfmThresEntry 4 }
    
    adlbPortPfmThresId3					OBJECT-TYPE
        SYNTAX  INTEGER	(0..30)
        ACCESS  read-write
        STATUS  mandatory
        DESCRIPTION
        " 性能统计门限ID3 (default=远端严重误码秒门限值) "
    ::= { hwMusaAdlbPortPfmThresEntry 5 }

	adlbPortPfmThresValue3				OBJECT-TYPE
        SYNTAX  INTEGER
        ACCESS  read-write
        STATUS  mandatory
        DESCRIPTION
        " 性能统计门限值3 (default=0) "
    ::= { hwMusaAdlbPortPfmThresEntry 6 }
    
    adlbPortPfmThresId4					OBJECT-TYPE
        SYNTAX  INTEGER	(0..30)
        ACCESS  read-write
        STATUS  mandatory
        DESCRIPTION
        " 性能统计门限ID4 (default=近端严重误码秒门限值) "
    ::= { hwMusaAdlbPortPfmThresEntry 7 }

	adlbPortPfmThresValue4				OBJECT-TYPE
        SYNTAX  INTEGER
        ACCESS  read-write
        STATUS  mandatory
        DESCRIPTION
        " 性能统计门限值4 (default=0) "
    ::= { hwMusaAdlbPortPfmThresEntry 8 }
    
    adlbPortPfmThresId5					OBJECT-TYPE
        SYNTAX  INTEGER	(0..30)
        ACCESS  read-write
        STATUS  mandatory
        DESCRIPTION
        " 性能统计门限ID5 (default=远端不可用时间门限值) "
    ::= { hwMusaAdlbPortPfmThresEntry 9 }

	adlbPortPfmThresValue5				OBJECT-TYPE
        SYNTAX  INTEGER
        ACCESS  read-write
        STATUS  mandatory
        DESCRIPTION
        " 性能统计门限值5 (default=0) "
    ::= { hwMusaAdlbPortPfmThresEntry 10 }
    
    adlbPortPfmThresId6					OBJECT-TYPE
        SYNTAX  INTEGER	(0..30)
        ACCESS  read-write
        STATUS  mandatory
        DESCRIPTION
        " 性能统计门限ID6 (default=近端不可用时间门限值) "
    ::= { hwMusaAdlbPortPfmThresEntry 11 }

	adlbPortPfmThresValue6				OBJECT-TYPE
        SYNTAX  INTEGER
        ACCESS  read-write
        STATUS  mandatory
        DESCRIPTION
        " 性能统计门限值6 (default=0) "
    ::= { hwMusaAdlbPortPfmThresEntry 12 }
    
    adlbPortPfmThresId7					OBJECT-TYPE
        SYNTAX  INTEGER	(0..30)
        ACCESS  read-write
        STATUS  mandatory
        DESCRIPTION
        " 性能统计门限ID7 (default=远端丢失秒门限值) "
    ::= { hwMusaAdlbPortPfmThresEntry 13 }

	adlbPortPfmThresValue7				OBJECT-TYPE
        SYNTAX  INTEGER
        ACCESS  read-write
        STATUS  mandatory
        DESCRIPTION
        " 性能统计门限值7 (default=0) "
    ::= { hwMusaAdlbPortPfmThresEntry 14 }
    
    adlbPortPfmThresId8					OBJECT-TYPE
        SYNTAX  INTEGER	(0..30)
        ACCESS  read-write
        STATUS  mandatory
        DESCRIPTION
        " 性能统计门限ID8 (default=近端丢失秒门限值) "
    ::= { hwMusaAdlbPortPfmThresEntry 15 }

	adlbPortPfmThresValue8				OBJECT-TYPE
        SYNTAX  INTEGER
        ACCESS  read-write
        STATUS  mandatory
        DESCRIPTION
        " 性能统计门限值8 (default=0) "
    ::= { hwMusaAdlbPortPfmThresEntry 16 }
    
-- ***************************************************************
--     |    |－ADLB端口性能管理组
--     |    |   |－端口特性参数表（R）
--     |    |   |   |－#框号
--     |    |   |   |－#槽位号
--     |    |   |   |－#端口索引号 
--     |    |   |   |－下行AS0通道速率（R） (单位:32KbPS)
--     |    |   |   |－下行LS0通道速率（R） (单位:32KbPS)
--     |    |   |   |－下行AS1通道速率（R） (单位:32KbPS)
--     |    |   |   |－上行LS0通道速率（R） (单位:32KbPS)
--     |    |   |   |－上行LS1通道速率（R） (单位:32KbPS)
--     |    |   |   |－上行交织通道延迟（R） (单位:ms) (一般小于等于配置的值)
--     |    |   |   |－下行交织通道延迟（R） (单位:ms) (一般小于等于配置的值)	
--     |    |   |   |－下行噪声容限（R） (单位:dB)
--     |    |   |   |－上行噪声容限（R） (单位:dB)
--     |    |   |   |－下行衰减（R） (单位:0.5dB)
--     |    |   |   |－上行衰减（R） (单位:0.5dB	)
--     |    |   |   |－下行通道每个RS码字包含FEC冗余校验字节数（R）
--     |    |   |   |－下行快速通道每个RS码字包含FEC冗余校验字节数（R）
--     |    |   |   |－上行交织通道每个RS码字包含FEC冗余校验字节数（R）
--     |    |   |   |－上行快速通道每个RS码字包含FEC冗余校验字节数（R）	
--     |    |   |   |－下行交织通道每个RS码字包含的DMT符号数=1,或0.5（R）
--     |    |   |   |－下行快速通道每个RS码字包含的DMT符号数=1（R）	
--     |    |   |   |－上行交织通道每个RS码字包含的DMT符号数=1,或0.5（R）
--     |    |   |   |－上行快速通道每个RS码字包含的DMT符号数=1（R）	
--     |    |   |   |－下行交织通道的交织深度（R）
--     |    |   |   |－上行交织通道的交织深度（R）	
--     |    |   |   |－下行最大可达到的速率（R） (单位:32Kbps)
--     |    |   |   |－上行最大可达到的速率（R） (单位:32Kbps)
--     |    |   |   |－总输出功率（R） (单位:dBm) (-31~31)
-- ***************************************************************

    -- 端口激活后特性参数表
    hwMusaAdlbPortLineDataTable    OBJECT-TYPE
        SYNTAX      SEQUENCE OF HwMusaAdlbPortLineDataEntry
        ACCESS      not-accessible
        STATUS      mandatory
    DESCRIPTION
    "Musa adlb port line operation data table."
    ::= { hwMusaAdlbPfm 1 }

   hwMusaAdlbPortLineDataEntry    OBJECT-TYPE
        SYNTAX         HwMusaAdlbPortLineDataEntry
        ACCESS         not-accessible
        STATUS         mandatory
    DESCRIPTION
    "This list contains adlb port line operation data variables."
    INDEX { hwMusaFrameIndex,
            hwMusaSlotIndex,
            adlbPortIndex }
    ::= { hwMusaAdlbPortLineDataTable  1 }

   HwMusaAdlbPortLineDataEntry    ::= SEQUENCE  {
		    adlbAs0DnRate            		INTEGER, 
		    adlbLs0DnRate            		INTEGER,
		    adlbAs1DnRate           		INTEGER, 
		    adlbLs0UpRate             		INTEGER,
		    adlbLs1UpRate             		INTEGER, 
		    adlbUpInterleaveDelay      		INTEGER,
		    adlbDnInterleaveDelay      		INTEGER, 
		    adlbDnNoiseMargin	   			INTEGER,
		    adlbUpNoiseMargin  	   			INTEGER, 
		    adlbDnAttenuation       		INTEGER,
		    adlbUpAttenuation         		INTEGER, 
		    adlbDnParityInterleave      	INTEGER,
		    adlbDnParityFast        		INTEGER, 
		    adlbUpParityInterleave        	INTEGER,
		    adlbUpParityFast          		INTEGER, 
		    adlbDnSymbolPerCodeInterleave 	INTEGER,
		    adlbDnSymbolPerCodeFast     	INTEGER,
		    adlbUpSymbolPerCodeInterleave   INTEGER,
		    adlbUpSymbolPerCodeFast     	INTEGER,
		    adlbDnInterleaveDepth         	INTEGER,
		    adlbUpInterleaveDepth         	INTEGER,
		    adlbMaxDnAttainableRate   		INTEGER,
		    adlbMaxUpAttainableRate   		INTEGER,
            adlbTotalOutputPower            INTEGER
          	}
                                                                                        
    adlbAs0DnRate				OBJECT-TYPE
        SYNTAX  INTEGER
        ACCESS  read-only
        STATUS  mandatory
        DESCRIPTION
        " 下行AS0通道速率 单位:32KbPS "
    ::= { hwMusaAdlbPortLineDataEntry 1 }

    adlbLs0DnRate            		OBJECT-TYPE
        SYNTAX  INTEGER
        ACCESS  read-only
        STATUS  mandatory
        DESCRIPTION
        " 下行LS0通道速率 单位:32KbPS "
    ::= { hwMusaAdlbPortLineDataEntry 2 }

    adlbAs1DnRate           		OBJECT-TYPE
        SYNTAX  INTEGER
        ACCESS  read-only
        STATUS  mandatory
        DESCRIPTION
        " 下行AS1通道速率 单位:32KbPS "
    ::= { hwMusaAdlbPortLineDataEntry 3 }

    adlbLs0UpRate             		OBJECT-TYPE
        SYNTAX  INTEGER
        ACCESS  read-only
        STATUS  mandatory
        DESCRIPTION
        " 上行LS0通道速率 单位:32KbPS "
    ::= { hwMusaAdlbPortLineDataEntry 4 }

    adlbLs1UpRate             		OBJECT-TYPE
        SYNTAX  INTEGER
        ACCESS  read-only
        STATUS  mandatory
        DESCRIPTION
        " 上行LS1通道速率 单位:32KbPS "
    ::= { hwMusaAdlbPortLineDataEntry 5 }

    adlbUpInterleaveDelay      		OBJECT-TYPE
        SYNTAX  INTEGER
        ACCESS  read-only
        STATUS  mandatory
        DESCRIPTION
        " 上行交织通道延迟 单位:ms (一般小于等于配置的值) "
    ::= { hwMusaAdlbPortLineDataEntry 6 }

    adlbDnInterleaveDelay      		OBJECT-TYPE
        SYNTAX  INTEGER
        ACCESS  read-only
        STATUS  mandatory
        DESCRIPTION
        " 下行交织通道延迟 单位:ms (一般小于等于配置的值) "
    ::= { hwMusaAdlbPortLineDataEntry 7 }

    adlbDnNoiseMargin	   			OBJECT-TYPE
        SYNTAX  INTEGER
        ACCESS  read-only
        STATUS  mandatory
        DESCRIPTION
        " 下行噪声容限 单位:dB "
    ::= { hwMusaAdlbPortLineDataEntry 8 }

    adlbUpNoiseMargin  	   			OBJECT-TYPE
        SYNTAX  INTEGER
        ACCESS  read-only
        STATUS  mandatory
        DESCRIPTION
        " 上行噪声容限 单位:dB "
    ::= { hwMusaAdlbPortLineDataEntry 9 }

    adlbDnAttenuation       		OBJECT-TYPE
        SYNTAX  INTEGER
        ACCESS  read-only
        STATUS  mandatory
        DESCRIPTION
        " 下行衰减 单位:0.5dB "
    ::= { hwMusaAdlbPortLineDataEntry 10 }

    adlbUpAttenuation         		OBJECT-TYPE
        SYNTAX  INTEGER
        ACCESS  read-only
        STATUS  mandatory
        DESCRIPTION
        " 上行衰减 单位:0.5dB "
    ::= { hwMusaAdlbPortLineDataEntry 11 }

    adlbDnParityInterleave      	OBJECT-TYPE
        SYNTAX  INTEGER
        ACCESS  read-only
        STATUS  mandatory
        DESCRIPTION
        " 下行交织通道每个RS码字包含FEC冗余校验字节数 "
    ::= { hwMusaAdlbPortLineDataEntry 12 }

    adlbDnParityFast        		OBJECT-TYPE
        SYNTAX  INTEGER
        ACCESS  read-only
        STATUS  mandatory
        DESCRIPTION
        " 下行快速通道每个RS码字包含FEC冗余校验字节数 "
    ::= { hwMusaAdlbPortLineDataEntry 13 }

    adlbUpParityInterleave        	OBJECT-TYPE
        SYNTAX  INTEGER
        ACCESS  read-only
        STATUS  mandatory
        DESCRIPTION
        " 上行交织通道每个RS码字包含FEC冗余校验字节数 "
    ::= { hwMusaAdlbPortLineDataEntry 14 }

    adlbUpParityFast          		OBJECT-TYPE
        SYNTAX  INTEGER
        ACCESS  read-only
        STATUS  mandatory
        DESCRIPTION
        " 上行快速通道每个RS码字包含FEC冗余校验字节数 "
    ::= { hwMusaAdlbPortLineDataEntry 15 }

    adlbDnSymbolPerCodeInterleave 	OBJECT-TYPE
        SYNTAX  INTEGER
        ACCESS  read-only
        STATUS  mandatory
        DESCRIPTION
        " 下行交织通道每个RS码字包含的DMT符号数=1,或0.5 "
    ::= { hwMusaAdlbPortLineDataEntry 16 }

    adlbDnSymbolPerCodeFast     	OBJECT-TYPE
        SYNTAX  INTEGER
        ACCESS  read-only
        STATUS  mandatory
        DESCRIPTION
        " 下行快速通道每个RS码字包含的DMT符号数=1 "
    ::= { hwMusaAdlbPortLineDataEntry 17 }

    adlbUpSymbolPerCodeInterleave   OBJECT-TYPE
        SYNTAX  INTEGER
        ACCESS  read-only
        STATUS  mandatory
        DESCRIPTION
        " 上行交织通道每个RS码字包含的DMT符号数=1,或0.5 "
    ::= { hwMusaAdlbPortLineDataEntry 18 }

    adlbUpSymbolPerCodeFast     	OBJECT-TYPE
        SYNTAX  INTEGER
        ACCESS  read-only
        STATUS  mandatory
        DESCRIPTION
        " 上行快速通道每个RS码字包含的DMT符号数=1 "
    ::= { hwMusaAdlbPortLineDataEntry 19 }

    adlbDnInterleaveDepth         	OBJECT-TYPE
        SYNTAX  INTEGER
        ACCESS  read-only
        STATUS  mandatory
        DESCRIPTION
        " 下行交织通道的交织深度 "
    ::= { hwMusaAdlbPortLineDataEntry 20 }

    adlbUpInterleaveDepth         	OBJECT-TYPE
        SYNTAX  INTEGER
        ACCESS  read-only
        STATUS  mandatory
        DESCRIPTION
        " 上行交织通道的交织深度 "
    ::= { hwMusaAdlbPortLineDataEntry 21 }

    adlbMaxDnAttainableRate   		OBJECT-TYPE
        SYNTAX  INTEGER
        ACCESS  read-only
        STATUS  mandatory
        DESCRIPTION
        " 下行最大可达到的速率 单位:32Kbps "
    ::= { hwMusaAdlbPortLineDataEntry 22 }

    adlbMaxUpAttainableRate   		OBJECT-TYPE
        SYNTAX  INTEGER
        ACCESS  read-only
        STATUS  mandatory
        DESCRIPTION
        " 上行最大可达到的速率 单位:32Kbps "
    ::= { hwMusaAdlbPortLineDataEntry 23 }

    adlbTotalOutputPower            OBJECT-TYPE
        SYNTAX  INTEGER
        ACCESS  read-only
        STATUS  mandatory
        DESCRIPTION
        " 总输出功率 (单位:dBm) (-31~31) "
    ::= { hwMusaAdlbPortLineDataEntry 24 }

-- ***************************************************************
--     |    |－ADLB端口性能管理组
--     |    |   |－端口近端告警统计表（R）
--     |    |   |   |－#框号
--     |    |   |   |－#槽位号
--     |    |   |   |－#端口索引号 
--     |    |   |   |－近端信号丢失总计数
--     |    |   |   |－近端高bit错误总计数
--     |    |   |   |－线路自动重新训练总计数
--     |    |   |   |－近端LOF总计数
--     |    |   |   |－总计数的有效时长 (单位:15分钟)
--     |    |   |   |－前15分钟近端信号丢失秒计数
--     |    |   |   |－前15分钟近端高bit错误计数
--     |    |   |   |－前15分钟线路自动重新训练计数
--     |    |   |   |－前15分钟近端LOF计数
--     |    |   |   |－当前24小时近端信号丢失秒计数
--     |    |   |   |－当前24小时近端高bit错误计数
--     |    |   |   |－当前24小时线路自动重新训练计数
--     |    |   |   |－当前24小时近端LOF计数
--     |    |   |   |－前24小时近端信号丢失秒计数
--     |    |   |   |－前24小时近端高bit错误计数
--     |    |   |   |－前24小时线路自动重新训练计数
--     |    |   |   |－前24小时近端LOF计数
--     |    |   |   |－前24小时远端RFI计数
--     |    |   |   |－前24小时远端ATU-R电源丢失计数
-- ***************************************************************

    -- 端口近端告警统计表
    hwMusaAdlbAtucAlarmDataTable    OBJECT-TYPE
        SYNTAX      SEQUENCE OF HwMusaAdlbAtucAlarmDataEntry
        ACCESS      not-accessible
        STATUS      mandatory
    DESCRIPTION
    "Musa adlb port ATUC alarm statistic data table."
    ::= { hwMusaAdlbPfm 2 }

    hwMusaAdlbAtucAlarmDataEntry    OBJECT-TYPE
        SYNTAX         HwMusaAdlbAtucAlarmDataEntry
        ACCESS         not-accessible
        STATUS         mandatory
    DESCRIPTION
    "This list contains adlb port ATUC alarm statistic data variables."
    INDEX { hwMusaFrameIndex,
            hwMusaSlotIndex,
            adlbPortIndex }
    ::= { hwMusaAdlbAtucAlarmDataTable  1 }

    HwMusaAdlbAtucAlarmDataEntry    ::= SEQUENCE  {
		    adlbAtucLos						INTEGER,
    		adlbAtucHighBitErr				INTEGER,
   			adlbAtucRetrain					INTEGER,
    		adlbAtucLof						INTEGER,
    		adlbAtucAlarmValidIntervals		INTEGER,
		    adlbAtucPrev15MinLos			INTEGER,
    		adlbAtucPrev15MinHighBitErr		INTEGER,
   			adlbAtucPrev15MinRetrain		INTEGER,
    		adlbAtucPrev15MinLof			INTEGER,
		    adlbAtucCurr1DayLos				INTEGER,
    		adlbAtucCurr1DayHighBitErr		INTEGER,
   			adlbAtucCurr1DayRetrain			INTEGER,
    		adlbAtucCurr1DayLof				INTEGER,
		    adlbAtucPrev1DayLos				INTEGER,
    		adlbAtucPrev1DayHighBitErr		INTEGER,
   			adlbAtucPrev1DayRetrain			INTEGER,
    		adlbAtucPrev1DayLof				INTEGER,
    		adlbClearAlarmstatistics 	    INTEGER
          	}
                                                                                        
    adlbAtucLos						OBJECT-TYPE
        SYNTAX  INTEGER
        ACCESS  read-only
        STATUS  mandatory
        DESCRIPTION
        " 近端信号丢失总计数 "
    ::= { hwMusaAdlbAtucAlarmDataEntry 1 }

	adlbAtucHighBitErr				OBJECT-TYPE
        SYNTAX  INTEGER
        ACCESS  read-only
        STATUS  mandatory
        DESCRIPTION
        " 近端高bit错误总计数 "
    ::= { hwMusaAdlbAtucAlarmDataEntry 2 }

	adlbAtucRetrain					OBJECT-TYPE
        SYNTAX  INTEGER
        ACCESS  read-only
        STATUS  mandatory
        DESCRIPTION
        " 线路自动重新训练总计数 "
    ::= { hwMusaAdlbAtucAlarmDataEntry 3 }

	adlbAtucLof						OBJECT-TYPE
        SYNTAX  INTEGER
        ACCESS  read-only
        STATUS  mandatory
        DESCRIPTION
        " 近端LOF总计数 "
    ::= { hwMusaAdlbAtucAlarmDataEntry 4 }

	adlbAtucAlarmValidIntervals		OBJECT-TYPE
        SYNTAX  INTEGER
        ACCESS  read-only
        STATUS  mandatory
        DESCRIPTION
        " 总计数的有效时长 (单位:15分钟) "
    ::= { hwMusaAdlbAtucAlarmDataEntry 5 }

    adlbAtucPrev15MinLos			OBJECT-TYPE
        SYNTAX  INTEGER
        ACCESS  read-only
        STATUS  mandatory
        DESCRIPTION
        " 前15分钟近端信号丢失秒计数 "
    ::= { hwMusaAdlbAtucAlarmDataEntry 6 }

	adlbAtucPrev15MinHighBitErr		OBJECT-TYPE
        SYNTAX  INTEGER
        ACCESS  read-only
        STATUS  mandatory
        DESCRIPTION
        " 前15分钟近端高bit错误计数 "
    ::= { hwMusaAdlbAtucAlarmDataEntry 7 }

	adlbAtucPrev15MinRetrain		OBJECT-TYPE
        SYNTAX  INTEGER
        ACCESS  read-only
        STATUS  mandatory
        DESCRIPTION
        " 前15分钟线路自动重新训练计数 "
    ::= { hwMusaAdlbAtucAlarmDataEntry 8 }

	adlbAtucPrev15MinLof			OBJECT-TYPE
        SYNTAX  INTEGER
        ACCESS  read-only
        STATUS  mandatory
        DESCRIPTION
        " 前15分钟近端LOF计数 "
    ::= { hwMusaAdlbAtucAlarmDataEntry 9 }

    adlbAtucCurr1DayLos				OBJECT-TYPE
        SYNTAX  INTEGER
        ACCESS  read-only
        STATUS  mandatory
        DESCRIPTION
        " 当前24小时近端信号丢失秒计数 "
    ::= { hwMusaAdlbAtucAlarmDataEntry 10 }

	adlbAtucCurr1DayHighBitErr		OBJECT-TYPE
        SYNTAX  INTEGER
        ACCESS  read-only
        STATUS  mandatory
        DESCRIPTION
        " 当前24小时近端高bit错误计数 "
    ::= { hwMusaAdlbAtucAlarmDataEntry 11 }

	adlbAtucCurr1DayRetrain			OBJECT-TYPE
        SYNTAX  INTEGER
        ACCESS  read-only
        STATUS  mandatory
        DESCRIPTION
        " 当前24小时线路自动重新训练计数 "
    ::= { hwMusaAdlbAtucAlarmDataEntry 12 }

	adlbAtucCurr1DayLof				OBJECT-TYPE
        SYNTAX  INTEGER
        ACCESS  read-only
        STATUS  mandatory
        DESCRIPTION
        " 当前24小时近端LOF计数 "
    ::= { hwMusaAdlbAtucAlarmDataEntry 13 }

    adlbAtucPrev1DayLos				OBJECT-TYPE
        SYNTAX  INTEGER
        ACCESS  read-only
        STATUS  mandatory
        DESCRIPTION
        " 前24小时近端信号丢失秒计数 "
    ::= { hwMusaAdlbAtucAlarmDataEntry 14 }

	adlbAtucPrev1DayHighBitErr		OBJECT-TYPE
        SYNTAX  INTEGER
        ACCESS  read-only
        STATUS  mandatory
        DESCRIPTION
        " 前24小时近端高bit错误计数 "
    ::= { hwMusaAdlbAtucAlarmDataEntry 15 }

	adlbAtucPrev1DayRetrain			OBJECT-TYPE
        SYNTAX  INTEGER
        ACCESS  read-only
        STATUS  mandatory
        DESCRIPTION
        " 前24小时线路自动重新训练计数 "
    ::= { hwMusaAdlbAtucAlarmDataEntry 16 }

	adlbAtucPrev1DayLof				OBJECT-TYPE
        SYNTAX  INTEGER
        ACCESS  read-only
        STATUS  mandatory
        DESCRIPTION
        " 前24小时近端LOF计数 "
    ::= { hwMusaAdlbAtucAlarmDataEntry 17 }
    
    adlbClearAlarmstatistics   OBJECT-TYPE
        SYNTAX  INTEGER
        ACCESS  write-only
        STATUS  mandatory
        DESCRIPTION
        " 清除端口告警统计信息 "
    ::= { hwMusaAdlbAtucAlarmDataEntry 18 }

-- ***************************************************************
--     |    |－ADLB端口性能管理组
--     |    |   |－端口远端告警统计表（R）
--     |    |   |   |－#框号
--     |    |   |   |－#槽位号
--     |    |   |   |－#端口索引号 
--     |    |   |   |－远端信号丢失总计数
--     |    |   |   |－远端高bit错误总计数
--     |    |   |   |－远端RFI总计数
--     |    |   |   |－远端ATU-R电源丢失总计数
--     |    |   |   |－总计数的有效时长 (单位:15分钟)
--     |    |   |   |－前15分钟远端信号丢失秒计数
--     |    |   |   |－前15分钟远端高bit错误计数
--     |    |   |   |－前15分钟远端RFI计数
--     |    |   |   |－前15分钟远端ATU-R电源丢失计数
--     |    |   |   |－当前24小时远端信号丢失秒计数
--     |    |   |   |－当前24小时远端高bit错误计数
--     |    |   |   |－当前24小时远端RFI计数
--     |    |   |   |－当前24小时远端ATU-R电源丢失计数
--     |    |   |   |－前24小时远端信号丢失秒计数
--     |    |   |   |－前24小时远端高bit错误计数
--     |    |   |   |－前24小时远端RFI计数
--     |    |   |   |－前24小时远端ATU-R电源丢失计数
-- ***************************************************************

    -- 端口远端告警统计表
    hwMusaAdlbAturAlarmDataTable    OBJECT-TYPE
        SYNTAX      SEQUENCE OF HwMusaAdlbAturAlarmDataEntry
        ACCESS      not-accessible
        STATUS      mandatory
    DESCRIPTION
    "Musa adlb port ATUR alarm statistic data table."
    ::= { hwMusaAdlbPfm 3 }

    hwMusaAdlbAturAlarmDataEntry    OBJECT-TYPE
        SYNTAX         HwMusaAdlbAturAlarmDataEntry
        ACCESS         not-accessible
        STATUS         mandatory
    DESCRIPTION
    "This list contains adlb port ATUR alarm statistic data variables."
    INDEX { hwMusaFrameIndex,
            hwMusaSlotIndex,
            adlbPortIndex }
    ::= { hwMusaAdlbAturAlarmDataTable  1 }

    HwMusaAdlbAturAlarmDataEntry    ::= SEQUENCE  {
		    adlbAturLos						INTEGER,
    		adlbAturHighBitErr				INTEGER,
   			adlbAturRfi						INTEGER,
    		adlbAturLpr						INTEGER,
    		adlbAturAlarmValidIntervals		INTEGER,
		    adlbAturPrev15MinLos			INTEGER,
    		adlbAturPrev15MinHighBitErr		INTEGER,
   			adlbAturPrev15MinRfi			INTEGER,
    		adlbAturPrev15MinLpr			INTEGER,
		    adlbAturCurr1DayLos				INTEGER,
    		adlbAturCurr1DayHighBitErr		INTEGER,
   			adlbAturCurr1DayRfi				INTEGER,
    		adlbAturCurr1DayLpr				INTEGER,
		    adlbAturPrev1DayLos				INTEGER,
    		adlbAturPrev1DayHighBitErr		INTEGER,
   			adlbAturPrev1DayRfi				INTEGER,
    		adlbAturPrev1DayLpr				INTEGER
          	}
                                                                                        
    adlbAturLos						OBJECT-TYPE
        SYNTAX  INTEGER
        ACCESS  read-only
        STATUS  mandatory
        DESCRIPTION
        " 远端信号丢失总计数 "
    ::= { hwMusaAdlbAturAlarmDataEntry 1 }

	adlbAturHighBitErr				OBJECT-TYPE
        SYNTAX  INTEGER
        ACCESS  read-only
        STATUS  mandatory
        DESCRIPTION
        " 远端高bit错误总计数 "
    ::= { hwMusaAdlbAturAlarmDataEntry 2 }

	adlbAturRfi						OBJECT-TYPE
        SYNTAX  INTEGER
        ACCESS  read-only
        STATUS  mandatory
        DESCRIPTION
        " 远端RFI总计数 "
    ::= { hwMusaAdlbAturAlarmDataEntry 3 }

	adlbAturLpr						OBJECT-TYPE
        SYNTAX  INTEGER
        ACCESS  read-only
        STATUS  mandatory
        DESCRIPTION
        " 远端ATU-R电源丢失总计数 "
    ::= { hwMusaAdlbAturAlarmDataEntry 4 }

	adlbAturAlarmValidIntervals		OBJECT-TYPE
        SYNTAX  INTEGER
        ACCESS  read-only
        STATUS  mandatory
        DESCRIPTION
        " 总计数的有效时长 (单位:15分钟) "
    ::= { hwMusaAdlbAturAlarmDataEntry 5 }

    adlbAturPrev15MinLos			OBJECT-TYPE
        SYNTAX  INTEGER
        ACCESS  read-only
        STATUS  mandatory
        DESCRIPTION
        " 前15分钟远端信号丢失秒计数 "
    ::= { hwMusaAdlbAturAlarmDataEntry 6 }

	adlbAturPrev15MinHighBitErr		OBJECT-TYPE
        SYNTAX  INTEGER
        ACCESS  read-only
        STATUS  mandatory
        DESCRIPTION
        " 前15分钟远端高bit错误计数 "
    ::= { hwMusaAdlbAturAlarmDataEntry 7 }

	adlbAturPrev15MinRfi			OBJECT-TYPE
        SYNTAX  INTEGER
        ACCESS  read-only
        STATUS  mandatory
        DESCRIPTION
        " 前15分钟远端RFI计数 "
    ::= { hwMusaAdlbAturAlarmDataEntry 8 }

	adlbAturPrev15MinLpr			OBJECT-TYPE
        SYNTAX  INTEGER
        ACCESS  read-only
        STATUS  mandatory
        DESCRIPTION
        " 前15分钟远端ATU-R电源丢失计数 "
    ::= { hwMusaAdlbAturAlarmDataEntry 9 }

    adlbAturCurr1DayLos				OBJECT-TYPE
        SYNTAX  INTEGER
        ACCESS  read-only
        STATUS  mandatory
        DESCRIPTION
        " 当前24小时远端信号丢失秒计数 "
    ::= { hwMusaAdlbAturAlarmDataEntry 10 }

	adlbAturCurr1DayHighBitErr		OBJECT-TYPE
        SYNTAX  INTEGER
        ACCESS  read-only
        STATUS  mandatory
        DESCRIPTION
        " 当前24小时远端高bit错误计数 "
    ::= { hwMusaAdlbAturAlarmDataEntry 11 }

	adlbAturCurr1DayRfi				OBJECT-TYPE
        SYNTAX  INTEGER
        ACCESS  read-only
        STATUS  mandatory
        DESCRIPTION
        " 当前24小时远端RFI计数 "
    ::= { hwMusaAdlbAturAlarmDataEntry 12 }

	adlbAturCurr1DayLpr				OBJECT-TYPE
        SYNTAX  INTEGER
        ACCESS  read-only
        STATUS  mandatory
        DESCRIPTION
        " 当前24小时远端ATU-R电源丢失计数 "
    ::= { hwMusaAdlbAturAlarmDataEntry 13 }

    adlbAturPrev1DayLos				OBJECT-TYPE
        SYNTAX  INTEGER
        ACCESS  read-only
        STATUS  mandatory
        DESCRIPTION
        " 前24小时远端信号丢失秒计数 "
    ::= { hwMusaAdlbAturAlarmDataEntry 14 }

	adlbAturPrev1DayHighBitErr		OBJECT-TYPE
        SYNTAX  INTEGER
        ACCESS  read-only
        STATUS  mandatory
        DESCRIPTION
        " 前24小时远端高bit错误计数 "
    ::= { hwMusaAdlbAturAlarmDataEntry 15 }

	adlbAturPrev1DayRfi				OBJECT-TYPE
        SYNTAX  INTEGER
        ACCESS  read-only
        STATUS  mandatory
        DESCRIPTION
        " 前24小时远端RFI计数 "
    ::= { hwMusaAdlbAturAlarmDataEntry 16 }

	adlbAturPrev1DayLpr				OBJECT-TYPE
        SYNTAX  INTEGER
        ACCESS  read-only
        STATUS  mandatory
        DESCRIPTION
        " 前24小时远端ATU-R电源丢失计数 "
    ::= { hwMusaAdlbAturAlarmDataEntry 17 }

-- ***************************************************************
--     |    |－ADLB端口性能管理组
--     |    |   |－端口近端性能统计总计数表（R）
--     |    |   |   |－#框号
--     |    |   |   |－#槽位号
--     |    |   |   |－#端口索引号        
--     |    |   |   |－近端交织通道发生CRC错的超帧总计数
--     |    |   |   |－近端快速通道发生CRC错的超帧总计数
--     |    |   |   |－近端交织通道发生FEC错的超帧总计数
--     |    |   |   |－近端快速通道发生FEC错的超帧总计数
--     |    |   |   |－发送的超帧总数
--     |    |   |   |－接收的超帧总数
--     |    |   |   |－近端计帧的时间,4000frames=1秒
--     |    |   |   |－近端计数有错误的超帧总数
--     |    |   |   |－近端发生在非严重误码秒期间的BACKGROUND块错误总数
--     |    |   |   |－近端误码秒总数
--     |    |   |   |－近端严重误码秒总数
--     |    |   |   |－近端无严重误码秒的超帧总数
--     |    |   |   |－近端不可用时间秒总计数
--     |    |   |   |－近端发生的比特交换总计数
--     |    |   |   |－近端丢失的秒计数总数
--     |    |   |   |－近端发生一次以上FEC的秒计数总数
--     |    |   |   |－发生快速重训练的总次数
--     |    |   |   |－快速重训练失败的总次数
--     |    |   |   |－统计总计数的有效时长 (单位:15分钟)
-- ***************************************************************

    -- 端口近端性能统计总计数表
    hwMusaAdlbAtucPerfDataTable    OBJECT-TYPE
        SYNTAX      SEQUENCE OF HwMusaAdlbAtucPerfDataEntry
        ACCESS      not-accessible
        STATUS      mandatory
    DESCRIPTION
    "Musa adlb port ATUC performance statistic data table."
    ::= { hwMusaAdlbPfm 4 }

    hwMusaAdlbAtucPerfDataEntry    OBJECT-TYPE
        SYNTAX         HwMusaAdlbAtucPerfDataEntry
        ACCESS         not-accessible
        STATUS         mandatory
    DESCRIPTION
    "This list contains adlb port ATUC performance statistic total data until now variables."
    INDEX { hwMusaFrameIndex,
            hwMusaSlotIndex,
            adlbPortIndex }
    ::= { hwMusaAdlbAtucPerfDataTable  1 }

    HwMusaAdlbAtucPerfDataEntry    ::= SEQUENCE  {
       		adlbAtucCrcErrInterleave     	INTEGER,
		    adlbAtucCrcErrFast				INTEGER,
		    adlbAtucFecErrInterleave		INTEGER,
		    adlbAtucFecErrFast				INTEGER,
		    adlbAtucSuperFrameSent			INTEGER,
		    adlbAtucSuperFrameReceived	    INTEGER,
		    adlbAtucTimeCount	           	INTEGER,
		    adlbAtucErrFrames				INTEGER,
		    adlbAtucBgBENotSES				INTEGER,
		    adlbAtucErrSecond               INTEGER,
		    adlbAtucSevereErrSecond         INTEGER,
		    adlbAtucNonSESFrames            INTEGER,
		    adlbAtucUnavailableSecond       INTEGER,
		    adlbAtucBitswaps                INTEGER,
		    adlbAtucLossSecond              INTEGER,
		    adlbAtucFecSecond               INTEGER,
		    adlbAtucFastRetrain             INTEGER,
		    adlbAtucFastRetrainFail         INTEGER,
		    adlbAtucPerfValidIntervals      INTEGER,
		    adlbClearPerfstatistics         INTEGER
           	}                              
                                                                                        
    adlbAtucCrcErrInterleave			OBJECT-TYPE
        SYNTAX  INTEGER
        ACCESS  read-only
        STATUS  mandatory
        DESCRIPTION
        " 近端交织通道发生CRC错的超帧总计数 "
    ::= { hwMusaAdlbAtucPerfDataEntry 1 }

    adlbAtucCrcErrFast				OBJECT-TYPE
        SYNTAX  INTEGER
        ACCESS  read-only
        STATUS  mandatory
        DESCRIPTION
        " 近端快速通道发生CRC错的超帧总计数 "
    ::= { hwMusaAdlbAtucPerfDataEntry 2 }

    adlbAtucFecErrInterleave		OBJECT-TYPE
        SYNTAX  INTEGER
        ACCESS  read-only
        STATUS  mandatory
        DESCRIPTION
        " 近端交织通道发生FEC错的超帧总计数 "
    ::= { hwMusaAdlbAtucPerfDataEntry 3 }

    adlbAtucFecErrFast				OBJECT-TYPE
        SYNTAX  INTEGER
        ACCESS  read-only
        STATUS  mandatory
        DESCRIPTION
        " 近端快速通道发生FEC错的超帧总计数 "
    ::= { hwMusaAdlbAtucPerfDataEntry 4 }

    adlbAtucSuperFrameSent			OBJECT-TYPE
        SYNTAX  INTEGER
        ACCESS  read-only
        STATUS  mandatory
        DESCRIPTION
        " 发送的超帧总数 "
    ::= { hwMusaAdlbAtucPerfDataEntry 5 }

    adlbAtucSuperFrameReceived	    OBJECT-TYPE
        SYNTAX  INTEGER
        ACCESS  read-only
        STATUS  mandatory
        DESCRIPTION
        " 接收的超帧总数 "
    ::= { hwMusaAdlbAtucPerfDataEntry 6 }

    adlbAtucTimeCount	           	OBJECT-TYPE
        SYNTAX  INTEGER
        ACCESS  read-only
        STATUS  mandatory
        DESCRIPTION
        " 近端计帧的时间,4000frames=1秒 "
    ::= { hwMusaAdlbAtucPerfDataEntry 7 }

    adlbAtucErrFrames				OBJECT-TYPE
        SYNTAX  INTEGER
        ACCESS  read-only
        STATUS  mandatory
        DESCRIPTION
        " 近端计数有错误的超帧总数 "
    ::= { hwMusaAdlbAtucPerfDataEntry 8 }

    adlbAtucBgBENotSES				OBJECT-TYPE
        SYNTAX  INTEGER
        ACCESS  read-only
        STATUS  mandatory
        DESCRIPTION
        " 近端发生在非严重误码秒期间的BACKGROUND块错误总数 "
    ::= { hwMusaAdlbAtucPerfDataEntry 9 }

    adlbAtucErrSecond               OBJECT-TYPE
        SYNTAX  INTEGER
        ACCESS  read-only
        STATUS  mandatory
        DESCRIPTION
        " 近端误码秒总数 "
    ::= { hwMusaAdlbAtucPerfDataEntry 10 }

    adlbAtucSevereErrSecond         OBJECT-TYPE
        SYNTAX  INTEGER
        ACCESS  read-only
        STATUS  mandatory
        DESCRIPTION
        " 近端严重误码秒总数 "
    ::= { hwMusaAdlbAtucPerfDataEntry 11 }

    adlbAtucNonSESFrames            OBJECT-TYPE
        SYNTAX  INTEGER
        ACCESS  read-only
        STATUS  mandatory
        DESCRIPTION
        " 近端无严重误码秒的超帧总数 "
    ::= { hwMusaAdlbAtucPerfDataEntry 12 }

    adlbAtucUnavailableSecond       OBJECT-TYPE
        SYNTAX  INTEGER
        ACCESS  read-only
        STATUS  mandatory
        DESCRIPTION
        " 近端不可用时间秒总计数 "
    ::= { hwMusaAdlbAtucPerfDataEntry 13 }

    adlbAtucBitswaps                OBJECT-TYPE
        SYNTAX  INTEGER
        ACCESS  read-only
        STATUS  mandatory
        DESCRIPTION
        " 近端发生的比特交换总计数 "
    ::= { hwMusaAdlbAtucPerfDataEntry 14 }

    adlbAtucLossSecond              OBJECT-TYPE
        SYNTAX  INTEGER
        ACCESS  read-only
        STATUS  mandatory
        DESCRIPTION
        " 近端丢失的秒计数总数 "
    ::= { hwMusaAdlbAtucPerfDataEntry 15 }

    adlbAtucFecSecond               OBJECT-TYPE
        SYNTAX  INTEGER
        ACCESS  read-only
        STATUS  mandatory
        DESCRIPTION
        " 近端发生一次以上FEC的秒计数总数 "
    ::= { hwMusaAdlbAtucPerfDataEntry 16 }

    adlbAtucFastRetrain             OBJECT-TYPE
        SYNTAX  INTEGER
        ACCESS  read-only
        STATUS  mandatory
        DESCRIPTION
        " 发生快速重训练的总次数 "
    ::= { hwMusaAdlbAtucPerfDataEntry 17 }

    adlbAtucFastRetrainFail         OBJECT-TYPE
        SYNTAX  INTEGER
        ACCESS  read-only
        STATUS  mandatory
        DESCRIPTION
        " 快速重训练失败的总次数 "
    ::= { hwMusaAdlbAtucPerfDataEntry 18 }

	adlbAtucPerfValidIntervals		OBJECT-TYPE
        SYNTAX  INTEGER
        ACCESS  read-only
        STATUS  mandatory
        DESCRIPTION
        " 统计总计数的有效时长 (单位:15分钟) "
    ::= { hwMusaAdlbAtucPerfDataEntry 19 }
    
    adlbClearPerfstatistics   OBJECT-TYPE
        SYNTAX  INTEGER
        ACCESS  write-only
        STATUS  mandatory
        DESCRIPTION
        " 清除端口性能统计信息 "
    ::= { hwMusaAdlbAtucPerfDataEntry 20 }
    
-- ***************************************************************
--     |    |－ADLB端口性能管理组
--     |    |   |－端口近端性能统计前15分钟计数表（R）
--     |    |   |   |－#框号
--     |    |   |   |－#槽位号
--     |    |   |   |－#端口索引号        
--     |    |   |   |－前15分钟近端交织通道发生CRC错的超帧计数
--     |    |   |   |－前15分钟近端快速通道发生CRC错的超帧计数
--     |    |   |   |－前15分钟近端交织通道发生FEC错的超帧计数
--     |    |   |   |－前15分钟近端快速通道发生FEC错的超帧计数
--     |    |   |   |－前15分钟发送的超帧数
--     |    |   |   |－前15分钟接收的超帧数
--     |    |   |   |－前15分钟近端计帧的时间,4000frames=1秒
--     |    |   |   |－前15分钟近端计数有错误的超帧数
--     |    |   |   |－前15分钟近端发生在非严重误码秒期间的BACKGROUND块错误数
--     |    |   |   |－前15分钟近端误码秒数
--     |    |   |   |－前15分钟近端严重误码秒数
--     |    |   |   |－前15分钟近端无严重误码秒的超帧数
--     |    |   |   |－前15分钟近端不可用时间秒计数
--     |    |   |   |－前15分钟近端发生的比特交换计数
--     |    |   |   |－前15分钟近端丢失的秒计数
--     |    |   |   |－前15分钟近端发生一次以上FEC的秒计数
--     |    |   |   |－前15分钟发生快速重训练的次数
--     |    |   |   |－前15分钟快速重训练失败的次数
-- ***************************************************************

    -- 端口近端性能统计前15分钟计数表
    hwMusaAdlbAtucPerfPrev15mDataTable    OBJECT-TYPE
        SYNTAX      SEQUENCE OF HwMusaAdlbAtucPerfPrev15mDataEntry
        ACCESS      not-accessible
        STATUS      mandatory
    DESCRIPTION
    "Musa adlb port ATUC performance statistic in previous 15 minutes data table."
    ::= { hwMusaAdlbPfm 5 }

    hwMusaAdlbAtucPerfPrev15mDataEntry    OBJECT-TYPE
        SYNTAX         HwMusaAdlbAtucPerfPrev15mDataEntry
        ACCESS         not-accessible
        STATUS         mandatory
    DESCRIPTION
    "This list contains adlb port ATUC performance statistic in previous 15 minutes data variables."
    INDEX { hwMusaFrameIndex,
            hwMusaSlotIndex,
            adlbPortIndex }
    ::= { hwMusaAdlbAtucPerfPrev15mDataTable  1 }

    HwMusaAdlbAtucPerfPrev15mDataEntry    ::= SEQUENCE  {
       		adlbAtucPrev15MinCrcErrInterleave     	INTEGER,
		    adlbAtucPrev15MinCrcErrFast				INTEGER,
		    adlbAtucPrev15MinFecErrInterleave		INTEGER,
		    adlbAtucPrev15MinFecErrFast				INTEGER,
		    adlbAtucPrev15MinSuperFrameSent			INTEGER,
		    adlbAtucPrev15MinSuperFrameReceived	    INTEGER,
		    adlbAtucPrev15MinTimeCount	           	INTEGER,
		    adlbAtucPrev15MinErrFrames				INTEGER,
		    adlbAtucPrev15MinBgBENotSES				INTEGER,
		    adlbAtucPrev15MinErrSecond              INTEGER,
		    adlbAtucPrev15MinSevereErrSecond        INTEGER,
		    adlbAtucPrev15MinNonSESFrames           INTEGER,
		    adlbAtucPrev15MinUnavailableSecond      INTEGER,
		    adlbAtucPrev15MinBitswaps               INTEGER,
		    adlbAtucPrev15MinLossSecond             INTEGER,
		    adlbAtucPrev15MinFecSecond              INTEGER,
		    adlbAtucPrev15MinFastRetrain            INTEGER,
		    adlbAtucPrev15MinFastRetrainFail        INTEGER
           	}                              

    adlbAtucPrev15MinCrcErrInterleave			OBJECT-TYPE
        SYNTAX  INTEGER
        ACCESS  read-only
        STATUS  mandatory
        DESCRIPTION
        " 前15分钟近端交织通道发生CRC错的超帧计数 "
    ::= { hwMusaAdlbAtucPerfPrev15mDataEntry 1 }

    adlbAtucPrev15MinCrcErrFast				OBJECT-TYPE
        SYNTAX  INTEGER
        ACCESS  read-only
        STATUS  mandatory
        DESCRIPTION
        " 前15分钟近端快速通道发生CRC错的超帧计数 "
    ::= { hwMusaAdlbAtucPerfPrev15mDataEntry 2 }

    adlbAtucPrev15MinFecErrInterleave		OBJECT-TYPE
        SYNTAX  INTEGER
        ACCESS  read-only
        STATUS  mandatory
        DESCRIPTION
        " 前15分钟近端交织通道发生FEC错的超帧计数 "
    ::= { hwMusaAdlbAtucPerfPrev15mDataEntry 3 }

    adlbAtucPrev15MinFecErrFast				OBJECT-TYPE
        SYNTAX  INTEGER
        ACCESS  read-only
        STATUS  mandatory
        DESCRIPTION
        " 前15分钟近端快速通道发生FEC错的超帧计数 "
    ::= { hwMusaAdlbAtucPerfPrev15mDataEntry 4 }

    adlbAtucPrev15MinSuperFrameSent			OBJECT-TYPE
        SYNTAX  INTEGER
        ACCESS  read-only
        STATUS  mandatory
        DESCRIPTION
        " 前15分钟发送的超帧数 "
    ::= { hwMusaAdlbAtucPerfPrev15mDataEntry 5 }

    adlbAtucPrev15MinSuperFrameReceived	    OBJECT-TYPE
        SYNTAX  INTEGER
        ACCESS  read-only
        STATUS  mandatory
        DESCRIPTION
        " 前15分钟接收的超帧数 "
    ::= { hwMusaAdlbAtucPerfPrev15mDataEntry 6 }

    adlbAtucPrev15MinTimeCount	           	OBJECT-TYPE
        SYNTAX  INTEGER
        ACCESS  read-only
        STATUS  mandatory
        DESCRIPTION
        " 前15分钟近端计帧的时间,4000frames=1秒 "
    ::= { hwMusaAdlbAtucPerfPrev15mDataEntry 7 }

    adlbAtucPrev15MinErrFrames				OBJECT-TYPE
        SYNTAX  INTEGER
        ACCESS  read-only
        STATUS  mandatory
        DESCRIPTION
        " 前15分钟近端计数有错误的超帧数 "
    ::= { hwMusaAdlbAtucPerfPrev15mDataEntry 8 }

    adlbAtucPrev15MinBgBENotSES				OBJECT-TYPE
        SYNTAX  INTEGER
        ACCESS  read-only
        STATUS  mandatory
        DESCRIPTION
        " 前15分钟近端发生在非严重误码秒期间的BACKGROUND块错误数 "
    ::= { hwMusaAdlbAtucPerfPrev15mDataEntry 9 }

    adlbAtucPrev15MinErrSecond               OBJECT-TYPE
        SYNTAX  INTEGER
        ACCESS  read-only
        STATUS  mandatory
        DESCRIPTION
        " 前15分钟近端误码秒数 "
    ::= { hwMusaAdlbAtucPerfPrev15mDataEntry 10 }

    adlbAtucPrev15MinSevereErrSecond         OBJECT-TYPE
        SYNTAX  INTEGER
        ACCESS  read-only
        STATUS  mandatory
        DESCRIPTION
        " 前15分钟近端严重误码秒数 "
    ::= { hwMusaAdlbAtucPerfPrev15mDataEntry 11 }

    adlbAtucPrev15MinNonSESFrames            OBJECT-TYPE
        SYNTAX  INTEGER
        ACCESS  read-only
        STATUS  mandatory
        DESCRIPTION
        " 前15分钟近端无严重误码秒的超帧数 "
    ::= { hwMusaAdlbAtucPerfPrev15mDataEntry 12 }

    adlbAtucPrev15MinUnavailableSecond       OBJECT-TYPE
        SYNTAX  INTEGER
        ACCESS  read-only
        STATUS  mandatory
        DESCRIPTION
        " 前15分钟近端不可用时间秒计数 "
    ::= { hwMusaAdlbAtucPerfPrev15mDataEntry 13 }

    adlbAtucPrev15MinBitswaps                OBJECT-TYPE
        SYNTAX  INTEGER
        ACCESS  read-only
        STATUS  mandatory
        DESCRIPTION
        " 前15分钟近端发生的比特交换计数 "
    ::= { hwMusaAdlbAtucPerfPrev15mDataEntry 14 }

    adlbAtucPrev15MinLossSecond              OBJECT-TYPE
        SYNTAX  INTEGER
        ACCESS  read-only
        STATUS  mandatory
        DESCRIPTION
        " 前15分钟近端丢失的秒计数 "
    ::= { hwMusaAdlbAtucPerfPrev15mDataEntry 15 }

    adlbAtucPrev15MinFecSecond               OBJECT-TYPE
        SYNTAX  INTEGER
        ACCESS  read-only
        STATUS  mandatory
        DESCRIPTION
        " 前15分钟近端发生一次以上FEC的秒计数 "
    ::= { hwMusaAdlbAtucPerfPrev15mDataEntry 16 }

    adlbAtucPrev15MinFastRetrain             OBJECT-TYPE
        SYNTAX  INTEGER
        ACCESS  read-only
        STATUS  mandatory
        DESCRIPTION
        " 前15分钟发生快速重训练的次数 "
    ::= { hwMusaAdlbAtucPerfPrev15mDataEntry 17 }

    adlbAtucPrev15MinFastRetrainFail         OBJECT-TYPE
        SYNTAX  INTEGER
        ACCESS  read-only
        STATUS  mandatory
        DESCRIPTION
        " 前15分钟快速重训练失败的次数 "
    ::= { hwMusaAdlbAtucPerfPrev15mDataEntry 18 }

-- ***************************************************************
--     |    |－ADLB端口性能管理组
--     |    |   |－端口近端性能统计当前24小时计数表（R）
--     |    |   |   |－#框号
--     |    |   |   |－#槽位号
--     |    |   |   |－#端口索引号        
--     |    |   |   |－当前24小时近端交织通道发生CRC错的超帧计数                
--     |    |   |   |－当前24小时近端快速通道发生CRC错的超帧计数                
--     |    |   |   |－当前24小时近端交织通道发生FEC错的超帧计数                
--     |    |   |   |－当前24小时近端快速通道发生FEC错的超帧计数                
--     |    |   |   |－当前24小时发送的超帧数                                   
--     |    |   |   |－当前24小时接收的超帧数                                   
--     |    |   |   |－当前24小时近端计帧的时间,4000frames=1秒                  
--     |    |   |   |－当前24小时近端计数有错误的超帧数                         
--     |    |   |   |－当前24小时近端发生在非严重误码秒期间的BACKGROUND块错误数 
--     |    |   |   |－当前24小时近端误码秒数                                   
--     |    |   |   |－当前24小时近端严重误码秒数                               
--     |    |   |   |－当前24小时近端无严重误码秒的超帧数                       
--     |    |   |   |－当前24小时近端不可用时间秒计数                             
--     |    |   |   |－当前24小时近端发生的比特交换计数                         
--     |    |   |   |－当前24小时近端丢失的秒计数                               
--     |    |   |   |－当前24小时近端发生一次以上FEC的秒计数                    
--     |    |   |   |－当前24小时发生快速重训练的次数                           
--     |    |   |   |－当前24小时快速重训练失败的次数                           
-- ***************************************************************

    -- 端口近端性能统计当前24小时计数表
    hwMusaAdlbAtucPerfCurr24hDataTable    OBJECT-TYPE
        SYNTAX      SEQUENCE OF HwMusaAdlbAtucPerfCurr24hDataEntry
        ACCESS      not-accessible
        STATUS      mandatory
    DESCRIPTION
    "Musa adlb port ATUC performance statistic data in current 24 hours table."
    ::= { hwMusaAdlbPfm 6 }

    hwMusaAdlbAtucPerfCurr24hDataEntry    OBJECT-TYPE
        SYNTAX         HwMusaAdlbAtucPerfCurr24hDataEntry
        ACCESS         not-accessible
        STATUS         mandatory
    DESCRIPTION
    "This list contains adlb port ATUC performance statistic data in current 24 hours variables."
    INDEX { hwMusaFrameIndex,
            hwMusaSlotIndex,
            adlbPortIndex }
    ::= { hwMusaAdlbAtucPerfCurr24hDataTable  1 }

    HwMusaAdlbAtucPerfCurr24hDataEntry    ::= SEQUENCE  {
       		adlbAtucCurr1DayCrcErrInterleave     	INTEGER,
		    adlbAtucCurr1DayCrcErrFast				INTEGER,
		    adlbAtucCurr1DayFecErrInterleave		INTEGER,
		    adlbAtucCurr1DayFecErrFast				INTEGER,
		    adlbAtucCurr1DaySuperFrameSent			INTEGER,
		    adlbAtucCurr1DaySuperFrameReceived	    INTEGER,
		    adlbAtucCurr1DayTimeCount	           	INTEGER,
		    adlbAtucCurr1DayErrFrames				INTEGER,
		    adlbAtucCurr1DayBgBENotSES				INTEGER,
		    adlbAtucCurr1DayErrSecond              	INTEGER,
		    adlbAtucCurr1DaySevereErrSecond        	INTEGER,
		    adlbAtucCurr1DayNonSESFrames           	INTEGER,
		    adlbAtucCurr1DayUnavailableSecond      	INTEGER,
		    adlbAtucCurr1DayBitswaps               	INTEGER,
		    adlbAtucCurr1DayLossSecond             	INTEGER,
		    adlbAtucCurr1DayFecSecond              	INTEGER,
		    adlbAtucCurr1DayFastRetrain            	INTEGER,
		    adlbAtucCurr1DayFastRetrainFail        	INTEGER
           	}                              

    adlbAtucCurr1DayCrcErrInterleave		OBJECT-TYPE
        SYNTAX  INTEGER
        ACCESS  read-only
        STATUS  mandatory
        DESCRIPTION
        " 当前24小时近端交织通道发生CRC错的超帧计数 "
    ::= { hwMusaAdlbAtucPerfCurr24hDataEntry 1 }

    adlbAtucCurr1DayCrcErrFast				OBJECT-TYPE
        SYNTAX  INTEGER
        ACCESS  read-only
        STATUS  mandatory
        DESCRIPTION
        " 当前24小时近端快速通道发生CRC错的超帧计数 "
    ::= { hwMusaAdlbAtucPerfCurr24hDataEntry 2 }

    adlbAtucCurr1DayFecErrInterleave		OBJECT-TYPE
        SYNTAX  INTEGER
        ACCESS  read-only
        STATUS  mandatory
        DESCRIPTION
        " 当前24小时近端交织通道发生FEC错的超帧计数 "
    ::= { hwMusaAdlbAtucPerfCurr24hDataEntry 3 }

    adlbAtucCurr1DayFecErrFast				OBJECT-TYPE
        SYNTAX  INTEGER
        ACCESS  read-only
        STATUS  mandatory
        DESCRIPTION
        " 当前24小时近端快速通道发生FEC错的超帧计数 "
    ::= { hwMusaAdlbAtucPerfCurr24hDataEntry 4 }

    adlbAtucCurr1DaySuperFrameSent			OBJECT-TYPE
        SYNTAX  INTEGER
        ACCESS  read-only
        STATUS  mandatory
        DESCRIPTION
        " 当前24小时发送的超帧数 "
    ::= { hwMusaAdlbAtucPerfCurr24hDataEntry 5 }

    adlbAtucCurr1DaySuperFrameReceived	    OBJECT-TYPE
        SYNTAX  INTEGER
        ACCESS  read-only
        STATUS  mandatory
        DESCRIPTION
        " 当前24小时接收的超帧数 "
    ::= { hwMusaAdlbAtucPerfCurr24hDataEntry 6 }

    adlbAtucCurr1DayTimeCount	           	OBJECT-TYPE
        SYNTAX  INTEGER
        ACCESS  read-only
        STATUS  mandatory
        DESCRIPTION
        " 当前24小时近端计帧的时间,4000frames=1秒 "
    ::= { hwMusaAdlbAtucPerfCurr24hDataEntry 7 }

    adlbAtucCurr1DayErrFrames				OBJECT-TYPE
        SYNTAX  INTEGER
        ACCESS  read-only
        STATUS  mandatory
        DESCRIPTION
        " 当前24小时近端计数有错误的超帧数 "
    ::= { hwMusaAdlbAtucPerfCurr24hDataEntry 8 }

    adlbAtucCurr1DayBgBENotSES				OBJECT-TYPE
        SYNTAX  INTEGER
        ACCESS  read-only
        STATUS  mandatory
        DESCRIPTION
        " 当前24小时近端发生在非严重误码秒期间的BACKGROUND块错误数 "
    ::= { hwMusaAdlbAtucPerfCurr24hDataEntry 9 }

    adlbAtucCurr1DayErrSecond               OBJECT-TYPE
        SYNTAX  INTEGER
        ACCESS  read-only
        STATUS  mandatory
        DESCRIPTION
        " 当前24小时近端误码秒数 "
    ::= { hwMusaAdlbAtucPerfCurr24hDataEntry 10 }

    adlbAtucCurr1DaySevereErrSecond         OBJECT-TYPE
        SYNTAX  INTEGER
        ACCESS  read-only
        STATUS  mandatory
        DESCRIPTION
        " 当前24小时近端严重误码秒数 "
    ::= { hwMusaAdlbAtucPerfCurr24hDataEntry 11 }

    adlbAtucCurr1DayNonSESFrames            OBJECT-TYPE
        SYNTAX  INTEGER
        ACCESS  read-only
        STATUS  mandatory
        DESCRIPTION
        " 当前24小时近端无严重误码秒的超帧数 "
    ::= { hwMusaAdlbAtucPerfCurr24hDataEntry 12 }

    adlbAtucCurr1DayUnavailableSecond       OBJECT-TYPE
        SYNTAX  INTEGER
        ACCESS  read-only
        STATUS  mandatory
        DESCRIPTION
        " 当前24小时近端不可用时间秒计数� "
    ::= { hwMusaAdlbAtucPerfCurr24hDataEntry 13 }

    adlbAtucCurr1DayBitswaps                OBJECT-TYPE
        SYNTAX  INTEGER
        ACCESS  read-only
        STATUS  mandatory
        DESCRIPTION
        " 当前24小时近端发生的比特交换计数 "
    ::= { hwMusaAdlbAtucPerfCurr24hDataEntry 14 }

    adlbAtucCurr1DayLossSecond              OBJECT-TYPE
        SYNTAX  INTEGER
        ACCESS  read-only
        STATUS  mandatory
        DESCRIPTION
        " 当前24小时近端丢失的秒计数 "
    ::= { hwMusaAdlbAtucPerfCurr24hDataEntry 15 }

    adlbAtucCurr1DayFecSecond               OBJECT-TYPE
        SYNTAX  INTEGER
        ACCESS  read-only
        STATUS  mandatory
        DESCRIPTION
        " 当前24小时近端发生一次以上FEC的秒计数 "
    ::= { hwMusaAdlbAtucPerfCurr24hDataEntry 16 }

    adlbAtucCurr1DayFastRetrain             OBJECT-TYPE
        SYNTAX  INTEGER
        ACCESS  read-only
        STATUS  mandatory
        DESCRIPTION
        " 当前24小时发生快速重训练的次数 "
    ::= { hwMusaAdlbAtucPerfCurr24hDataEntry 17 }

    adlbAtucCurr1DayFastRetrainFail         OBJECT-TYPE
        SYNTAX  INTEGER
        ACCESS  read-only
        STATUS  mandatory
        DESCRIPTION
        " 当前24小时快速重训练失败的次数 "
    ::= { hwMusaAdlbAtucPerfCurr24hDataEntry 18 }
    
-- ***************************************************************
--     |    |－ADLB端口性能管理组
--     |    |   |－端口近端性能统计前24小时计数表（R）
--     |    |   |   |－#框号
--     |    |   |   |－#槽位号
--     |    |   |   |－#端口索引号        
--     |    |   |   |－前24小时近端交织通道发生CRC错的超帧计数                 
--     |    |   |   |－前24小时近端快速通道发生CRC错的超帧计数                 
--     |    |   |   |－前24小时近端交织通道发生FEC错的超帧计数                 
--     |    |   |   |－前24小时近端快速通道发生FEC错的超帧计数                 
--     |    |   |   |－前24小时发送的超帧数                                    
--     |    |   |   |－前24小时接收的超帧数                                    
--     |    |   |   |－前24小时近端计帧的时间,4000frames=1秒                   
--     |    |   |   |－前24小时近端计数有错误的超帧数                          
--     |    |   |   |－前24小时近端发生在非严重误码秒期间的BACKGROUND块错误数  
--     |    |   |   |－前24小时近端误码秒数                                    
--     |    |   |   |－前24小时近端严重误码秒数                                
--     |    |   |   |－前24小时近端无严重误码秒的超帧数                        
--     |    |   |   |－前24小时近端不可用时间秒计数                              
--     |    |   |   |－前24小时近端发生的比特交换计数                          
--     |    |   |   |－前24小时近端丢失的秒计数                                
--     |    |   |   |－前24小时近端发生一次以上FEC的秒计数                     
--     |    |   |   |－前24小时发生快速重训练的次数                            
--     |    |   |   |－前24小时快速重训练失败的次数                            
-- ***************************************************************

    -- 端口近端性能统计24小时计数表
    hwMusaAdlbAtucPerfPrev24hDataTable    OBJECT-TYPE
        SYNTAX      SEQUENCE OF HwMusaAdlbAtucPerfPrev24hDataEntry
        ACCESS      not-accessible
        STATUS      mandatory
    DESCRIPTION
    "Musa adlb port ATUC performance statistic data in previous 24 hours table."
    ::= { hwMusaAdlbPfm 7 }

    hwMusaAdlbAtucPerfPrev24hDataEntry    OBJECT-TYPE
        SYNTAX         HwMusaAdlbAtucPerfPrev24hDataEntry
        ACCESS         not-accessible
        STATUS         mandatory
    DESCRIPTION
    "This list contains adlb port ATUC performance statistic data in previous 24 hours variables."
    INDEX { hwMusaFrameIndex,
            hwMusaSlotIndex,
            adlbPortIndex }
    ::= { hwMusaAdlbAtucPerfPrev24hDataTable  1 }

    HwMusaAdlbAtucPerfPrev24hDataEntry    ::= SEQUENCE  {
       		adlbAtucPrev1DayCrcErrInterleave    	INTEGER,
		    adlbAtucPrev1DayCrcErrFast				INTEGER,
		    adlbAtucPrev1DayFecErrInterleave		INTEGER,
		    adlbAtucPrev1DayFecErrFast				INTEGER,
		    adlbAtucPrev1DaySuperFrameSent			INTEGER,
		    adlbAtucPrev1DaySuperFrameReceived	    INTEGER,
		    adlbAtucPrev1DayTimeCount	           	INTEGER,
		    adlbAtucPrev1DayErrFrames				INTEGER,
		    adlbAtucPrev1DayBgBENotSES				INTEGER,
		    adlbAtucPrev1DayErrSecond           	INTEGER,
		    adlbAtucPrev1DaySevereErrSecond        	INTEGER,
		    adlbAtucPrev1DayNonSESFrames           	INTEGER,
		    adlbAtucPrev1DayUnavailableSecond      	INTEGER,
		    adlbAtucPrev1DayBitswaps               	INTEGER,
		    adlbAtucPrev1DayLossSecond             	INTEGER,
		    adlbAtucPrev1DayFecSecond              	INTEGER,
		    adlbAtucPrev1DayFastRetrain            	INTEGER,
		    adlbAtucPrev1DayFastRetrainFail        	INTEGER
           	}                              

    adlbAtucPrev1DayCrcErrInterleave		OBJECT-TYPE
        SYNTAX  INTEGER
        ACCESS  read-only
        STATUS  mandatory
        DESCRIPTION
        " 前24小时近端交织通道发生CRC错的超帧计数 "
    ::= { hwMusaAdlbAtucPerfPrev24hDataEntry 1 }

    adlbAtucPrev1DayCrcErrFast				OBJECT-TYPE
        SYNTAX  INTEGER
        ACCESS  read-only
        STATUS  mandatory
        DESCRIPTION
        " 前24小时近端快速通道发生CRC错的超帧计数 "
    ::= { hwMusaAdlbAtucPerfPrev24hDataEntry 2 }

    adlbAtucPrev1DayFecErrInterleave		OBJECT-TYPE
        SYNTAX  INTEGER
        ACCESS  read-only
        STATUS  mandatory
        DESCRIPTION
        " 前24小时近端交织通道发生FEC错的超帧计数 "
    ::= { hwMusaAdlbAtucPerfPrev24hDataEntry 3 }

    adlbAtucPrev1DayFecErrFast				OBJECT-TYPE
        SYNTAX  INTEGER
        ACCESS  read-only
        STATUS  mandatory
        DESCRIPTION
        " 前24小时近端快速通道发生FEC错的超帧计数 "
    ::= { hwMusaAdlbAtucPerfPrev24hDataEntry 4 }

    adlbAtucPrev1DaySuperFrameSent			OBJECT-TYPE
        SYNTAX  INTEGER
        ACCESS  read-only
        STATUS  mandatory
        DESCRIPTION
        " 前24小时发送的超帧数 "
    ::= { hwMusaAdlbAtucPerfPrev24hDataEntry 5 }

    adlbAtucPrev1DaySuperFrameReceived	    OBJECT-TYPE
        SYNTAX  INTEGER
        ACCESS  read-only
        STATUS  mandatory
        DESCRIPTION
        " 前24小时接收的超帧数 "
    ::= { hwMusaAdlbAtucPerfPrev24hDataEntry 6 }

    adlbAtucPrev1DayTimeCount	           	OBJECT-TYPE
        SYNTAX  INTEGER
        ACCESS  read-only
        STATUS  mandatory
        DESCRIPTION
        " 前24小时近端计帧的时间,4000frames=1秒 "
    ::= { hwMusaAdlbAtucPerfPrev24hDataEntry 7 }

    adlbAtucPrev1DayErrFrames				OBJECT-TYPE
        SYNTAX  INTEGER
        ACCESS  read-only
        STATUS  mandatory
        DESCRIPTION
        " 前24小时近端计数有错误的超帧数 "
    ::= { hwMusaAdlbAtucPerfPrev24hDataEntry 8 }

    adlbAtucPrev1DayBgBENotSES				OBJECT-TYPE
        SYNTAX  INTEGER
        ACCESS  read-only
        STATUS  mandatory
        DESCRIPTION
        " 前24小时近端发生在非严重误码秒期间的BACKGROUND块错误数 "
    ::= { hwMusaAdlbAtucPerfPrev24hDataEntry 9 }

    adlbAtucPrev1DayErrSecond               OBJECT-TYPE
        SYNTAX  INTEGER
        ACCESS  read-only
        STATUS  mandatory
        DESCRIPTION
        " 前24小时近端误码秒数 "
    ::= { hwMusaAdlbAtucPerfPrev24hDataEntry 10 }

    adlbAtucPrev1DaySevereErrSecond         OBJECT-TYPE
        SYNTAX  INTEGER
        ACCESS  read-only
        STATUS  mandatory
        DESCRIPTION
        " 前24小时近端严重误码秒数 "
    ::= { hwMusaAdlbAtucPerfPrev24hDataEntry 11 }

    adlbAtucPrev1DayNonSESFrames            OBJECT-TYPE
        SYNTAX  INTEGER
        ACCESS  read-only
        STATUS  mandatory
        DESCRIPTION
        " 前24小时近端无严重误码秒的超帧数 "
    ::= { hwMusaAdlbAtucPerfPrev24hDataEntry 12 }

    adlbAtucPrev1DayUnavailableSecond       OBJECT-TYPE
        SYNTAX  INTEGER
        ACCESS  read-only
        STATUS  mandatory
        DESCRIPTION
        " 前24小时近端不可用时间秒计数 "
    ::= { hwMusaAdlbAtucPerfPrev24hDataEntry 13 }

    adlbAtucPrev1DayBitswaps                OBJECT-TYPE
        SYNTAX  INTEGER
        ACCESS  read-only
        STATUS  mandatory
        DESCRIPTION
        " 前24小时近端发生的比特交换计数 "
    ::= { hwMusaAdlbAtucPerfPrev24hDataEntry 14 }

    adlbAtucPrev1DayLossSecond              OBJECT-TYPE
        SYNTAX  INTEGER
        ACCESS  read-only
        STATUS  mandatory
        DESCRIPTION
        " 前24小时近端丢失的秒计数 "
    ::= { hwMusaAdlbAtucPerfPrev24hDataEntry 15 }

    adlbAtucPrev1DayFecSecond               OBJECT-TYPE
        SYNTAX  INTEGER
        ACCESS  read-only
        STATUS  mandatory
        DESCRIPTION
        " 前24小时近端发生一次以上FEC的秒计数 "
    ::= { hwMusaAdlbAtucPerfPrev24hDataEntry 16 }

    adlbAtucPrev1DayFastRetrain             OBJECT-TYPE
        SYNTAX  INTEGER
        ACCESS  read-only
        STATUS  mandatory
        DESCRIPTION
        " 前24小时发生快速重训练的次数 "
    ::= { hwMusaAdlbAtucPerfPrev24hDataEntry 17 }

    adlbAtucPrev1DayFastRetrainFail         OBJECT-TYPE
        SYNTAX  INTEGER
        ACCESS  read-only
        STATUS  mandatory
        DESCRIPTION
        " 前24小时快速重训练失败的次数 "
    ::= { hwMusaAdlbAtucPerfPrev24hDataEntry 18 }

-- ***************************************************************
--     |    |－ADLB端口性能管理组
--     |    |   |－端口远端性能统计总计数表（R）
--     |    |   |   |－#框号
--     |    |   |   |－#槽位号
--     |    |   |   |－#端口索引号        
--     |    |   |   |－远端交织通道发生CRC错的超帧总计数
--     |    |   |   |－远端快速通道发生CRC错的超帧总计数
--     |    |   |   |－远端交织通道发生FEC错的超帧总计数
--     |    |   |   |－远端快速通道发生FEC错的超帧总计数
--     |    |   |   |－远端计帧的时间,4000frames=1秒
--     |    |   |   |－远端计数有错误的超帧总数
--     |    |   |   |－远端发生在非严重误码秒期间的BACKGROUND块错误总数
--     |    |   |   |－远端误码秒总数
--     |    |   |   |－远端严重误码秒总数
--     |    |   |   |－远端无严重误码秒的超帧总数
--     |    |   |   |－远端不可用时间秒总计数
--     |    |   |   |－远端丢失的秒计数总数
--     |    |   |   |－远端发生一次以上FEC的秒计数总数
--     |    |   |   |－统计总计数的有效时长 (单位:15分钟)
-- ***************************************************************

    -- 端口远端性能统计总计数表
    hwMusaAdlbAturPerfDataTable    OBJECT-TYPE
        SYNTAX      SEQUENCE OF HwMusaAdlbAturPerfDataEntry
        ACCESS      not-accessible
        STATUS      mandatory
    DESCRIPTION
    "Musa adlb port ATUR performance statistic data until now table."
    ::= { hwMusaAdlbPfm 8 }

    hwMusaAdlbAturPerfDataEntry    OBJECT-TYPE
        SYNTAX         HwMusaAdlbAturPerfDataEntry
        ACCESS         not-accessible
        STATUS         mandatory
    DESCRIPTION
    "This list contains adlb port ATUR performance statistic data until now variables."
    INDEX { hwMusaFrameIndex,
            hwMusaSlotIndex,
            adlbPortIndex }
    ::= { hwMusaAdlbAturPerfDataTable  1 }

    HwMusaAdlbAturPerfDataEntry    ::= SEQUENCE  {
       		adlbAturCrcErrInterleave     	INTEGER,
		    adlbAturCrcErrFast				INTEGER,
		    adlbAturFecErrInterleave		INTEGER,
		    adlbAturFecErrFast				INTEGER,
		    adlbAturTimeCount	           	INTEGER,
		    adlbAturErrFrames				INTEGER,
		    adlbAturBgBENotSES				INTEGER,
		    adlbAturErrSecond               INTEGER,
		    adlbAturSevereErrSecond         INTEGER,
		    adlbAturNonSESFrames            INTEGER,
		    adlbAturUnavailableSecond       INTEGER,
		    adlbAturLossSecond              INTEGER,
		    adlbAturFecSecond               INTEGER,
		    adlbAturPerfValidIntervals      INTEGER
          	}
                                                                                        
    adlbAturCrcErrInterleave			OBJECT-TYPE
        SYNTAX  INTEGER
        ACCESS  read-only
        STATUS  mandatory
        DESCRIPTION
        " 远端交织通道发生CRC错的超帧总计数 "
    ::= { hwMusaAdlbAturPerfDataEntry 1 }

    adlbAturCrcErrFast				OBJECT-TYPE
        SYNTAX  INTEGER
        ACCESS  read-only
        STATUS  mandatory
        DESCRIPTION
        " 远端快速通道发生CRC错的超帧总计数 "
    ::= { hwMusaAdlbAturPerfDataEntry 2 }

    adlbAturFecErrInterleave		OBJECT-TYPE
        SYNTAX  INTEGER
        ACCESS  read-only
        STATUS  mandatory
        DESCRIPTION
        " 远端交织通道发生FEC错的超帧总计数 "
    ::= { hwMusaAdlbAturPerfDataEntry 3 }

    adlbAturFecErrFast				OBJECT-TYPE
        SYNTAX  INTEGER
        ACCESS  read-only
        STATUS  mandatory
        DESCRIPTION
        " 远端快速通道发生FEC错的超帧总计数 "
    ::= { hwMusaAdlbAturPerfDataEntry 4 }

    adlbAturTimeCount	           	OBJECT-TYPE
        SYNTAX  INTEGER
        ACCESS  read-only
        STATUS  mandatory
        DESCRIPTION
        " 远端计帧的时间,4000frames=1秒 "
    ::= { hwMusaAdlbAturPerfDataEntry 5 }

    adlbAturErrFrames				OBJECT-TYPE
        SYNTAX  INTEGER
        ACCESS  read-only
        STATUS  mandatory
        DESCRIPTION
        " 远端计数有错误的超帧总数 "
    ::= { hwMusaAdlbAturPerfDataEntry 6 }

    adlbAturBgBENotSES				OBJECT-TYPE
        SYNTAX  INTEGER
        ACCESS  read-only
        STATUS  mandatory
        DESCRIPTION
        " 远端发生在非严重误码秒期间的BACKGROUND块错误总数 "
    ::= { hwMusaAdlbAturPerfDataEntry 7 }

    adlbAturErrSecond               OBJECT-TYPE
        SYNTAX  INTEGER
        ACCESS  read-only
        STATUS  mandatory
        DESCRIPTION
        " 远端误码秒总数 "
    ::= { hwMusaAdlbAturPerfDataEntry 8 }

    adlbAturSevereErrSecond         OBJECT-TYPE
        SYNTAX  INTEGER
        ACCESS  read-only
        STATUS  mandatory
        DESCRIPTION
        " 远端严重误码秒总数 "
    ::= { hwMusaAdlbAturPerfDataEntry 9 }

    adlbAturNonSESFrames            OBJECT-TYPE
        SYNTAX  INTEGER
        ACCESS  read-only
        STATUS  mandatory
        DESCRIPTION
        " 远端无严重误码秒的超帧总数 "
    ::= { hwMusaAdlbAturPerfDataEntry 10 }

    adlbAturUnavailableSecond       OBJECT-TYPE
        SYNTAX  INTEGER
        ACCESS  read-only
        STATUS  mandatory
        DESCRIPTION
        " 远端不可用时间秒总计数 "
    ::= { hwMusaAdlbAturPerfDataEntry 11 }

    adlbAturLossSecond              OBJECT-TYPE
        SYNTAX  INTEGER
        ACCESS  read-only
        STATUS  mandatory
        DESCRIPTION
        " 远端丢失的秒计数总数 "
    ::= { hwMusaAdlbAturPerfDataEntry 12 }

    adlbAturFecSecond               OBJECT-TYPE
        SYNTAX  INTEGER
        ACCESS  read-only
        STATUS  mandatory
        DESCRIPTION
        " 远端发生一次以上FEC的秒计数总数 "
    ::= { hwMusaAdlbAturPerfDataEntry 13 }

	adlbAturPerfValidIntervals		OBJECT-TYPE
        SYNTAX  INTEGER
        ACCESS  read-only
        STATUS  mandatory
        DESCRIPTION
        " 统计总计数的有效时长 (单位:15分钟) "
    ::= { hwMusaAdlbAturPerfDataEntry 14 }
    
-- ***************************************************************
--     |    |－ADLB端口性能管理组
--     |    |   |－端口远端性能统计前15分钟计数表（R）
--     |    |   |   |－#框号
--     |    |   |   |－#槽位号
--     |    |   |   |－#端口索引号        
--     |    |   |   |－前15分钟远端交织通道发生CRC错的超帧计数
--     |    |   |   |－前15分钟远端快速通道发生CRC错的超帧计数
--     |    |   |   |－前15分钟远端交织通道发生FEC错的超帧计数
--     |    |   |   |－前15分钟远端快速通道发生FEC错的超帧计数
--     |    |   |   |－前15分钟远端计帧的时间,4000frames=1秒
--     |    |   |   |－前15分钟远端计数有错误的超帧数
--     |    |   |   |－前15分钟远端发生在非严重误码秒期间的BACKGROUND块错误数
--     |    |   |   |－前15分钟远端误码秒数
--     |    |   |   |－前15分钟远端严重误码秒数
--     |    |   |   |－前15分钟远端无严重误码的超帧数
--     |    |   |   |－前15分钟远端不可用时间秒计数
--     |    |   |   |－前15分钟远端丢失的秒计数
--     |    |   |   |－前15分钟远端发生一次以上FEC的秒计数
-- ***************************************************************

    -- 端口远端性能统计前15分钟计数表
    hwMusaAdlbAturPerfPrev15mDataTable    OBJECT-TYPE
        SYNTAX      SEQUENCE OF HwMusaAdlbAturPerfPrev15mDataEntry
        ACCESS      not-accessible
        STATUS      mandatory
    DESCRIPTION
    "Musa adlb port ATUR performance statistic data in previous 15 minutes table."
    ::= { hwMusaAdlbPfm 9 }

    hwMusaAdlbAturPerfPrev15mDataEntry    OBJECT-TYPE
        SYNTAX         HwMusaAdlbAturPerfPrev15mDataEntry
        ACCESS         not-accessible
        STATUS         mandatory
    DESCRIPTION
    "This list contains adlb port ATUR performance statistic data in previous 15 minutes variables."
    INDEX { hwMusaFrameIndex,
            hwMusaSlotIndex,
            adlbPortIndex }
    ::= { hwMusaAdlbAturPerfPrev15mDataTable  1 }

    HwMusaAdlbAturPerfPrev15mDataEntry    ::= SEQUENCE  {
       		adlbAturPrev15MinCrcErrInterleave     	INTEGER,
		    adlbAturPrev15MinCrcErrFast				INTEGER,
		    adlbAturPrev15MinFecErrInterleave		INTEGER,
		    adlbAturPrev15MinFecErrFast				INTEGER,
		    adlbAturPrev15MinTimeCount	           	INTEGER,
		    adlbAturPrev15MinErrFrames				INTEGER,
		    adlbAturPrev15MinBgBENotSES				INTEGER,
		    adlbAturPrev15MinErrSecond              INTEGER,
		    adlbAturPrev15MinSevereErrSecond        INTEGER,
		    adlbAturPrev15MinNonSESFrames           INTEGER,
		    adlbAturPrev15MinUnavailableSecond      INTEGER,
		    adlbAturPrev15MinLossSecond             INTEGER,
		    adlbAturPrev15MinFecSecond              INTEGER
          	}
                                                                                        
    adlbAturPrev15MinCrcErrInterleave			OBJECT-TYPE
        SYNTAX  INTEGER
        ACCESS  read-only
        STATUS  mandatory
        DESCRIPTION
        " 前15分钟远端交织通道发生CRC错的超帧计数 "
    ::= { hwMusaAdlbAturPerfPrev15mDataEntry 1 }

    adlbAturPrev15MinCrcErrFast				OBJECT-TYPE
        SYNTAX  INTEGER
        ACCESS  read-only
        STATUS  mandatory
        DESCRIPTION
        " 前15分钟远端快速通道发生CRC错的超帧计数 "
    ::= { hwMusaAdlbAturPerfPrev15mDataEntry 2 }

    adlbAturPrev15MinFecErrInterleave		OBJECT-TYPE
        SYNTAX  INTEGER
        ACCESS  read-only
        STATUS  mandatory
        DESCRIPTION
        " 前15分钟远端交织通道发生FEC错的超帧计数 "
    ::= { hwMusaAdlbAturPerfPrev15mDataEntry 3 }

    adlbAturPrev15MinFecErrFast				OBJECT-TYPE
        SYNTAX  INTEGER
        ACCESS  read-only
        STATUS  mandatory
        DESCRIPTION
        " 前15分钟远端快速通道发生FEC错的超帧计数 "
    ::= { hwMusaAdlbAturPerfPrev15mDataEntry 4 }

    adlbAturPrev15MinTimeCount	           	OBJECT-TYPE
        SYNTAX  INTEGER
        ACCESS  read-only
        STATUS  mandatory
        DESCRIPTION
        " 前15分钟远端计帧的时间,4000frames=1秒 "
    ::= { hwMusaAdlbAturPerfPrev15mDataEntry 5 }

    adlbAturPrev15MinErrFrames				OBJECT-TYPE
        SYNTAX  INTEGER
        ACCESS  read-only
        STATUS  mandatory
        DESCRIPTION
        " 前15分钟远端计数有错误的超帧数 "
    ::= { hwMusaAdlbAturPerfPrev15mDataEntry 6 }

    adlbAturPrev15MinBgBENotSES				OBJECT-TYPE
        SYNTAX  INTEGER
        ACCESS  read-only
        STATUS  mandatory
        DESCRIPTION
        " 前15分钟远端发生在非严重误码秒期间的BACKGROUND块错误数 "
    ::= { hwMusaAdlbAturPerfPrev15mDataEntry 7 }

    adlbAturPrev15MinErrSecond               OBJECT-TYPE
        SYNTAX  INTEGER
        ACCESS  read-only
        STATUS  mandatory
        DESCRIPTION
        " 前15分钟远端误码秒数 "
    ::= { hwMusaAdlbAturPerfPrev15mDataEntry 8 }

    adlbAturPrev15MinSevereErrSecond         OBJECT-TYPE
        SYNTAX  INTEGER
        ACCESS  read-only
        STATUS  mandatory
        DESCRIPTION
        " 前15分钟远端严重误码秒数 "
    ::= { hwMusaAdlbAturPerfPrev15mDataEntry 9 }

    adlbAturPrev15MinNonSESFrames            OBJECT-TYPE
        SYNTAX  INTEGER
        ACCESS  read-only
        STATUS  mandatory
        DESCRIPTION
        " 前15分钟远端无严重误码秒的超帧数 "
    ::= { hwMusaAdlbAturPerfPrev15mDataEntry 10 }

    adlbAturPrev15MinUnavailableSecond       OBJECT-TYPE
        SYNTAX  INTEGER
        ACCESS  read-only
        STATUS  mandatory
        DESCRIPTION
        " 前15分钟远端不可用时间秒计数 "
    ::= { hwMusaAdlbAturPerfPrev15mDataEntry 11 }

    adlbAturPrev15MinLossSecond              OBJECT-TYPE
        SYNTAX  INTEGER
        ACCESS  read-only
        STATUS  mandatory
        DESCRIPTION
        " 前15分钟远端丢失的秒计数 "
    ::= { hwMusaAdlbAturPerfPrev15mDataEntry 12 }

    adlbAturPrev15MinFecSecond               OBJECT-TYPE
        SYNTAX  INTEGER
        ACCESS  read-only
        STATUS  mandatory
        DESCRIPTION
        " 前15分钟远端发生一次以上FEC的秒计数 "
    ::= { hwMusaAdlbAturPerfPrev15mDataEntry 13 }

-- ***************************************************************
--     |    |－ADLB端口性能管理组
--     |    |   |－端口远端性能统计当前24小时表（R）
--     |    |   |   |－#框号
--     |    |   |   |－#槽位号
--     |    |   |   |－#端口索引号        
--     |    |   |   |－当前24小时远端交织通道发生CRC错的超帧计数
--     |    |   |   |－当前24小时远端快速通道发生CRC错的超帧计数
--     |    |   |   |－当前24小时远端交织通道发生FEC错的超帧计数
--     |    |   |   |－当前24小时远端快速通道发生FEC错的超帧计数
--     |    |   |   |－当前24小时远端计帧的时间,4000frames=1秒
--     |    |   |   |－当前24小时远端计数有错误的超帧数
--     |    |   |   |－当前24小时远端发生在非严重误码秒期间的BACKGROUND块错误数
--     |    |   |   |－当前24小时远端误码秒数
--     |    |   |   |－当前24小时远端严重误码秒数
--     |    |   |   |－当前24小时远端无严重误码的超帧数
--     |    |   |   |－当前24小时远端不可用时间秒计数
--     |    |   |   |－当前24小时远端丢失的秒计数
--     |    |   |   |－当前24小时远端发生一次以上FEC的秒计数
-- ***************************************************************

    -- 端口远端性能统计当前24小时计数表
    hwMusaAdlbAturPerfCurr24hDataTable    OBJECT-TYPE
        SYNTAX      SEQUENCE OF HwMusaAdlbAturPerfCurr24hDataEntry
        ACCESS      not-accessible
        STATUS      mandatory
    DESCRIPTION
    "Musa adlb port ATUR performance statistic data in current 24 hours table."
    ::= { hwMusaAdlbPfm 10 }

    hwMusaAdlbAturPerfCurr24hDataEntry    OBJECT-TYPE
        SYNTAX         HwMusaAdlbAturPerfCurr24hDataEntry
        ACCESS         not-accessible
        STATUS         mandatory
    DESCRIPTION
    "This list contains adlb port ATUR performance statistic data in current 24 hours variables."
    INDEX { hwMusaFrameIndex,
            hwMusaSlotIndex,
            adlbPortIndex }
    ::= { hwMusaAdlbAturPerfCurr24hDataTable  1 }

    HwMusaAdlbAturPerfCurr24hDataEntry    ::= SEQUENCE  {
       		adlbAturCurr1DayCrcErrInterleave     	INTEGER,
		    adlbAturCurr1DayCrcErrFast				INTEGER,
		    adlbAturCurr1DayFecErrInterleave		INTEGER,
		    adlbAturCurr1DayFecErrFast				INTEGER,
		    adlbAturCurr1DayTimeCount	           	INTEGER,
		    adlbAturCurr1DayErrFrames				INTEGER,
		    adlbAturCurr1DayBgBENotSES				INTEGER,
		    adlbAturCurr1DayErrSecond               INTEGER,
		    adlbAturCurr1DaySevereErrSecond         INTEGER,
		    adlbAturCurr1DayNonSESFrames            INTEGER,
		    adlbAturCurr1DayUnavailableSecond       INTEGER,
		    adlbAturCurr1DayLossSecond              INTEGER,
		    adlbAturCurr1DayFecSecond               INTEGER
          	}
                                                                                        
    adlbAturCurr1DayCrcErrInterleave		OBJECT-TYPE
        SYNTAX  INTEGER
        ACCESS  read-only
        STATUS  mandatory
        DESCRIPTION
        " 当前24小时远端交织通道发生CRC错的超帧计数 "
    ::= { hwMusaAdlbAturPerfCurr24hDataEntry 1 }

    adlbAturCurr1DayCrcErrFast				OBJECT-TYPE
        SYNTAX  INTEGER
        ACCESS  read-only
        STATUS  mandatory
        DESCRIPTION
        " 当前24小时远端快速通道发生CRC错的超帧计数 "
    ::= { hwMusaAdlbAturPerfCurr24hDataEntry 2 }

    adlbAturCurr1DayFecErrInterleave		OBJECT-TYPE
        SYNTAX  INTEGER
        ACCESS  read-only
        STATUS  mandatory
        DESCRIPTION
        " 当前24小时远端交织通道发生FEC错的超帧计数 "
    ::= { hwMusaAdlbAturPerfCurr24hDataEntry 3 }

    adlbAturCurr1DayFecErrFast				OBJECT-TYPE
        SYNTAX  INTEGER
        ACCESS  read-only
        STATUS  mandatory
        DESCRIPTION
        " 当前24小时远端快速通道发生FEC错的超帧计数 "
    ::= { hwMusaAdlbAturPerfCurr24hDataEntry 4 }

    adlbAturCurr1DayTimeCount	           	OBJECT-TYPE
        SYNTAX  INTEGER
        ACCESS  read-only
        STATUS  mandatory
        DESCRIPTION
        " 当前24小时远端计帧的时间,4000frames=1秒 "
    ::= { hwMusaAdlbAturPerfCurr24hDataEntry 5 }

    adlbAturCurr1DayErrFrames				OBJECT-TYPE
        SYNTAX  INTEGER
        ACCESS  read-only
        STATUS  mandatory
        DESCRIPTION
        " 当前24小时远端计数有错误的超帧数 "
    ::= { hwMusaAdlbAturPerfCurr24hDataEntry 6 }

    adlbAturCurr1DayBgBENotSES				OBJECT-TYPE
        SYNTAX  INTEGER
        ACCESS  read-only
        STATUS  mandatory
        DESCRIPTION
        " 当前24小时远端发生在非严重误码秒期间的BACKGROUND块错误数 "
    ::= { hwMusaAdlbAturPerfCurr24hDataEntry 7 }

    adlbAturCurr1DayErrSecond               OBJECT-TYPE
        SYNTAX  INTEGER
        ACCESS  read-only
        STATUS  mandatory
        DESCRIPTION
        " 当前24小时远端误码秒数 "
    ::= { hwMusaAdlbAturPerfCurr24hDataEntry 8 }

    adlbAturCurr1DaySevereErrSecond         OBJECT-TYPE
        SYNTAX  INTEGER
        ACCESS  read-only
        STATUS  mandatory
        DESCRIPTION
        " 当前24小时远端严重误码秒数 "
    ::= { hwMusaAdlbAturPerfCurr24hDataEntry 9 }

    adlbAturCurr1DayNonSESFrames            OBJECT-TYPE
        SYNTAX  INTEGER
        ACCESS  read-only
        STATUS  mandatory
        DESCRIPTION
        " 当前24小时远端无严重误码秒的超帧数 "
    ::= { hwMusaAdlbAturPerfCurr24hDataEntry 10 }

    adlbAturCurr1DayUnavailableSecond       OBJECT-TYPE
        SYNTAX  INTEGER
        ACCESS  read-only
        STATUS  mandatory
        DESCRIPTION
        " 当前24小时远端不可用时间计秒数 "
    ::= { hwMusaAdlbAturPerfCurr24hDataEntry 11 }

    adlbAturCurr1DayLossSecond              OBJECT-TYPE
        SYNTAX  INTEGER
        ACCESS  read-only
        STATUS  mandatory
        DESCRIPTION
        " 当前24小时远端丢失的秒计数 "
    ::= { hwMusaAdlbAturPerfCurr24hDataEntry 12 }

    adlbAturCurr1DayFecSecond               OBJECT-TYPE
        SYNTAX  INTEGER
        ACCESS  read-only
        STATUS  mandatory
        DESCRIPTION
        " 当前24小时远端发生一次以上FEC的秒计数 "
    ::= { hwMusaAdlbAturPerfCurr24hDataEntry 13 }

-- ***************************************************************
--     |    |－ADLB端口性能管理组
--     |    |   |－端口远端性能统计表（R）
--     |    |   |   |－#框号
--     |    |   |   |－#槽位号
--     |    |   |   |－#端口索引号        
--     |    |   |   |－前24小时远端交织通道发生CRC错的超帧计数
--     |    |   |   |－前24小时远端快速通道发生CRC错的超帧计数
--     |    |   |   |－前24小时远端交织通道发生FEC错的超帧计数
--     |    |   |   |－前24小时远端快速通道发生FEC错的超帧计数
--     |    |   |   |－前24小时远端计帧的时间,4000frames=1秒
--     |    |   |   |－前24小时远端计数有错误的超帧数
--     |    |   |   |－前24小时远端发生在非严重误码秒期间的BACKGROUND块错误数
--     |    |   |   |－前24小时远端误码秒数
--     |    |   |   |－前24小时远端严重误码秒数
--     |    |   |   |－前24小时远端无严重误码的超帧数
--     |    |   |   |－前24小时远端不可用时间秒计数
--     |    |   |   |－前24小时远端丢失的秒计数
--     |    |   |   |－前24小时远端发生一次以上FEC的秒计数
-- ***************************************************************

    -- 端口远端性能统计前24小时计数表
    hwMusaAdlbAturPerfPrev24hDataTable    OBJECT-TYPE
        SYNTAX      SEQUENCE OF HwMusaAdlbAturPerfPrev24hDataEntry
        ACCESS      not-accessible
        STATUS      mandatory
    DESCRIPTION
    "Musa adlb port ATUR performance statistic data in previous 24 hours table."
    ::= { hwMusaAdlbPfm 11}

    hwMusaAdlbAturPerfPrev24hDataEntry    OBJECT-TYPE
        SYNTAX         HwMusaAdlbAturPerfPrev24hDataEntry
        ACCESS         not-accessible
        STATUS         mandatory
    DESCRIPTION
    "This list contains adlb port ATUR performance statistic data in previous 24 hours variables."
    INDEX { hwMusaFrameIndex,
            hwMusaSlotIndex,
            adlbPortIndex }
    ::= { hwMusaAdlbAturPerfPrev24hDataTable  1 }

    HwMusaAdlbAturPerfPrev24hDataEntry    ::= SEQUENCE  {
       		adlbAturPrev1DayCrcErrInterleave     	INTEGER,
		    adlbAturPrev1DayCrcErrFast				INTEGER,
		    adlbAturPrev1DayFecErrInterleave		INTEGER,
		    adlbAturPrev1DayFecErrFast				INTEGER,
		    adlbAturPrev1DayTimeCount	           	INTEGER,
		    adlbAturPrev1DayErrFrames				INTEGER,
		    adlbAturPrev1DayBgBENotSES				INTEGER,
		    adlbAturPrev1DayErrSecond               INTEGER,
		    adlbAturPrev1DaySevereErrSecond         INTEGER,
		    adlbAturPrev1DayNonSESFrames            INTEGER,
		    adlbAturPrev1DayUnavailableSecond       INTEGER,
		    adlbAturPrev1DayLossSecond              INTEGER,
		    adlbAturPrev1DayFecSecond               INTEGER
          	}
                                                                                        
    adlbAturPrev1DayCrcErrInterleave		OBJECT-TYPE
        SYNTAX  INTEGER
        ACCESS  read-only
        STATUS  mandatory
        DESCRIPTION
        " 前24小时远端交织通道发生CRC错的超帧计数 "
    ::= { hwMusaAdlbAturPerfPrev24hDataEntry 1 }

    adlbAturPrev1DayCrcErrFast				OBJECT-TYPE
        SYNTAX  INTEGER
        ACCESS  read-only
        STATUS  mandatory
        DESCRIPTION
        " 前24小时远端快速通道发生CRC错的超帧计数 "
    ::= { hwMusaAdlbAturPerfPrev24hDataEntry 2 }

    adlbAturPrev1DayFecErrInterleave		OBJECT-TYPE
        SYNTAX  INTEGER
        ACCESS  read-only
        STATUS  mandatory
        DESCRIPTION
        " 前24小时远端交织通道发生FEC错的超帧计数 "
    ::= { hwMusaAdlbAturPerfPrev24hDataEntry 3 }

    adlbAturPrev1DayFecErrFast				OBJECT-TYPE
        SYNTAX  INTEGER
        ACCESS  read-only
        STATUS  mandatory
        DESCRIPTION
        " 前24小时远端快速通道发生FEC错的超帧计数 "
    ::= { hwMusaAdlbAturPerfPrev24hDataEntry 4 }

    adlbAturPrev1DayTimeCount	           	OBJECT-TYPE
        SYNTAX  INTEGER
        ACCESS  read-only
        STATUS  mandatory
        DESCRIPTION
        " 前24小时远端计帧的时间,4000frames=1秒 "
    ::= { hwMusaAdlbAturPerfPrev24hDataEntry 5 }

    adlbAturPrev1DayErrFrames				OBJECT-TYPE
        SYNTAX  INTEGER
        ACCESS  read-only
        STATUS  mandatory
        DESCRIPTION
        " 前24小时远端计数有错误的超帧数 "
    ::= { hwMusaAdlbAturPerfPrev24hDataEntry 6 }

    adlbAturPrev1DayBgBENotSES				OBJECT-TYPE
        SYNTAX  INTEGER
        ACCESS  read-only
        STATUS  mandatory
        DESCRIPTION
        " 前24小时远端发生在非严重误码秒期间的BACKGROUND块错误数 "
    ::= { hwMusaAdlbAturPerfPrev24hDataEntry 7 }

    adlbAturPrev1DayErrSecond               OBJECT-TYPE
        SYNTAX  INTEGER
        ACCESS  read-only
        STATUS  mandatory
        DESCRIPTION
        " 前24小时远端误码秒数 "
    ::= { hwMusaAdlbAturPerfPrev24hDataEntry 8 }

    adlbAturPrev1DaySevereErrSecond         OBJECT-TYPE
        SYNTAX  INTEGER
        ACCESS  read-only
        STATUS  mandatory
        DESCRIPTION
        " 前24小时远端严重误码秒数 "
    ::= { hwMusaAdlbAturPerfPrev24hDataEntry 9 }

    adlbAturPrev1DayNonSESFrames            OBJECT-TYPE
        SYNTAX  INTEGER
        ACCESS  read-only
        STATUS  mandatory
        DESCRIPTION
        " 前24小时远端无严重误码秒的超帧数 "
    ::= { hwMusaAdlbAturPerfPrev24hDataEntry 10 }

    adlbAturPrev1DayUnavailableSecond       OBJECT-TYPE
        SYNTAX  INTEGER
        ACCESS  read-only
        STATUS  mandatory
        DESCRIPTION
        " 前24小时远端不可用时间秒计数 "
    ::= { hwMusaAdlbAturPerfPrev24hDataEntry 11 }

    adlbAturPrev1DayLossSecond              OBJECT-TYPE
        SYNTAX  INTEGER
        ACCESS  read-only
        STATUS  mandatory
        DESCRIPTION
        " 前24小时远端丢失的秒计数 "
    ::= { hwMusaAdlbAturPerfPrev24hDataEntry 12 }

    adlbAturPrev1DayFecSecond               OBJECT-TYPE
        SYNTAX  INTEGER
        ACCESS  read-only
        STATUS  mandatory
        DESCRIPTION
        " 前24小时远端发生一次以上FEC的秒计数 "
    ::= { hwMusaAdlbAturPerfPrev24hDataEntry 13 }

-- ***************************************************************
--     |    |－ADLB端口性能管理组
--     |    |   |－端口当前线路近端故障状态表（R）
--     |    |   |   |－#框号
--     |    |   |   |－#槽位号
--     |    |   |   |－#端口索引号        
--     |    |   |   |－近端丢失导频信号
--     |    |   |   |－近端严重帧错误
--     |    |   |   |－近端信号失步
--     |    |   |   |－近端帧失步
--     |    |   |   |－近端交织通道缓冲区CRC校验错,上报FEBE:近端块错误
--     |    |   |   |－近端非交织通道缓冲区CRC校验错,上报FEBE:近端块错误
--     |    |   |   |－近端交织通道前向错误校正指示
--     |    |   |   |－近端非交织通道前向错误校正指示
-- ***************************************************************

    -- 端口当前线路近端故障状态表
    hwMusaAdlbAtucLineDefectTable    OBJECT-TYPE
        SYNTAX      SEQUENCE OF HwMusaAdlbAtucLineDefectEntry
        ACCESS      not-accessible
        STATUS      mandatory
    DESCRIPTION
    "Musa adlb port ATUC line defect state table."
    ::= { hwMusaAdlbPfm 12 }

    hwMusaAdlbAtucLineDefectEntry    OBJECT-TYPE
        SYNTAX         HwMusaAdlbAtucLineDefectEntry
        ACCESS         not-accessible
        STATUS         mandatory
    DESCRIPTION
    "This list contains adlb port ATUC line defect state variables."
    INDEX { hwMusaFrameIndex,
            hwMusaSlotIndex,
            adlbPortIndex }
    ::= { hwMusaAdlbAtucLineDefectTable  1 }

    HwMusaAdlbAtucLineDefectEntry    ::= SEQUENCE  {
		    adlbAtucLpsState    			INTEGER,
		    adlbAtucSefState	       		INTEGER,
		    adlbAtucLosState                INTEGER,
		    adlbAtucLofState                INTEGER,
		    adlbAtucFebeInterleaveState     INTEGER,
		    adlbAtucFebeFastState  			INTEGER,
		    adlbAtucFecInterleaveState     	INTEGER,
		    adlbAtucFecFastState  			INTEGER
           	}                              
                                                                                        
    adlbAtucLpsState				OBJECT-TYPE
        SYNTAX  INTEGER
        ACCESS  read-only
        STATUS  mandatory
        DESCRIPTION
        " 近端丢失导频信号 "
    ::= { hwMusaAdlbAtucLineDefectEntry 1 }

    adlbAtucSefState	       		OBJECT-TYPE
        SYNTAX  INTEGER
        ACCESS  read-only
        STATUS  mandatory
        DESCRIPTION
        " 近端严重帧错误 "
    ::= { hwMusaAdlbAtucLineDefectEntry 2 }

    adlbAtucLosState           		OBJECT-TYPE
        SYNTAX  INTEGER
        ACCESS  read-only
        STATUS  mandatory
        DESCRIPTION
        " 近端信号失步 "
    ::= { hwMusaAdlbAtucLineDefectEntry 3 }

    adlbAtucLofState           		OBJECT-TYPE
        SYNTAX  INTEGER
        ACCESS  read-only
        STATUS  mandatory
        DESCRIPTION
        " 近端帧失步 "
    ::= { hwMusaAdlbAtucLineDefectEntry 4 }

    adlbAtucFebeInterleaveState		OBJECT-TYPE
        SYNTAX  INTEGER
        ACCESS  read-only
        STATUS  mandatory
        DESCRIPTION
        " 近端交织通道缓冲区CRC校验错,上报FEBE:远端块错误 "
    ::= { hwMusaAdlbAtucLineDefectEntry 5 }

    adlbAtucFebeFastState   		OBJECT-TYPE
        SYNTAX  INTEGER
        ACCESS  read-only
        STATUS  mandatory
        DESCRIPTION
        " 近端非交织通道缓冲区CRC校验错,上报FEBE:远端块错误 "
    ::= { hwMusaAdlbAtucLineDefectEntry 6 }

    adlbAtucFecInterleaveState 		OBJECT-TYPE
        SYNTAX  INTEGER
        ACCESS  read-only
        STATUS  mandatory
        DESCRIPTION
        " 近端交织通道前向错误校正指示 "
    ::= { hwMusaAdlbAtucLineDefectEntry 7 }

    adlbAtucFecFastState	  		OBJECT-TYPE
        SYNTAX  INTEGER
        ACCESS  read-only
        STATUS  mandatory
        DESCRIPTION
        " 近端非交织通道前向错误校正指示 "
    ::= { hwMusaAdlbAtucLineDefectEntry 8 }

-- ***************************************************************
--     |    |－ADLB端口性能管理组
--     |    |   |－端口当前线路远端故障状态表（R）                          
--     |    |   |   |－#框号                                                
--     |    |   |   |－#槽位号                                              
--     |    |   |   |－#端口索引号                                          
--     |    |   |   |－远端设备丢失导频信号                                 
--     |    |   |   |－远端设备远端故障(sef)指示                            
--     |    |   |   |－远端设备信号失步                                     
--     |    |   |   |－远端设备远端失效指示                                 
--     |    |   |   |－远端交织通道缓冲区CRC校验错,上报FEBE:远端块错误      
--     |    |   |   |－远端非交织通道缓冲区CRC校验错,上报FEBE:远端块错误    
--     |    |   |   |－远端交织通道前向错误校正指示                         
--     |    |   |   |－远端非交织通道前向错误校正指示                       
-- ***************************************************************

    -- 端口当前线路远端故障状态表
    hwMusaAdlbAturLineDefectTable    OBJECT-TYPE
        SYNTAX      SEQUENCE OF HwMusaAdlbAturLineDefectEntry
        ACCESS      not-accessible
        STATUS      mandatory
    DESCRIPTION
    "Musa adlb port ATUR line defect state table."
    ::= { hwMusaAdlbPfm 13 }

    hwMusaAdlbAturLineDefectEntry    OBJECT-TYPE
        SYNTAX         HwMusaAdlbAturLineDefectEntry
        ACCESS         not-accessible
        STATUS         mandatory
    DESCRIPTION
    "This list contains adlb port ATUR line defect state variables."
    INDEX { hwMusaFrameIndex,
            hwMusaSlotIndex,
            adlbPortIndex }
    ::= { hwMusaAdlbAturLineDefectTable  1 }

    HwMusaAdlbAturLineDefectEntry    ::= SEQUENCE  {
		    adlbAturLpsState 				INTEGER,
		    adlbAturRdiState   				INTEGER,
		    adlbAturLosState           		INTEGER,
		    adlbAturFriState           		INTEGER,
		    adlbAturFebeInterleaveState		INTEGER,
		    adlbAturFebeFastState  			INTEGER,
		    adlbAturFecInterleaveState 		INTEGER,
		    adlbAturFecFastState	  		INTEGER
           	}                              
                                                                                        
    adlbAturLpsState				OBJECT-TYPE
        SYNTAX  INTEGER
        ACCESS  read-only
        STATUS  mandatory
        DESCRIPTION
        " 远端设备丢失导频信号 "
    ::= { hwMusaAdlbAturLineDefectEntry 1 }

    adlbAturRdiState	       		OBJECT-TYPE
        SYNTAX  INTEGER
        ACCESS  read-only
        STATUS  mandatory
        DESCRIPTION
        " 远端设备远端故障(sef)指示 "
    ::= { hwMusaAdlbAturLineDefectEntry 2 }

    adlbAturLosState           		OBJECT-TYPE
        SYNTAX  INTEGER
        ACCESS  read-only
        STATUS  mandatory
        DESCRIPTION
        " 远端设备信号失步 "
    ::= { hwMusaAdlbAturLineDefectEntry 3 }

    adlbAturFriState           		OBJECT-TYPE
        SYNTAX  INTEGER
        ACCESS  read-only
        STATUS  mandatory
        DESCRIPTION
        " 远端设备远端失效指示 "
    ::= { hwMusaAdlbAturLineDefectEntry 4 }

    adlbAturFebeInterleaveState		OBJECT-TYPE
        SYNTAX  INTEGER
        ACCESS  read-only
        STATUS  mandatory
        DESCRIPTION
        " 远端交织通道缓冲区CRC校验错,上报FEBE:远端块错误 "
    ::= { hwMusaAdlbAturLineDefectEntry 5 }

    adlbAturFebeFastState	  		OBJECT-TYPE
        SYNTAX  INTEGER
        ACCESS  read-only
        STATUS  mandatory
        DESCRIPTION
        " 远端非交织通道缓冲区CRC校验错,上报FEBE:远端块错误 "
    ::= { hwMusaAdlbAturLineDefectEntry 6 }

    adlbAturFecInterleaveState 		OBJECT-TYPE
        SYNTAX  INTEGER
        ACCESS  read-only
        STATUS  mandatory
        DESCRIPTION
        " 远端交织通道前向错误校正指示 "
    ::= { hwMusaAdlbAturLineDefectEntry 7 }

    adlbAturFecFastState	  		OBJECT-TYPE
        SYNTAX  INTEGER
        ACCESS  read-only
        STATUS  mandatory
        DESCRIPTION
        " 远端非交织通道前向错误校正指示 "
    ::= { hwMusaAdlbAturLineDefectEntry 8 }

-- ***************************************************************
--     |    |－ADLB端口性能管理组
--     |    |   |－端口当前ATM层近端故障状态表（R）
--     |    |   |   |－#框号
--     |    |   |   |－#槽位号
--     |    |   |   |－#端口索引号        
--     |    |   |   |－近端交织通道信元头校正指示
--     |    |   |   |－近端快速通道信元头校正指示
--     |    |   |   |－近端交织通道无信元定界指示
--     |    |   |   |－近端快速通道无信元定界指示
--     |    |   |   |－近端交织通道信元定界丢失指示
--     |    |   |   |－近端非交织通道信元定界丢失指示
--     |    |   |   |－近端交织通道信元定界丢失故障
--     |    |   |   |－近端非交织通道信元定界丢失故障
-- ***************************************************************

    -- 端口当前ATM层近端故障状态表
    hwMusaAdlbAtucAtmDefectTable    OBJECT-TYPE
        SYNTAX      SEQUENCE OF HwMusaAdlbAtucAtmDefectEntry
        ACCESS      not-accessible
        STATUS      mandatory
    DESCRIPTION
    "Musa adlb port ATUC atm defect state table."
    ::= { hwMusaAdlbPfm 14 }

    hwMusaAdlbAtucAtmDefectEntry    OBJECT-TYPE
        SYNTAX         HwMusaAdlbAtucAtmDefectEntry
        ACCESS         not-accessible
        STATUS         mandatory
    DESCRIPTION
    "This list contains adlb port ATUC atm defect state variables."
    INDEX { hwMusaFrameIndex,
            hwMusaSlotIndex,
            adlbPortIndex }
    ::= { hwMusaAdlbAtucAtmDefectTable  1 }

    HwMusaAdlbAtucAtmDefectEntry    ::= SEQUENCE  {
		    adlbAtucHecInterleave        	INTEGER,
		    adlbAtucHecFast			        INTEGER,
		    adlbAtucNcdInterleave           INTEGER,
		    adlbAtucNcdFast			        INTEGER,
		    adlbAtucOcdInterleave           INTEGER,
		    adlbAtucOcdFast			        INTEGER,
		    adlbAtucLcdInterleave           INTEGER,
		    adlbAtucLcdFast			        INTEGER
           	}                              
                                                                                        
    adlbAtucHecInterleave			OBJECT-TYPE
        SYNTAX  INTEGER
        ACCESS  read-only
        STATUS  mandatory
        DESCRIPTION
        " 近端交织通道信元头校正指示 "
    ::= { hwMusaAdlbAtucAtmDefectEntry 1 }

    adlbAtucHecFast			        OBJECT-TYPE
        SYNTAX  INTEGER
        ACCESS  read-only
        STATUS  mandatory
        DESCRIPTION
        " 近端快速通道信元头校正指示 "
    ::= { hwMusaAdlbAtucAtmDefectEntry 2 }

    adlbAtucNcdInterleave           OBJECT-TYPE
        SYNTAX  INTEGER
        ACCESS  read-only
        STATUS  mandatory
        DESCRIPTION
        " 近端交织通道无信元定界指示 "
    ::= { hwMusaAdlbAtucAtmDefectEntry 3 }

    adlbAtucNcdFast			        OBJECT-TYPE
        SYNTAX  INTEGER
        ACCESS  read-only
        STATUS  mandatory
        DESCRIPTION
        " 近端快速通道无信元定界指示 "
    ::= { hwMusaAdlbAtucAtmDefectEntry 4 }

    adlbAtucOcdInterleave           OBJECT-TYPE
        SYNTAX  INTEGER
        ACCESS  read-only
        STATUS  mandatory
        DESCRIPTION
        " 近端交织通道信元定界丢失指示 "
    ::= { hwMusaAdlbAtucAtmDefectEntry 5 }

    adlbAtucOcdFast			        OBJECT-TYPE
        SYNTAX  INTEGER
        ACCESS  read-only
        STATUS  mandatory
        DESCRIPTION
        " 近端非交织通道信元定界丢失指示 "
    ::= { hwMusaAdlbAtucAtmDefectEntry 6 }

    adlbAtucLcdInterleave           OBJECT-TYPE
        SYNTAX  INTEGER
        ACCESS  read-only
        STATUS  mandatory
        DESCRIPTION
        " 近端交织通道信元定界丢失故障 "
    ::= { hwMusaAdlbAtucAtmDefectEntry 7 }

    adlbAtucLcdFast			        OBJECT-TYPE
        SYNTAX  INTEGER
        ACCESS  read-only
        STATUS  mandatory
        DESCRIPTION
        " 近端非交织通道信元定界丢失故障 "
    ::= { hwMusaAdlbAtucAtmDefectEntry 8 }

-- ***************************************************************
--     |    |－ADLB端口性能管理组
--     |    |   |－端口当前ATM层远端故障状态表（R）
--     |    |   |   |－#框号
--     |    |   |   |－#槽位号
--     |    |   |   |－#端口索引号        
--     |    |   |   |－远端交织通道信元头校正指示
--     |    |   |   |－远端快速通道信元头校正指示
--     |    |   |   |－远端交织通道无信元定界指示
--     |    |   |   |－远端快速通道无信元定界指示
--     |    |   |   |－远端交织通道信元定界丢失指示
--     |    |   |   |－远端非交织通道信元定界丢失指示
--     |    |   |   |－远端交织通道信元定界丢失故障
--     |    |   |   |－远端非交织通道信元定界丢失故障
-- ***************************************************************

    -- 端口当前ATM层远端故障状态表
    hwMusaAdlbAturAtmDefectTable    OBJECT-TYPE
        SYNTAX      SEQUENCE OF HwMusaAdlbAturAtmDefectEntry
        ACCESS      not-accessible
        STATUS      mandatory
    DESCRIPTION
    "Musa adlb port ATUR atm defect state table."
    ::= { hwMusaAdlbPfm 15 }

    hwMusaAdlbAturAtmDefectEntry    OBJECT-TYPE
        SYNTAX         HwMusaAdlbAturAtmDefectEntry
        ACCESS         not-accessible
        STATUS         mandatory
    DESCRIPTION
    "This list contains adlb port ATUR atm defect state variables."
    INDEX { hwMusaFrameIndex,
            hwMusaSlotIndex,
            adlbPortIndex }
    ::= { hwMusaAdlbAturAtmDefectTable  1 }

    HwMusaAdlbAturAtmDefectEntry    ::= SEQUENCE  {
		    adlbAturHecInterleave        	INTEGER,
		    adlbAturHecFast        			INTEGER,
		    adlbAturNcdInterleave           INTEGER,
		    adlbAturNcdFast        			INTEGER,
		    adlbAturOcdInterleave           INTEGER,
		    adlbAturOcdFast        			INTEGER,
		    adlbAturLcdInterleave           INTEGER,
		    adlbAturLcdFast        			INTEGER
           	}                              
                                                                                        
    adlbAturHecInterleave			OBJECT-TYPE
        SYNTAX  INTEGER
        ACCESS  read-only
        STATUS  mandatory
        DESCRIPTION
        " 远端交织通道信元头校正指示 "
    ::= { hwMusaAdlbAturAtmDefectEntry 1 }

    adlbAturHecFast			        OBJECT-TYPE
        SYNTAX  INTEGER
        ACCESS  read-only
        STATUS  mandatory
        DESCRIPTION
        " 远端快速通道信元头校正指示 "
    ::= { hwMusaAdlbAturAtmDefectEntry 2 }

    adlbAturNcdInterleave           OBJECT-TYPE
        SYNTAX  INTEGER
        ACCESS  read-only
        STATUS  mandatory
        DESCRIPTION
        " 远端交织通道无信元定界指示 "
    ::= { hwMusaAdlbAturAtmDefectEntry 3 }

    adlbAturNcdFast			        OBJECT-TYPE
        SYNTAX  INTEGER
        ACCESS  read-only
        STATUS  mandatory
        DESCRIPTION
        " 远端快速通道无信元定界指示 "
    ::= { hwMusaAdlbAturAtmDefectEntry 4 }

    adlbAturOcdInterleave           OBJECT-TYPE
        SYNTAX  INTEGER
        ACCESS  read-only
        STATUS  mandatory
        DESCRIPTION
        " 远端交织通道信元定界丢失指示 "
    ::= { hwMusaAdlbAturAtmDefectEntry 5 }

    adlbAturOcdFast			        OBJECT-TYPE
        SYNTAX  INTEGER
        ACCESS  read-only
        STATUS  mandatory
        DESCRIPTION
        " 远端非交织通道信元定界丢失指示 "
    ::= { hwMusaAdlbAturAtmDefectEntry 6 }

    adlbAturLcdInterleave           OBJECT-TYPE
        SYNTAX  INTEGER
        ACCESS  read-only
        STATUS  mandatory
        DESCRIPTION
        " 远端交织通道信元定界丢失故障 "
    ::= { hwMusaAdlbAturAtmDefectEntry 7 }

    adlbAturLcdFast			        OBJECT-TYPE
        SYNTAX  INTEGER
        ACCESS  read-only
        STATUS  mandatory
        DESCRIPTION
        " 远端非交织通道信元定界丢失故障 "
    ::= { hwMusaAdlbAturAtmDefectEntry 8 }

-- ***************************************************************
--     |    |－ADLB端口性能管理组
--     |    |   |－端口载波比特分配表（R）
--     |    |   |   |－#框号
--     |    |   |   |－#槽位号
--     |    |   |   |－#端口索引号 
--     |    |   |   |－下行每个帧所分配的BIT数
--     |    |   |   |－上行每个帧所分配的BIT数
--     |    |   |   |－下行子载波BIT数的分配情况
--     |    |   |   |－上行子载波BIT数的分配情况
-- ***************************************************************

    -- 端口载波比特分配表
    hwMusaAdlbPortBitsTable    OBJECT-TYPE
        SYNTAX      SEQUENCE OF HwMusaAdlbPortBitsEntry
        ACCESS      not-accessible
        STATUS      mandatory
    DESCRIPTION
    "Musa adlb port bits distribution table."
    ::= { hwMusaAdlbPfm 16 }

    hwMusaAdlbPortBitsEntry    OBJECT-TYPE
        SYNTAX         HwMusaAdlbPortBitsEntry
        ACCESS         not-accessible
        STATUS         mandatory
    DESCRIPTION
    "This list contains adlb port bits distribution variables."
    INDEX { hwMusaFrameIndex,
            hwMusaSlotIndex,
            adlbPortIndex }
    ::= { hwMusaAdlbPortBitsTable  1 }

    HwMusaAdlbPortBitsEntry    ::= SEQUENCE  {
		    adlbDnBitsPerFrame        INTEGER,
		    adlbUpBitsPerFrame        INTEGER,
		    adlbDnBitAllocate		  DisplayString,
		    adlbUpBitAllocate		  DisplayString
           	}                              
                                                                                        
    adlbDnBitsPerFrame			OBJECT-TYPE
        SYNTAX  INTEGER
        ACCESS  read-only
        STATUS  mandatory
        DESCRIPTION
        " 下行每个帧所分配的BIT数 "
    ::= { hwMusaAdlbPortBitsEntry 1 }
    
    adlbUpBitsPerFrame			OBJECT-TYPE
        SYNTAX  INTEGER
        ACCESS  read-only
        STATUS  mandatory
        DESCRIPTION
        " 上行每个帧所分配的BIT数 "
    ::= { hwMusaAdlbPortBitsEntry 2 }
    
    adlbDnBitAllocate		  OBJECT-TYPE
        SYNTAX  DisplayString
        ACCESS  read-only
        STATUS  mandatory
        DESCRIPTION
        " 下行子载波BIT数的分配情况 "
    ::= { hwMusaAdlbPortBitsEntry 3 }
    
    adlbUpBitAllocate		  OBJECT-TYPE
        SYNTAX  DisplayString
        ACCESS  read-only
        STATUS  mandatory
        DESCRIPTION
        " 上行子载波BIT数的分配情况 "
    ::= { hwMusaAdlbPortBitsEntry 4 }
    

-- ***************************************************************
--     |    |－ADLB端口性能管理组
--     |    |   |－端口载波信噪比分配表（R）
--     |    |   |   |－#框号
--     |    |   |   |－#槽位号
--     |    |   |   |－#端口号 
--     |    |   |   |－下行子载波信噪比的分配情况(单位:0.5db)
--     |    |   |   |－上行子载波信噪比的分配情况(单位:0.5db)
-- ***************************************************************

    -- 端口载波信噪比分配表
    hwMusaAdlbCarrierSnrTable    OBJECT-TYPE
        SYNTAX      SEQUENCE OF HwMusaAdlbCarrierSnrEntry
        ACCESS      not-accessible
        STATUS      mandatory
    DESCRIPTION
    "Musa adlb port carrier snr distribution table."
    ::= { hwMusaAdlbPfm 17 }

    hwMusaAdlbCarrierSnrEntry    OBJECT-TYPE
        SYNTAX         HwMusaAdlbCarrierSnrEntry
        ACCESS         not-accessible
        STATUS         mandatory
    DESCRIPTION
    "This list contains adlb port carrier snr distribution variables."
    INDEX { hwMusaFrameIndex,
            hwMusaSlotIndex,
            adlbPortIndex }
    ::= { hwMusaAdlbCarrierSnrTable  1 }

    HwMusaAdlbCarrierSnrEntry    ::= SEQUENCE  {    
		    adlbDnSnrAllocate   DisplayString,
		    adlbUpSnrAllocate   DisplayString
           	}                              
                                                                                        
    adlbDnSnrAllocate 		OBJECT-TYPE
        SYNTAX  DisplayString
        ACCESS  read-only
        STATUS  mandatory
        DESCRIPTION
        " 下行子载波信噪比的分配情况(单位:0.5db) "
    ::= { hwMusaAdlbCarrierSnrEntry 1 }
    
    adlbUpSnrAllocate		OBJECT-TYPE
        SYNTAX  DisplayString
        ACCESS  read-only
        STATUS  mandatory
        DESCRIPTION
        " 上行子载波信噪比的分配情况(单位:0.5db) "
    ::= { hwMusaAdlbCarrierSnrEntry 2 }

-- ***************************************************************
--     |    |－ADLB维测管理组
--     |    |   |－端口维测表（W） 
--     |    |   |   |－#框号
--     |    |   |   |－#槽位号
--     |    |   |   |－#端口索引号 
--     |    |   |   |－端口环回（W）(
--     |    |	|   |	1:命MODEM端口的ATM层(AS0与LS0两通道环回)环回
--     |    |   |   |	2:ADLB申请ATU-R上报破坏的CRC
--     |    |   |   |	3:ADLB停止申请ATU-R上报破坏的CRC
--     |    |   |   |	4:ADLB发送破坏的CRC
--     |    |   |   |	5:ADLB发送破坏的CRC停止
--     |    |   |   |	6:ADLB申请ATU-R进行自测试
--     |    |   |   |	7:ADLB申请ATU-R修改测试参数(衰减与噪声容限) )
-- ***************************************************************

    -- 端口维测表
    hwMusaAdlbPortTestTable    OBJECT-TYPE
        SYNTAX      SEQUENCE OF HwMusaAdlbPortTestEntry
        ACCESS      not-accessible
        STATUS      mandatory
    DESCRIPTION
    "Musa adlb port test table."
    ::= { hwMusaAdlbTest 1 }

   hwMusaAdlbPortTestEntry    OBJECT-TYPE
        SYNTAX         HwMusaAdlbPortTestEntry
        ACCESS         not-accessible
        STATUS         mandatory
    DESCRIPTION
    "This list contains Musa adlb port test variables."
    INDEX { hwMusaFrameIndex,
            hwMusaSlotIndex,
            adlbPortIndex }
    ::= { hwMusaAdlbPortTestTable  1 }

   HwMusaAdlbPortTestEntry    ::= SEQUENCE  {
   			adlbPortTestOper		INTEGER
            }            
    
    adlbPortTestOper		OBJECT-TYPE
        SYNTAX  INTEGER {
                            atmLoop			(1), 
                            aturErrCrc		(2),
                            stopAturErrCrc	(3),
                            sendErrCrc		(4),
                            stopSendErrCrc	(5),
                            aturAutoLoop	(6),
                            aturChgLoopParam(7)                            
                       }
        ACCESS  write-only
        STATUS  mandatory
        DESCRIPTION
        " 端口环回（W）(
			1:命MODEM端口的ATM层(AS0与LS0两通道环回)环回
			2:ADLB申请ATU-R上报破坏的CRC
			3:ADLB停止申请ATU-R上报破坏的CRC
			4:ADLB发送破坏的CRC
			5:ADLB发送破坏的CRC停止
			6:ADLB申请ATU-R进行自测试
			7:ADLB申请ATU-R修改测试参数(衰减与噪声容限) ) "
    ::= { hwMusaAdlbPortTestEntry 1 }
        
  
END
