Wellfleet-NML-MIB DEFINITIONS ::= BEGIN

-- Created by mdl2asn version 3.1
-- Creation date: Wed Aug 30 16:45:56 EDT 1995


    IMPORTS

      IpAddress, Counter, Gauge, TimeTicks, Opaque, enterprises, mgmt
        FROM RFC1155-SMI
      OBJECT-TYPE
        FROM RFC-1212
      TRAP-TYPE
        FROM RFC-1215
      DisplayString, mib-2
        FROM RFC1213-MIB
      wfBridgeGroup
        FROM Wellfleet-COMMON-MIB;

    wfBrNativeModeLan	OBJECT IDENTIFIER ::= { wfBridgeGroup 5 }

    wfNmlBaseTable OBJECT-TYPE
        SYNTAX	SEQUENCE OF WfNmlBaseEntry
        ACCESS	not-accessible
        STATUS	mandatory
        DESCRIPTION
                "NML Base record - Contains NML Configuration parameters"
        ::= { wfBrNativeModeLan 2 }

    wfNmlBaseEntry OBJECT-TYPE
        SYNTAX	WfNmlBaseEntry
        ACCESS	not-accessible
        STATUS	mandatory
        DESCRIPTION
                "An entry in the NML Base table"
        INDEX	{ wfNmlCircuit }
        ::= { wfNmlBaseTable 1 }

    WfNmlBaseEntry ::= SEQUENCE {
    	    wfNmlDelete
    		INTEGER,
    	    wfNmlDisable
    		INTEGER,
    	    wfNmlCircuit
    		INTEGER,
    	    wfNmlAddSecurityHeader
    		INTEGER,
    	    wfNmlSAIDType
    		INTEGER,
    	    wfNmlSAIDValue
    		INTEGER,
    	    wfNmlCUGValue
    		INTEGER,
    	    wfNmlCUGDrop
    		INTEGER,
    	    wfNmlCUGPacketsDropped
    		INTEGER
        }

    wfNmlDelete OBJECT-TYPE
        SYNTAX	INTEGER {
    		    created(1),
    		    deleted(2)
    		}
        ACCESS	read-write
        STATUS	mandatory
        DESCRIPTION
                "Create/Delete parameter"
        DEFVAL	{ created }
        ::= { wfNmlBaseEntry 1 }

    wfNmlDisable OBJECT-TYPE
        SYNTAX	INTEGER {
    		    enabled(1),
    		    disabled(2)
    		}
        ACCESS	read-write
        STATUS	mandatory
        DESCRIPTION
                "Enable/Disable parameter"
        DEFVAL	{ enabled }
        ::= { wfNmlBaseEntry 2 }

    wfNmlCircuit OBJECT-TYPE
        SYNTAX	INTEGER
        ACCESS	read-only
        STATUS	mandatory
        DESCRIPTION
                "Circuit being used"
        ::= { wfNmlBaseEntry 3 }

    wfNmlAddSecurityHeader OBJECT-TYPE
        SYNTAX	INTEGER {
    		    add(1),
    		    check(2),
    		    drop(3)
    		}
        ACCESS	read-write
        STATUS	mandatory
        DESCRIPTION
                "Indicates if Security header should be added and verified
                or just verified on egress of this circuit"
        DEFVAL	{ add }
        ::= { wfNmlBaseEntry 4 }

    wfNmlSAIDType OBJECT-TYPE
        SYNTAX	INTEGER {
    		    individual(1),
    		    group(2)
    		}
        ACCESS	read-write
        STATUS	mandatory
        DESCRIPTION
                "Type of SAID to be used. Group or individual"
        DEFVAL	{ individual }
        ::= { wfNmlBaseEntry 5 }

    wfNmlSAIDValue OBJECT-TYPE
        SYNTAX	INTEGER
        ACCESS	read-write
        STATUS	mandatory
        DESCRIPTION
                "Indicates value for Group or Individual SAID"
        ::= { wfNmlBaseEntry 6 }

    wfNmlCUGValue OBJECT-TYPE
        SYNTAX	INTEGER
        ACCESS	read-write
        STATUS	mandatory
        DESCRIPTION
                "Indicates Closed User Group id to be placed in MDF field of frame"
        ::= { wfNmlBaseEntry 7 }

    wfNmlCUGDrop OBJECT-TYPE
        SYNTAX	INTEGER {
    		    drop(1),
    		    forward(2)
    		}
        ACCESS	read-write
        STATUS	mandatory
        DESCRIPTION
                "Indicates action to perfrom if security search of table fails"
        DEFVAL	{ drop }
        ::= { wfNmlBaseEntry 8 }

    wfNmlCUGPacketsDropped OBJECT-TYPE
        SYNTAX	INTEGER
        ACCESS	read-only
        STATUS	mandatory
        DESCRIPTION
                "Indicates packets dropped for security check"
        ::= { wfNmlBaseEntry 9 }

    wfNmlTrafficFilterTable OBJECT-TYPE
        SYNTAX	SEQUENCE OF WfNmlTrafficFilterEntry
        ACCESS	not-accessible
        STATUS	mandatory
        DESCRIPTION
                "Native mode Lan Traffic Filters"
        ::= { wfBrNativeModeLan 3 }

    wfNmlTrafficFilterEntry OBJECT-TYPE
        SYNTAX	WfNmlTrafficFilterEntry
        ACCESS	not-accessible
        STATUS	mandatory
        DESCRIPTION
                "An entry in wfNmlTrafficFilterTable."
        INDEX	{ wfNmlTrafficFilterCircuit,
    		  wfNmlTrafficFilterRuleNumber,
    		  wfNmlTrafficFilterFragment }
        ::= { wfNmlTrafficFilterTable 1 }

    WfNmlTrafficFilterEntry ::= SEQUENCE {
    	    wfNmlTrafficFilterCreate
    		INTEGER,
    	    wfNmlTrafficFilterEnable
    		INTEGER,
    	    wfNmlTrafficFilterStatus
    		INTEGER,
    	    wfNmlTrafficFilterCounter
    		Counter,
    	    wfNmlTrafficFilterDefinition
    		Opaque,
    	    wfNmlTrafficFilterReserved
    		INTEGER,
    	    wfNmlTrafficFilterCircuit
    		INTEGER,
    	    wfNmlTrafficFilterRuleNumber
    		INTEGER,
    	    wfNmlTrafficFilterFragment
    		INTEGER,
    	    wfNmlTrafficFilterName
    		DisplayString
        }

    wfNmlTrafficFilterCreate OBJECT-TYPE
        SYNTAX	INTEGER {
    		    created(1),
    		    deleted(2)
    		}
        ACCESS	read-write
        STATUS	mandatory
        DESCRIPTION
                "Defines the existence of the traffic filter rule:
                created - traffic filter exists
                delete - traffic filter does not exist and can be deleted."
        DEFVAL	{ created }
        ::= { wfNmlTrafficFilterEntry 1 }

    wfNmlTrafficFilterEnable OBJECT-TYPE
        SYNTAX	INTEGER {
    		    enabled(1),
    		    disabled(2)
    		}
        ACCESS	read-write
        STATUS	mandatory
        DESCRIPTION
                "Defines whether or not the traffic filter rule should be used:
                enabled - activate the rule.
                disabled - inactivate the rule."
        DEFVAL	{ enabled }
        ::= { wfNmlTrafficFilterEntry 2 }

    wfNmlTrafficFilterStatus OBJECT-TYPE
        SYNTAX	INTEGER {
    		    active(1),
    		    error(2),
    		    inactive(3)
    		}
        ACCESS	read-only
        STATUS	mandatory
        DESCRIPTION
                "Defines the current status of the traffic filter:
                inactive - the rule is not in use.
                active - the rule is being used.
                error - the application detected an error in the rule."
        DEFVAL	{ inactive }
        ::= { wfNmlTrafficFilterEntry 3 }

    wfNmlTrafficFilterCounter OBJECT-TYPE
        SYNTAX	Counter
        ACCESS	read-only
        STATUS	mandatory
        DESCRIPTION
                "The number of received packets that have
                matched this rule."
        ::= { wfNmlTrafficFilterEntry 4 }

    wfNmlTrafficFilterDefinition OBJECT-TYPE
        SYNTAX	Opaque
        ACCESS	read-write
        STATUS	mandatory
        DESCRIPTION
                "The filter rule definition."
        ::= { wfNmlTrafficFilterEntry 5 }

    wfNmlTrafficFilterReserved OBJECT-TYPE
        SYNTAX	INTEGER
        ACCESS	read-only
        STATUS	mandatory
        DESCRIPTION
                "Reserved field."
        ::= { wfNmlTrafficFilterEntry 6 }

    wfNmlTrafficFilterCircuit OBJECT-TYPE
        SYNTAX	INTEGER
        ACCESS	read-only
        STATUS	mandatory
        DESCRIPTION
                "The ID of the Bridge Circuit to which the
                filter is applied."
        ::= { wfNmlTrafficFilterEntry 7 }

    wfNmlTrafficFilterRuleNumber OBJECT-TYPE
        SYNTAX	INTEGER
        ACCESS	read-only
        STATUS	mandatory
        DESCRIPTION
                "ID for the rule."
        ::= { wfNmlTrafficFilterEntry 8 }

    wfNmlTrafficFilterFragment OBJECT-TYPE
        SYNTAX	INTEGER
        ACCESS	read-only
        STATUS	mandatory
        DESCRIPTION
                "Fragment number - for large rules."
        ::= { wfNmlTrafficFilterEntry 9 }

    wfNmlTrafficFilterName OBJECT-TYPE
        SYNTAX	DisplayString
        ACCESS	read-write
        STATUS	mandatory
        DESCRIPTION
                "name of the rule number"
        ::= { wfNmlTrafficFilterEntry 10 }

    END  -- Wellfleet-NML-MIB
