--
-- Based on General System MIB dated: 06-10-96
-- MIB Revision Dated: 06-27-96 
-- Updated after meeting with OSCAR Development Team
-- MIB Revision Dated: 09-24-96 
-- 
-- MIB Revision : 1.0 dated 1-17-97
-- Change Desc. : None. 
-- 
-- MIB Revision : 1.1 dated 2-4-97
-- Change Desc. : Swapped object in Frimware Inf. group for cosmetic reasons.
-- 
-- 
-- MIB Revision : 1.2 dated 2-19-97
-- Change Desc. : Modified system configuration and smart config. objects
-- 
-- 
-- MIB Revision : 1.3 dated 2-25-97
-- Change Desc. : Modified sytem card table, system control group 
--                and system firmware group. -A.Llanes 
-- 
-- 
-- MIB Revision : 1.4 dated 3-10-97
-- Change Desc. : Fixed McmSysCardEntry by removing "String" from the object 
--                mcmSysCardPcbRevisionString. -A.Llanes 
-- 
-- MIB Revision : 1.5 dated 3-13-97
-- Change Desc. : Range check changes.
-- 
-- 
-- MIB Revision : 1.6 dated 3-24-97
-- Change Desc. : Add mcmSysValidateCommunityGroup, modify power supply types, and 
--                add a new field for receive bandwidth utilization and renamed the 
--                existing link bandwidth utilization to link transmit bandwidth 
--                utilization. -A.Llanes
-- 
-- MIB Revision : 1.7 dated 4-16-97
-- Change Desc. : Changes trap ENTERPRISE from micom-oscar to micom-system. A. Llanes
-- 
-- 
-- MIB Revision : 1.8 dated 4-17-97
-- Change Desc. : Change the Trap Subscription Action from 
--                write-only to read-write, as per Robert Thacker's request. A. Llanes
-- 
-- 
-- MIB Revision : 1.9 dated 4-25-97
-- Change Desc. : Correct range values in the mcmSysTimeOfDayGroup group
-- 
-- *** RELEASE 1.1 ***
-- MIB Revision : 1.10 dated 4-15-97
-- Change Desc. : Support rollback functionality and 
--                modify Console Port group. A. Llanes
--
-- MIB Revision : 1.11 dated 4-30-97
-- Change Desc. : Added FR DCE related changes as per FR DCE/HTDS MIB 
--		Req't Document (dated 4/20/97) - R. Carmona.
-- 
--
-- MIB Revision : 1.12 dated 5-07-97
-- Change Desc. : Changed Community table index to an enumeration 
--                to support rel 1.1 CAPABILITIES.  - S.Gaur/Shridhar K.
--
--
-- MIB Revision : 1.13 dated 5-8-97
-- Change Desc. : Rearranged FR DCE related objects for SNMP compliance
--		for modifications from 4400 1.0 to 4400 1.1.
--		Merged Community String's Range from 0..25 to 1..25 to
--		disallow NULL Community names. - R. Carmona
--
--
-- MIB Revision : 1.14 dated 5-13-97
-- Change Desc. : Modified the access level of the object 
--                LastCommunityPriviledgeLevel to six
--                member enumerated string to reflect the 
--                CAPABILITIES functionality-Shridhar
--
-- MIB Revision : 1.15 dated 6-03-97
-- Change Desc. : Added System Rollback Traps, added and 
--                renamed enumerations for mcmSysRestartReason,
--                added mcmSysRollbackStatus, and modified
--                mcmSysRollbackConfirm, as per Mario Cedillo's
--                request. - A. LLanes  
--
-- MIB Revision : 1.16 dated 6-26-97
-- Change Desc. : Added two extra objects to the end of the
--                system card table to support Nortel nomenclature
--                for the 4400 H/W. -A.Llanes
-- 
-- MIB Revision : 1.17 dated 6-27-97
-- Change Desc. : Added Trap Descriptions. -A.Llanes 
--
-- *** RELEASE 2.0 ***
-- MIB Revision : 2.0 dated 7-24-97
-- Change Desc. : Added enumerations for SysIfExtType objects
--		  for ISDN functionality as per 7/22/97 meeting
--		  with RC, Bhushan, Klaus S., Bernd S., Amparo,
--		  MG, DS, and TM.  -R. Carmona 
--
-- MIB Revision : 2.1 dated 8-26-97
-- Change Desc. : Modified mcmSysRestartReason object based on Brian P.'s request.
--                And, Introduction of DCE-Conn device type. - B. Jafari
--
-- MIB Revision : 2.2 dated 9-15-97
-- Change Desc. : Minor modification to enumerations requested by Brian P. (duplicates)
--                and other fixes to fix compilation problems       -S. Gaur
--
-- MIB Revision : 2.3 dated 10-8-97
-- Change Desc. : Replaced MPA with 4400, and other minor changes. - B. Jafari. 
--
-- MIB Revision : 2.4 dated 10-17-97
-- Change Desc. : Added isdn-LAPD and isdn-BRI device types. - B. Jafari. 
--
-- MIB Revision : 2.5 dated 10-28-97
-- Change Desc. : Introduced 'lim' (logical interface module) to reflect 
--                a card's former 'slot' notation; e.g. 'slotB' is 
--                now regarded as 'limB', and added four 'lim' types
--                for future expansion. - B. Jafari.
--
-- MIB Revision : 2.6 dated 10-31-97
-- Change Desc. : Modified CAPABILITIES for objects inside mcmSysCommitTrackingGroup. - B. Jafari. 
--
--
-- MIB Revision : 2.7 dated 11-06-97
-- Change Desc. : Changed all object names and descriptions that had "slot" to module. -S. Gaur 
--
--
-- MIB Revision : 2.8 dated 1-05-98
-- Change Desc. : Modified the System card table name to System LIM table.
--                Reorganized the (mcm/nvm)SysLimModuleAddress and (mcm/nvm)SysIfExtModule
--                enumerations to enforce better guidelines for LIM ordering on 
--                the Passport 4400.
--                Added the mcmSysPhysTable to map a particular physical slot
--                to the corresponding Logical Interface Module (LIM).
--                Changed all object names and descriptions that had card to LIM.
--                                                                                    - S. Gaur
--
-- MIB Revision : 2.9 dated 3-06-98
-- Change Desc. : Changed SYNTAX field for mcmSysCfgDRAMSize and mcmSysCfgFlashMemorySize 
--                objects.  The format was changed from bytes to megabytes.           - S. Gaur 
--
--*** RELEASE 2.1 ***
-- MIB Revision : 3.0 dated 4-09-98
-- Change Desc. : Added enumerations for (mcm/nvm)SysIfExtPPADeviceType for release
--                2.1 ISDN BRI voice card functionality.
--         
--
-- *** RELEASE 3.0 *** 
-- MIB Revision : 3.1 dated 6-25-98
-- Change Desc. : Deprecated the mcmSysHWTypeModelType object, replacing 
--                its functionality with the mcmSysHWTypeCPUType object.
--                Added the mcmSysHWTypeGenCfgType and  
--                mcmSysTimeOfLastReset objects. 
--                Added enumeration thirty seven to the
--                (mcm/nvm)SysIfExtPPADeviceType.        
--                Replaced all instances of the "4400" string with the 
--                generic string "access device".
--                                               -S. Gaur
--
-- MIB Revision : 3.2 dated 8-17-98
-- Change Desc. : Added enumeration 38 to 40 (mcm/nvm)SysIfExtPPADeviceType. 
--                Please note this enmumeration was wrongly defined for 
--                mcmIfextType in the previous revision. 
--                Changes per K. Seggelke.
--                                                              - S. Gaur
--
-- MIB Revision : 3.3 dated 8-24-98
-- Change Desc. : Changed enumeration 1 from "4300" to "reserved" for 
--                mcmSysHWTypeGenCfgType.
--                                                              - S. Gaur
-- MIB Revision : 3.2 dated 8-28-98
-- Change Desc. : Merged From BRI branch to 3.1 branch.
--                Moved down ISDN-Voice enumerations for 
--                (mcm/nvm)SysIfExtPPADeviceType.
--                                                              - S. Gaur
-- MIB Revision : 3.4 dated 11-02-98
-- Change Desc. : Severity Levels were added to Traps.
--						-F. Kottab
--
MICOM-SYS-MIB DEFINITIONS ::= BEGIN
	IMPORTS
                TimeTicks
                                FROM RFC1155-SMI 
		Counter, Gauge, IpAddress 
                   		FROM RFC1155-SMI
		OBJECT-TYPE
                    		FROM RFC-1212
		TRAP-TYPE
                		FROM RFC-1215
	    	micom-oscar 
		    		FROM MICOM-OSCAR-MIB
		DisplayString 
				FROM SNMPv2-TC;


-- group OBJECT IDENTIFIERs



	micom-system			OBJECT IDENTIFIER ::= {micom-oscar 1}

	sys-configuration		OBJECT IDENTIFIER ::= {micom-system 1}
	sys-control			OBJECT IDENTIFIER ::= {micom-system 2}
	sys-statistics			OBJECT IDENTIFIER ::= {micom-system 3}
	sys-trap			OBJECT IDENTIFIER ::= {micom-system 4}


mcmSysHWTypeGroup    OBJECT IDENTIFIER ::= {sys-configuration 1}

mcmSysHWTypeModelType OBJECT-TYPE
	SYNTAX	DisplayString (SIZE (50))
	ACCESS	read-only
	STATUS	deprecated
	DESCRIPTION
	  "NAME = ;
	   DESC = **NOTE: THIS OBJECT HAS BEEN  \
                  DEPRECATED. Its functionality \
                  has been replaced by the      \
                  mcmSysHWTypeCPUType object    \
                  located below in this group.**\
                                                \  
                  The model name/type of the \
                  access device.;
	   HELP = ;
	   CAPABILITIES = NET_CFG, VPN_DISP;"
	 ::= { mcmSysHWTypeGroup 1}

mcmSysHWTypeRevisionLevel OBJECT-TYPE
	SYNTAX	INTEGER
	ACCESS	read-only
	STATUS	mandatory
	DESCRIPTION
	  "NAME = ;
	   DESC = The revision level of the \
                  access device.;
	   HELP = ;
	   CAPABILITIES = NET_CFG, VPN_DISP;"
	 ::= { mcmSysHWTypeGroup 2}

mcmSysHWTypeManufRevDate OBJECT-TYPE
	SYNTAX	DisplayString (SIZE (25))
	ACCESS	read-only
	STATUS	mandatory
	DESCRIPTION
	  "NAME = ;
	   DESC = The manufacture/revision date \
                  of the access device .;
	   HELP = ;
	   CAPABILITIES = NET_CFG, VPN_DISP;"
	 ::= { mcmSysHWTypeGroup 3}

mcmSysHWTypeSerialNumber OBJECT-TYPE
	SYNTAX	DisplayString (SIZE (9))
	ACCESS	read-only
	STATUS	mandatory
	DESCRIPTION
	  "NAME = ;
	   DESC = The serial number of \
                  the access device..;
	   HELP = ;
	   CAPABILITIES = NET_CFG, VPN_DISP;"
	 ::= { mcmSysHWTypeGroup 4}

mcmSysHWTypeModuleID OBJECT-TYPE
	SYNTAX	INTEGER
	ACCESS	read-only
	STATUS	mandatory
	DESCRIPTION
	  "NAME = ;
	   DESC = The module ID of the access \
                  device.;
	   HELP = ;
	   CAPABILITIES = NET_CFG, VPN_DISP;"
	 ::= { mcmSysHWTypeGroup 5}

mcmSysHWTypeMACAddress OBJECT-TYPE
	SYNTAX	OCTET STRING (SIZE(6))
	ACCESS	read-only
	STATUS	mandatory
	DESCRIPTION
	  "NAME = ;
	   DESC = The base MAC address assigned \
                  to the access device.;
	   HELP = ;
	   CAPABILITIES = NET_CFG, VPN_DISP;"
	 ::= { mcmSysHWTypeGroup 6}

mcmSysHWTypeCPUType OBJECT-TYPE
	SYNTAX	DisplayString (SIZE (50))
	ACCESS	read-only
	STATUS	mandatory
	DESCRIPTION
	  "NAME = ;
	   DESC = Indicates the CPU type for this \
                  access device;
	   HELP = ;
	   CAPABILITIES = NET_CFG, VPN_DISP;"
	 ::= { mcmSysHWTypeGroup 7}

mcmSysHWTypeGenCfgType OBJECT-TYPE
	SYNTAX	INTEGER {
                reserved     (1),
                passport4400 (2)
                }
	ACCESS	read-only
	STATUS	mandatory
	DESCRIPTION
	  "NAME = ;
	   DESC = Indicates the model type for this \
                  access device.;
	   HELP = ;
	   CAPABILITIES = NET_CFG, VPN_DISP;"
	 ::= { mcmSysHWTypeGroup 8}

mcmSysCfgGroup    OBJECT IDENTIFIER ::= {sys-configuration 2}

mcmSysCfgCPUConfiguration OBJECT-TYPE
	SYNTAX	INTEGER {
		base (1),
		companion040 (2),
		companion060 (3)
		}
	ACCESS	read-only
	STATUS	mandatory
	DESCRIPTION
	  "NAME = ;
	   DESC = The CPU configuration for this
                  access device.;
	   HELP = ;
	   CAPABILITIES = NET_CFG, VPN_DISP;"
	 ::= { mcmSysCfgGroup 1}

mcmSysCfgPrimaryWANPort OBJECT-TYPE
	SYNTAX	INTEGER {
		present (1),
		notPresent (2)
		}
	ACCESS	read-only
	STATUS	mandatory
	DESCRIPTION
	  "NAME = ;
	   DESC = Indicates the presence of the \
                  Primary WAN port.;
	   HELP = ;
	   CAPABILITIES = NET_CFG, VPN_DISP;"
	 ::= { mcmSysCfgGroup 2}

mcmSysCfgPrimaryWANPortPhyMedia OBJECT-TYPE
	SYNTAX	INTEGER {
		none (1),
		unknown (2),
		link56k (3),
		generalserial (4),
		t1e1 (5),
		isdn (6)
		}
	ACCESS	read-only
	STATUS	mandatory
	DESCRIPTION
	  "NAME = ;
	   DESC = Indicates the physical media 
                  of Primary WAN port.;
	   HELP = ;
	   CAPABILITIES = NET_CFG, VPN_DISP;"
	 ::= { mcmSysCfgGroup 3}

mcmSysCfgDCESerialPortPhyMedia OBJECT-TYPE
	SYNTAX	INTEGER {
		none (1),
		unknown (2),
		rs232(3),
		v35 (4),
		v36 (5),
		x21 (6)
		}
	ACCESS	read-only
	STATUS	mandatory
	DESCRIPTION
	  "NAME = ;
	   DESC = Indicates the detected DCE \
                  serial port on the access \ 
                  device.;
	   HELP = ;
	   CAPABILITIES = NET_CFG, VPN_DISP;"
	 ::= { mcmSysCfgGroup 4}

mcmSysCfgQUICCExpansionModule1 OBJECT-TYPE
	SYNTAX	INTEGER {
		present (1),
		notPresent (2)
		}
	ACCESS	read-only
	STATUS	mandatory
	DESCRIPTION
	  "NAME = ;
	   DESC = QUICC Expansion module detected.;
	   HELP = ;
	   CAPABILITIES = NET_CFG, VPN_DISP;"
	 ::= { mcmSysCfgGroup 5}

mcmSysCfgQUICCExpansionModule2 OBJECT-TYPE
	SYNTAX	INTEGER {
		present (1),
		notPresent (2)
		}
	ACCESS	read-only
	STATUS	mandatory
	DESCRIPTION
	  "NAME = ;
	   DESC = QUICC Expansion module-2 is detected.;
	   HELP = ;
	   CAPABILITIES = NET_CFG, VPN_DISP;"
	 ::= { mcmSysCfgGroup 6}

mcmSysCfgFeatureRTCBatteryStatus OBJECT-TYPE
	SYNTAX	INTEGER {
		noBattery (1),
		batteryLow (2),
		batteryOK (3)
		}
	ACCESS	read-only
	STATUS	mandatory
	DESCRIPTION
	  "NAME = ;
	   DESC = TimeOfDay/SRAM module detected.;
	   HELP = ;
	   CAPABILITIES = NET_CFG, VPN_DISP;"
	 ::= { mcmSysCfgGroup 7}

mcmSysCfgDRAMSize OBJECT-TYPE
	SYNTAX	INTEGER {
                size4Mbytes  (1),
                size8Mbytes  (2),
                size16Mbytes (3),
                size32Mbytes (4),
                size64Mbytes (5)
                }
	ACCESS	read-only
	STATUS	mandatory
	DESCRIPTION
	  "NAME = ;
	   DESC = Total installed DRAM memory size in megabytes.;
	   HELP = ;
	   CAPABILITIES = NET_CFG, VPN_DISP;"
	 ::= { mcmSysCfgGroup 8}

mcmSysCfgFlashMemorySize OBJECT-TYPE
	SYNTAX	INTEGER {
                size4Mbytes  (1),
                size8Mbytes  (2),
                size16Mbytes (3),
                size32Mbytes (4),
                size64Mbytes (5)
                }
	ACCESS	read-only
	STATUS	mandatory
	DESCRIPTION
	  "NAME = ;
	   DESC = Total installed Flash memory size in megabytes.;
	   HELP = ;
	   CAPABILITIES = NET_CFG, VPN_DISP;"
	 ::= { mcmSysCfgGroup 9}


-- LIM Table

mcmSysLimTable OBJECT-TYPE
	SYNTAX	SEQUENCE OF McmSysLimEntry
	ACCESS	not-accessible
	STATUS	mandatory
	DESCRIPTION
	  "NAME = ;
	   DESC = Table to view an individual Logical \
                  Interface Modules(LIM) on the access \
                  device.;
	   HELP = Table to view the hardware \
	   CAPABILITIES = NET_CFG, VPN_DISP;"
	::= {sys-configuration 3}

mcmSysLimEntry OBJECT-TYPE
	SYNTAX	McmSysLimEntry
	ACCESS	not-accessible
	STATUS	mandatory
	DESCRIPTION
	  "NAME = ;
	   DESC = Entry pertaining to a specific logical module.;
	   HELP = This includes the Name, Part number, and rev. level.;
	   CAPABILITIES = ;"
	INDEX		{mcmSysLimModuleAddress}
	::= {mcmSysLimTable 1}

McmSysLimEntry ::= SEQUENCE {
	mcmSysLimModuleAddress		INTEGER,
	mcmSysLimModuleName		DisplayString,
	mcmSysLimPcbPartNumber	        DisplayString,
        mcmSysLimPcbRelease             DisplayString,
	mcmSysLimSerialNumber		DisplayString,
	mcmSysLimMfgDate		DisplayString
	}

mcmSysLimModuleAddress OBJECT-TYPE
	SYNTAX	INTEGER {
		limA (1),
		lim1 (2),
		lim2 (3),
		lim3 (4),
		lim4 (5),
		limB (6),
		limC (7),
		limD (8),
		limE (9)
		}
	ACCESS	read-only
	STATUS	mandatory
	DESCRIPTION
	  "NAME = ;
	   DESC = lim (logical interface module) identifies \
                  the address of the module within the unit;
	   HELP = ;
	   CAPABILITIES = ;"
	::= {mcmSysLimEntry 1}

mcmSysLimModuleName OBJECT-TYPE
	SYNTAX  DisplayString (SIZE(0..20))	
	ACCESS	read-only
	STATUS	mandatory
	DESCRIPTION
	  "NAME = ;
	   DESC = Displays the name of the module \
		  in the specific location;
                  NOTE : this object was previously named \
                  mcmSysCardModuleName.;
	   HELP = ;
           CAPABILITIES = ;"
	::= {mcmSysLimEntry 2}

mcmSysLimPcbPartNumber OBJECT-TYPE
	SYNTAX  DisplayString (SIZE(0..16))	
	ACCESS	read-only
	STATUS	mandatory
	DESCRIPTION
	  "NAME = ;
	   DESC = Displays the part number of the module in \
                  the specific location;
	   HELP = ;
           CAPABILITIES = ;"
	::= {mcmSysLimEntry 3}

mcmSysLimPcbRelease OBJECT-TYPE
	SYNTAX  DisplayString (SIZE(0..4))	
	ACCESS	read-only
	STATUS	mandatory
	DESCRIPTION
	  "NAME = ;
	   DESC = Displays the release level of the module in \
                  the specific location.;
	   HELP = ;
           CAPABILITIES = ;"
	::= {mcmSysLimEntry 4}

mcmSysLimSerialNumber OBJECT-TYPE
	SYNTAX  DisplayString (SIZE(0..13))	
	ACCESS	read-only
	STATUS	mandatory
	DESCRIPTION
	  "NAME = ;
	   DESC = Displays the serial number of the module in \
                  the specific location.;
	   HELP = ;
           CAPABILITIES = ;"
	::= {mcmSysLimEntry 5}

mcmSysLimMfgDate OBJECT-TYPE
	SYNTAX  DisplayString (SIZE(0..7))	
	ACCESS	read-only
	STATUS	mandatory
	DESCRIPTION
	  "NAME = ;
	   DESC = Displays the manufacturing date of the module in \
                  the specific location.;
	   HELP = ;

           CAPABILITIES = ;"
	::= {mcmSysLimEntry 6}

-- PHYS Table

mcmSysPhysTable OBJECT-TYPE
	SYNTAX	SEQUENCE OF McmSysPhysEntry
	ACCESS	not-accessible
	STATUS	mandatory
	DESCRIPTION
	  "NAME = ;
	   DESC = Table to map physical cards to   \
                  Logical Interface Modules (LIM) on \
                  the access device
	   HELP =  ;
	   CAPABILITIES = NET_CFG, VPN_DISP;"
	::= {sys-configuration 16}

mcmSysPhysEntry OBJECT-TYPE
	SYNTAX	McmSysPhysEntry
	ACCESS	not-accessible
	STATUS	mandatory
	DESCRIPTION
	  "NAME = ;
	   DESC = Entry pertaining to a specific physical module.;
	   HELP = ;
	   CAPABILITIES = ;"
	INDEX		{mcmSysPhysModuleAddress}
	::= {mcmSysPhysTable 1}

McmSysPhysEntry ::= SEQUENCE {
	mcmSysPhysModuleAddress		INTEGER,
	mcmSysLogModuleAddress		INTEGER
	}

mcmSysPhysModuleAddress OBJECT-TYPE
	SYNTAX	INTEGER (1..5)
	ACCESS	read-only
	STATUS	mandatory
	DESCRIPTION
	  "NAME = ;
	   DESC = The value of this object identifies \
                  the physical slot address of the module \
                  within the unit;
	   HELP = ;
	   CAPABILITIES = ;"
	::= {mcmSysPhysEntry 1}

mcmSysLogModuleAddress OBJECT-TYPE
        SYNTAX INTEGER {
		limA (1),
		lim1 (2),
		lim2 (3),
		lim3 (4),
		lim4 (5),
		limB (6),
		limC (7),
		limD (8),
		limE (9),
		none (10)
                }
	ACCESS	read-only
	STATUS	mandatory
	DESCRIPTION
	  "NAME = ;
	   DESC = The value of this object identifies \
                  the logical interface module (lim) address;
	   HELP = ;
           CAPABILITIES = ;"
	::= {mcmSysPhysEntry 2}


-- Chassis Group

mcmSysChassisGroup    OBJECT IDENTIFIER ::= {sys-configuration 4}

mcmSysChassisNumberOfModules OBJECT-TYPE
	SYNTAX	INTEGER {
		moduleThree (1),
		moduleFive (2)
		}
	ACCESS	read-only
	STATUS	mandatory
	DESCRIPTION
	  "NAME = ;
	   DESC = Chassis style: number of modules.;
                  NOTE : this object was previously named \
                  mcmSysChassisNumberOfSlots.;
	   HELP = ;
	   CAPABILITIES = NET_CFG, VPN_DISP;"
	::= { mcmSysChassisGroup 1}

mcmSysChassisCoolingFan OBJECT-TYPE
	SYNTAX	INTEGER {
		running (1),
		notRunning (2)
		}
	ACCESS	read-only
	STATUS	mandatory
	DESCRIPTION
	  "NAME = ;
	   DESC =Chassis cooling fan status.;
	   HELP = ;
	   CAPABILITIES = NET_CFG, VPN_DISP;"
	::= { mcmSysChassisGroup 2}

mcmSysChassisPowerSupplyType OBJECT-TYPE
	SYNTAX	INTEGER {
		type-A (1),
		type-B (2)
		}
	ACCESS	read-only
	STATUS	mandatory
	DESCRIPTION
	  "NAME = ;
	   DESC = Specifies the type of power supply \
		  based on type of voltage;
	   HELP = ;
           CAPABILITIES = NET_CFG, VPN_DISP;"
	::= { mcmSysChassisGroup 3}

mcmSysChassisPowerSupplyStatus OBJECT-TYPE
	SYNTAX	INTEGER {
		normal (1),
		fault (2)
		}
	ACCESS	read-only
	STATUS	mandatory
	DESCRIPTION
	  "NAME = ;
	   DESC = Fault indicates that at least one \
		  power supply module is down;
	   HELP = ;
           CAPABILITIES = NET_CFG, VPN_DISP;"
	::= { mcmSysChassisGroup 4}

mcmSysChassisPowerSupplyModuleCount OBJECT-TYPE
	SYNTAX	INTEGER (1..5)
	ACCESS	read-only
	STATUS	mandatory
	DESCRIPTION
	  "NAME = ;
	   DESC = Specifies the number of power \
		  supply modules installed;
	   HELP = ;
           CAPABILITIES = NET_CFG, VPN_DISP;"
	::= { mcmSysChassisGroup 5}

mcmSysChassisPowerSupplyRedundant OBJECT-TYPE
	SYNTAX	INTEGER {
		yes (1),
		no (2)
		}
	ACCESS	read-only
	STATUS	mandatory
	DESCRIPTION
	  "NAME = ;
	   DESC = Indicates whether there are \
		  redundant power supply modules;
	   HELP = ;
           CAPABILITIES = NET_CFG, VPN_DISP;"
	::= { mcmSysChassisGroup 6}

-- Time of Day Group

mcmSysTimeOfDayGroup    OBJECT IDENTIFIER ::= {sys-configuration 5}

mcmSysTimeOfDay		OBJECT IDENTIFIER ::= {mcmSysTimeOfDayGroup 1}

mcmSysTimeOfDaySec OBJECT-TYPE
	SYNTAX	INTEGER (0..59)
	ACCESS	read-write
	STATUS	mandatory
	DESCRIPTION
	  "NAME = ;
	   DESC = System Time of day in seconds.;
	   HELP = ;
	   CAPABILITIES = NET_CFG, VPN_DISP;"
	 ::= { mcmSysTimeOfDay 1}

mcmSysTimeOfDayMin OBJECT-TYPE
	SYNTAX	INTEGER (0..59)
	ACCESS	read-write
	STATUS	mandatory
	DESCRIPTION
	  "NAME = ;
	   DESC = System Time of day in minutes.;
	   HELP = ;
	   CAPABILITIES = NET_CFG, VPN_DISP;"
	 ::= { mcmSysTimeOfDay 2}

mcmSysTimeOfDayHour OBJECT-TYPE
	SYNTAX	INTEGER (0..23)
	ACCESS	read-write
	STATUS	mandatory
	DESCRIPTION
	  "NAME = ;
	   DESC = System Time of day in hours.;
	   HELP = ;
	   CAPABILITIES = NET_CFG, VPN_DISP;"
	 ::= { mcmSysTimeOfDay 3}

mcmSysTimeOfDayDay OBJECT-TYPE
	SYNTAX	INTEGER {
		sunday (1),
		monday (2),
		tuesday (3),
		wednesday (4),
		thursday (5),
		friday (6),
		saturday (7)
	}
	ACCESS	read-write
	STATUS	mandatory
	DESCRIPTION
	  "NAME = ;
	   DESC = System Time of day, the Day.;
	   HELP = ;
	   CAPABILITIES = NET_CFG, VPN_DISP;"
	 ::= { mcmSysTimeOfDay 4}

mcmSysTimeOfDayDate OBJECT-TYPE
	SYNTAX	INTEGER (1..31)
	ACCESS	read-write
	STATUS	mandatory
	DESCRIPTION
	  "NAME = ;
	   DESC = System Time of day. The date.;
	   HELP = ;
	   CAPABILITIES = NET_CFG, VPN_DISP;"
	 ::= { mcmSysTimeOfDay 5}

mcmSysTimeOfDayMonth OBJECT-TYPE
	SYNTAX	INTEGER (1..12)
	ACCESS	read-write
	STATUS	mandatory
	DESCRIPTION
	  "NAME = ;
	   DESC = System Time of day. The Month.;
	   HELP = ;
	   CAPABILITIES = NET_CFG, VPN_DISP;"
	 ::= { mcmSysTimeOfDay 6}

mcmSysTimeOfDayYear OBJECT-TYPE
	SYNTAX	INTEGER (1970..2070) 
	ACCESS	read-write
	STATUS	mandatory
	DESCRIPTION
	  "NAME = ;
	   DESC = System Time of day. The Year.;
	   HELP = ;
	   CAPABILITIES = NET_CFG, VPN_DISP;"
	 ::= { mcmSysTimeOfDay 7}

mcmSysAsciiTimeOfDay OBJECT-TYPE
	SYNTAX	DisplayString(SIZE(20..25)) 
	ACCESS	read-only
	STATUS	mandatory
	DESCRIPTION
	  "NAME = ;
	   DESC = This object will give the ascii version of \
		  the time of day. This would be the same time \
		  as reflected by all the other objects of \
		  this group put togther;
	   HELP = ;
           CAPABILITIES = NET_CFG, VPN_DISP;"
	 ::= { mcmSysTimeOfDayGroup 2}


-- Firmware Information Group

mcmSysFirmwareGroup    OBJECT IDENTIFIER ::= {sys-configuration 6}

mcmSysOperationalType OBJECT-TYPE
	SYNTAX	INTEGER {
		accessRouter (1),
		accessRouterAndNAS (2),
		nmCoreRouter (3),
		concentratingRouter (4),
		backboneRouter (5),
		other (6)
		}
	ACCESS	read-write
	STATUS	mandatory
	DESCRIPTION
	  "NAME = ;
	   DESC = Network Operational mode of this \
                  access device.;
	   HELP = ;
	   CAPABILITIES = NET_CFG, VPN_DISP;"
	::= { mcmSysFirmwareGroup 1}

mcmSysFirmwareConfigCommitBank OBJECT-TYPE
	SYNTAX	INTEGER {
		bank3 (1),
		bank4 (2),
		none (3)
		}
	ACCESS	read-write
	STATUS	mandatory
	DESCRIPTION
	  "NAME = ;
	   DESC = The Default Confi. Image (global).;
	   HELP = Committed Config. Image Bank.;
	   CAPABILITIES = NET_CFG, VPN_DISP;"
	::= { mcmSysFirmwareGroup 2}


mcmSysFirmwareConfigSaveBank OBJECT-TYPE
	SYNTAX	INTEGER {
		bank3 (1),
		bank4 (2)
		}
	ACCESS	read-write
	STATUS	mandatory
	DESCRIPTION
	  "NAME = ;
	   DESC = Default Software Image Bank.;
	   HELP = Committed Code Image (global).;
	   CAPABILITIES = NET_CFG, VPN_DISP;"
	::= { mcmSysFirmwareGroup 3}

mcmSysFirmwareConfigActiveBank OBJECT-TYPE
	SYNTAX	INTEGER {
		bank3 (1),
		bank4 (2),
		none (3)
		}
	ACCESS	read-write
	STATUS	mandatory
	DESCRIPTION
	  "NAME = ;
	   DESC = The active Configuration Image Bank.;
	   HELP = ;
	   CAPABILITIES = NET_CFG, VPN_DISP;"
	::= { mcmSysFirmwareGroup 4}

mcmSysFirmwareConfigReadBank OBJECT-TYPE
	SYNTAX	INTEGER {
		bank3 (1),
		bank4 (2)
		}
	ACCESS	read-only
	STATUS	mandatory
	DESCRIPTION
	  "NAME = ;
	   DESC = The Bank that the Configuration Read from.;
	   HELP = ;
	   CAPABILITIES = NET_CFG, VPN_DISP;"
	::= { mcmSysFirmwareGroup 5}

mcmSysFirmwareCodeReadBank OBJECT-TYPE
	SYNTAX	INTEGER {
		bank1 (1),
		bank2 (2)
		}
	ACCESS	read-only
	STATUS	mandatory
	DESCRIPTION
	  "NAME = ;
	   DESC =The Bank that the Code Read from.;
	   HELP = ;
	   CAPABILITIES = NET_CFG, VPN_DISP;"
	::= { mcmSysFirmwareGroup 6}

mcmSysFirmwareCodeCommitBank OBJECT-TYPE
	SYNTAX	INTEGER {
		bank1 (1),
		bank2 (2),
		none (3)
		}
	ACCESS	read-write
	STATUS	mandatory
	DESCRIPTION
	  "NAME = ;
	   DESC =The Bank that the Code is committed from.;
	   HELP = ;
	   CAPABILITIES = NET_CFG, VPN_DISP;"
	::= { mcmSysFirmwareGroup 7}

mcmSysFirmwareVersion OBJECT-TYPE
	SYNTAX	DisplayString (SIZE (64))
	ACCESS	read-only
	STATUS	mandatory
	DESCRIPTION
	  "NAME = ;
	   DESC = The Code Version that this access \
                  device is running on.;
	   HELP = ;
	   CAPABILITIES = NET_CFG, VPN_DISP;"
	::= { mcmSysFirmwareGroup 8}

mcmSysFirmwareConfigVersion OBJECT-TYPE
	SYNTAX	DisplayString (SIZE (64))
	ACCESS	read-only
	STATUS	mandatory
	DESCRIPTION
	  "NAME = ;
	   DESC = The Configuration Version that this \
                  access device is running on.;
	   HELP = ;
	   CAPABILITIES = NET_CFG, VPN_DISP;"
	::= { mcmSysFirmwareGroup 9}

mcmSysFirmwareImageTable OBJECT-TYPE
	SYNTAX	SEQUENCE OF McmSysFirmwareImageEntry
	ACCESS	not-accessible
	STATUS	mandatory
	DESCRIPTION
	  "NAME = ;
	   DESC = The Firmware Image Table contains  \
                  information about the Code Image.;
	   HELP = ;
	   CAPABILITIES = NET_CFG, VPN_DISP;"
	::= { sys-configuration 7}

mcmSysFirmwareImageEntry OBJECT-TYPE
	SYNTAX	McmSysFirmwareImageEntry
	ACCESS	not-accessible
	STATUS	mandatory
	DESCRIPTION
	  "NAME = ;
	   DESC = The entry that pertains to Code Image.;
	   HELP = ;
	   CAPABILITIES = ;"
	INDEX		{ mcmSysFirmwareImageIndex }
	::= {mcmSysFirmwareImageTable 1}

McmSysFirmwareImageEntry ::= SEQUENCE {
	mcmSysFirmwareImageIndex		INTEGER,
	mcmSysFirmwareImageBank			INTEGER,
	mcmSysFirmwareImageSoftware		INTEGER,
	mcmSysFirmwareImageFilename		DisplayString,	
	mcmSysFirmwareImageRevision		DisplayString,
	mcmSysFirmwareImageSize			INTEGER,
	mcmSysFirmwareImageCommitStatus		INTEGER,
	mcmSysFirmwareImageBurnCount		Counter
	}

mcmSysFirmwareImageIndex OBJECT-TYPE
	SYNTAX	INTEGER 
	ACCESS	read-only
	STATUS	mandatory
	DESCRIPTION
	  "NAME = ;
	   DESC = The Index value for a specific Image.;
	   HELP = ;
	   CAPABILITIES = ;"
	::= { mcmSysFirmwareImageEntry 1}

mcmSysFirmwareImageBank OBJECT-TYPE
	SYNTAX	INTEGER {
		bank0 (1),
		bank1 (2),
		bank2 (3),
		bank3 (4),
		bank4 (5)
		}
	ACCESS	read-only
	STATUS	mandatory
	DESCRIPTION
	  "NAME = ;
	   DESC = The Specific ImageBank that holds the Code \
                  Image or Config Image.;
	   HELP = ;
	   CAPABILITIES = ;"
	::= { mcmSysFirmwareImageEntry 2}

mcmSysFirmwareImageSoftware OBJECT-TYPE
	SYNTAX	INTEGER {
		boot (1),
		code (2),
		config (3)
		}
	ACCESS	read-only
	STATUS	mandatory
	DESCRIPTION
	  "NAME = ;
	   DESC = This indicates that the specific Software \
                  is a boot Code, Image Code  or a Config Code.;
	   HELP = ;
	   CAPABILITIES = ;"
	::= { mcmSysFirmwareImageEntry 3}

mcmSysFirmwareImageFilename OBJECT-TYPE
	SYNTAX	DisplayString (SIZE(0..16))
	ACCESS	read-only
	STATUS	mandatory
	DESCRIPTION
	  "NAME = ;
	   DESC =This indicates the File name of the Firmware.;
	   HELP = ;
	   CAPABILITIES = ;"
	::= { mcmSysFirmwareImageEntry 4}
	
mcmSysFirmwareImageRevision OBJECT-TYPE
	SYNTAX	DisplayString (SIZE(0..64))
	ACCESS	read-only
	STATUS	mandatory
	DESCRIPTION
	  "NAME = ;
	   DESC = This indicates the Revision level of the \
                  specific Firmware.;
	   HELP = ;
	   CAPABILITIES = ;"
	::= { mcmSysFirmwareImageEntry 5}

mcmSysFirmwareImageSize OBJECT-TYPE
	SYNTAX	INTEGER
	ACCESS	read-only
	STATUS	mandatory
	DESCRIPTION
	  "NAME = ;
	   DESC = This indicates the size of the Firmware in bytes.;
	   HELP = ;
	   CAPABILITIES = ;"
	::= { mcmSysFirmwareImageEntry 6}

mcmSysFirmwareImageCommitStatus OBJECT-TYPE
	SYNTAX	INTEGER {
		committed (1),
		notCommitted(2),
		committedAndActive(3),
		committedAndNotActive(4)
	}
	ACCESS	read-only
	STATUS	mandatory
	DESCRIPTION
	  "NAME = ;
	   DESC = This indicates the Firmware Image Commit Status.;
	   HELP = ;
	   CAPABILITIES = ;"
	::= { mcmSysFirmwareImageEntry 7}

mcmSysFirmwareImageBurnCount OBJECT-TYPE
	SYNTAX	Counter
	ACCESS	read-only
	STATUS	mandatory
	DESCRIPTION
	  "NAME = ;
	   DESC = This indicates the global burn count.;
	   HELP = ;
	   CAPABILITIES = ;"
	::= { mcmSysFirmwareImageEntry 8}


-- Smart Configurator Attributes

mcmSysSmartCfgGroup    OBJECT IDENTIFIER ::= {sys-configuration 8}
mcmSysSmartCfgAction OBJECT-TYPE
	SYNTAX	INTEGER {
		update (1)
		}
	ACCESS	write-only
	STATUS	mandatory
	DESCRIPTION
	  "NAME = ;
	   DESC = Directs system to update secondary (Flash) storage \
                  by saving present configuration. Or directs discard \
                  of present re-configures.;
	   HELP = ;
	   CAPABILITIES = NET_CFG, VPN_DISP;"
	::= { mcmSysSmartCfgGroup 1}

mcmSysSmartCfgStatus OBJECT-TYPE
	SYNTAX	INTEGER {
		ok (1),
		failed (2)
	}
	ACCESS	read-only
	STATUS	mandatory
	DESCRIPTION
	  "NAME = ;
	   DESC = Indicates if system is currently being \
                  re-configured.;
	   HELP = ;
	   CAPABILITIES = NET_CFG, VPN_DISP;"
	::= { mcmSysSmartCfgGroup 2}


-- Community String

mcmSysCommunityStringTable OBJECT-TYPE
	SYNTAX	SEQUENCE OF McmSysCommunityStringEntry
	ACCESS	not-accessible
	STATUS	mandatory
	DESCRIPTION
	  "NAME = ;
	   DESC = The System Community String Table.;
	   HELP = ;
	   CAPABILITIES = NET_CFG, VPN_NONE;"
	::= { sys-configuration 9}

mcmSysCommunityStringEntry OBJECT-TYPE
	SYNTAX	McmSysCommunityStringEntry
	ACCESS	not-accessible
	STATUS	mandatory
	DESCRIPTION
	  "NAME = ;
	   DESC = Entry that pertains to the Community \
                  string.;
	   HELP = ;
	   CAPABILITIES = ;"
	INDEX		{ mcmSysCommunityStringIndex }
	::= {mcmSysCommunityStringTable 1}

McmSysCommunityStringEntry ::= SEQUENCE {
	mcmSysCommunityStringIndex		INTEGER,
	mcmSysCommunityStringCommunity		DisplayString
	}

mcmSysCommunityStringIndex OBJECT-TYPE
	SYNTAX	INTEGER {
			nSP-Configurator (1),
			nSP-Operator	 (2),
			nSP-Monitor		 (3),
			customer-Configurator (4),
			customer-Operator	  (5),
			customer-Monitor	  (6)
			}
	ACCESS	read-write
	STATUS	mandatory
	DESCRIPTION
	  "NAME = ;
	   DESC = The Index value for each Community Strings.;
	   HELP = ;
	   CAPABILITIES = ;"
	::= { mcmSysCommunityStringEntry 1}

mcmSysCommunityStringCommunity OBJECT-TYPE
	SYNTAX	DisplayString(SIZE(1..25))
	ACCESS	read-write
	STATUS	mandatory
	DESCRIPTION
	  "NAME = ;
	   DESC = Community String used as access password.;
	   HELP = ;
	   CAPABILITIES = ;"
	::= { mcmSysCommunityStringEntry 2}

mcmSysValidateCommunityGroup OBJECT IDENTIFIER ::= {sys-configuration 10}

mcmSysValidateCommunity OBJECT-TYPE
	SYNTAX	DisplayString(SIZE(0..25)) 
	ACCESS	write-only
	STATUS	mandatory
	DESCRIPTION
	  "NAME = ;
	   DESC = This parameter contains the password \
                  obtained by the command line user interface.;
	   HELP = ;
           CAPABILITIES = NET_CFG, VPN_DISP;"
	 ::= { mcmSysValidateCommunityGroup 1}

mcmSysLastCommunityPriviledgeLevel  OBJECT-TYPE
	SYNTAX	INTEGER {
		nspConfigurator (1),
		nspOperator (2),
		nspMonitor (3),
		customerConfigurator (4),
		customerOperator (5),
		customerMonitor (6)
		}
	ACCESS	read-only
	STATUS	mandatory
	DESCRIPTION
	  "NAME = ;
	   DESC = This parameter contains the priviledge \
                  level from the last valid password.;
	   HELP = ;
           CAPABILITIES = NET_CFG, VPN_DISP;"
	 ::= { mcmSysValidateCommunityGroup 2}

mcmSysConsolePortGroup    OBJECT IDENTIFIER ::= {sys-configuration 11}

mcmSysConsolePortBaudRate OBJECT-TYPE
	SYNTAX	INTEGER {
		bps2400 (1),
		bps4800 (2),
		bps9600 (3),
		bps19200 (4),
		bps38400 (5)
		}
	ACCESS	read-write
	STATUS	mandatory
	DESCRIPTION
	  "NAME = ;
	   DESC = Set Console (and Debugger) Speed;
	   HELP = Set Console Speed;
	   CAPABILITIES = NET_CFG, VPN_DISP;"
	DEFVAL	{ 3 }
	::= { mcmSysConsolePortGroup 1}

mcmSysConsolePortStopBits OBJECT-TYPE
	SYNTAX	INTEGER (1..2)
	ACCESS	read-write
	STATUS	mandatory
	DESCRIPTION
	  "NAME = ;
	   DESC = Set Console number of stop bits;
	   HELP = Set Console number of stop bits;
	   CAPABILITIES = NET_CFG, VPN_DISP;"
	DEFVAL	{ 1 }
	::= { mcmSysConsolePortGroup 2}

mcmSysConsolePortDataBits OBJECT-TYPE
	SYNTAX	INTEGER (5..8)
	ACCESS	read-write
	STATUS	mandatory
	DESCRIPTION
	  "NAME = ;
	   DESC = Set Console number of Data bits (excluding start, \
                  stop and parity bits);
	   HELP = Set Console number of Data bits (excluding start, \
                  stop and parity bits);
	   CAPABILITIES = NET_CFG, VPN_DISP;"
	DEFVAL	{ 8 }
	::= { mcmSysConsolePortGroup 3}

mcmSysConsolePortParity OBJECT-TYPE
	SYNTAX	INTEGER {
		off (1),
		even (2),
		odd (3)
		}
	ACCESS	read-write
	STATUS	mandatory
	DESCRIPTION
	  "NAME = ;
	   DESC = Set Console parity bit;
	   HELP = Set Console parity bit;
	   CAPABILITIES = NET_CFG, VPN_DISP;"
	DEFVAL	{ 1 }
	::= { mcmSysConsolePortGroup 4}


mcmSysCommitTrackingGroup    OBJECT IDENTIFIER ::= {sys-configuration 12}

mcmSysCommitTrackingCounter OBJECT-TYPE
	SYNTAX	Counter
	ACCESS	read-only
	STATUS	mandatory
	DESCRIPTION
	  "NAME = ;
	   DESC = The Counter that pertains to the Commit Tracking.;
	   HELP = ;
	   CAPABILITIES = NET_CFG, VPN_NONE;"
	::= { mcmSysCommitTrackingGroup 1}

mcmSysCommitTrackingSrcIPAddressOfLastCommit OBJECT-TYPE
	SYNTAX	IpAddress
	ACCESS	read-only
	STATUS	mandatory
	DESCRIPTION
	  "NAME = ;
	   DESC = The IP address of the SNMP manager that issued \
                  the last successful SET operation.;
	   HELP = ;
	   CAPABILITIES = NET_CFG, VPN_NONE;"
	::= { mcmSysCommitTrackingGroup 2}

mcmSysCommitTrackingCommunityOfLastCommit OBJECT-TYPE
	SYNTAX	DisplayString
	ACCESS	read-only
	STATUS	mandatory
	DESCRIPTION
	  "NAME = ;
	   DESC = The community of the last successful SET.;
	   HELP = ;
	   CAPABILITIES = NET_CFG, VPN_NONE;"
	::= { mcmSysCommitTrackingGroup 3}

mcmSysCommitTrackingTimeOfLastCommit OBJECT-TYPE
	SYNTAX	TimeTicks
	ACCESS	read-only
	STATUS	mandatory
	DESCRIPTION
	  "NAME = ;
	   DESC = The system uptime in ticks when the last \
                  SET was serviced.;
	   HELP = ;
	   CAPABILITIES = NET_CFG, VPN_NONE;"
	::= { mcmSysCommitTrackingGroup 4}


mcmSysIfExtTable OBJECT-TYPE
	SYNTAX	SEQUENCE OF McmSysIfExtEntry
	ACCESS	not-accessible
	STATUS	mandatory
	DESCRIPTION
	  "NAME = ;
	   DESC = The Interface table that contains \
                  information about IfExtension in this \
                  access device.;
	   HELP = ;
	   CAPABILITIES = NET_CFG, VPN_DISP;"
	::= { sys-configuration 13}

mcmSysIfExtEntry OBJECT-TYPE
	SYNTAX	McmSysIfExtEntry
	ACCESS	not-accessible
	STATUS	mandatory
	DESCRIPTION
	  "NAME = ;
	   DESC = The specific Entry that pertains to \
                  IfExt in this access device.; 
	   HELP = ;
	   CAPABILITIES = ;"
	INDEX		{ mcmSysIfExtIfIndex }
	::= {mcmSysIfExtTable 1}

McmSysIfExtEntry ::= SEQUENCE {
	mcmSysIfExtIfIndex		INTEGER,
	mcmSysIfExtName			DisplayString,
	mcmSysIfExtType			INTEGER,
	mcmSysIfExtLinkUpDownTrapEnable	INTEGER,
	mcmSysIfExtConnectorPresent	INTEGER,
	mcmSysIfExtPersistenceType	INTEGER,
	mcmSysIfExtState		INTEGER,
	mcmSysIfExtPPA			INTEGER,
	mcmSysIfExtModule		INTEGER,
	mcmSysIfExtChannel		INTEGER,
	mcmSysIfExtPPADeviceType	INTEGER
	}

mcmSysIfExtIfIndex OBJECT-TYPE
	SYNTAX	INTEGER (1..255)
	ACCESS	read-only
	STATUS	mandatory
	DESCRIPTION
	  "NAME = ;
	   DESC = The Index value of the specifc entry.;
	   HELP = ;
	   CAPABILITIES = ;"
	::= { mcmSysIfExtEntry 1}

mcmSysIfExtName OBJECT-TYPE
	SYNTAX	DisplayString (SIZE (25))
	ACCESS	read-only
	STATUS	mandatory
	DESCRIPTION
	  "NAME = ;
	   DESC = The Name of the specific IfExt entry.;
	   HELP = ;
	   CAPABILITIES = ;"
	::= { mcmSysIfExtEntry 2}

mcmSysIfExtType OBJECT-TYPE
       SYNTAX  INTEGER {
                   other(1),          -- none of the following
                   regular1822(2),
                   hdh1822(3),
                   ddnX25(4),
                   rfc877x25(5),
                   ethernetCsmacd(6),
                   iso88023Csmacd(7),
                   iso88024TokenBus(8),
                   iso88025TokenRing(9),
                   iso88026Man(10),
                   starLan(11),
                   proteon10Mbit(12),
                   proteon80Mbit(13),
                   hyperchannel(14),
                   fddi(15),
                   lapb(16),
                   sdlc(17),
                   ds1(18),           -- DS1/E1 (RFC 1406)
                   e1(19),            -- obsolete
                   basicISDN(20),
                   primaryISDN(21),
                   propPointToPointSerial(22), -- proprietary serial
                   ppp(23),
                   softwareLoopback(24),
                   eon(25),            -- CLNP over IP (RFC 1070)
                   ethernet3Mbit(26),
                   nsip(27),           -- XNS over IP
                   slip(28),           -- generic SLIP
                   ultra(29),          -- ULTRA technologies
                   ds3(30),            -- T-3
                   sip(31),            -- SMDS
                   frameRelay(32),    -- DTE only
                   rs232(33),
                   para(34),           -- parallel-port
                   arcnet(35),         -- arcnet
                   arcnetPlus(36),     -- arcnet plus
                   atm(37),            -- ATM cells
                   miox25(38),
                   sonet(39),          -- SONET or SDH
                   x25ple(40),
                   iso88022llc(41),
                   localTalk(42),
                   smdsDxi(43),
                   frameRelayService(44),  -- Frame relay DCE
                   v35(45),
                   hssi(46),
                   hippi(47),
                   modem(48),          -- Generic modem
                   aal5(49),           -- AAL5 over ATM
                   sonetPath(50),
                   sonetVT(51),
                   smdsIcip(52),       -- SMDS InterCarrier Interface
                   propVirtual(53),    -- proprietary virtual/internal
                   propMultiplexor(54), -- proprietary multiplexing
		   isdn(63),		-- ISDN D channel signaling
		   isdns(75),		-- ISDN BRI physical ST interface
		   isdnu(76),		-- ISDN BRI physical U interface
		   lapd(77),		-- ISDN LAP-D
		   ds0(81)		-- ISDN B channel	
               }
	ACCESS	read-only
	STATUS	mandatory
	DESCRIPTION
	  "NAME = ;
	   DESC = The values of this field are kept \
		  the same as the values for the \
		  ifExtType defined in \
		  the extension to MIB II (RFC1573);
	   HELP = ;
           CAPABILITIES = ;"
	::= { mcmSysIfExtEntry 3}

mcmSysIfExtLinkUpDownTrapEnable OBJECT-TYPE
	SYNTAX	INTEGER {
		yes (1),
		no (2)
	}
	ACCESS	read-write
	STATUS	mandatory
	DESCRIPTION
	  "NAME = ;
	   DESC = This indicates if the LinkUpDownTrap \
                  is enabled or not.;
	   HELP = ;
	   CAPABILITIES = ;"
	::= { mcmSysIfExtEntry 4}

mcmSysIfExtConnectorPresent OBJECT-TYPE
	SYNTAX	INTEGER {
		yes (1),
		no (2)
	}
	ACCESS	read-only
	STATUS	mandatory
	DESCRIPTION
	  "NAME = ;
	   DESC = This indicates if the IfExt entry \
                  has a phisical connector present.;
	   HELP = ;
	   CAPABILITIES = ;"
	::= { mcmSysIfExtEntry 5}

mcmSysIfExtPersistenceType OBJECT-TYPE
	SYNTAX	INTEGER {
		volatile (1),
		non-volatile (2)
	}
	ACCESS	read-only
	STATUS	mandatory
	DESCRIPTION
	  "NAME = ;
	   DESC = This indicates if the Persistence Type \
                  is volatile or non-volatile.;
	   HELP = ;
	   CAPABILITIES = ;"
	::= { mcmSysIfExtEntry 6}

mcmSysIfExtState OBJECT-TYPE
	SYNTAX	INTEGER {
		configured (1),
		not-configured (2)
	}
	ACCESS	read-only
	STATUS	mandatory
	DESCRIPTION
	  "NAME = ;
	   DESC = This indicates that if the IfExt entry \
                  is configured or not.;
	   HELP = ;
	   CAPABILITIES = ;"
	::= { mcmSysIfExtEntry 7}

mcmSysIfExtPPA OBJECT-TYPE
	SYNTAX	INTEGER 
	ACCESS	read-only
	STATUS	mandatory
	DESCRIPTION
	  "NAME = ;
	   DESC = The PPA of the port;
	   HELP = ;
	   CAPABILITIES = ;"
	::= { mcmSysIfExtEntry 8}

mcmSysIfExtModule OBJECT-TYPE
	SYNTAX	INTEGER {
		limA (1),
		lim1 (2),
		lim2 (3),
		lim3 (4),
		lim4 (5),
		limB (6),
		limC (7),
		limD (8),
		limE (9)
		}
	ACCESS	read-only
	STATUS	mandatory
	DESCRIPTION
	  "NAME = ;
	   DESC = The logical interface module address \
                  of this interface \
                  NOTE : this object was previously named \
                  mcmSysIfExtSlot.;
	   HELP = ;
	   CAPABILITIES = ;"
	::= { mcmSysIfExtEntry 9}

mcmSysIfExtChannel OBJECT-TYPE
	SYNTAX	INTEGER
	ACCESS	read-only
	STATUS	mandatory
	DESCRIPTION
	  "NAME = ;
	   DESC = The channel number of this interface... \
		  FR DCE: N/A, WAN Driver: SCC number, \
		  WAN Connector: corresponding SCC number;
	   HELP = ;
	   CAPABILITIES = ;"
	::= { mcmSysIfExtEntry 10}

mcmSysIfExtPPADeviceType OBJECT-TYPE
	SYNTAX	INTEGER {
		wanDriver-FRDTE (1),
		ethDriver (2),
		loopDriver (3),
		nullDevice (4),
		noDevice (5),
		frDevice-DTE (6),
		wanConn (7),
		isdn-B1-ch (8),
		isdn-B2-ch (9),
		isdn-D-ch (10),
		isdn-conn (11),
		voiceVP (12),
		nmVP (13),
		dataVP (14),
		t1Net (15),
		t1Loc (16),
		t1Frac (17),
		serialDevice (18),
		euvmCh (19),
		t1DP1 (20),
		t1DP2 (21),
		e1Net (22),
		e1Loc (23),
		e1Frac (24),
		e1DP1 (25),
		e1DP2 (26),
		iuvmCh (27),
		dvmCh (28),
		frDevice-DCE (29),
		wanDriver-FRDCE (30),
		wanDriver-FRTDS (31),
		dce-Conn (32),
		csu-t1 (33),
		csu-56k (34),
		isdn-LAPD (35),
		isdn-BRI (36),
                csu-e1 (37),
                panlDCE(38),       
                panlDTE(39),       
                standardFR(40),       
                voice-isdn-BRI-ch (41),
                voice-isdn-BRI    (42),
                voice-isdn-LAPD   (43),
                voice-isdn-D-ch   (44),
                voice-isdn-B1-ch  (45),
                voice-isdn-B2-ch  (46)
		}
	ACCESS	read-only
	STATUS	mandatory
	DESCRIPTION
	  "NAME = ;
	   DESC = The PPA device type of this interface.;
	   HELP = ;
	   CAPABILITIES = ;"
	::= { mcmSysIfExtEntry 11}


-- Rollback Group

mcmSysRollbackGroup    OBJECT IDENTIFIER ::= {sys-configuration 14}

mcmSysRollbackFeature OBJECT-TYPE
	SYNTAX	INTEGER {
		enabled (1),
		disabled (2)
		}
	ACCESS	read-write
	STATUS	mandatory
	DESCRIPTION
	  "NAME = ;
	   DESC = This indicates if the RollBack feature is \
                  enabled or disabled.;
	   HELP = ;
	   CAPABILITIES = NET_CFG, VPN_DISP;"
	::= { mcmSysRollbackGroup 1}

mcmSysRollbackStatus OBJECT-TYPE
	SYNTAX	INTEGER {
		required (1),
		not-required (2),
		next-reset (3)
		}
	ACCESS	read-only
	STATUS	mandatory
	DESCRIPTION
	  "NAME = ;
	   DESC = This indicates whether Confirm system \
		  Rollback is required or not. Or will \
                  Confirm at the next reset.;
	   HELP = ;
	   CAPABILITIES = NET_CFG, VPN_DISP;"
	::= { mcmSysRollbackGroup 2}

mcmSysRollbackConfirm  OBJECT-TYPE
	SYNTAX	INTEGER {
		confirm (1)
		}
	ACCESS	write-only
	STATUS	mandatory
	DESCRIPTION
	  "NAME = ;
	   DESC = This confirms that previous System Configuration \
                  or Code bank changes are accepted and that the \
                  System is NOT to timeout, reset and go back to
                  previous Config or Code bank.;
	   HELP = ;
	   CAPABILITIES = NET_CFG, VPN_DISP;"
	::= { mcmSysRollbackGroup 3}


--  Parallel table to the Interface Extension table

nvmSysIfExtTable OBJECT-TYPE
	SYNTAX	SEQUENCE OF NvmSysIfExtEntry
	ACCESS	not-accessible
	STATUS	mandatory
	DESCRIPTION
	  "NAME = ;
	   DESC = The Interface table that contains \
                  information about IfExtension in this \
                  access device.; 
	   HELP = ;
	   CAPABILITIES = NET_CFG, VPN_DISP;"
	::= { sys-configuration 15}

nvmSysIfExtEntry OBJECT-TYPE
	SYNTAX	NvmSysIfExtEntry
	ACCESS	not-accessible
	STATUS	mandatory
	DESCRIPTION
	  "NAME = ;
	   DESC = The specific Entry that pertains to \
                  IfExt in this access device.;
	   HELP = ;
	   CAPABILITIES = ;"
	INDEX		{ nvmSysIfExtIfIndex }
	::= {nvmSysIfExtTable 1}

NvmSysIfExtEntry ::= SEQUENCE {
	nvmSysIfExtIfIndex		INTEGER,
	nvmSysIfExtName			DisplayString,
	nvmSysIfExtType			INTEGER,
	nvmSysIfExtLinkUpDownTrapEnable	INTEGER,
	nvmSysIfExtConnectorPresent	INTEGER,
	nvmSysIfExtPersistenceType	INTEGER,
	nvmSysIfExtState		INTEGER,
	nvmSysIfExtPPA			INTEGER,
	nvmSysIfExtModule			INTEGER,
	nvmSysIfExtChannel			INTEGER,
	nvmSysIfExtPPADeviceType		INTEGER
	}

nvmSysIfExtIfIndex OBJECT-TYPE
	SYNTAX	INTEGER (1..255)
	ACCESS	read-only
	STATUS	mandatory
	DESCRIPTION
	  "NAME = ;
	   DESC = The Index value of the specifc entry.;
	   HELP = ;
	   CAPABILITIES = ;"
	::= { nvmSysIfExtEntry 1}

nvmSysIfExtName OBJECT-TYPE
	SYNTAX	DisplayString (SIZE (25))
	ACCESS	read-only
	STATUS	mandatory
	DESCRIPTION
	  "NAME = ;
	   DESC = The Name of the specific IfExt entry.;
	   HELP = ;
	   CAPABILITIES = ;"
	::= { nvmSysIfExtEntry 2}

nvmSysIfExtType OBJECT-TYPE
       SYNTAX  INTEGER {
                   other(1),          -- none of the following
                   regular1822(2),
                   hdh1822(3),
                   ddnX25(4),
                   rfc877x25(5),
                   ethernetCsmacd(6),
                   iso88023Csmacd(7),
                   iso88024TokenBus(8),
                   iso88025TokenRing(9),
                   iso88026Man(10),
                   starLan(11),
                   proteon10Mbit(12),
                   proteon80Mbit(13),
                   hyperchannel(14),
                   fddi(15),
                   lapb(16),
                   sdlc(17),
                   ds1(18),           -- DS1/E1 (RFC 1406)
                   e1(19),            -- obsolete
                   basicISDN(20),
                   primaryISDN(21),
                   propPointToPointSerial(22), -- proprietary serial
                   ppp(23),
                   softwareLoopback(24),
                   eon(25),            -- CLNP over IP (RFC 1070)
                   ethernet3Mbit(26),
                   nsip(27),           -- XNS over IP
                   slip(28),           -- generic SLIP
                   ultra(29),          -- ULTRA technologies
                   ds3(30),            -- T-3
                   sip(31),            -- SMDS
                   frameRelay(32),    -- DTE only
                   rs232(33),
                   para(34),           -- parallel-port
                   arcnet(35),         -- arcnet
                   arcnetPlus(36),     -- arcnet plus
                   atm(37),            -- ATM cells
                   miox25(38),
                   sonet(39),          -- SONET or SDH
                   x25ple(40),
                   iso88022llc(41),
                   localTalk(42),
                   smdsDxi(43),
                   frameRelayService(44),  -- Frame relay DCE
                   v35(45),
                   hssi(46),
                   hippi(47),
                   modem(48),          -- Generic modem
                   aal5(49),           -- AAL5 over ATM
                   sonetPath(50),
                   sonetVT(51),
                   smdsIcip(52),       -- SMDS InterCarrier Interface
                   propVirtual(53),    -- proprietary virtual/internal
                   propMultiplexor(54), -- proprietary multiplexing
		   isdn(63),		-- ISDN D channel signaling
		   isdns(75),		-- ISDN BRI physical ST interface
		   isdnu(76),		-- ISDN BRI physical U interface
		   lapd(77),		-- ISDN LAP-D
		   ds0(81)		-- ISDN B channel
               }
	ACCESS	read-only
	STATUS	mandatory
	DESCRIPTION
	  "NAME = ;
	   DESC = The values of this field are kept \
		  the same as the values for the \
		  ifExtType defined in \
		  the extension to MIB II (RFC1573);
	   HELP = ;
           CAPABILITIES = ;"
	::= { nvmSysIfExtEntry 3}

nvmSysIfExtLinkUpDownTrapEnable OBJECT-TYPE
	SYNTAX	INTEGER {
		yes (1),
		no (2)
	}
	ACCESS	read-only
	STATUS	mandatory
	DESCRIPTION
	  "NAME = ;
	   DESC = This indicates if the LinkUpDownTrap \
                  is enabled or not.;
	   HELP = ;
	   CAPABILITIES = ;"
	::= { nvmSysIfExtEntry 4}

nvmSysIfExtConnectorPresent OBJECT-TYPE
	SYNTAX	INTEGER {
		yes (1),
		no (2)
	}
	ACCESS	read-only
	STATUS	mandatory
	DESCRIPTION
	  "NAME = ;
	   DESC = This indicates if the IfExt entry \
                  has a phisical connector present.;
           HELP = ;
	   CAPABILITIES = ;"
	::= { nvmSysIfExtEntry 5}

nvmSysIfExtPersistenceType OBJECT-TYPE
	SYNTAX	INTEGER {
		volatile (1),
		non-volatile (2)
	}
	ACCESS	read-only
	STATUS	mandatory
	DESCRIPTION
	  "NAME = ;
	   DESC =  This indicates if the Persistence Type \
                  is volatile or non-volatile.;
	   HELP = ;
	   CAPABILITIES = ;"
	::= { nvmSysIfExtEntry 6}

nvmSysIfExtState OBJECT-TYPE
	SYNTAX	INTEGER {
		configured (1),
		not-configured (2)
	}
	ACCESS	read-only
	STATUS	mandatory
	DESCRIPTION
	  "NAME = ;
	   DESC =  This indicates that if the IfExt entry \
                  is configured or not.;
	   HELP = ;
	   CAPABILITIES = ;"
	::= { nvmSysIfExtEntry 7}

nvmSysIfExtPPA OBJECT-TYPE
	SYNTAX	INTEGER 
	ACCESS	read-only
	STATUS	mandatory
	DESCRIPTION
	  "NAME = ;
	   DESC = The PPA of the port;
	   HELP = ;
	   CAPABILITIES = ;"
	::= { nvmSysIfExtEntry 8}

nvmSysIfExtModule OBJECT-TYPE
	SYNTAX	INTEGER {
		limA (1),
		lim1 (2),
		lim2 (3),
		lim3 (4),
		lim4 (5),
		limB (6),
		limC (7),
		limD (8),
		limE (9)
		}
	ACCESS	read-only
	STATUS	mandatory
	DESCRIPTION
	  "NAME = ;
	   DESC = The logical interface module address \
                  of this interface \
                  NOTE : this object was previously named \
                  nvmSysIfExtSlot.;
	   HELP = ;
	   CAPABILITIES = ;"
	::= { nvmSysIfExtEntry 9}

nvmSysIfExtChannel OBJECT-TYPE
	SYNTAX	INTEGER
	ACCESS	read-only
	STATUS	mandatory
	DESCRIPTION
	  "NAME = ;
	   DESC = The channel number of this interface... \
		  FR DCE: N/A, WAN Driver: SCC number, \
		  WAN Connector: corresponding SCC number;
	   HELP = ;
	   CAPABILITIES = ;"
	::= { nvmSysIfExtEntry 10}

nvmSysIfExtPPADeviceType OBJECT-TYPE
	SYNTAX	INTEGER {
		wanDriver-FRDTE (1),
		ethDriver (2),
		loopDriver (3),
		nullDevice (4),
		noDevice (5),
		frDevice-DTE (6),
		wanConn (7),
		isdn-B1-ch (8),
		isdn-B2-ch (9),
		isdn-D-ch (10),
		isdn-conn (11),
		voiceVP (12),
		nmVP (13),
		dataVP (14),
		t1Net (15),
		t1Loc (16),
		t1Frac (17),
		serialDevice (18),
		euvmCh (19),
		t1DP1 (20),
		t1DP2 (21),
		e1Net (22),
		e1Loc (23),
		e1Frac (24),
		e1DP1 (25),
		e1DP2 (26),
		iuvmCh (27),
		dvmCh (28),
		frDevice-DCE (29),
		wanDriver-FRDCE (30),
		wanDriver-FRTDS (31),
		dce-Conn (32),
		csu-t1 (33),
		csu-56k (34),
		isdn-LAPD (35),
		isdn-BRI (36),
                csu-e1 (37),
                panlDCE(38),       
                panlDTE(39),       
                standardFR(40),       
                voice-isdn-BRI-ch (41),
                voice-isdn-BRI    (42),
                voice-isdn-LAPD   (43),
                voice-isdn-D-ch   (44),
                voice-isdn-B1-ch  (45),
                voice-isdn-B2-ch  (46)
      		}
	ACCESS	read-only
	STATUS	mandatory
	DESCRIPTION
	  "NAME = ;
	   DESC = The PPA device type of this interface.;
	   HELP = ;
	   CAPABILITIES = ;"
	::= { nvmSysIfExtEntry 11}


-- Control Group

mcmSysResetGroup    OBJECT IDENTIFIER ::= {sys-control 1}

mcmSysResetAction OBJECT-TYPE
	SYNTAX	INTEGER {
		cpu-only (1),
		currentConfig (2),
		factoryDefaults (3)
		}
	ACCESS	write-only
	STATUS	mandatory
	DESCRIPTION
	  "NAME = ;
	   DESC = Reset Unit, restart the CPU only,  warm start \
                  or factory default (cold start).;
	   HELP = ;
	   CAPABILITIES = NET_CFG, VPN_DISP;"
	::= { mcmSysResetGroup 1}

mcmSysRestartReason OBJECT-TYPE
	SYNTAX	INTEGER {
		hwButtonCurrentReset(1),
		cliCurrentReset(2),
		hwButtonOrCLICPUReset(3),
		watchdogTimer(4),
		noQUICCClock(5),
		doubleBusFault(6),
		powerUp(8),
		unknownHardwareFault(9),
		switchCodeConfigHWButtonReset(11),
		switchCodeConfigCLICurrReset(12),
		switchCodeConfigCPUReset(13),
		switchCodeConfigwatchdogTimer(14),
		switchCodeConfigNoQUICCClock(15),
		switchCodeConfigdoubleBusFault(16),
		switchCodeConfigRollbackTimer(17),
		switchCodeConfigPowerUp(18),
		switchCodeConfigUnknownHWFault(19),
		switchCodeHWButtonReset(21),
		switchCodeCLICurrReset(22),
		switchCodeCPUReset(23),
		switchCodewatchdogTimer(24),
		switchCodeNoQUICCClock(25),
		switchCodedoubleBusFault(26),
		switchCodeRollbackTimer(27),
		switchCodePowerUp(28),
		switchCodeUnknownHWFault(29),
		switchConfigHWButtonReset(31),
		switchConfigCLICurrReset(32),
		switchConfigCPUReset(33),
		switchConfigwatchdogTimer(34),
		switchConfigNoQUICCClock(35),
		switchConfigdoubleBusFault(36),
		switchConfigRollbackTimer(37),
		switchConfigPowerUp(38),
		switchConfigUnknownHWFault(39),
		hwButtonResetToDefault(41),
		cliResetToDefault(42),
		cpuResetWithCommittedCOnfig(43),
		powerUpWithDefaultedConfig(48),
		configDefaultUnknownHWFault(49),
		hwButtonDefaultUnknownSWState(51),
		cliDefaultResetUnknownSWState(52),
		powerUpDefaultUnknownSWState(58),
		configDefaultUnknownSWHWState(59)
		}
	ACCESS	read-only
	STATUS	mandatory
	DESCRIPTION
	  "NAME = ;
	   DESC = Reset Restart Reason Codes;
	   HELP = Reason Code for last Reset;
	   CAPABILITIES = NET_CFG, VPN_DISP;"
	::= { mcmSysResetGroup 2}

mcmSysTimeOfLastReset OBJECT-TYPE
	SYNTAX	DisplayString(SIZE(20..25)) 
	ACCESS	read-only
	STATUS	mandatory
	DESCRIPTION
	  "NAME = ;
	   DESC = This object will indicate the time of \
                  when the access device was last reset.
	   HELP = ;
           CAPABILITIES = NET_CFG, VPN_DISP;"
	::= { mcmSysResetGroup 3}

mcmSysCfgLockGroup    OBJECT IDENTIFIER ::= {sys-control 2}

mcmSysCfgLock OBJECT-TYPE
	SYNTAX	DisplayString (SIZE(0..80))
	ACCESS	read-write
	STATUS	mandatory
	DESCRIPTION
	  "NAME = ;
	   DESC = Indicates if system config is locked.;
	   HELP = ;
	   CAPABILITIES = NET_CFG, VPN_DISP;"
	::= { mcmSysCfgLockGroup 1}

-- Statistics

mcmSysUtilGroup    OBJECT IDENTIFIER ::= {sys-statistics 1}

mcmSysCpuUtilization OBJECT-TYPE
	SYNTAX	Gauge
	ACCESS	read-only
	STATUS	mandatory
	DESCRIPTION
	  "NAME = ;
	   DESC = Indicates the CPU utilization  in percent.;
	   HELP = ;
	   CAPABILITIES = NET_CFG, VPN_DISP;"
	::= { mcmSysUtilGroup 1}

mcmSysLinkTransmitBandwidthUtilization OBJECT-TYPE
	SYNTAX	Gauge
	ACCESS	read-only
	STATUS	mandatory
	DESCRIPTION
	  "NAME = ;
	   DESC = Indicates the Bandwidth Utilization in percent.;
	   HELP = ;
	   CAPABILITIES = NET_CFG, VPN_DISP;"
	::= { mcmSysUtilGroup 2}

mcmSysInternalRAMUtilization OBJECT-TYPE
	SYNTAX	Gauge
	ACCESS	read-only
	STATUS	mandatory
	DESCRIPTION
	  "NAME = ;
	   DESC = Indicates internal RAM Utilization in percent.;
	   HELP = ;
	   CAPABILITIES = NET_CFG, VPN_DISP;"
	::= { mcmSysUtilGroup 3}

mcmSysLinkReceiveBandwidthUtilization OBJECT-TYPE
	SYNTAX	Gauge
	ACCESS	read-only
	STATUS	mandatory
	DESCRIPTION
	  "NAME = ;
	   DESC = Indicates the Link Receive Bandwidth utilization.;
	   HELP = ;
	   CAPABILITIES = NET_CFG, VPN_DISP;"
	::= { mcmSysUtilGroup 4}

-- Traps Group

mcmSysTrapSubscriptionTable OBJECT-TYPE
	SYNTAX	SEQUENCE OF McmSysTrapSubscriptionEntry
	ACCESS	not-accessible
	STATUS	mandatory
	DESCRIPTION
	  "NAME = ;
	   DESC = This Table displays the System Trap \
                  subscription information of this \
                  access device.;
	   HELP = ;
	   CAPABILITIES = NET_CFG, VPN_DISP;"
	::= {sys-trap 1}

mcmSysTrapSubscriptionEntry OBJECT-TYPE
	SYNTAX	McmSysTrapSubscriptionEntry
	ACCESS	not-accessible
	STATUS	mandatory
	DESCRIPTION
	  "NAME = ;
	   DESC = Entry that pertains to a specific TRAP.;
	   HELP = ;
	   CAPABILITIES = NET_CFG, VPN_DISP;"
	INDEX		{ mcmSysTrapSubscriptionIPAddress }
	::= {mcmSysTrapSubscriptionTable 1}

McmSysTrapSubscriptionEntry ::= SEQUENCE {
	mcmSysTrapSubscriptionIPAddress		IpAddress,
	mcmSysTrapSubscriptionCommunityString		DisplayString,
	mcmSysTrapSubscriptionAction			INTEGER
	}

mcmSysTrapSubscriptionIPAddress OBJECT-TYPE
	SYNTAX	IpAddress
	ACCESS	read-write
	STATUS	mandatory
	DESCRIPTION
	  "NAME = ;
	   DESC = IP address of the SNMP Manager subscribing Traps.;
	   HELP = ;
	   CAPABILITIES = NET_CFG, VPN_DISP;"
	::= { mcmSysTrapSubscriptionEntry 1}

mcmSysTrapSubscriptionCommunityString OBJECT-TYPE
	SYNTAX	DisplayString
	ACCESS	read-write
	STATUS	mandatory
	DESCRIPTION
	  "NAME = ;
	   DESC = Community string for this subscriber.;
	   HELP = ;
	   CAPABILITIES = NET_CFG, VPN_DISP;"
	::= { mcmSysTrapSubscriptionEntry 2}

mcmSysTrapSubscriptionAction OBJECT-TYPE
	SYNTAX	INTEGER {
		subscribe (1),
		cancel (2)
		}
	ACCESS	read-write
	STATUS	mandatory
	DESCRIPTION
	  "NAME = ;
	   DESC = Action to take: add or delete subscriber.;
	   HELP = ;
	   CAPABILITIES = NET_CFG, VPN_DISP;"
	::= { mcmSysTrapSubscriptionEntry 3}


mcmSysTrapThresholdGroup    OBJECT IDENTIFIER ::= {sys-trap 2}

mcmSysTrapCPUUtilThreshold OBJECT-TYPE
	SYNTAX	INTEGER (1..100)
	ACCESS	read-write
	STATUS	mandatory
	DESCRIPTION
	  "NAME = ;
	   DESC = Indicates the configured threshold for \
                  CPU Utilization.;
	   HELP = ;
	   CAPABILITIES = NET_CFG, VPN_DISP;"
	DEFVAL	{ 90 }
	::= { mcmSysTrapThresholdGroup 1}

mcmSysTrapBandwidthUtilThreshold OBJECT-TYPE
	SYNTAX	INTEGER (1..100)
	ACCESS	read-write
	STATUS	mandatory
	DESCRIPTION
	  "NAME = ;
	   DESC = Indicates the configured threshold for \
                  bandwidth utilization.;
	   HELP = ;
	   CAPABILITIES = NET_CFG, VPN_DISP;"
	DEFVAL	{ 90 }
	::= { mcmSysTrapThresholdGroup 2}

mcmSysTrapRAMUtilThreshold OBJECT-TYPE
	SYNTAX	INTEGER (1..100)
	ACCESS	read-write
	STATUS	mandatory
	DESCRIPTION
	  "NAME = ;
	   DESC = Indicates the configured threshold for \
                  RAM utilization.;
	   HELP = ;
	   CAPABILITIES = NET_CFG, VPN_DISP;"
	DEFVAL	{ 90 }
	::= { mcmSysTrapThresholdGroup 3}

-- Trap Messages

mcmSysMainPowerSupplyFailure TRAP-TYPE
	ENTERPRISE	micom-system
	VARIABLES	{ mcmSysAsciiTimeOfDay }
	DESCRIPTION
	  "NAME = ;
	   DESC = System TRAP message: indication of Power Supply \
                  failure.\
		  Severity Level: CRITICAL.;
	   HELP = Power Supply Jumper may not be set properly.\
                  Please contact the System Administrator, or\
                  field Personnel.;"
	::= 1

mcmSysChassisFanFailure TRAP-TYPE
	ENTERPRISE	micom-system
	VARIABLES	{ mcmSysAsciiTimeOfDay }
	DESCRIPTION
	  "NAME = ;
	   DESC = System TRAP message: indication of a chassis \
                  FAN failure on the access device.\
		  Severity Level: MINOR.;
	   HELP = Fan is not running. Please contact the System\
                  administrator, or Filed Personnel.;"
	::= 2

mcmSysSystemReset TRAP-TYPE
	ENTERPRISE	micom-system
	VARIABLES	{ mcmSysAsciiTimeOfDay }
	DESCRIPTION
	  "NAME = ;
	   DESC = System TRAP message: indication of system Reset \
                  (warm start).\
		  Severity Level: INFORMATIVE.;
	   HELP = A system reset has occured. If normal \
                  operation did not resume after the Reset, Please \
                  contact the System Administrator, or Field \
                  Personnel.;" 
	::= 3

mcmSysBatteryLow TRAP-TYPE
	ENTERPRISE	micom-system
	VARIABLES	{ mcmSysAsciiTimeOfDay }
	DESCRIPTION
	  "NAME = ;
	   DESC = System TRAP message: Indication of Battery Low.\
		  Severity Level: MINOR.;
	   HELP = The access device is experiencing a Battery \
                  Low condition. Please contact the System \
                  Administrator or Field Personnel.;"
	::= 4

mcmSysConfigChanged TRAP-TYPE
	ENTERPRISE	micom-system
	VARIABLES	{ mcmSysAsciiTimeOfDay }
	DESCRIPTION
	  "NAME = ;
	   DESC = An indication of configuration change in \
                  the access device.\
		  Severity Level: MAJOR.;
	   HELP = Configuration has changed in access device. Please \
                  consult the System Administrator, or Field Personnel \
                  if the configuration has affected your applications.;"
	::= 5

mcmSysCPUUtilExceeded TRAP-TYPE
	ENTERPRISE	micom-system
	VARIABLES	{ mcmSysAsciiTimeOfDay }
	DESCRIPTION
	  "NAME = ;
	   DESC = System TRAP message: Indication of CPU Utilization \
                  exceeded for configured threshold.\
		  Severity Level: MAJOR.;
	   HELP = The access device has exceeded its configured threshold \
                  value for CPU Utilization. 
                  This value can be changed using set sys traps cpu 1 - 100.\ 
                  Or Consult your system Administrator, or field Personnel if \
                  this value needs to be changed.;"
	::= 6

mcmSysBandwidthUtilExceeded TRAP-TYPE
	ENTERPRISE	micom-system
	VARIABLES	{ mcmSysAsciiTimeOfDay }
	DESCRIPTION
	  "NAME = ;
	   DESC = System TRAP message: Indication of Bandwidth  \
                  Utilization exceeded for configured threshold.\
		  Severity Level: MAJOR.;
	   HELP = The access device has exceeded its Configured \
                  threshold value for its bandwidth utilization. \
                  This value can be changed using set sys traps \
                  bandwidth 1-100 or Consult your system \
                  Administrator, or Field Personnel if this value needs \
                  to be changed.;"
	::= 7

mcmSysRAMUtilExceeded TRAP-TYPE
	ENTERPRISE	micom-system
	VARIABLES	{ mcmSysAsciiTimeOfDay }
	DESCRIPTION
	  "NAME = ;
	   DESC = System TRAP message: Indication of RAM  \
                  Utilization exceeded for configured threshold.\
		  Severity Level: MAJOR.;
	   HELP = It is an indication of surpassing the configured \
                  value for RAM utilization. This value can be changed
                  using set sys traps ram 1-100 or Consult your system \
                  administrator, or Field Personnel if this value needs \
                  to be changed.;"
	::= 8

mcmSysRollbackEnabled TRAP-TYPE
	ENTERPRISE	micom-system
	VARIABLES	{ mcmSysAsciiTimeOfDay }
	DESCRIPTION
	  "NAME = ;
	   DESC = System TRAP message: Indication of System  \
                  Rollback Feature enabled.\
		  Severity Level: INFORMATIVE.; 
	   HELP = This is an indication of the Rollback feature \
                  being enabled. Please disable this feature if \
                  it is not desired, or consult your System Admin.\
                  or Field Personnel.;"
	::= 9

mcmSysRollbackDisabled TRAP-TYPE
	ENTERPRISE	micom-system
	VARIABLES	{ mcmSysAsciiTimeOfDay }
	DESCRIPTION
	  "NAME = ;
	   DESC = System TRAP message: Indication of System  \
                  Rollback Feature disabled.\
		  Severity Level: INFORMATIVE.;
	   HELP = This is an indication of the Rollback feature \
                  being disabled. Please enable this feature if \
                  it is required. Otherwise, consult your system \
                  admin. or Field Personnel.;"
	::= 10 

mcmSysRollbackArmed TRAP-TYPE
	ENTERPRISE	micom-system
	VARIABLES	{ mcmSysAsciiTimeOfDay }
	DESCRIPTION
	  "NAME = ;
	   DESC = System TRAP message: Indication of System  \
                  Rollback Feature armed, resulting from User \
                  committing/activating Code/Config Bank for \
                  next reset.\
		  Severity Level: INFORMATIVE.;
	   HELP = This is an indication of user committing a new \
                  code bank/Config Bank after the access device \
                  is reset the next time around. If this \
                  condition is not needed, consult your System \
                  Admin. or Field personnel.;"
	::= 11 

mcmSysRollbackDisarmed TRAP-TYPE
	ENTERPRISE	micom-system
	VARIABLES	{ mcmSysAsciiTimeOfDay }
	DESCRIPTION
	  "NAME = ;
	   DESC = System TRAP message: Indication of System  \
                  Rollback Feature confirmed for this session.\
 		  Severity Level: INFORMATIVE.;
	   HELP = This is a condition of disarming previously \ 
                  committed Code Bank/config Bank that was going \
                  to occur after a reset. If it is not desirable, \
                  reverse the condition., ;"
	::= 12 

-- End of Trap Messages

END
