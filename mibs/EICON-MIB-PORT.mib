-- Documents: 285-518-1.

EICON-MIB-PORT DEFINITIONS  ::=  BEGIN


IMPORTS
	Counter,  Gauge,  TimeTicks, enterprises
		FROM RFC1155-SMI
	OBJECT-TYPE
		FROM RFC-1212
	TRAP-TYPE
		FROM RFC-1215
	DisplayString, sysName
		FROM RFC1213-MIB;

eicon           OBJECT IDENTIFIER  ::= { enterprises 434 }
management      OBJECT IDENTIFIER  ::= { eicon 2 }
mibv2           OBJECT IDENTIFIER  ::= { management 2 }
module          OBJECT IDENTIFIER  ::= { mibv2 4 }

--      Title

port    OBJECT IDENTIFIER  ::= { mibv2 3 }

--      The port group contains information about all ports configured
--     in the server. It is composed of one attribute and the following table:
--              portTable.

OperState ::= INTEGER {
	other (1),              -- none of the following
	disabled (2),           -- not in ready state
	ready (3),              -- in ready state
	active (4),             -- ready and operating
	busy (5)                        -- operating but cannot accept more traffic
	}

AdminState ::= INTEGER {
	start (1),
	stop (2),
	dump (3),
	test (4),
	invalid (5)
	}

 ActionState ::= INTEGER {
	done (1),
	failed (2),
	in-progress (3)
	}

CardRef ::= INTEGER (1..6)      -- EiconCard reference on the server.

PortRef ::= INTEGER (1..48)     -- Port reference on the server.

PortName ::= DisplayString (SIZE (1..15))       -- Port name composed of up to 15 ascii characters.

PositiveInteger ::= INTEGER (0..2147483647)


portNumberOfPorts       OBJECT-TYPE
	SYNTAX  PortRef
	ACCESS  read-only 
	STATUS  mandatory
	DESCRIPTION     
		"The number of existing ports on all installed EiconCards, as seen by the Agent."
	::= { port 1 }

portTable               OBJECT-TYPE
	SYNTAX  SEQUENCE OF  PortEntry
	ACCESS  not-accessible
	STATUS  mandatory
	DESCRIPTION     
		"The table of the ports seen by the agent."
	::= { port 2 }

portEntry               OBJECT-TYPE
	SYNTAX  PortEntry
	ACCESS  not-accessible
	STATUS  mandatory
	DESCRIPTION     
		"The set of attributes for one port."
	INDEX           { portIndex }
	::= { portTable 1 }

PortEntry ::= SEQUENCE {
	portIndex
		PortRef,
	portLanaNo
		PortRef,
	portName
		PortName,
	portCardLocation
		CardRef,
	portDescription
		DisplayString,
	portOperState
		OperState,
	portAdminStateCtr
		AdminState,
	portOpenTime            -- Not supported by Agent
		TimeTicks,
	portProtocols
		INTEGER,
	portDialerType
		INTEGER,
	portActionState
		ActionState,
	portActionError
		INTEGER
	}

portIndex               OBJECT-TYPE
	SYNTAX  PortRef
	ACCESS  read-only 
	STATUS  mandatory
	DESCRIPTION     
		"The index of the port generated by the Agent. 
		Used in all other tables refering to ports."
	::= { portEntry 1 }

portLanaNo              OBJECT-TYPE
	SYNTAX  PortRef
	ACCESS  read-only 
	STATUS  mandatory
	DESCRIPTION     
		"The LANA number of the port from the configuration, range: 1..48."
	::= { portEntry 2 }

portName                OBJECT-TYPE
	SYNTAX  PortName
	ACCESS  read-only 
	STATUS  mandatory
	DESCRIPTION     
		"The unique port name."
	::= { portEntry 3 }

portCardLocation        OBJECT-TYPE
	SYNTAX  CardRef
	ACCESS  read-only 
	STATUS  mandatory
	DESCRIPTION     
		"The card reference. It should match the cardIndex 
		(from the cardTable) of the card that this port belongs to."
	::= { portEntry 4 }

portDescription         OBJECT-TYPE
	SYNTAX  DisplayString (SIZE(0..256))
	ACCESS  read-write
	STATUS  mandatory
	DESCRIPTION     
		"A general  description of the port set by the Operator."
	::= { portEntry 5 }

portOperState           OBJECT-TYPE
	SYNTAX  OperState
	ACCESS  read-only 
	STATUS  mandatory
	DESCRIPTION     
		"The operational state of the port."
	::= { portEntry 6 }

portAdminStateCtr       OBJECT-TYPE
	SYNTAX  AdminState
	ACCESS  read-write
	STATUS  mandatory
	DESCRIPTION     
		"The parameter that can be modified by the Operator in order to change the state of the 	
		port. The value 'locked' is used to stop the port, the value 'unlocked' isued to start the      
		port."
	::= { portEntry 7 }

portOpenTime            OBJECT-TYPE
	SYNTAX  TimeTicks
	ACCESS  read-only 
	STATUS  mandatory
	DESCRIPTION     
		"The time the port was activated."
	::= { portEntry 8 }

portProtocols           OBJECT-TYPE
	SYNTAX  INTEGER
	ACCESS  read-only 
	STATUS  mandatory
	DESCRIPTION     
		"The mask indicating what is running on the port: lapb=0x1,
		sdlc=0x2, x25=0x4, frbs=0x8, dialer=0x100, ppp=0x1000."
	::= { portEntry 9 }

portDialerType          OBJECT-TYPE
	SYNTAX  INTEGER {
			direct (1),
			v25bis (2),
			v22bis (3),
			at-cmd (4),
			isdn-stat (5),
			v32bis (6),
			none (7),
			other (8)
			}
	ACCESS  read-only 
		STATUS  mandatory
	DESCRIPTION     
		"The dialer type."
	::= { portEntry 10 }

portActionState         OBJECT-TYPE
	SYNTAX  ActionState
	ACCESS  read-only 
	STATUS  mandatory
	DESCRIPTION     
		"The state of the operation performed on the port by the Agent as a result of setting 
		the values to the portAdminStateCtr. The Management station will poll that variable
		after initiating an action on the port.  The value done(1) indicates that the action 
		terminated successfully. The value failed(2) indicates that the action terminated with an       
		error. In this case the variable portActionError indicates the error code."
	::= { portEntry 11 }

portActionError         OBJECT-TYPE
	SYNTAX  INTEGER {
		no-error (0),
		err-WARNING (1),
		err-PARTIAL (2),
		err-ABORT (3),
		err-FAILED (4)
	}
	ACCESS  read-only 
	STATUS  mandatory
	DESCRIPTION     
		"The error code after the unsuccessful operation."
	::= { portEntry 12 }


--      This section contains the definition of port specific traps. 
--      Will not be implemented in the current release of the Agent.

portTrapStateChange     TRAP-TYPE
	ENTERPRISE      eicon
	VARIABLES       { sysName,  portIndex, portOperState  }
	DESCRIPTION
		"The trap indicates that the port has changed state."
	::=  31


END
