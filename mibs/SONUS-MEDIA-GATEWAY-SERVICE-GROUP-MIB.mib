--
-- This SMIv2 module has been generated by smidump 0.2-cvs. Do not edit.
--

SONUS-MEDIA-GATEWAY-SERVICE-GROUP-MIB DEFINITIONS ::= BEGIN

IMPORTS
    Integer32, MODULE-IDENTITY, OBJECT-TYPE
        FROM SNMPv2-SMI
    RowStatus
        FROM SNMPv2-TC
    sonusSignallingMIBs
        FROM SONUS-SMI
    SonusBoolean, SonusName, SonusNameReference
        FROM SONUS-TC;

sonusMediaGatewayServiceGroupMIB MODULE-IDENTITY
    LAST-UPDATED    "200102030000Z"
    ORGANIZATION    
            "Sonus Networks, Inc."
    CONTACT-INFO    
            "   Customer Support    
             Sonus Networks, Inc,
             5 Carlisle Road
             Westford, MA 01886
             USA
             
             Tel: 978-692-8999
             Fax: 978-392-9118
             E-mail: cs.snmp@sonusnet.com"
    DESCRIPTION     
            "The MIB Module for Media Gateway Service Group management."
    ::= { sonusSignallingMIBs 3 }


sonusMediaGatewayServiceGroupMIBObjects OBJECT IDENTIFIER
    ::= { sonusMediaGatewayServiceGroupMIB 1 }

sonusMgsgServiceGrp OBJECT IDENTIFIER
    ::= { sonusMediaGatewayServiceGroupMIBObjects 1 }

sonusMgsgServiceGrpNextIndex OBJECT-TYPE
    SYNTAX          Integer32
    MAX-ACCESS      read-only
    STATUS          current
    DESCRIPTION     
            "The next valid index to use when creating a new sonusMgsgServiceGrpEntry"
    ::= { sonusMgsgServiceGrp 1 }

sonusMgsgServiceGrpTable OBJECT-TYPE
    SYNTAX          SEQUENCE OF SonusMgsgServiceGrpEntry
    MAX-ACCESS      not-accessible
    STATUS          current
    DESCRIPTION     
            "This table contains information about each Media Gateway Service Group
             configured to be a member of the node. 
             
             A management entity may create rows for Service Group that are
             anticipated to be supported in the future."
    ::= { sonusMgsgServiceGrp 2 }

sonusMgsgServiceGrpEntry OBJECT-TYPE
    SYNTAX          SonusMgsgServiceGrpEntry
    MAX-ACCESS      not-accessible
    STATUS          current
    DESCRIPTION     
            "This table describes the Media Gateway Service Groups that are configured as
             members of the Marlin Node."
    INDEX           { sonusMgsgServiceGrpListIndex }
    ::= { sonusMgsgServiceGrpTable 1 }

SonusMgsgServiceGrpEntry ::=
    SEQUENCE {
        sonusMgsgServiceGrpListIndex    Integer32,
        sonusMgsgServiceGrpName         SonusName,
        sonusMgsgServiceGrpAdminState   INTEGER,
        sonusMgsgServiceGrpControllerName SonusNameReference,
        sonusMgsgServiceGrpType         INTEGER,
        sonusMgsgServiceGrpMode         INTEGER,
        sonusMgsgServiceGrpAction       INTEGER,
        sonusMgsgServiceGrpTimeout      Integer32,
        sonusMgsgServiceGrpRowStatus    RowStatus
    }

sonusMgsgServiceGrpListIndex OBJECT-TYPE
    SYNTAX          Integer32
    MAX-ACCESS      read-only
    STATUS          current
    DESCRIPTION     
            "The index of the Media Gateway Service Group entry."
    ::= { sonusMgsgServiceGrpEntry 1 }

sonusMgsgServiceGrpName OBJECT-TYPE
    SYNTAX          SonusName
    MAX-ACCESS      read-write
    STATUS          current
    DESCRIPTION     
            "The name of the Media Gateway Service Group."
    ::= { sonusMgsgServiceGrpEntry 2 }

sonusMgsgServiceGrpAdminState OBJECT-TYPE
    SYNTAX          INTEGER { disabled(1), enabled(2) }
    MAX-ACCESS      read-write
    STATUS          current
    DESCRIPTION     
            "The admin state of the Media Gateway Service Group."
    DEFVAL          { 1 }
    ::= { sonusMgsgServiceGrpEntry 3 }

sonusMgsgServiceGrpControllerName OBJECT-TYPE
    SYNTAX          SonusNameReference
    MAX-ACCESS      read-write
    STATUS          current
    DESCRIPTION     
            "The Name of the Media Gateway Controller which controls this service group"
    ::= { sonusMgsgServiceGrpEntry 4 }

sonusMgsgServiceGrpType OBJECT-TYPE
    SYNTAX          INTEGER { ipdc(1), mgcp(2) }
    MAX-ACCESS      read-write
    STATUS          current
    DESCRIPTION     
            "The type(protocol) of media gateway control protocol
             Note: ipdc value is obsolete and can not be used"
    DEFVAL          { mgcp }
    ::= { sonusMgsgServiceGrpEntry 5 }

sonusMgsgServiceGrpMode OBJECT-TYPE
    SYNTAX          INTEGER { blocked(1), unblocked(2) }
    MAX-ACCESS      read-write
    STATUS          current
    DESCRIPTION     
            "Whether the Service Group is in Blocked or Unblocked Mode"
    DEFVAL          { blocked }
    ::= { sonusMgsgServiceGrpEntry 6 }

sonusMgsgServiceGrpAction OBJECT-TYPE
    SYNTAX          INTEGER { dryup(1), force(2) }
    MAX-ACCESS      read-write
    STATUS          current
    DESCRIPTION     
            "Indicates whether the service group is to be put in blocked immediately or 
             after a dry-up period"
    DEFVAL          { dryup }
    ::= { sonusMgsgServiceGrpEntry 7 }

sonusMgsgServiceGrpTimeout OBJECT-TYPE
    SYNTAX          Integer32 (1..1440)
    MAX-ACCESS      read-write
    STATUS          current
    DESCRIPTION     
            "The TimeOut Period for DryUp In Minutes"
    DEFVAL          { 60 }
    ::= { sonusMgsgServiceGrpEntry 8 }

sonusMgsgServiceGrpRowStatus OBJECT-TYPE
    SYNTAX          RowStatus
    MAX-ACCESS      read-write
    STATUS          current
    DESCRIPTION     
            ""
    ::= { sonusMgsgServiceGrpEntry 9 }

sonusMgsgServiceGrpStatTable OBJECT-TYPE
    SYNTAX          SEQUENCE OF SonusMgsgServiceGrpStatEntry
    MAX-ACCESS      not-accessible
    STATUS          current
    DESCRIPTION     
            "This table contains status information about each MGSG service group
             in the Marlin Switch node.  "
    ::= { sonusMediaGatewayServiceGroupMIBObjects 2 }

sonusMgsgServiceGrpStatEntry OBJECT-TYPE
    SYNTAX          SonusMgsgServiceGrpStatEntry
    MAX-ACCESS      not-accessible
    STATUS          current
    DESCRIPTION     
            "This table describes the status of MGSG Service Groups"
    INDEX           { sonusMgsgServiceGrpStatListIndex }
    ::= { sonusMgsgServiceGrpStatTable 1 }

SonusMgsgServiceGrpStatEntry ::=
    SEQUENCE {
        sonusMgsgServiceGrpStatListIndex Integer32,
        sonusMgsgServiceGrpStatName     SonusNameReference,
        sonusMgsgServiceGrpStatStatus   INTEGER
    }

sonusMgsgServiceGrpStatListIndex OBJECT-TYPE
    SYNTAX          Integer32
    MAX-ACCESS      read-only
    STATUS          current
    DESCRIPTION     
            "The index of the MGSG Service Group."
    ::= { sonusMgsgServiceGrpStatEntry 1 }

sonusMgsgServiceGrpStatName OBJECT-TYPE
    SYNTAX          SonusNameReference
    MAX-ACCESS      read-only
    STATUS          current
    DESCRIPTION     
            "The name of the MGSG Service Group."
    ::= { sonusMgsgServiceGrpStatEntry 2 }

sonusMgsgServiceGrpStatStatus OBJECT-TYPE
    SYNTAX          INTEGER { available(1), unavailable(2), blocked(3) }
    MAX-ACCESS      read-only
    STATUS          current
    DESCRIPTION     
            "The state of the MGSG Service Group."
    ::= { sonusMgsgServiceGrpStatEntry 3 }

sonusMgsgCktTable OBJECT-TYPE
    SYNTAX          SEQUENCE OF SonusMgsgCktEntry
    MAX-ACCESS      not-accessible
    STATUS          current
    DESCRIPTION     
            "The Mgsg Ckt table describes the ckts in a MGSG
             service Group."
    ::= { sonusMediaGatewayServiceGroupMIBObjects 3 }

sonusMgsgCktEntry OBJECT-TYPE
    SYNTAX          SonusMgsgCktEntry
    MAX-ACCESS      not-accessible
    STATUS          current
    DESCRIPTION     
            "This is the admin table for MGSG Circuits"
    INDEX           { sonusMgsgCktShelfIndex, sonusMgsgCktSlotIndex, 
                      sonusMgsgCktDs1Index, sonusMgsgCktDs0Index }
    ::= { sonusMgsgCktTable 1 }

SonusMgsgCktEntry ::=
    SEQUENCE {
        sonusMgsgCktShelfIndex          Integer32,
        sonusMgsgCktSlotIndex           Integer32,
        sonusMgsgCktDs1Index            Integer32,
        sonusMgsgCktDs0Index            Integer32,
        sonusMgsgCktSrvGrpName          SonusNameReference,
        sonusMgsgCktMode                INTEGER,
        sonusMgsgCktAction              INTEGER,
        sonusMgsgCktTimeout             Integer32,
        sonusMgsgCktAdminState          INTEGER,
        sonusMgsgCktProfileName         SonusNameReference,
        sonusMgsgCktType                INTEGER,
        sonusMgsgCktDchanSwitchType     INTEGER,
        sonusMgsgCktRowStatus           RowStatus
    }

sonusMgsgCktShelfIndex OBJECT-TYPE
    SYNTAX          Integer32 (1..6)
    MAX-ACCESS      read-only
    STATUS          current
    DESCRIPTION     
            "The Shelf Index for this Ckt Table"
    ::= { sonusMgsgCktEntry 1 }

sonusMgsgCktSlotIndex OBJECT-TYPE
    SYNTAX          Integer32 (1..16)
    MAX-ACCESS      read-only
    STATUS          current
    DESCRIPTION     
            "The Slot Index for this Ckt Table"
    ::= { sonusMgsgCktEntry 2 }

sonusMgsgCktDs1Index OBJECT-TYPE
    SYNTAX          Integer32 (1..28)
    MAX-ACCESS      read-only
    STATUS          current
    DESCRIPTION     
            "The Ds1 Index for this Ckt Table"
    ::= { sonusMgsgCktEntry 3 }

sonusMgsgCktDs0Index OBJECT-TYPE
    SYNTAX          Integer32 (1..32)
    MAX-ACCESS      read-only
    STATUS          current
    DESCRIPTION     
            "Identifies the channel the ckt represents."
    ::= { sonusMgsgCktEntry 4 }

sonusMgsgCktSrvGrpName OBJECT-TYPE
    SYNTAX          SonusNameReference
    MAX-ACCESS      read-write
    STATUS          current
    DESCRIPTION     
            "The name of the MGSG Service Group this ckt is under."
    ::= { sonusMgsgCktEntry 5 }

sonusMgsgCktMode OBJECT-TYPE
    SYNTAX          INTEGER { blocked(1), unblocked(2) }
    MAX-ACCESS      read-write
    STATUS          current
    DESCRIPTION     
            "Whether the Circuit is in Blocked or Unblocked Mode"
    DEFVAL          { blocked }
    ::= { sonusMgsgCktEntry 6 }

sonusMgsgCktAction OBJECT-TYPE
    SYNTAX          INTEGER { dryup(1), force(2) }
    MAX-ACCESS      read-write
    STATUS          current
    DESCRIPTION     
            "Indicates whether the circuit is to be put in blocked immediately or 
             after a dry-up period"
    DEFVAL          { dryup }
    ::= { sonusMgsgCktEntry 7 }

sonusMgsgCktTimeout OBJECT-TYPE
    SYNTAX          Integer32 (1..1440)
    MAX-ACCESS      read-write
    STATUS          current
    DESCRIPTION     
            "The TimeOut Period for DryUp In Minutes"
    DEFVAL          { 60 }
    ::= { sonusMgsgCktEntry 8 }

sonusMgsgCktAdminState OBJECT-TYPE
    SYNTAX          INTEGER { disabled(1), enabled(2) }
    MAX-ACCESS      read-write
    STATUS          current
    DESCRIPTION     
            "The admin state of the MGSG Ckt."
    ::= { sonusMgsgCktEntry 9 }

sonusMgsgCktProfileName OBJECT-TYPE
    SYNTAX          SonusNameReference
    MAX-ACCESS      read-write
    STATUS          current
    DESCRIPTION     
            "The ckt profile name assigned to the MGSG ckt."
    ::= { sonusMgsgCktEntry 10 }

sonusMgsgCktType OBJECT-TYPE
    SYNTAX          INTEGER { data(1), dchan-user(2), dchan-ntwk(3) }
    MAX-ACCESS      read-write
    STATUS          current
    DESCRIPTION     
            "The type of the MGSG Ckt. (data or a D-channel)"
    DEFVAL          { 1 }
    ::= { sonusMgsgCktEntry 11 }

sonusMgsgCktDchanSwitchType OBJECT-TYPE
    SYNTAX          INTEGER { ni2(1), sw4ess(2), sw5esscust(3), dms(4), 
                        kdd(5), ntt(6), itu(7), net5(8), sw1tr6(9), 
                        ts014(10), vn(11) }
    MAX-ACCESS      read-write
    STATUS          current
    DESCRIPTION     
            "For Ckts of type D-chan this describes the switch type that D-chan is connected to."
    DEFVAL          { itu }
    ::= { sonusMgsgCktEntry 12 }

sonusMgsgCktRowStatus OBJECT-TYPE
    SYNTAX          RowStatus
    MAX-ACCESS      read-write
    STATUS          current
    DESCRIPTION     
            ""
    ::= { sonusMgsgCktEntry 13 }

sonusMgsgCktStatTable OBJECT-TYPE
    SYNTAX          SEQUENCE OF SonusMgsgCktStatEntry
    MAX-ACCESS      not-accessible
    STATUS          current
    DESCRIPTION     
            "This table contains status information about each MGSG ckt 
             in the Marlin Switch node. ."
    ::= { sonusMediaGatewayServiceGroupMIBObjects 4 }

sonusMgsgCktStatEntry OBJECT-TYPE
    SYNTAX          SonusMgsgCktStatEntry
    MAX-ACCESS      not-accessible
    STATUS          current
    DESCRIPTION     
            "This table describes the status of the configured MGSG ckts."
    INDEX           { sonusMgsgCktStatShelfIndex, 
                      sonusMgsgCktStatSlotIndex, 
                      sonusMgsgCktStatDs1Index, sonusMgsgCktStatDs0Index }
    ::= { sonusMgsgCktStatTable 1 }

SonusMgsgCktStatEntry ::=
    SEQUENCE {
        sonusMgsgCktStatShelfIndex      Integer32,
        sonusMgsgCktStatSlotIndex       Integer32,
        sonusMgsgCktStatDs1Index        Integer32,
        sonusMgsgCktStatDs0Index        Integer32,
        sonusMgsgCktStatSrvGrpName      SonusNameReference,
        sonusMgsgCktStatMgcState        INTEGER,
        sonusMgsgCktStatLocalHwState    INTEGER,
        sonusMgsgCktStatDryupInProgress SonusBoolean
    }

sonusMgsgCktStatShelfIndex OBJECT-TYPE
    SYNTAX          Integer32
    MAX-ACCESS      read-only
    STATUS          current
    DESCRIPTION     
            "The Shelf Index for this Ckt Table"
    ::= { sonusMgsgCktStatEntry 1 }

sonusMgsgCktStatSlotIndex OBJECT-TYPE
    SYNTAX          Integer32
    MAX-ACCESS      read-only
    STATUS          current
    DESCRIPTION     
            "The Slot Index for this Ckt Table"
    ::= { sonusMgsgCktStatEntry 2 }

sonusMgsgCktStatDs1Index OBJECT-TYPE
    SYNTAX          Integer32
    MAX-ACCESS      read-only
    STATUS          current
    DESCRIPTION     
            "The Ds1 Index for this Ckt Table"
    ::= { sonusMgsgCktStatEntry 3 }

sonusMgsgCktStatDs0Index OBJECT-TYPE
    SYNTAX          Integer32
    MAX-ACCESS      read-only
    STATUS          current
    DESCRIPTION     
            "Identifies the channel the ckt represents."
    ::= { sonusMgsgCktStatEntry 4 }

sonusMgsgCktStatSrvGrpName OBJECT-TYPE
    SYNTAX          SonusNameReference
    MAX-ACCESS      read-only
    STATUS          current
    DESCRIPTION     
            "The name of the MGSG Service Group this ckt is under."
    ::= { sonusMgsgCktStatEntry 5 }

sonusMgsgCktStatMgcState OBJECT-TYPE
    SYNTAX          INTEGER { notPresent(1), outOfService(2), 
                        maintenance(3), blocked(4), loopback(5), idle(6), 
                        inUse(7), connected(8), disabled(9), 
                        dualToneLoop(10) }
    MAX-ACCESS      read-only
    STATUS          current
    DESCRIPTION     
            "The state of MGSG ckt, as reported to the Media Gateway Controller "
    ::= { sonusMgsgCktStatEntry 6 }

sonusMgsgCktStatLocalHwState OBJECT-TYPE
    SYNTAX          INTEGER { available(1), unavailable(2) }
    MAX-ACCESS      read-only
    STATUS          current
    DESCRIPTION     
            "The local state of the MGSG ckt from a hardware perspective"
    ::= { sonusMgsgCktStatEntry 7 }

sonusMgsgCktStatDryupInProgress OBJECT-TYPE
    SYNTAX          SonusBoolean
    MAX-ACCESS      read-only
    STATUS          current
    DESCRIPTION     
            "This object indicates whether a dry-up is in progress or not on the circuit"
    ::= { sonusMgsgCktStatEntry 8 }

sonusMediaGatewayServiceGroupMIBNotifications OBJECT IDENTIFIER
    ::= { sonusMediaGatewayServiceGroupMIB 2 }

sonusMediaGatewayServiceGroupMIBNotificationsPrefix OBJECT IDENTIFIER
    ::= { sonusMediaGatewayServiceGroupMIBNotifications 0 }

sonusMediaGatewayServiceGroupMIBNotificationsObjects OBJECT IDENTIFIER
    ::= { sonusMediaGatewayServiceGroupMIBNotifications 1 }

END -- end of module SONUS-MEDIA-GATEWAY-SERVICE-GROUP-MIB.
