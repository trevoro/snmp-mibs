BLUECOAT-AV-MIB DEFINITIONS ::= BEGIN

	IMPORTS
		MODULE-IDENTITY,OBJECT-TYPE,NOTIFICATION-TYPE, Counter32, Counter64,
			Gauge32 FROM SNMPv2-SMI
		DisplayString,DateAndTime
			FROM SNMPv2-TC
		blueCoatMgmt
			FROM BLUECOAT-MIB;

	blueCoatAvMib MODULE-IDENTITY
		LAST-UPDATED "0704160000Z"
		ORGANIZATION "Blue Coat Systems, Inc."
		CONTACT-INFO
		"support@bluecoat.com"
		DESCRIPTION
			"The AV MIB is used to monitor
			antivirus related info."
		::= { blueCoatMgmt 10 }

blueCoatAvMibObjects
                OBJECT IDENTIFIER ::= { blueCoatAvMib 1 }

blueCoatAvMibNotificationObjects
                OBJECT IDENTIFIER ::= { blueCoatAvMib 2 }

blueCoatAvMibNotifications
                OBJECT IDENTIFIER ::= { blueCoatAvMib 3 }

-----------------------------------------------------------------------------------

avFilesScanned OBJECT-TYPE
        SYNTAX          Counter64
        MAX-ACCESS      read-only
        STATUS          current
        DESCRIPTION
                        "Sum of number of files scanned using all protocols.
                        An archive containing multiple files will count as
                        one file."
        ::= { blueCoatAvMibObjects 1  }

avVirusesDetected OBJECT-TYPE
        SYNTAX          Counter32
        MAX-ACCESS      read-only
        STATUS          current
        DESCRIPTION
                        "Sum of number of infected files detected using all
                        protocols. A file containing multiple infections will
                        count as one infected file."
        ::= { blueCoatAvMibObjects 2  }

avPatternVersion OBJECT-TYPE
         SYNTAX  DisplayString
         MAX-ACCESS read-only
         STATUS  current
         DESCRIPTION
                 "AV pattern version."
         ::= { blueCoatAvMibObjects 3 }

avPatternDateTime OBJECT-TYPE
    SYNTAX     DateAndTime
    MAX-ACCESS read-only
    STATUS     current
    DESCRIPTION
        "Release date and time of the av pattern."
    ::= { blueCoatAvMibObjects 4 }

avEngineVersion OBJECT-TYPE
         SYNTAX  DisplayString
         MAX-ACCESS read-only
         STATUS  current
         DESCRIPTION
                 "AV engine version."
         ::= { blueCoatAvMibObjects 5 }

avVendorName OBJECT-TYPE
         SYNTAX  DisplayString
         MAX-ACCESS read-only
         STATUS  current
         DESCRIPTION
                 "AV vendor name."
         ::= { blueCoatAvMibObjects 6 }

avLicenseDaysRemaining OBJECT-TYPE
        SYNTAX          INTEGER
        MAX-ACCESS      read-only
        STATUS          current
        DESCRIPTION
                 "AV license days remaining."
         ::= { blueCoatAvMibObjects 7 }

avPublishedFirmwareVersion OBJECT-TYPE
         SYNTAX  DisplayString
         MAX-ACCESS read-only
         STATUS  current
         DESCRIPTION
                 "ProxyAV version published on the automatic update location."
         ::= { blueCoatAvMibObjects 8 }

avInstalledFirmwareVersion OBJECT-TYPE
         SYNTAX  DisplayString
         MAX-ACCESS read-only
         STATUS  current
         DESCRIPTION
                 "Currently installed ProxyAV firmware version."
         ::= { blueCoatAvMibObjects 9 }

avSlowICAPConnections OBJECT-TYPE
        SYNTAX          Gauge32  
        MAX-ACCESS      read-only
        STATUS          current
        DESCRIPTION
                 "The number of ICAP connections that are considered 'slow' -
                 receiving data for more than the configured time threshold
                 (by default 60 seconds)."
         ::= { blueCoatAvMibObjects 10 }
         
avICAPFilesScanned OBJECT-TYPE
        SYNTAX          Counter64
        MAX-ACCESS      read-only
        STATUS          current
        DESCRIPTION
                 "Number of files scanned using the ICAP protocol.
                 An archive containing multiple files will count as
                 one file."
         ::= { blueCoatAvMibObjects 11 }

avICAPVirusesDetected OBJECT-TYPE
        SYNTAX          Counter32
        MAX-ACCESS      read-only
        STATUS          current
        DESCRIPTION
                 "Number of infected files detected using the ICAP
                 protocol. A file containing multiple infections will
                 count as one infected file."
         ::= { blueCoatAvMibObjects 12 }

avSecureICAPFilesScanned OBJECT-TYPE
        SYNTAX          Counter64
        MAX-ACCESS      read-only
        STATUS          current
        DESCRIPTION
                 "Number of files scanned using the Secure ICAP protocol.
                 An archive containing multiple files will count as
                 one file."
         ::= { blueCoatAvMibObjects 13 }

avSecureICAPVirusesDetected OBJECT-TYPE
        SYNTAX          Counter32
        MAX-ACCESS      read-only
        STATUS          current
        DESCRIPTION
                 "Number of infected files detected using the Secure ICAP
                 protocol. A file containing multiple infections will
                 count as one infected file."
         ::= { blueCoatAvMibObjects 14 }

-----------------------------------------------------------------------------------

avUpdateFailureReason OBJECT-TYPE
         SYNTAX  DisplayString
         MAX-ACCESS not-accessible
         STATUS  current
         DESCRIPTION
                 "The reason why the av engine/pattern/firmware update failed."
         ::= { blueCoatAvMibNotificationObjects 1 }

avUrl OBJECT-TYPE
         SYNTAX  DisplayString
         MAX-ACCESS not-accessible
         STATUS  current
         DESCRIPTION
                 "The URL for use in notifications."
         ::= { blueCoatAvMibNotificationObjects 2 }

avVirusName OBJECT-TYPE
         SYNTAX  DisplayString
         MAX-ACCESS not-accessible
         STATUS  current
         DESCRIPTION
                 "The name of the infection found."
         ::= { blueCoatAvMibNotificationObjects 3 }

avVirusDetails OBJECT-TYPE
         SYNTAX  DisplayString
         MAX-ACCESS not-accessible
         STATUS  current
         DESCRIPTION
                 "More details about the infection found."
         ::= { blueCoatAvMibNotificationObjects 4 }

avErrorCode OBJECT-TYPE
         SYNTAX  DisplayString
         MAX-ACCESS not-accessible
         STATUS  current
         DESCRIPTION
                 "Error code identifying the scan exception, like max_file_size_exceeded."
         ::= { blueCoatAvMibNotificationObjects 5 }

avErrorDetails OBJECT-TYPE
         SYNTAX  DisplayString
         MAX-ACCESS not-accessible
         STATUS  current
         DESCRIPTION
                 "More details about the scan exception."
         ::= { blueCoatAvMibNotificationObjects 6 }

avPreviousFirmwareVersion OBJECT-TYPE
         SYNTAX  DisplayString
         MAX-ACCESS not-accessible
         STATUS  current
         DESCRIPTION
                 "The firmware version before the firmware update."
         ::= { blueCoatAvMibNotificationObjects 7 }

avICTMWarningReason OBJECT-TYPE
         SYNTAX  DisplayString
         MAX-ACCESS not-accessible
         STATUS  current
         DESCRIPTION
                 "The reason of the Intelligent Connection Traffic Monitoring warning."
         ::= { blueCoatAvMibNotificationObjects 8 }
		 
avTestAlertText OBJECT-TYPE
		 SYNTAX DisplayString
		 MAX-ACCESS not-accessible
		 STATUS current
		 DESCRIPTION
				 "Test alert text."
		 ::= { blueCoatAvMibNotificationObjects 11 }

-----------------------------------------------------------------------------------

avAntivirusUpdateSuccess NOTIFICATION-TYPE
        OBJECTS { avVendorName, avEngineVersion, avPatternVersion, avPatternDateTime }
        STATUS current
        DESCRIPTION
                "Successful av engine/pattern update."
        ::= { blueCoatAvMibNotifications 1 }

avAntivirusUpdateFailed NOTIFICATION-TYPE
        OBJECTS { avUpdateFailureReason, avVendorName, avEngineVersion, avPatternVersion, avPatternDateTime }
        STATUS current
        DESCRIPTION
                "Av engine/pattern update failed, avUpdateFailureReason provides more details."
        ::= { blueCoatAvMibNotifications 2 }

avVirusDetected NOTIFICATION-TYPE
        OBJECTS { avUrl, avVirusName, avVirusDetails }
        STATUS current
        DESCRIPTION
                "Infected file detected at avUrl."
        ::= { blueCoatAvMibNotifications 3 }

avFileServed NOTIFICATION-TYPE
        OBJECTS { avUrl, avErrorCode, avErrorDetails }
        STATUS current
        DESCRIPTION
                "File served without scanning. It could not be scanned completely due to a scan exception."
        ::= { blueCoatAvMibNotifications 4 }

avFileBlocked NOTIFICATION-TYPE
        OBJECTS { avUrl, avErrorCode, avErrorDetails }
        STATUS current
        DESCRIPTION
                "File blocked. It could not be scanned completely due to a scan exception."
        ::= { blueCoatAvMibNotifications 5 }

avNewFirmwareAvailable NOTIFICATION-TYPE
        OBJECTS { avInstalledFirmwareVersion, avPublishedFirmwareVersion }
        STATUS current
        DESCRIPTION
                "New firmware version published at the Blue Coat download location."
        ::= { blueCoatAvMibNotifications 6 }

avFirmwareUpdateSuccess NOTIFICATION-TYPE
        OBJECTS { avPreviousFirmwareVersion, avInstalledFirmwareVersion }
        STATUS current
        DESCRIPTION
                "Firmware update completed successfully."
        ::= { blueCoatAvMibNotifications 7 }

avFirmwareUpdateFailed NOTIFICATION-TYPE
        OBJECTS { avInstalledFirmwareVersion, avPublishedFirmwareVersion, avUpdateFailureReason }
        STATUS current
        DESCRIPTION
                "Firmware update failed."
        ::= { blueCoatAvMibNotifications 8 }

avAntivirusLicenseWarning NOTIFICATION-TYPE
        OBJECTS { avVendorName, avLicenseDaysRemaining }
        STATUS current
        DESCRIPTION
                "The antivirus license is about to expire."
        ::= { blueCoatAvMibNotifications 9 }

avICTMWarning NOTIFICATION-TYPE
        OBJECTS { avICTMWarningReason, avSlowICAPConnections }
        STATUS current
        DESCRIPTION
                "The warning from the Intelligent Connection Traffic Monitoring
                feature that the number of 'slow' connections has crossed the
                threshold value."
        ::= { blueCoatAvMibNotifications 10 }
		
avTestAlert NOTIFICATION-TYPE
		OBJECTS { avTestAlertText }
		STATUS current
		DESCRIPTION
				"A test alert."
		::= { blueCoatAvMibNotifications 11 }
		
avLicenseUpdateSuccessful NOTIFICATION-TYPE
        OBJECTS { avVendorName, avLicenseDaysRemaining }
        STATUS current
        DESCRIPTION
                "License update was successful."
        ::= { blueCoatAvMibNotifications 13 }

avLicenseUpdateFailed NOTIFICATION-TYPE
        OBJECTS { avVendorName, avLicenseDaysRemaining, avUpdateFailureReason }
        STATUS current
        DESCRIPTION
                "License update failed."
        ::= { blueCoatAvMibNotifications 14 }

avRebooted NOTIFICATION-TYPE
        STATUS current
        DESCRIPTION
                "AV Rebooted"
        ::= { blueCoatAvMibNotifications 15 }
END
