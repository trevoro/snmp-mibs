Wellfleet-IPACCT-MIB DEFINITIONS ::= BEGIN

-- Created by mdl2asn version 3.1
-- Creation date: Fri Apr 19 17:23:14 EDT 1996


    IMPORTS

      IpAddress, Counter, TimeTicks
        FROM RFC1155-SMI
      OBJECT-TYPE
        FROM RFC-1212
      wfAccountingGroup
        FROM Wellfleet-COMMON-MIB;


    wfIpAcctGroup	OBJECT IDENTIFIER ::= { wfAccountingGroup 1 }

    wfIpAcctBase	OBJECT IDENTIFIER ::= { wfIpAcctGroup 1 }

    wfIpAcctBaseCreate OBJECT-TYPE
        SYNTAX	INTEGER {
    		    created(1),
    		    deleted(2)
    		}
        ACCESS	read-write
        STATUS	mandatory
        DESCRIPTION
                "Create/Delete parameter. Default is created.
                Users perform a set operation on this
                object in order to create/delete IP_ACCT."
        DEFVAL	{ created }
        ::= { wfIpAcctBase 1 }

    wfIpAcctBaseEnable OBJECT-TYPE
        SYNTAX	INTEGER {
    		    enabled(1),
    		    disabled(2)
    		}
        ACCESS	read-write
        STATUS	mandatory
        DESCRIPTION
                "Enable/Disable parameter. Default is enabled.
                Users perform a set operation on this
                object in order to enable/disable IP_ACCT."
        DEFVAL	{ enabled }
        ::= { wfIpAcctBase 2 }

    wfIpAcctBaseThreshold OBJECT-TYPE
        SYNTAX	INTEGER(1..10240)
        ACCESS	read-write
        STATUS	mandatory
        DESCRIPTION
                "The max number of entries in the IP accounting table"
        DEFVAL	{ 512 }
        ::= { wfIpAcctBase 3 }

    wfIpAcctBaseTransitCount OBJECT-TYPE
        SYNTAX	INTEGER(1..10240)
        ACCESS	read-write
        STATUS	mandatory
        DESCRIPTION
                "Number of transit entries to be accounted for that do not
                match the access-list src-dest pairs"
        DEFVAL	{ 512 }
        ::= { wfIpAcctBase 4 }

    wfIpAcctBaseTrapPercent OBJECT-TYPE
        SYNTAX	INTEGER(1..100)
        ACCESS	read-write
        STATUS	mandatory
        DESCRIPTION
                "When this % of table entries are counted a trap is sent to
                the TI console"
        DEFVAL	{ 80 }
        ::= { wfIpAcctBase 5 }

    wfIpAcctAge OBJECT-TYPE
        SYNTAX	TimeTicks
        ACCESS	read-only
        STATUS	mandatory
        DESCRIPTION
                "Number of ticks (seconds) since the 1st entry in the accounting table"
        ::= { wfIpAcctBase 6 }

    wfIpCkAcctFlag OBJECT-TYPE
        SYNTAX	INTEGER
        ACCESS	read-write
        STATUS	mandatory
        DESCRIPTION
                "This is set when user wants to make a snapshot of the active
                table into the checkpoint table"
        ::= { wfIpAcctBase 7 }

    wfIpCkAcctAge OBJECT-TYPE
        SYNTAX	TimeTicks
        ACCESS	read-only
        STATUS	mandatory
        DESCRIPTION
                "Number of clock ticks since the first entry in the
                checkpoint accounting table"
        ::= { wfIpAcctBase 8 }

    wfIpAcctTable OBJECT-TYPE
        SYNTAX	SEQUENCE OF WfIpAcctTableEntry
        ACCESS	not-accessible
        STATUS	mandatory
        DESCRIPTION
                "A list of elements in the IP accounting table"
        ::= { wfIpAcctGroup 2 }

    wfIpAcctTableEntry OBJECT-TYPE
        SYNTAX	WfIpAcctTableEntry
        ACCESS	not-accessible
        STATUS	mandatory
        DESCRIPTION
                "A src-dest based entry in the table"
        INDEX	{ wfIpAcctTableSrcAddr,
    		  wfIpAcctTableDestAddr }
        ::= { wfIpAcctTable 1 }

    WfIpAcctTableEntry ::= SEQUENCE {
    	    wfIpAcctTableSrcAddr
    		IpAddress,
    	    wfIpAcctTableDestAddr
    		IpAddress,
    	    wfIpAcctTablePkts
    		Counter,
    	    wfIpAcctTableBytes
    		Counter
        }

    wfIpAcctTableSrcAddr OBJECT-TYPE
        SYNTAX	IpAddress
        ACCESS	read-only
        STATUS	mandatory
        DESCRIPTION
                "Source IP address of Packet"
        ::= { wfIpAcctTableEntry 1 }

    wfIpAcctTableDestAddr OBJECT-TYPE
        SYNTAX	IpAddress
        ACCESS	read-only
        STATUS	mandatory
        DESCRIPTION
                "Dest IP address of Packet"
        ::= { wfIpAcctTableEntry 2 }

    wfIpAcctTablePkts OBJECT-TYPE
        SYNTAX	Counter
        ACCESS	read-only
        STATUS	mandatory
        DESCRIPTION
                "Number of pkts with this src-dest address pair"
        ::= { wfIpAcctTableEntry 3 }

    wfIpAcctTableBytes OBJECT-TYPE
        SYNTAX	Counter
        ACCESS	read-only
        STATUS	mandatory
        DESCRIPTION
                "Number of bytes with this src-dest address pair"
        ::= { wfIpAcctTableEntry 4 }

    wfIpAcctCctTable OBJECT-TYPE
        SYNTAX	SEQUENCE OF WfIpAcctCctTableEntry
        ACCESS	not-accessible
        STATUS	mandatory
        DESCRIPTION
                "List of interfaces - circuits configured with IP accounting"
        ::= { wfIpAcctGroup 3 }

    wfIpAcctCctTableEntry OBJECT-TYPE
        SYNTAX	WfIpAcctCctTableEntry
        ACCESS	not-accessible
        STATUS	mandatory
        DESCRIPTION
                "An IP accounting circuit definition"
        INDEX	{ wfIpAcctCctNum }
        ::= { wfIpAcctCctTable 1 }

    WfIpAcctCctTableEntry ::= SEQUENCE {
    	    wfIpAcctCctDelete
    		INTEGER,
    	    wfIpAcctCctDisable
    		INTEGER,
    	    wfIpAcctCctNum
    		INTEGER
        }

    wfIpAcctCctDelete OBJECT-TYPE
        SYNTAX	INTEGER {
    		    created(1),
    		    deleted(2)
    		}
        ACCESS	read-write
        STATUS	mandatory
        DESCRIPTION
                "Create/Delete parameter. Default is created.
                Users perform a set operation on this
                object in order to create/delete an IP accounting interface."
        DEFVAL	{ created }
        ::= { wfIpAcctCctTableEntry 1 }

    wfIpAcctCctDisable OBJECT-TYPE
        SYNTAX	INTEGER {
    		    enabled(1),
    		    disabled(2)
    		}
        ACCESS	read-write
        STATUS	mandatory
        DESCRIPTION
                "Enable/Disable parameter. Default is enabled.
                Users perform a set operation on this
                object in order to enable/disable an IP accounting on an interface."
        DEFVAL	{ enabled }
        ::= { wfIpAcctCctTableEntry 2 }

    wfIpAcctCctNum OBJECT-TYPE
        SYNTAX	INTEGER
        ACCESS	read-only
        STATUS	mandatory
        DESCRIPTION
                "The Circuit Number that this interface runs over"
        ::= { wfIpAcctCctTableEntry 3 }

    wfIpCkAcctTable OBJECT-TYPE
        SYNTAX	SEQUENCE OF WfIpCkAcctTableEntry
        ACCESS	not-accessible
        STATUS	mandatory
        DESCRIPTION
                "A list of elements in the IP checkpoint accounting table"
        ::= { wfIpAcctGroup 4 }

    wfIpCkAcctTableEntry OBJECT-TYPE
        SYNTAX	WfIpCkAcctTableEntry
        ACCESS	not-accessible
        STATUS	mandatory
        DESCRIPTION
                "A src-dest based entry in the checkpoint table"
        INDEX	{ wfIpCkAcctTableSrcAddr,
    		  wfIpCkAcctTableDestAddr }
        ::= { wfIpCkAcctTable 1 }

    WfIpCkAcctTableEntry ::= SEQUENCE {
    	    wfIpCkAcctTableSrcAddr
    		IpAddress,
    	    wfIpCkAcctTableDestAddr
    		IpAddress,
    	    wfIpCkAcctTablePkts
    		Counter,
    	    wfIpCkAcctTableBytes
    		Counter
        }

    wfIpCkAcctTableSrcAddr OBJECT-TYPE
        SYNTAX	IpAddress
        ACCESS	read-only
        STATUS	mandatory
        DESCRIPTION
                "Source IP address of Packet in checkpoint table"
        ::= { wfIpCkAcctTableEntry 1 }

    wfIpCkAcctTableDestAddr OBJECT-TYPE
        SYNTAX	IpAddress
        ACCESS	read-only
        STATUS	mandatory
        DESCRIPTION
                "Dest IP address of Packet in checkpoint table"
        ::= { wfIpCkAcctTableEntry 2 }

    wfIpCkAcctTablePkts OBJECT-TYPE
        SYNTAX	Counter
        ACCESS	read-only
        STATUS	mandatory
        DESCRIPTION
                "Number of pkts with this src-dest address pair in checkpoint table"
        ::= { wfIpCkAcctTableEntry 3 }

    wfIpCkAcctTableBytes OBJECT-TYPE
        SYNTAX	Counter
        ACCESS	read-only
        STATUS	mandatory
        DESCRIPTION
                "Number of bytes with this src-dest address pair in checkpoint table"
        ::= { wfIpCkAcctTableEntry 4 }

END  -- Wellfleet-IPACCT-MIB
