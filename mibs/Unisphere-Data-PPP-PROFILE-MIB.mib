-- *****************************************************************************
-- Unisphere-Data-PPP-PROFILE-MIB
--
-- Unisphere Networks Inc. Enterprise MIB
-- PPP Profile MIB
--
-- Copyright (c) 2001, 2002 Unisphere Networks, Inc.  All Rights Reserved.
-- *****************************************************************************

Unisphere-Data-PPP-PROFILE-MIB DEFINITIONS ::= BEGIN

IMPORTS
    MODULE-IDENTITY, OBJECT-TYPE, Integer32, Unsigned32
        FROM SNMPv2-SMI
    MODULE-COMPLIANCE, OBJECT-GROUP
        FROM SNMPv2-CONF
    usDataMibs
        FROM Unisphere-Data-MIBs
    UsdEnable, UsdSetMap, UsdName
        FROM Unisphere-Data-TC
    UsdPppAuthentication
        FROM Unisphere-Data-PPP-MIB;

usdPppProfileMIB  MODULE-IDENTITY
    LAST-UPDATED "200201251400Z"  -- 25-Jan-02 09:00 AM EST
    ORGANIZATION "Unisphere Networks, Inc."
    CONTACT-INFO
        "       Unisphere Networks, Inc.
        Postal: 10 Technology Park Drive
                Westford, MA  01886
                USA
        Tel:    +1 978 589 5800
        Email:  mib@UnisphereNetworks.com"
    DESCRIPTION
        "The Point-to-Point Protocol (PPP) Profile MIB for the Unisphere
        Netowrks enterprise.  This MIB provides configuration parameters that
        extend the tables found in the Unisphere-Data-PROFILE-MIB to support
        profiles for PPP interfaces."
    -- Revision History
    REVISION    "200201251400Z"  -- 25-Jan-02 09:00 AM EST  - RX 4.0
    DESCRIPTION
        "Added usdPppProfileAuthenticatorVirtualRouter."
    REVISION    "200201161758Z"  -- 16-Jan-02 12:58 PM EST  - RX 3.4
    DESCRIPTION
        "Added support for negotiation of the IPCP option netmask."
    REVISION    "200201081943Z"  -- 08-Jan-02 02:43 PM EST  - RX 3.3
    DESCRIPTION
        "Added support for dynamic multilink PPP (MLPPP) interfaces."
    REVISION    "200110021241Z"  -- 02-Oct-01 08:41 AM EDT  - RX 3.0
    DESCRIPTION
        "Initial version of this MIB module."
    ::= { usDataMibs 45 }


-- +++++++++++++++++++++++++++++++++++++++++++++++++++++++++++++++++++++++++++++
-- Managed objects
-- +++++++++++++++++++++++++++++++++++++++++++++++++++++++++++++++++++++++++++++

usdPppProfileObjects     OBJECT IDENTIFIER ::= { usdPppProfileMIB 1 }

usdPppProfile            OBJECT IDENTIFIER ::= { usdPppProfileObjects 1 }

--
-- This MIB defines configuration profile structure for PPP interfaces.
-- The creation/deletion of profiles and mapping of profile names to profile
-- indices is coordinated in the Unisphere-Data-PROFILE-MIB.
--

--
-- The PPP Profile Table
--

usdPppProfileTable OBJECT-TYPE
    SYNTAX      SEQUENCE OF UsdPppProfileEntry
    MAX-ACCESS  not-accessible
    STATUS      current
    DESCRIPTION
        "This table contains profiles for configuring PPP interfaces.

        Entries in this table are created/deleted as a side-effect of
        corresponding operations to the usdProfileNameTable in the
        Unisphere-Data-PROFILE-MIB."
    ::= { usdPppProfile 1 }

usdPppProfileEntry OBJECT-TYPE
    SYNTAX      UsdPppProfileEntry
    MAX-ACCESS  not-accessible
    STATUS      current
    DESCRIPTION
        "A profile describing configuration of a PPP interface."
    INDEX     { usdPppProfileId }
    ::= { usdPppProfileTable 1 }

UsdPppProfileEntry ::= SEQUENCE {
    usdPppProfileId                         Unsigned32,
    usdPppProfileSetMap                     UsdSetMap,
    usdPppProfileLcpMagicNumber             INTEGER,
    usdPppProfileLcpKeepalive               Integer32,
    usdPppProfileLcpAuthentication          UsdPppAuthentication,
    usdPppProfileIpPeerDnsPriority          UsdEnable,
    usdPppProfileIpPeerWinsPriority         UsdEnable,
    usdPppProfileLcpInitialMRU              INTEGER,
    usdPppProfilePacketLog                  UsdEnable,
    usdPppProfileStateLog                   UsdEnable,
    usdPppProfileChapMinChallengeLength     INTEGER,
    usdPppProfileChapMaxChallengeLength     INTEGER,
    usdPppProfilePassiveMode                UsdEnable,
    usdPppProfileMlppp                      UsdEnable,
    usdPppProfileIpcpNetmask                UsdEnable,
    usdPppProfileAuthenticatorVirtualRouter UsdName }

usdPppProfileId OBJECT-TYPE
    SYNTAX      Unsigned32
    MAX-ACCESS  not-accessible
    STATUS      current
    DESCRIPTION
        "The integer identifier associated with this profile.  A value for this
        identifier is determined by locating or creating a profile name in the
        Unisphere-Data-PROFILE-MIB.usdProfileNameTable."
    ::= { usdPppProfileEntry 1 }

usdPppProfileSetMap OBJECT-TYPE
    SYNTAX      UsdSetMap
    MAX-ACCESS  read-write
    STATUS      current
    DESCRIPTION
        "A bitmap representing which objects in this entry have been explicitly
        configured.  See the definition of the UsdSetMap TEXTUAL-CONVENTION for
        details of use.

        The INDEX object(s) and this object are excluded from representation
        (i.e. their bits are never set).

        When a SET request does not explicitly configure UsdSetMap, bits in
        UsdSetMap are set as a side-effect of configuring other profile
        attributes in the same entry.

        If, however, a SET request explicitly configures UsdSetMap, the
        explicitly configured value overrides 1) any previous bit settings, and
        2) any simultaneous 'side-effect' settings that would otherwise occur.

        Once set, bits can only be cleared by explicitly configuring UsdSetMap."
    ::= { usdPppProfileEntry 2 }

usdPppProfileLcpMagicNumber   OBJECT-TYPE
    SYNTAX      INTEGER {
                    false(1),
                    true(2) }
    MAX-ACCESS  read-write
    STATUS      current
    DESCRIPTION
        "If true(2) then the local node will attempt to perform Magic Number
        negotiation with the remote node.  If false(1) then this negotiation is
        not performed.  In any event, the local node will comply with any magic
        number negotiations attempted by the remote node, per the PPP
        specification."
    DEFVAL    { false }
    ::= { usdPppProfileEntry 3 }

usdPppProfileLcpKeepalive OBJECT-TYPE
    SYNTAX      Integer32 (0|30..300)
    UNITS       "seconds"
    MAX-ACCESS  read-write
    STATUS      current
    DESCRIPTION
        "Keepalive interval in seconds.  A value of zero disables keepalive.
        Keepalive is performed using LCP Echo."
    DEFVAL    { 30 }
    ::= { usdPppProfileEntry 4 }

usdPppProfileLcpAuthentication OBJECT-TYPE
    SYNTAX      UsdPppAuthentication
    MAX-ACCESS  read-write
    STATUS      current
    DESCRIPTION
        "Specifies the type(s) of authentication, if any, to be negotiated with
        the peer:
          none      No authentication is negotiated.
          pap       PAP negotiation only.
          chap      CHAP negotiation only.
          papChap   PAP negotiation is attempted first; if fails, attempt CHAP.
          chapPap   CHAP negotiation is attempted first; if fails, attempt PAP.

        Setting this object to none will set  
        usdPppProfileAuthenticatorVirtualRouter object to an empty string."
    DEFVAL    { none }
    ::= { usdPppProfileEntry 5 }

usdPppProfileIpPeerDnsPriority OBJECT-TYPE
    SYNTAX      UsdEnable
    MAX-ACCESS  read-write
    STATUS      current
    DESCRIPTION
        "When enabled, allows peer's DNS address to prevail in the event of a
        negotiation conflict; when disabled, the local PPP interface's DNS
        address prevails."
    DEFVAL    { disable }
    ::= { usdPppProfileEntry 6 }

usdPppProfileIpPeerWinsPriority OBJECT-TYPE
    SYNTAX      UsdEnable
    MAX-ACCESS  read-write
    STATUS      current
    DESCRIPTION
        "When enabled, allows peer's WINS address to prevail in the event of a
        negotiation conflict; when disabled, the local PPP interface's WINS
        address prevails."
    DEFVAL    { disable }
    ::= { usdPppProfileEntry 7 }

usdPppProfileLcpInitialMRU OBJECT-TYPE
    SYNTAX      INTEGER (1|64..65535)
    MAX-ACCESS  read-write
    STATUS      current
    DESCRIPTION
        "The initial Maximum Receive Unit (MRU) that the local PPP entity will
        advertise to the remote entity.

        If the value of this variable is 1 then the local PPP entity will
        advertise an MRU value determined by its underlying media interface."
    DEFVAL    { 1 }
    ::= { usdPppProfileEntry 8 }

usdPppProfilePacketLog OBJECT-TYPE
    SYNTAX      UsdEnable
    MAX-ACCESS  read-write
    STATUS      current
    DESCRIPTION
        "When enabled, allows packet logging on dynamic PPP interfaces."
    DEFVAL    { disable }
    ::= { usdPppProfileEntry 9 }

usdPppProfileStateLog OBJECT-TYPE
    SYNTAX      UsdEnable
    MAX-ACCESS  read-write
    STATUS      current
    DESCRIPTION
        "When enabled, allows state machine logging on dynamic PPP interfaces."
    DEFVAL    { disable }
    ::= { usdPppProfileEntry 10 }

usdPppProfileChapMinChallengeLength OBJECT-TYPE
    SYNTAX      INTEGER (8..63)
    MAX-ACCESS  read-write
    STATUS      current
    DESCRIPTION
        "Minimum value of the CHAP authenticator challenge length value.  This
        value is never allowed to be set to a value greater than
        usdPppProfileChapMaxChallengeLength."
    DEFVAL    { 16 }
    ::= { usdPppProfileEntry 11 }

usdPppProfileChapMaxChallengeLength OBJECT-TYPE
    SYNTAX      INTEGER (8..63)
    MAX-ACCESS  read-write
    STATUS      current
    DESCRIPTION
        "Maximum value of the CHAP authenticator challenge length value. This
        value is never allowed to be set to a value less than
        usdPppLinkConfigChapMinChallengeLength."
    DEFVAL    { 32 }
    ::= { usdPppProfileEntry 12 }

usdPppProfilePassiveMode OBJECT-TYPE
    SYNTAX      UsdEnable
    MAX-ACCESS  read-write
    STATUS      current
    DESCRIPTION
        "When enabled, LCP state machine is forced into passive mode on lower
        layer UP message.  It adds compatibility with slow and buggy clients."
    DEFVAL    { disable }
    ::= { usdPppProfileEntry 13 }

usdPppProfileMlppp OBJECT-TYPE
    SYNTAX      UsdEnable
    MAX-ACCESS  read-write
    STATUS      current
    DESCRIPTION
        "Enables the creation of dynamic multi-link PPP interfaces."
    DEFVAL    { disable }
    ::= { usdPppProfileEntry 14 }

usdPppProfileIpcpNetmask OBJECT-TYPE
    SYNTAX      UsdEnable
    MAX-ACCESS  read-write
    STATUS      current
    DESCRIPTION
        "Enables the negotiation of the IPCP option netmask (0x90) during IPCP
        negotiation."
    DEFVAL { disable }
    ::= { usdPppProfileEntry 15 }

usdPppProfileAuthenticatorVirtualRouter OBJECT-TYPE
    SYNTAX      UsdName
    MAX-ACCESS  read-write
    STATUS      current
    DESCRIPTION
        "The name of the virtual router (Unisphere-Data-ROUTER-MIB.usdRouterName)
        to be used for authentication on the PPP interface.  Setting this object
        statically binds the authenticating virtual router with the PPP interface.  
        If this object is not explicitly set or it is set to null string, then 
        this object is ignored and the virtual router used for authentication is 
        determined by other means.  On a Set operation, if the value of this object
        is not null and does not correspond to an existing virtual router, then 
        an inconsistentValue error is returned.

        Setting this object to non null string returns inconsistentValue value error 
        if usdPppProfileConfigAuthentication object is none or not configured."
    ::= { usdPppProfileEntry 16 }


-- +++++++++++++++++++++++++++++++++++++++++++++++++++++++++++++++++++++++++++++
-- Notifications
-- +++++++++++++++++++++++++++++++++++++++++++++++++++++++++++++++++++++++++++++

-- No notifications are defined in this MIB.


-- +++++++++++++++++++++++++++++++++++++++++++++++++++++++++++++++++++++++++++++
-- Conformance information
-- +++++++++++++++++++++++++++++++++++++++++++++++++++++++++++++++++++++++++++++

usdPppProfileConformance OBJECT IDENTIFIER ::= { usdPppProfileMIB 4 }
usdPppProfileCompliances OBJECT IDENTIFIER ::= { usdPppProfileConformance 1 }
usdPppProfileGroups      OBJECT IDENTIFIER ::= { usdPppProfileConformance 2 }

-- compliance statements

usdPppProfileCompliance MODULE-COMPLIANCE
    STATUS      obsolete
    DESCRIPTION
        "Obsolete compliance statement for entities which implement the
        Unisphere PPP Profile MIB.  This statement became obsolete when support
        was added for multi-link PPP interfaces."
    MODULE   -- this module
        MANDATORY-GROUPS {
            usdPppProfileGroup }
    ::= { usdPppProfileCompliances 1 }                                 -- RX 3.0

usdPppProfileCompliance2 MODULE-COMPLIANCE
    STATUS      obsolete
    DESCRIPTION
        "Obsolete compliance statement for entities which implement the
        Unisphere PPP Profile MIB.  This statement became obsolete when support
        was added for negotiation of IPCP option netmask."
    MODULE   -- this module
        MANDATORY-GROUPS {
            usdPppProfileGroup2 }
    ::= { usdPppProfileCompliances 2 }                                 -- RX 3.3

usdPppProfileCompliance3 MODULE-COMPLIANCE
    STATUS      obsolete
    DESCRIPTION
        "Obsolete compliance statement for entities which implement the
        Unisphere PPP Profile MIB.  This statement became obsolete when the
        usdPppProfileAuthenticatorVirtualRouter object was added."
    MODULE   -- this module
        MANDATORY-GROUPS {
            usdPppProfileGroup3 }
    ::= { usdPppProfileCompliances 3 }                                 -- RX 3.4

usdPppProfileCompliance4 MODULE-COMPLIANCE
    STATUS      current
    DESCRIPTION
        "The compliance statement for entities which implement the Unisphere PPP
        Profile MIB."
    MODULE   -- this module
        MANDATORY-GROUPS {
            usdPppProfileGroup4 }
    ::= { usdPppProfileCompliances 4 }                                 -- RX 4.0


-- units of conformance

usdPppProfileGroup OBJECT-GROUP
    OBJECTS {
        usdPppProfileSetMap,
        usdPppProfileLcpMagicNumber,
        usdPppProfileLcpKeepalive,
        usdPppProfileLcpAuthentication,
        usdPppProfileIpPeerDnsPriority,
        usdPppProfileIpPeerWinsPriority,
        usdPppProfileLcpInitialMRU,
        usdPppProfilePacketLog,
        usdPppProfileStateLog,
        usdPppProfileChapMinChallengeLength,
        usdPppProfileChapMaxChallengeLength,
        usdPppProfilePassiveMode }
    STATUS      obsolete
    DESCRIPTION
        "Obsolete collection of objects providing management of profile
        functionality for PPP interfaces in a Unisphere product.  This group
        became obsolete when support was added for MLPPP."
    ::= { usdPppProfileGroups 1 }

usdPppProfileGroup2 OBJECT-GROUP
    OBJECTS {
        usdPppProfileSetMap,
        usdPppProfileLcpMagicNumber,
        usdPppProfileLcpKeepalive,
        usdPppProfileLcpAuthentication,
        usdPppProfileIpPeerDnsPriority,
        usdPppProfileIpPeerWinsPriority,
        usdPppProfileLcpInitialMRU,
        usdPppProfilePacketLog,
        usdPppProfileStateLog,
        usdPppProfileChapMinChallengeLength,
        usdPppProfileChapMaxChallengeLength,
        usdPppProfilePassiveMode,
        usdPppProfileMlppp }
    STATUS      obsolete
    DESCRIPTION
        "Obsolete collection of objects providing management of profile
        functionality for PPP interfaces in a Unisphere product.  This group
        became obsolete when support was added for negotiation of IPCP option
        netmask."
    ::= { usdPppProfileGroups 2 }

usdPppProfileGroup3 OBJECT-GROUP
    OBJECTS {
        usdPppProfileSetMap,
        usdPppProfileLcpMagicNumber,
        usdPppProfileLcpKeepalive,
        usdPppProfileLcpAuthentication,
        usdPppProfileIpPeerDnsPriority,
        usdPppProfileIpPeerWinsPriority,
        usdPppProfileLcpInitialMRU,
        usdPppProfilePacketLog,
        usdPppProfileStateLog,
        usdPppProfileChapMinChallengeLength,
        usdPppProfileChapMaxChallengeLength,
        usdPppProfilePassiveMode,
        usdPppProfileMlppp,
        usdPppProfileIpcpNetmask }
    STATUS      obsolete
    DESCRIPTION
        "Obsolete collection of objects providing management of profile
        functionality for PPP interfaces in a Unisphere product.  This group
        became obsolete when the usdPppProfileAuthenticatorVirtualRouter object
        was added."
    ::= { usdPppProfileGroups 3 }

usdPppProfileGroup4 OBJECT-GROUP
    OBJECTS {
        usdPppProfileSetMap,
        usdPppProfileLcpMagicNumber,
        usdPppProfileLcpKeepalive,
        usdPppProfileLcpAuthentication,
        usdPppProfileIpPeerDnsPriority,
        usdPppProfileIpPeerWinsPriority,
        usdPppProfileLcpInitialMRU,
        usdPppProfilePacketLog,
        usdPppProfileStateLog,
        usdPppProfileChapMinChallengeLength,
        usdPppProfileChapMaxChallengeLength,
        usdPppProfilePassiveMode,
        usdPppProfileMlppp,
        usdPppProfileIpcpNetmask,
        usdPppProfileAuthenticatorVirtualRouter }
    STATUS      current
    DESCRIPTION
        "A collection of objects providing management of profile functionality
        for PPP interfaces in a Unisphere product."
    ::= { usdPppProfileGroups 4 }

END
