SCA-MPLINK2-MIB DEFINITIONS ::= BEGIN

-- Copyright (C) 1997 Intel Corporation. All rights reserved.
--
-- MP Link 2 MIB, $Date: 1997/07/04 13:46:15 $
--
-- Defines objects for proprietary multi protocol links.
--
-- Change History:

IMPORTS
    TimeTicks, Counter                             FROM RFC1155-SMI
    DisplayString                       FROM RFC1213-MIB
    scanet                              FROM SCANET-MIB
    OBJECT-TYPE                         FROM RFC-1212
	 TRAP-TYPE FROM RFC-1215;


OnOff ::= INTEGER { on(1), off(2) }
Attachment ::= INTEGER { none(1), tenbase-t(2), aui(3),
    id0(4), id1(5), id2(6), id3(7),
    eia530-dce(8), test-plug(9),
    v11-dce(10), v24-dce(11), v35-dce(12), v36-dce(13),
    eia530-dte(14),
    v11-dte(15), v24-dte(16), v35-dte(17), v36-dte(18),
    empty(19), isdn(20), pcmcia-async(21),
    isdn-e1-rj45(22), isdn-e1-bnc(23), isdn-t1-rj45(24) }
CompType ::= INTEGER { proprietary(1), stac(2) }
Direction ::= INTEGER { unknown(1), incoming(2), outgoing(3) }
DataState ::= INTEGER { down(1), timeCut(2), up(3) }
ConnectState ::= INTEGER { create(1), down(2), outgoingCall(3),
    incomingCall(4), incomingDisconnect(5), outgoingDisconnect(6),
    waitDisconnectConfirm(7), error(8), destroy(9), timeCut(10), idle(11),
    up(12), empty(13) }



mplk2                OBJECT IDENTIFIER ::= { scanet 44 }
  mpl2Service        OBJECT IDENTIFIER ::= { mplk2 1 }
  mpl2LanSpecific    OBJECT IDENTIFIER ::= { mplk2 2 }
  mpl2WanSpecific    OBJECT IDENTIFIER ::= { mplk2 3 }
  mpl2IfSpecific     OBJECT IDENTIFIER ::= { mplk2 4 }
  mpl2General        OBJECT IDENTIFIER ::= { mplk2 5 }




mpl2ServiceTable OBJECT-TYPE
    SYNTAX SEQUENCE OF Mpl2ServiceEntry
    ACCESS not-accessible
    STATUS mandatory
    DESCRIPTION
        "This table contains information on MP Links.
        These entries applies to LAN entries as well as
        WAN entries."
    ::= { mpl2Service 1 }

mpl2ServiceEntry OBJECT-TYPE
    SYNTAX Mpl2ServiceEntry
    ACCESS not-accessible
    STATUS mandatory
    DESCRIPTION
        "Information on a particular MP Link."
    INDEX { mpl2ServiceNumber }
    ::= { mpl2ServiceTable 1 }

Mpl2ServiceEntry ::=
    SEQUENCE {
        mpl2ServiceNumber
            INTEGER,
        mpl2ServiceSlotNumber
            INTEGER,
        mpl2ServicePlugNumber
            INTEGER,
        mpl2ServicePlugName
            DisplayString,
        mpl2ServiceAttachment
            Attachment,
        mpl2ServiceProvider
            INTEGER,
        mpl2ServiceBytesSentUpper
            Counter,
        mpl2ServiceBytesSentLower
            Counter,
        mpl2ServiceBytesReceivedUpper
            Counter,
        mpl2ServiceBytesReceivedLower
            Counter,
        mpl2ServiceLock
            OnOff
    }


mpl2ServiceNumber OBJECT-TYPE
    SYNTAX INTEGER
    ACCESS read-only
    STATUS mandatory
    DESCRIPTION
        "The MP Link number. The MP Link number is the
        same as the ifIndex for the corresponding
        upper group in the MIB-2 ifGroup."
    ::= { mpl2ServiceEntry 1 }

mpl2ServiceSlotNumber OBJECT-TYPE
    SYNTAX INTEGER
    ACCESS read-only
    STATUS mandatory
    DESCRIPTION
        "The Slot position of the card. Set to 0 for
        stand-alone products."
    ::= { mpl2ServiceEntry 2 }

mpl2ServicePlugNumber OBJECT-TYPE
    SYNTAX INTEGER
    ACCESS read-only
    STATUS mandatory
    DESCRIPTION
        "The plug number of the physical interface to
        which the MP Link is associated."
    ::= { mpl2ServiceEntry 3 }

mpl2ServicePlugName OBJECT-TYPE
    SYNTAX DisplayString (SIZE (1..30))
    ACCESS read-only
    STATUS mandatory
    DESCRIPTION
        "The name of the physical interface to which
        the MP Link is associated."
    ::= { mpl2ServiceEntry 4 }

mpl2ServiceAttachment OBJECT-TYPE
    SYNTAX Attachment
    ACCESS read-only
    STATUS mandatory
    DESCRIPTION
        "The connector type used to connect the router
        to the LAN or WAN."
    ::= { mpl2ServiceEntry 5 }

mpl2ServiceProvider OBJECT-TYPE
    SYNTAX INTEGER { lan(1), lapbHdlc(2), pppHdlc(3), frHdlc(4),
                     frAttachment(5), lapbIsdn(6), pppIsdn(7),
                     isdnAttachment(8), x25Lapb(9), x25Attachment(10),
                     slip(11), pppMultiMaster(12), pppPcmciaModem(16) }
    ACCESS read-only
    STATUS mandatory
    DESCRIPTION
        "The type of provider for this MP Link. For WAN
        links this specifies the actual protocol
        stack."
    ::= { mpl2ServiceEntry 6 }

mpl2ServiceBytesSentUpper OBJECT-TYPE
    SYNTAX Counter
    ACCESS read-only
    STATUS mandatory
    DESCRIPTION
        "The upper 32 bits of the 64 bits counter which
        is the number of octets (bytes) sent via the MP
        Link."
    ::= { mpl2ServiceEntry 7 }

mpl2ServiceBytesSentLower OBJECT-TYPE
    SYNTAX Counter
    ACCESS read-only
    STATUS mandatory
    DESCRIPTION
        "The lower 32 bits of the 64 bits counter which
        is the number of octets (bytes) sent via the MP
        Link."
    ::= { mpl2ServiceEntry 8 }

mpl2ServiceBytesReceivedUpper OBJECT-TYPE
    SYNTAX Counter
    ACCESS read-only
    STATUS mandatory
    DESCRIPTION
        "The lower 32 bits of the 64 bits counter which
        is the number of octets (bytes) sent via the MP
        Link."
    ::= { mpl2ServiceEntry 9 }

mpl2ServiceBytesReceivedLower OBJECT-TYPE
    SYNTAX Counter
    ACCESS read-only
    STATUS mandatory
    DESCRIPTION
        "The lower 32 bits of the 64 bits counter which
        is the number of octets (bytes) received via
        the MP Link."
    ::= { mpl2ServiceEntry 10 }

mpl2ServiceLock OBJECT-TYPE
    SYNTAX OnOff
    ACCESS read-write
    STATUS mandatory
    DESCRIPTION
        "Indicates whether an MP Link has been locked
        from local management. The link may be unlocked
        by setting the value to 'off' and locked by
        setting the value to 'on'."
    ::= { mpl2ServiceEntry 11 }


mpl2LanTable OBJECT-TYPE
    SYNTAX SEQUENCE OF Mpl2LanEntry
    ACCESS not-accessible
    STATUS mandatory
    DESCRIPTION
        "This table contains information on LAN MP
        Links."
    ::= { mpl2LanSpecific 1 }

mpl2LanEntry OBJECT-TYPE
    SYNTAX Mpl2LanEntry
    ACCESS not-accessible
    STATUS mandatory
    DESCRIPTION
        "Information on a particular LAN MP Link."
    INDEX { mpl2LanNumber }
    ::= { mpl2LanTable 1 }

Mpl2LanEntry ::=
    SEQUENCE {
        mpl2LanNumber
            INTEGER,
        mpl2LanRxCRCErrors
            Counter,
        mpl2LanRxOverrun
            Counter,
        mpl2LanRxLong
            Counter,
        mpl2LanRxOverflow
            Counter,
        mpl2LanRxAlnErrors
            Counter,
        mpl2LanRxOuts
            Counter,
        mpl2LanRxShort
            Counter,
        mpl2LanTxDeferred
            Counter,
        mpl2LanTxUnderrun
            Counter,
        mpl2LanTxSQEFailure
            Counter,
        mpl2LanTxExcDeferral
            Counter,
        mpl2LanTxCollExceed
            Counter,
        mpl2LanTxLateColl
            Counter,
        mpl2LanTxCollisions
            Counter,
        mpl2LanTxNoCarrier
            Counter
    }

mpl2LanNumber OBJECT-TYPE
    SYNTAX INTEGER
    ACCESS read-only
    STATUS mandatory
    DESCRIPTION
        "The LAN MP Link number. The MP Link number is
        the same as the ifIndex for the corresponding
        upper group in the MIB-2 ifGroup."
    ::= { mpl2LanEntry 1 }

mpl2LanRxCRCErrors OBJECT-TYPE
    SYNTAX Counter
    ACCESS read-only
    STATUS mandatory
    DESCRIPTION
        "The number of frames received which were
        discarded due to Cyclic Redundancy Check (CRC)
        errors."
    ::= { mpl2LanEntry 2 }

mpl2LanRxOverrun OBJECT-TYPE
    SYNTAX Counter
    ACCESS read-only
    STATUS mandatory
    DESCRIPTION
        "The number of frames received which were lost
        due to RAM overloads within the router. This
        should not occur."
    ::= { mpl2LanEntry 3 }

mpl2LanRxLong OBJECT-TYPE
    SYNTAX Counter
    ACCESS read-only
    STATUS mandatory
    DESCRIPTION
        "The number of frames received which were
        discarded due to being larger than the maximum
        allowable length on the LAN."
    ::= { mpl2LanEntry 4 }

mpl2LanRxOverflow OBJECT-TYPE
    SYNTAX Counter
    ACCESS read-only
    STATUS mandatory
    DESCRIPTION
        "The number of frames received which were
        discarded due to lack of buffer capacity."
    ::= { mpl2LanEntry 5 }

mpl2LanRxAlnErrors OBJECT-TYPE
    SYNTAX Counter
    ACCESS read-only
    STATUS mandatory
    DESCRIPTION
        "The number of frames received which were
        discarded due to having the wrong frame
        length."
    ::= { mpl2LanEntry 6 }

mpl2LanRxOuts OBJECT-TYPE
    SYNTAX Counter
    ACCESS read-only
    STATUS mandatory
    DESCRIPTION
        "The number of frames received which were
        processed by higher layer protocols."
    ::= { mpl2LanEntry 7 }

mpl2LanRxShort OBJECT-TYPE
    SYNTAX Counter
    ACCESS read-only
    STATUS mandatory
    DESCRIPTION
        "The number of frames received which were
        discarded due to being shorter than the smallest
        allowable length on the LAN."
    ::= { mpl2LanEntry 8 }

mpl2LanTxDeferred OBJECT-TYPE
    SYNTAX Counter
    ACCESS read-only
    STATUS mandatory
    DESCRIPTION
        "The number of outgoing frames which were
        discarded due to a busy link."
    ::= { mpl2LanEntry 9 }

mpl2LanTxUnderrun OBJECT-TYPE
    SYNTAX Counter
    ACCESS read-only
    STATUS mandatory
    DESCRIPTION
        "The number of outgoing frames which were
        discarded due to overload."
    ::= { mpl2LanEntry 10 }

mpl2LanTxSQEFailure OBJECT-TYPE
    SYNTAX Counter
    ACCESS read-only
    STATUS mandatory
    DESCRIPTION
        "The number of outbound frames which had
        Signal Quality Errors (SQE)."
    ::= { mpl2LanEntry 11 }

mpl2LanTxExcDeferral OBJECT-TYPE
    SYNTAX Counter
    ACCESS read-only
    STATUS mandatory
    DESCRIPTION
        "The number of transmission attempts which were delayed
        for more than 3.2 ms."
    ::= { mpl2LanEntry 12 }

mpl2LanTxCollExceed OBJECT-TYPE
    SYNTAX Counter
    ACCESS read-only
    STATUS mandatory
    DESCRIPTION
        "The number of outbound frames which were
        discarded due to exceeding 16 collisions on the
        Ethernet."
    ::= { mpl2LanEntry 13 }

mpl2LanTxLateColl OBJECT-TYPE
    SYNTAX Counter
    ACCESS read-only
    STATUS mandatory
    DESCRIPTION
        "The number of collisions occurring after the
        first 512 bytes of a frame had been
        transmitted."
    ::= { mpl2LanEntry 14 }

mpl2LanTxCollisions OBJECT-TYPE
    SYNTAX Counter
    ACCESS read-only
    STATUS mandatory
    DESCRIPTION
        "The number of outgoing frames which were
        discarded due to collisions that occurred
        during transmissions."
    ::= { mpl2LanEntry 15 }

mpl2LanTxNoCarrier OBJECT-TYPE
    SYNTAX Counter
    ACCESS read-only
    STATUS mandatory
    DESCRIPTION
        "The number of No Carrier detections during
        transmissions."
    ::= { mpl2LanEntry 16 }


mpl2WanTable OBJECT-TYPE
    SYNTAX SEQUENCE OF Mpl2WanEntry
    ACCESS not-accessible
    STATUS mandatory
    DESCRIPTION
        "This table contains information on WAN MP
        Links."
    ::= { mpl2WanSpecific 1 }

mpl2WanEntry OBJECT-TYPE
    SYNTAX Mpl2WanEntry
    ACCESS not-accessible
    STATUS mandatory
    DESCRIPTION
        "Information on a particular WAN MP Link."
    INDEX { mpl2WanNumber }
    ::= { mpl2WanTable 1 }

Mpl2WanEntry ::=
    SEQUENCE {
        mpl2WanNumber
            INTEGER,
        mpl2WanDataState
            DataState,
        mpl2WanDataStateTimer
            INTEGER,
        mpl2WanConnectState
            ConnectState,
        mpl2WanConnectStateTimer
            INTEGER,
        mpl2WanCompression
            OnOff,
        mpl2WanCompressionType
            CompType,
        mpl2WanCallsSucceeded
            Counter,
        mpl2WanCallsFailed
            Counter,
        mpl2WanCallsAccepted
            Counter,
        mpl2WanCallsRejected
            Counter,
        mpl2WanRetries
            Counter,
        mpl2WanDirection
            Direction,
        mpl2WanHasBackup
            OnOff,
        mpl2WanBackupFor
            INTEGER,
        mpl2WanBackupForAttachment
             OnOff,
        mpl2WanIsSlave
            OnOff,
        mpl2WanPppMaster
            INTEGER,
        mpl2WanPppSlaveUpCount
            INTEGER,
        mpl2WanActivityTimeLeft
            INTEGER,
        mpl2WanActivity
            OnOff,
        mpl2WanTimer
            OnOff
    }

mpl2WanNumber OBJECT-TYPE
    SYNTAX INTEGER
    ACCESS read-only
    STATUS mandatory
    DESCRIPTION
        "The WAN MP Link number. The MP Link number is
        the same as the ifIndex for the corresponding
        upper group in the MIB-2 ifGroup."
    ::= { mpl2WanEntry 1 }

mpl2WanDataState OBJECT-TYPE
    SYNTAX DataState
    ACCESS read-only
    STATUS mandatory
    DESCRIPTION
        "The state of the MP Link seen from the higher
        layer protocol."
    ::= { mpl2WanEntry 2 }

mpl2WanDataStateTimer OBJECT-TYPE
    SYNTAX INTEGER
    ACCESS read-only
    STATUS mandatory
    DESCRIPTION
        "The time in seconds since the MP Link entered
        the Data State."
    ::= { mpl2WanEntry 3 }

mpl2WanConnectState OBJECT-TYPE
    SYNTAX ConnectState
    ACCESS read-only
    STATUS mandatory
    DESCRIPTION
        "Indicates the connection state of the WAN MP
        Link."
    ::= { mpl2WanEntry 4 }

mpl2WanConnectStateTimer OBJECT-TYPE
    SYNTAX INTEGER
    ACCESS read-only
    STATUS mandatory
    DESCRIPTION
        "The time in seconds since the MP Link entered
        the Connect State."
    ::= { mpl2WanEntry 5 }

mpl2WanCompression OBJECT-TYPE
    SYNTAX OnOff
    ACCESS read-only
    STATUS mandatory
    DESCRIPTION
        "Indicates if data compression is used over the
        WAN MP Link. For frame relay links compression
        is not negotiated. For all other WAN protocols
        the compression will remain 'off' if not
        configured in both routers over the link."
    ::= { mpl2WanEntry 6 }

mpl2WanCompressionType OBJECT-TYPE
    SYNTAX CompType
    ACCESS read-only
    STATUS mandatory
    DESCRIPTION
        "Proprietary compression is used for LAPB and
        X.25 MP Links. For all other WAN protocols the
        Stac compression algorithm is used."
    ::= { mpl2WanEntry 7 }

mpl2WanCallsSucceeded OBJECT-TYPE
    SYNTAX Counter
    ACCESS read-only
    STATUS mandatory
    DESCRIPTION
        "The number of outgoing call which succeeded in
        making the connection."
    ::= { mpl2WanEntry 8 }

mpl2WanCallsFailed OBJECT-TYPE
    SYNTAX Counter
    ACCESS read-only
    STATUS mandatory
    DESCRIPTION
        "The number of outgoing call which failed to
        make the connection."
    ::= { mpl2WanEntry 9 }

mpl2WanCallsAccepted OBJECT-TYPE
    SYNTAX Counter
    ACCESS read-only
    STATUS mandatory
    DESCRIPTION
        "The number of incoming calls which were
        accepted on this link."
    ::= { mpl2WanEntry 10 }

mpl2WanCallsRejected OBJECT-TYPE
    SYNTAX Counter
    ACCESS read-only
    STATUS mandatory
    DESCRIPTION
        "The number of incoming calls which were
        rejected on this link."
    ::= { mpl2WanEntry 11 }

mpl2WanRetries OBJECT-TYPE
    SYNTAX INTEGER
    ACCESS read-write
    STATUS mandatory
    DESCRIPTION
        "The number of retries made for outgoing
        calls. May be set to zero which causes the
        call sequence to restarted."
    ::= { mpl2WanEntry 12 }

mpl2WanDirection OBJECT-TYPE
    SYNTAX Direction
    ACCESS read-only
    STATUS mandatory
    DESCRIPTION
        "Shows who initiated the call. 'incoming' if the
        call was initiated by the remote router and
        'outgoing' if the call was inititated by this
        router. For PPP Multi Links the direction
        refers the the direction of the first slave
        link."
    ::= { mpl2WanEntry 13 }

mpl2WanHasBackup OBJECT-TYPE
    SYNTAX OnOff
    ACCESS read-only
    STATUS mandatory
    DESCRIPTION
        "Indicates whether this link has a backup link
        configured for it."
    ::= { mpl2WanEntry 14 }

mpl2WanBackupFor OBJECT-TYPE
    SYNTAX INTEGER
    ACCESS read-only
    STATUS mandatory
    DESCRIPTION
        "Shows the primary link for which this link is
        the backup. The value 0 indicates that this is
        not a backup link."
    ::= { mpl2WanEntry 15 }

mpl2WanBackupForAttachment OBJECT-TYPE
    SYNTAX OnOff
    ACCESS read-only
    STATUS mandatory
    DESCRIPTION
        "Indicates whether this link is a backup for an
        attachment."
    ::= { mpl2WanEntry 16 }

mpl2WanIsSlave OBJECT-TYPE
    SYNTAX OnOff
    ACCESS read-only
    STATUS mandatory
    DESCRIPTION
        "Indicates whether this link is a slave link
        associated with a PPP Multi Link."
    ::= { mpl2WanEntry 17 }

mpl2WanPppMaster OBJECT-TYPE
    SYNTAX INTEGER
    ACCESS read-only
    STATUS mandatory
    DESCRIPTION
        "Indicates the master link for a slave link.
        For master links and links not associated with
        a PPP Multi Link the value is 0."
    ::= { mpl2WanEntry 18 }

mpl2WanPppSlaveUpCount OBJECT-TYPE
    SYNTAX INTEGER
    ACCESS read-only
    STATUS mandatory
    DESCRIPTION
        "The number of slave links in Connect State
        'up'. For slave links and links not associated
        with a PPP Multi Link the value is 1."
    ::= { mpl2WanEntry 19 }

mpl2WanActivityTimeLeft OBJECT-TYPE
    SYNTAX INTEGER
    ACCESS read-only
    STATUS mandatory
    DESCRIPTION
        "The time remaining in seconds until the Daily
        Activity Limit will close and lock the link.
        When the Daily Activity Limit has been reached,
        the link can be activated by setting
        mpl2WanActivity to 'on'."
    ::= { mpl2WanEntry 20 }

mpl2WanActivity OBJECT-TYPE
    SYNTAX OnOff
    ACCESS read-write
    STATUS mandatory
    DESCRIPTION
        "Indicates whether the Daily Activity Limit has
        been reached and locked the link. To unlock the
        link set the value to 'off'. It is not possible
        to set to the value to 'on'."
    ::= { mpl2WanEntry 21 }

mpl2WanTimer OBJECT-TYPE
    SYNTAX OnOff
    ACCESS read-only
    STATUS mandatory
    DESCRIPTION
        "Indicates whether an MP Link timer has locked
        the link. 'on' means the link is locked."
    ::= { mpl2WanEntry 22 }


mpl2IfStackTable  OBJECT-TYPE
    SYNTAX SEQUENCE OF Mpl2IfStackEntry
    ACCESS not-accessible
    STATUS mandatory
    DESCRIPTION
        "This table contains information on the relationships
        between the multiple sub-layers of network interfaces.
        In particular, it contains information on which sub-
        layers run 'on top of' which other sub-layers.  Each
        sub-layer corresponds to a conceptual row in the
        ifTable."
    ::= { mpl2IfSpecific 1 }


mpl2IfStackEntry  OBJECT-TYPE
    SYNTAX Mpl2IfStackEntry
    ACCESS not-accessible
    STATUS mandatory
    DESCRIPTION
        "Information on a particular relationship between two
        sub-layers, specifying that one sub-layer runs on
        'top' of the other sub-layer.  Each sub-layer
        corresponds to a conceptual row in the ifTable."
    INDEX { mpl2IfStackNumber }
    ::= { mpl2IfStackTable 1 }


Mpl2IfStackEntry ::=
    SEQUENCE {
        mpl2IfStackNumber       INTEGER,
        mpl2IfStackLowerLayer   INTEGER
    }


mpl2IfStackNumber  OBJECT-TYPE
    SYNTAX INTEGER
    ACCESS read-only
    STATUS mandatory
    DESCRIPTION
        "The MP Link number. The MP Link number is the
        same as the ifIndex for the corresponding
        upper group in the MIB-2 ifGroup."
    ::= { mpl2IfStackEntry 1 }


mpl2IfStackLowerLayer  OBJECT-TYPE
    SYNTAX INTEGER
    ACCESS read-only
    STATUS mandatory
    DESCRIPTION
        "The value of ifIndex corresponding to the lower sub-
        layer of the relationship, i.e., the sub-layer which
        runs 'below' the sub-layer identified by the
        corresponding instance of mpl2IfStackNumber.  If
        there is no lower sub-layer, then this object has the
        value 0."
    ::= { mpl2IfStackEntry 2 }


mpl2GeneralOverviewChange  OBJECT-TYPE
    SYNTAX TimeTicks
    ACCESS read-only
    STATUS mandatory
    DESCRIPTION
        "The value of sysUpTime at the time any MP Link
        seen from the overview changed state or the
        like."
    ::= { mpl2General 1 }


---
--- Trap section
---

mpl2LockEvent TRAP-TYPE
    ENTERPRISE  mplk2
    VARIABLES   { mpl2ServiceNumber, mpl2ServiceLock }
    DESCRIPTION
        "Lock state changed to <mpl2ServiceLock> for link <mpl2ServiceNumber>.
        This trap is sent when an MP Link is locked or
        unlocked from local management or via SNMP."
::= 1

mpl2WanRetriesEvent TRAP-TYPE
    ENTERPRISE  mplk2
    VARIABLES   { mpl2WanNumber, mpl2WanRetries }
    DESCRIPTION
        "Max. retries exceeded (<mpl2WanRetries>) for link <mpl2WanNumber>.
        This trap is sent when an MP Link has had more
        failed connect-attempts than allowed in the
        configuration."
::= 2

mpl2WanActivityEvent TRAP-TYPE
    ENTERPRISE  mplk2
    VARIABLES   { mpl2WanNumber, mpl2WanActivity }
    DESCRIPTION
        "Daily Activity Limit has been reached. Link <mpl2WanNumber> locked.
         This trap is sent when the Daily Activity
        Limit has been reached and locked the link."
::= 3

mpl2WanTimerEvent TRAP-TYPE
    ENTERPRISE  mplk2
    VARIABLES   { mpl2WanNumber, mpl2WanTimer }
    DESCRIPTION
        "Link timer has changed lock state to <WanTimer> for link <WanNumber>.
        This trap is sent when an MP Link timer has
        locked or unlocked the link."
::= 4

END
