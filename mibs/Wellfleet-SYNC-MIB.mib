Wellfleet-SYNC-MIB DEFINITIONS ::= BEGIN

-- Created by mdl2asn version 3.1
-- Creation date: Wed Aug 30 16:48:41 EDT 1995


    IMPORTS

      Counter, Gauge, TimeTicks
        FROM RFC1155-SMI
      OBJECT-TYPE
        FROM RFC-1212
      DisplayString
        FROM RFC1213-MIB
      wfLine
        FROM Wellfleet-COMMON-MIB;


    wfSyncTable OBJECT-TYPE
        SYNTAX	SEQUENCE OF WfSyncEntry
        ACCESS	not-accessible
        STATUS	mandatory
        DESCRIPTION
                "SYNC  line record"
        ::= { wfLine 5 }

    wfSyncEntry OBJECT-TYPE
        SYNTAX	WfSyncEntry
        ACCESS	not-accessible
        STATUS	mandatory
        DESCRIPTION
                "An entry in the SYNC table"
        INDEX	{ wfSyncSlot,
    		  wfSyncConnector }
        ::= { wfSyncTable 1 }

    WfSyncEntry ::= SEQUENCE {
    	    wfSyncDelete
    		INTEGER,
    	    wfSyncDisable
    		INTEGER,
    	    wfSyncState
    		INTEGER,
    	    wfSyncSlot
    		INTEGER,
    	    wfSyncConnector
    		INTEGER,
    	    wfSyncCct
    		INTEGER,
    	    wfSyncBofl
    		INTEGER,
    	    wfSyncBoflTmo
    		INTEGER,
    	    wfSyncMtu
    		INTEGER,
    	    wfSyncMadr
    		OCTET STRING,
    	    wfSyncPromiscuous
    		INTEGER,
    	    wfSyncXid
    		INTEGER,
    	    wfSyncClkSource
    		INTEGER,
    	    wfSyncClkSpeed
    		INTEGER,
    	    wfSyncSignalMode
    		INTEGER,
    	    wfSyncRtsEnable
    		INTEGER,
    	    wfSyncBurstCount
    		INTEGER,
    	    wfSyncService
    		INTEGER,
    	    wfSyncRetryCount
    		INTEGER,
    	    wfSyncLinkIdleTimer
    		INTEGER,
    	    wfSyncRetryTimer
    		INTEGER,
    	    wfSyncExtendedAddress
    		INTEGER,
    	    wfSyncExtendedAddressForce
    		INTEGER,
    	    wfSyncExtendedControl
    		INTEGER,
    	    wfSyncExtendedControlForce
    		INTEGER,
    	    wfSyncConnectAttempts
    		INTEGER,
    	    wfSyncWindowSizeTx
    		INTEGER,
    	    wfSyncWindowSizeTxExtc
    		INTEGER,
    	    wfSyncMinFrameSpace
    		INTEGER,
    	    wfSyncLocalAddress
    		INTEGER,
    	    wfSyncRemoteAddress
    		INTEGER,
    	    wfSyncPassThruLocalMadr
    		OCTET STRING,
    	    wfSyncPassThruRemoteMadr
    		OCTET STRING,
    	    wfSyncWanProtocol
    		INTEGER,
    	    wfSyncCrcSize
    		INTEGER,
    	    wfSyncRxOctets
    		Counter,
    	    wfSyncRxFrames
    		Counter,
    	    wfSyncTxOctets
    		Counter,
    	    wfSyncTxFrames
    		Counter,
    	    wfSyncRxErrors
    		Counter,
    	    wfSyncTxErrors
    		Counter,
    	    wfSyncLackRescRx
    		Counter,
    	    wfSyncLackRescTx
    		Counter,
    	    wfSyncUnderFlowTx
    		Counter,
    	    wfSyncRejectsTx
    		Counter,
    	    wfSyncRejectsRx
    		Counter,
    	    wfSyncOverFlowRx
    		Counter,
    	    wfSyncFramesIncompRx
    		Counter,
    	    wfSyncBadFramesRx
    		Counter,
    	    wfSyncFrameRejectsRx
    		Counter,
    	    wfSyncRuntsRx
    		Counter,
    	    wfSyncT1Timeouts
    		Counter,
    	    wfSyncMemoryErrors
    		Counter,
    	    wfSyncMediaType
    		INTEGER,
    	    wfSyncCfgTxQueueLength
    		INTEGER,
    	    wfSyncCfgRxQueueLength
    		INTEGER,
    	    wfSyncTxQueueLength
    		INTEGER,
    	    wfSyncRxQueueLength
    		INTEGER,
    	    wfSyncRxReplenMisses
    		Counter,
    	    wfSyncStartUpMode
    		INTEGER,
    	    wfSyncIdleRRFrames
    		INTEGER,
    	    wfSyncMultilineMode
    		INTEGER,
    	    wfSyncBODExamPeriod
    		INTEGER,
    	    wfSyncBODFullThreshold
    		INTEGER,
    	    wfSyncBODRecoverThreshold
    		INTEGER,
    	    wfSyncBODPeriodsToFail
    		INTEGER,
    	    wfSyncKG84ACycle
    		INTEGER,
    	    wfSyncKG84ASyncLossInterval
    		INTEGER,
    	    wfSyncKG84ARemoteResyncWait
    		INTEGER,
    	    wfSyncKG84ASyncPulse
    		INTEGER,
    	    wfSyncKG84AResyncs
    		INTEGER,
    	    wfSyncKG84AResyncsDetected
    		INTEGER,
    	    wfSyncKG84ABsu
    		INTEGER,
    	    wfSyncKG84AState
    		INTEGER,
    	    wfSyncKG84AOkFrames
    		INTEGER,
    	    wfSyncPollingEnable
    		INTEGER,
    	    wfSyncBackupPool
    		INTEGER,
    	    wfSyncDemandPool
    		INTEGER,
    	    wfSyncLineNumber
    		INTEGER,
    	    wfSyncHoldDownTime
    		INTEGER,
    	    wfSyncNetworkType
    		INTEGER,
    	    wfSyncActiveCct
    		INTEGER,
    	    wfSyncCableType
    		INTEGER,
    	    wfSyncRxDropPackets
    		Counter,
    	    wfSyncTxDropPackets
    		Counter,
    	    wfSyncModule
    		INTEGER,
    	    wfSyncActualConnector
    		INTEGER,
    	    wfSyncLineCoding
    		INTEGER,
    	    wfSyncLastChange
    		TimeTicks,
    	    wfSyncOutQLen
    		Gauge,
    	    wfSyncRemoteLpbkDetection
    		INTEGER,
    	    wfSyncLastState
    		INTEGER,
    	    wfSyncExternalClkSpeed
    		INTEGER,
    	    wfSyncBChannelOverride
    		INTEGER,
    	    wfSyncBChannel
    		INTEGER,
    	    wfSyncForceIFTF
    		INTEGER,
    	    wfSyncPriority
    		INTEGER,
    	    wfSyncTurboBofl
    		INTEGER,
    	    wfSyncBoflNum
    		INTEGER,
    	    wfSyncBoflLen
    		INTEGER,
    	    wfSyncTurboBoflMisses
    		INTEGER,
    	    wfSyncTurboBoflInvocations
    		INTEGER,
    	    wfSyncBandwidthOnDemandPool
    		INTEGER,
    	    wfSyncBODRecoverPeriodsToPass
    		INTEGER,
    	    wfSyncBODHistory
    		DisplayString,
    	    wfSyncBODDebugFlag
    		INTEGER,
    	    wfSyncBChRateAdaption
    		INTEGER,
    	    wfSyncBChActualRateAdaption
    		INTEGER,
            wfSyncWanType
                INTEGER,
            wfSyncAsyncBaudRate
                INTEGER,
            wfSyncCfgAsyncCmndMaxIdles
                INTEGER,
            wfSyncAsyncCmndMaxIdles
                INTEGER,
            wfSyncCfgAsyncDataMaxIdles
                INTEGER,
            wfSyncAsyncDataMaxIdles
                INTEGER,
            wfSyncFramesAbortTx
    		Counter,
            wfSyncPasyncParityType
                INTEGER,
            wfSyncPasyncCharacterLength
                INTEGER,
            wfSyncPasyncStopLength
                INTEGER,
            wfSyncPasyncBaudRate
                INTEGER,
            wfSyncLocalConnectionState
                INTEGER,
            wfSyncRemoteConnectionState
                INTEGER,
            wfSyncTimeSlotAssignment
                DisplayString,
            wfSyncEiaStatus
                INTEGER,
            wfSyncEiaStatusReset
                INTEGER,
	        wfSyncUcastMap
		        INTEGER,
		    wfSyncAsyncCfgMaxIdleTimer
		        INTEGER
        }

    wfSyncDelete OBJECT-TYPE
        SYNTAX	INTEGER {
    		    created(1),
    		    deleted(2)
    		}
        ACCESS	read-write
        STATUS	mandatory
        DESCRIPTION
                "Create/Delete parameter"
        DEFVAL	{ created }
        ::= { wfSyncEntry 1 }

    wfSyncDisable OBJECT-TYPE
        SYNTAX	INTEGER {
    		    enabled(1),
    		    disabled(2)
    		}
        ACCESS	read-write
        STATUS	mandatory
        DESCRIPTION
                "Enable/Disable parameter"
        DEFVAL	{ enabled }
        ::= { wfSyncEntry 2 }

    wfSyncState OBJECT-TYPE
        SYNTAX	INTEGER {
    		    up(1),
    		    down(2),
    		    init(3),
    		    wait(4),
    		    notpresent(5),
    		    dsrwait(6),
    		    holddown(7),
    		    remoteloop(8),
    		    lineloopbofltest(19),
    		    notpres(20)
    		}
        ACCESS	read-only
        STATUS	mandatory
        DESCRIPTION
                "Line Driver state variable, Reflects the current state of the
                Line Driver.  NOTPRESENT is an obsoleted state.  It is replaced
                with NOTPRES."
        DEFVAL	{ notpres }
        ::= { wfSyncEntry 3 }

    wfSyncSlot OBJECT-TYPE
        SYNTAX	INTEGER
        ACCESS	read-only
        STATUS	mandatory
        DESCRIPTION
                "Instance ID Slot, filled in by driver"
        ::= { wfSyncEntry 4 }

    wfSyncConnector OBJECT-TYPE
        SYNTAX	INTEGER
        ACCESS	read-only
        STATUS	mandatory
        DESCRIPTION
                "Instance ID Connector, filled in by driver. For the ASN
                this attribute is an encoded value and is equal to
                'module'*10 + 'connector'. Where 'module' is defined in
                attribute 86 and 'connector' is defined in attribute 78
                of this table. For non-ASN platforms this attribute is
                the physical connector number on the slot."
        ::= { wfSyncEntry 5 }

    wfSyncCct OBJECT-TYPE
        SYNTAX	INTEGER(1..1023)
        ACCESS	read-write
        STATUS	mandatory
        DESCRIPTION
                "CCT number for this line instance"
        ::= { wfSyncEntry 6 }

    wfSyncBofl OBJECT-TYPE
        SYNTAX	INTEGER {
    		    enabled(1),
    		    disabled(2)
    		}
        ACCESS	read-write
        STATUS	mandatory
        DESCRIPTION
                "breath of life parameter"
        DEFVAL	{ enabled }
        ::= { wfSyncEntry 7 }

    wfSyncBoflTmo OBJECT-TYPE
        SYNTAX	INTEGER(1..60)
        ACCESS	read-write
        STATUS	mandatory
        DESCRIPTION
                "breath of life timeout in seconds"
        DEFVAL	{ 5 }
        ::= { wfSyncEntry 8 }

    wfSyncMtu OBJECT-TYPE
        SYNTAX	INTEGER(3..4608)
        ACCESS	read-write
        STATUS	mandatory
        DESCRIPTION
                "MTU parameter, this is buffer size for SYNC media, fixed"
        DEFVAL	{ 1600 }
        ::= { wfSyncEntry 9 }

    wfSyncMadr OBJECT-TYPE
        SYNTAX	OCTET STRING
        ACCESS	read-only
        STATUS	mandatory
        DESCRIPTION
                "Line MAC address, fixed - line driver fills in from the 48 bit
                address stored in the serial number prom for this connector."
        ::= { wfSyncEntry 10 }

    wfSyncPromiscuous OBJECT-TYPE
        SYNTAX	INTEGER {
    		    enabled(1),
    		    disabled(2)
    		}
        ACCESS	read-write
        STATUS	mandatory
        DESCRIPTION
                "The promiscuous parameter allows address filtering based on the local
                and remote addresses.  When enabled, all frames are received, disabled
                indicates only frames destined for this local address are received"
        DEFVAL	{ disabled }
        ::= { wfSyncEntry 11 }

    wfSyncXid OBJECT-TYPE
        SYNTAX	INTEGER {
    		    enabled(1),
    		    disabled(2)
    		}
        ACCESS	read-write
        STATUS	mandatory
        DESCRIPTION
                "XID enable/disable parameter. This parameter is used to enable
                or disable transmission/reception of Test XID frames."
        DEFVAL	{ disabled }
        ::= { wfSyncEntry 12 }

    wfSyncClkSource OBJECT-TYPE
        SYNTAX	INTEGER {
    		    internal(1),
    		    external(2)
    		}
        ACCESS	read-write
        STATUS	mandatory
        DESCRIPTION
                "Tx/Rx clock source is either internally or external generated."
        DEFVAL	{ external }
        ::= { wfSyncEntry 13 }

    wfSyncClkSpeed OBJECT-TYPE
        SYNTAX	INTEGER {
    		    clk1200b(1200),
    		    clk2400b(2401),
    		    clk4800b(4807),
    		    clk7200b(7204),
    		    clk9600b(9615),
    		    clk19200b(19230),
    		    clk32000b(32051),
    		    clk38400b(38461),
    		    clk56k(56818),
    		    clk64k(64102),
    		    clk125k(125000),
    		    clk230k(227272),
    		    clk420k(416666),
    		    clk625k(625000),
    		    clk833k(833333),
    		    clk1mb(1250000),
    		    clk2mb(2500000),
    		    clk5mb(5000000)
    		}
        ACCESS	read-write
        STATUS	mandatory
        DESCRIPTION
                "Internal Tx/Rx clock speed. This speed selection is valid only when
                internal clocking is selected."
        DEFVAL	{ clk64k }
        ::= { wfSyncEntry 14 }

    wfSyncSignalMode OBJECT-TYPE
        SYNTAX	INTEGER {
    		    balanced(1),
    		    unbalanced(2)
    		}
        ACCESS	read-write
        STATUS	mandatory
        DESCRIPTION
                "The signal mode parameter indicates the line paramter balanced or
                unbalanced."
        DEFVAL	{ balanced }
        ::= { wfSyncEntry 15 }

    wfSyncRtsEnable OBJECT-TYPE
        SYNTAX	INTEGER {
    		    enabled(1),
    		    disabled(2),
    		    kg84aenabled(3)
    		}
        ACCESS	read-write
        STATUS	mandatory
        DESCRIPTION
                "Note: In KG84 support, RTS has a different meaning"
        DEFVAL	{ disabled }
        ::= { wfSyncEntry 16 }

    wfSyncBurstCount OBJECT-TYPE
        SYNTAX	INTEGER {
    		    enabled(1),
    		    disabled(2),
    		    unlimited(3)
    		}
        ACCESS	read-write
        STATUS	mandatory
        DESCRIPTION
                "Allows control over the DMA burst cycle duration on MK5025 based products.
                This attribute is ignored for AN and ASN products.  The default is always
                8 short word bursts (ENABLED).  There are only two cases in which this
                attribute should be changed.

                Case 1:  In certain cases with DSDE and DSE link modules when one or both
                     of the ethernet ports are suffering from excessive TxUflo or RxOflo
                     errors,  the BurstCount of one or both SYNC interfaces can be set to
                     single short word bursts (DISABLED).  The only modules for which this
                     may be necessary are the DSDE (5430 - Dual Sync, Dual Enet) (module ID
                     112) and the DSE (5420 - Dual Sync, Single Enet) (module ID 116).
                     If after making the change,  the TxUflo or RxOflo errors persist on the
                     ethernet or this SYNC interface starts to get UnderFlowTx or OverFlowRx
                     errors,  then the Link Module is overloaded and a more significant
                     software configuration change or a hardware configuration change is
                     needed.

                Case 2:  When a SYNC interface on an mk5025 based Link Module is getting
                     UnderFlowTx or OverFlowRx errors while running at bandwidths greater
                     than 2Mbps,  the errors may be eliminated by setting this attribute to
                     unlimited burst mode (UNLIMITED).  If after making the change,  the
                     errors persist or the same errors start on another SYNC interface or
                     one of the ethernet interfaces on the same module starts to get TxUflo
                     or RxOflo errors,  then the Link Module is overloaded and a more
                     significant software configuration change or a hardware configuration
                     change is needed.  For 6Mbps full duplex operation,  this attribute
                     will most likely need to be set to UNLIMITED and all other interfaces
                     on this module will most likely have to be deconfigured."
        DEFVAL	{ enabled }
        ::= { wfSyncEntry 17 }

    wfSyncService OBJECT-TYPE
        SYNTAX	INTEGER {
    		    transparent(1),
    		    llc1(2),
    		    llc2(3)
    		}
        ACCESS	read-write
        STATUS	mandatory
        DESCRIPTION
                "Service type for this circuit. Transparent is raw HDLC mode, LLC1 will
                prefix the HDLC address and control fields to the frame.  The LLC2 service
                provides the LAPB protocol service."
        DEFVAL	{ llc1 }
        ::= { wfSyncEntry 18 }

    wfSyncRetryCount OBJECT-TYPE
        SYNTAX	INTEGER(1..64)
        ACCESS	read-write
        STATUS	mandatory
        DESCRIPTION
                "The Retry count parameter indicates the number of retransmission
                attempts which will be tried per frame before a line is determined
                to be down.  The retry count is max attempts following expiration of
                the T1 timer.  This parameter is equal to the N2 counter in ICB."
        DEFVAL	{ 16 }
        ::= { wfSyncEntry 19 }

    wfSyncLinkIdleTimer OBJECT-TYPE
        SYNTAX	INTEGER(1..9999)
        ACCESS	read-write
        STATUS	mandatory
        DESCRIPTION
                "The link idle parameter is the number of seconds before a line has
                been determined to be idle.  An idle line is considered disconnectd
                This value is expressed in seconds."
        DEFVAL	{ 9 }
        ::= { wfSyncEntry 20 }

    wfSyncRetryTimer OBJECT-TYPE
        SYNTAX	INTEGER(1..9999)
        ACCESS	read-write
        STATUS	mandatory
        DESCRIPTION
                "The Retry Timer parameter indicates the timeout in tenths of seconds for a
                response to be heard form the link.  Link control frames are sent at
                the expiration of this timer value.  The frames will be resent up to
                retry count (N2) at which time the link will be disconnected."
        DEFVAL	{ 30 }
        ::= { wfSyncEntry 21 }

    wfSyncExtendedAddress OBJECT-TYPE
        SYNTAX	INTEGER {
    		    enabled(1),
    		    disabled(2)
    		}
        ACCESS	read-write
        STATUS	mandatory
        DESCRIPTION
                "This parameter controls length determination of the address field.
                When this parameter is enabled, the first bit of the address field
                be tested to determine the length of address field in octets."
        DEFVAL	{ disabled }
        ::= { wfSyncEntry 22 }

    wfSyncExtendedAddressForce OBJECT-TYPE
        SYNTAX	INTEGER {
    		    enabled(1),
    		    disabled(2)
    		}
        ACCESS	read-write
        STATUS	mandatory
        DESCRIPTION
                "When this parameter is enabled, the receiver will assume that all
                address fields are 2 octets in length regardless of the first two
                bits of the control field.  Usefull only in Transparent Mode."
        DEFVAL	{ disabled }
        ::= { wfSyncEntry 23 }

    wfSyncExtendedControl OBJECT-TYPE
        SYNTAX	INTEGER {
    		    enabled(1),
    		    disabled(2)
    		}
        ACCESS	read-write
        STATUS	mandatory
        DESCRIPTION
                "This parameter allows the control fields of all S and I frames to
                become 2 octets in length instead of one.  Numbering of all I frame
                become modulo 128 instead of modulo 8.  The control field of U
                frames remains one octet in length."
        DEFVAL	{ disabled }
        ::= { wfSyncEntry 24 }

    wfSyncExtendedControlForce OBJECT-TYPE
        SYNTAX	INTEGER {
    		    enabled(1),
    		    disabled(2)
    		}
        ACCESS	read-write
        STATUS	mandatory
        DESCRIPTION
                "This parameter when enabled will force all control fields to become
                two octets in length regardless the first two bits in the control
                field.  Usefull only in Transparent Mode. (LLC1)"
        DEFVAL	{ disabled }
        ::= { wfSyncEntry 25 }

    wfSyncConnectAttempts OBJECT-TYPE
        SYNTAX	INTEGER(1..9999)
        ACCESS	read-write
        STATUS	mandatory
        DESCRIPTION
                "This parameter controls the number of connection attempts which
                will be made during a LAPB connection request.  This parameter
                is applicable only during LLC2 service."
        DEFVAL	{ 10 }
        ::= { wfSyncEntry 26 }

    wfSyncWindowSizeTx OBJECT-TYPE
        SYNTAX	INTEGER(1..7)
        ACCESS	read-write
        STATUS	mandatory
        DESCRIPTION
                "The window size parameter controls the number of I frames which
                may be transmitted without acknowledgement. Non EXTC mode."
        DEFVAL	{ 1 }
        ::= { wfSyncEntry 27 }

    wfSyncWindowSizeTxExtc OBJECT-TYPE
        SYNTAX	INTEGER(1..7)
        ACCESS	read-write
        STATUS	mandatory
        DESCRIPTION
                "The window size parameter controls the number of I frames which
                may be transmitted without acknowledgement in EXTC mode."
        DEFVAL	{ 1 }
        ::= { wfSyncEntry 28 }

    wfSyncMinFrameSpace OBJECT-TYPE
        SYNTAX	INTEGER(1..32)
        ACCESS	read-write
        STATUS	mandatory
        DESCRIPTION
                "The minimum frame spacing parameter defines the number of flags
                that are transmitted between adjacent frames."
        DEFVAL	{ 1 }
        ::= { wfSyncEntry 29 }

    wfSyncLocalAddress OBJECT-TYPE
        SYNTAX	INTEGER {
    		    addressdte(3),
    		    addressdce(1),
    		    addressexplicit(7)
    		}
        ACCESS	read-write
        STATUS	mandatory
        DESCRIPTION
                "The local address parameter contains the DTE,DCE or EXPLICIT
                value expressed as a single octet.  It may be extended to 2
                octets if EXTA has been set."
        DEFVAL	{ addressexplicit }
        ::= { wfSyncEntry 30 }

    wfSyncRemoteAddress OBJECT-TYPE
        SYNTAX	INTEGER {
    		    addressdte(3),
    		    addressdce(1),
    		    addressexplicit(7)
    		}
        ACCESS	read-write
        STATUS	mandatory
        DESCRIPTION
                "The remote address parameter contains the DTE,DCE or EXPLICIT
                value expressed as a single octet.  It may be extended to 2
                octets if EXTA has been set."
        DEFVAL	{ addressexplicit }
        ::= { wfSyncEntry 31 }

    wfSyncPassThruLocalMadr OBJECT-TYPE
        SYNTAX	OCTET STRING
        ACCESS	read-write
        STATUS	mandatory
        DESCRIPTION
                "48 bit MAC address of Local end of Sync Passthru circuit"
        ::= { wfSyncEntry 32 }

    wfSyncPassThruRemoteMadr OBJECT-TYPE
        SYNTAX	OCTET STRING
        ACCESS	read-write
        STATUS	mandatory
        DESCRIPTION
                "48 bit MAC address of Remote end of Sync Passthru circuit"
        ::= { wfSyncEntry 33 }

    wfSyncWanProtocol OBJECT-TYPE
        SYNTAX	INTEGER {
    		    standard(1),
    		    passthru(2),
    		    ppp(3),
    		    smds(4),
    		    framerelay(5),
    		    x25(6),
    		    switch(7),
    		    sw(8),
    		    atm(9),
    		    lapb(10),
    		    sdlc(11),
                    aot(12)
    		}
        ACCESS	read-write
        STATUS	mandatory
        DESCRIPTION
                "WAN protocol selection is provided via this parameter. The
                supported protocols can be selected per interface."
        DEFVAL	{ standard }
        ::= { wfSyncEntry 34 }

    wfSyncCrcSize OBJECT-TYPE
        SYNTAX	INTEGER {
    		    crc16bit(1),
    		    crc32bit(2)
    		}
        ACCESS	read-write
        STATUS	mandatory
        DESCRIPTION
                "CRC size parameter, 16 bit standard CCITT or extended 32 bit CRC"
        DEFVAL	{ crc16bit }
        ::= { wfSyncEntry 35 }

    wfSyncRxOctets OBJECT-TYPE
        SYNTAX	Counter
        ACCESS	read-only
        STATUS	mandatory
        DESCRIPTION
                "Number of octets received without error"
        ::= { wfSyncEntry 36 }

    wfSyncRxFrames OBJECT-TYPE
        SYNTAX	Counter
        ACCESS	read-only
        STATUS	mandatory
        DESCRIPTION
                "Number of frames received without error"
        ::= { wfSyncEntry 37 }

    wfSyncTxOctets OBJECT-TYPE
        SYNTAX	Counter
        ACCESS	read-only
        STATUS	mandatory
        DESCRIPTION
                "Number of octets transmitted without error"
        ::= { wfSyncEntry 38 }

    wfSyncTxFrames OBJECT-TYPE
        SYNTAX	Counter
        ACCESS	read-only
        STATUS	mandatory
        DESCRIPTION
                "Number of frames transmitted without error"
        ::= { wfSyncEntry 39 }

    wfSyncRxErrors OBJECT-TYPE
        SYNTAX	Counter
        ACCESS	read-only
        STATUS	mandatory
        DESCRIPTION
                "Number of receive errors"
        ::= { wfSyncEntry 40 }

    wfSyncTxErrors OBJECT-TYPE
        SYNTAX	Counter
        ACCESS	read-only
        STATUS	mandatory
        DESCRIPTION
                "Number of transmission errors"
        ::= { wfSyncEntry 41 }

    wfSyncLackRescRx OBJECT-TYPE
        SYNTAX	Counter
        ACCESS	read-only
        STATUS	mandatory
        DESCRIPTION
                "Number of Rx frames dropped due to lack of buffer resources"
        ::= { wfSyncEntry 42 }

    wfSyncLackRescTx OBJECT-TYPE
        SYNTAX	Counter
        ACCESS	read-only
        STATUS	mandatory
        DESCRIPTION
                "Number of frames clipped in driver's transmit routine due to transmit
                congestion."
        ::= { wfSyncEntry 43 }

    wfSyncUnderFlowTx OBJECT-TYPE
        SYNTAX	Counter
        ACCESS	read-only
        STATUS	mandatory
        DESCRIPTION
                "Number of transmission underflows, device FIFO went empty before
                next DMA request was granted."
        ::= { wfSyncEntry 44 }

    wfSyncRejectsTx OBJECT-TYPE
        SYNTAX	Counter
        ACCESS	read-only
        STATUS	mandatory
        DESCRIPTION
                "For the mk50 driver: Number of reject frames which were
                    transmitted
                 For the quicsync driver: Not used
                 For the quicsync driver in Async mode: Number of frames
                    that grew, due to escaping, larger than a buffer"
        ::= { wfSyncEntry 45 }

    wfSyncRejectsRx OBJECT-TYPE
        SYNTAX	Counter
        ACCESS	read-only
        STATUS	mandatory
        DESCRIPTION
                "For the mk50 driver: Number of reject frames which were
                    received
                 For the quicsync driver: Number of HDLC frames received with
                    a non-matching address
                 For the quicsync driver in Async mode: Number of frames
                    received that did not fit within a buffer"
        ::= { wfSyncEntry 46 }

    wfSyncOverFlowRx OBJECT-TYPE
        SYNTAX	Counter
        ACCESS	read-only
        STATUS	mandatory
        DESCRIPTION
                "Number of receive overflows, device FIFO overflowed before next
                DMA cycle granted.  No buffer resources available."
        ::= { wfSyncEntry 47 }

    wfSyncFramesIncompRx OBJECT-TYPE
        SYNTAX	Counter
        ACCESS	read-only
        STATUS	mandatory
        DESCRIPTION
                "Number of frames which were incompletely received. These are frames
                which may have resulted from FRMRR errors."
        ::= { wfSyncEntry 48 }

    wfSyncBadFramesRx OBJECT-TYPE
        SYNTAX	Counter
        ACCESS	read-only
        STATUS	mandatory
        DESCRIPTION
                "Number of bad receive frames, caused by FCS errors or non octet aligned."
        ::= { wfSyncEntry 49 }

    wfSyncFrameRejectsRx OBJECT-TYPE
        SYNTAX	Counter
        ACCESS	read-only
        STATUS	mandatory
        DESCRIPTION
                "Number of Frame Rejects received"
        ::= { wfSyncEntry 50 }

    wfSyncRuntsRx OBJECT-TYPE
        SYNTAX	Counter
        ACCESS	read-only
        STATUS	mandatory
        DESCRIPTION
                "Number of runt frames received or number of frames where
                 the Carrier Detect signal was lost during reception."
        ::= { wfSyncEntry 51 }

    wfSyncT1Timeouts OBJECT-TYPE
        SYNTAX	Counter
        ACCESS	read-only
        STATUS	mandatory
        DESCRIPTION
                "Number of T1 timeout's detected. The T1 timer is the link
                retransmission timer.  Link control frames will be retransmitted
                when T1 expires.  This is a count of the number of timeouts."
        ::= { wfSyncEntry 52 }

    wfSyncMemoryErrors OBJECT-TYPE
        SYNTAX	Counter
        ACCESS	read-only
        STATUS	mandatory
        DESCRIPTION
                "Number of memory access errors detected. A MERR is the expiration of
                a DMA cycle without the bus being granted within 26us."
        ::= { wfSyncEntry 53 }

    wfSyncMediaType OBJECT-TYPE
        SYNTAX	INTEGER {
    		    default(1),
    		    t1(2),
    		    e1(3),
    		    raisedtr(4),
    		    v25bis(5),
    		    bri(6),
    		    isdnleased(7),
		    hayes(8)
    		}
        ACCESS	read-write
        STATUS	mandatory
        DESCRIPTION
                "Media type selection is provided via this parameter"
        DEFVAL	{ default }
        ::= { wfSyncEntry 54 }

    wfSyncCfgTxQueueLength OBJECT-TYPE
        SYNTAX	INTEGER(0..255)
        ACCESS	read-write
        STATUS	mandatory
        DESCRIPTION
                "Configured Transmit Queue Length. Values other than zero over-ride the
                router selected values.  A value of zero has a special meaning.  Zero
                causes router based default values to be used.  Values larger than the
                compiled ring size are truncated to the compiled ring size. "
        ::= { wfSyncEntry 55 }

    wfSyncCfgRxQueueLength OBJECT-TYPE
        SYNTAX	INTEGER(0..255)
        ACCESS	read-write
        STATUS	mandatory
        DESCRIPTION
                "Configured Receive Queue Length. Values other than zero over-ride the
                router selected values.  A value of zero has a special meaning.  Zero
                causes router based default values to be used.  Values larger than the
                compiled ring size are truncated to the compiled ring size. "
        ::= { wfSyncEntry 56 }

    wfSyncTxQueueLength OBJECT-TYPE
        SYNTAX	INTEGER
        ACCESS	read-only
        STATUS	mandatory
        DESCRIPTION
                "Current Transmit Queue Length."
        ::= { wfSyncEntry 57 }

    wfSyncRxQueueLength OBJECT-TYPE
        SYNTAX	INTEGER
        ACCESS	read-only
        STATUS	mandatory
        DESCRIPTION
                "Current Receive Queue Length."
        ::= { wfSyncEntry 58 }

    wfSyncRxReplenMisses OBJECT-TYPE
        SYNTAX	Counter
        ACCESS	read-only
        STATUS	mandatory
        DESCRIPTION
                "Number of packet buffer misses while attempting to replenish driver
                receive ring."
        ::= { wfSyncEntry 59 }

    wfSyncStartUpMode OBJECT-TYPE
        SYNTAX	INTEGER {
    		    active(1),
    		    passive(2)
    		}
        ACCESS	read-write
        STATUS	mandatory
        DESCRIPTION
                "Initiation of link level for LLC2 running LAPB"
        DEFVAL	{ active }
        ::= { wfSyncEntry 60 }

    wfSyncIdleRRFrames OBJECT-TYPE
        SYNTAX	INTEGER {
    		    on(1),
    		    off(2)
    		}
        ACCESS	read-write
        STATUS	mandatory
        DESCRIPTION
                "Transmit Link level RR's (Reciever Readys) during idle time. Every
                wfSyncLinkIdleTimer expiration an RR will be sent."
        DEFVAL	{ off }
        ::= { wfSyncEntry 61 }

    wfSyncMultilineMode OBJECT-TYPE
        SYNTAX	INTEGER {
    		    standard(1),
    		    monitor(2),
    		    primary(3),
    		    secondary(4)
    		}
        ACCESS	read-write
        STATUS	mandatory
        DESCRIPTION
                "This indicates the roll the sync line plays in a
                Bandwidth on Demand multiline circuit.  If this is
                not BOD, the mode is standard."
        DEFVAL	{ standard }
        ::= { wfSyncEntry 62 }

    wfSyncBODExamPeriod OBJECT-TYPE
        SYNTAX	INTEGER(5..200)
        ACCESS	read-write
        STATUS	mandatory
        DESCRIPTION
                "This indicates the interval that the line should
                be polled for possible congestion.  This value is in
                tenths of a second"
        DEFVAL	{ 10 }
        ::= { wfSyncEntry 63 }

    wfSyncBODFullThreshold OBJECT-TYPE
        SYNTAX	INTEGER(10..100)
        ACCESS	read-write
        STATUS	mandatory
        DESCRIPTION
                "This is the percentage of the theoretical maximum line
                throughput that must be reached or exceeded before the line is
                considered congested."
        DEFVAL	{ 70 }
        ::= { wfSyncEntry 64 }

    wfSyncBODRecoverThreshold OBJECT-TYPE
        SYNTAX	INTEGER(10..100)
        ACCESS	read-write
        STATUS	mandatory
        DESCRIPTION
                "This is the recovery threshold expressed as a percentage of the
                theoretical maximum line throughput.  The actual throughput must fall
                below this percentage in order for the BOD circuit to
                revert back to the primary line only. This value should be
                set to less than one half the value of wfSyncBODFullThreshold
                to avoid toggling the secondary."
        DEFVAL	{ 20 }
        ::= { wfSyncEntry 65 }

    wfSyncBODPeriodsToFail OBJECT-TYPE
        SYNTAX	INTEGER(1..100)
        ACCESS	read-write
        STATUS	mandatory
        DESCRIPTION
                "This is the number of consecutive periods where the line
                throughput is above the congestion threshold required to declare
                the line congested."
        DEFVAL	{ 10 }
        ::= { wfSyncEntry 66 }

    wfSyncKG84ACycle OBJECT-TYPE
        SYNTAX	INTEGER {
    		    cycle5ms(5),
    		    cycle10ms(10),
    		    cycle25ms(25),
    		    cycle50ms(50),
    		    cycle100ms(100),
    		    cycle200ms(200),
    		    cycle500ms(500)
    		}
        ACCESS	read-write
        STATUS	mandatory
        DESCRIPTION
                "Monitor sample time in milliseconds"
        DEFVAL	{ cycle100ms }
        ::= { wfSyncEntry 67 }

    wfSyncKG84ASyncLossInterval OBJECT-TYPE
        SYNTAX	INTEGER {
    		    num2cycles(2),
    		    num5cycles(5),
    		    num10cycles(10),
    		    num25cycles(25),
    		    num50cycles(50),
    		    num100cycles(100),
    		    num200cycles(200),
    		    num500cycles(500)
    		}
        ACCESS	read-write
        STATUS	mandatory
        DESCRIPTION
                "timer starts when FCS error detected; if no good frame received
                during this time, declare loss of synchronization"
        DEFVAL	{ num50cycles }
        ::= { wfSyncEntry 68 }

    wfSyncKG84ARemoteResyncWait OBJECT-TYPE
        SYNTAX	INTEGER {
    		    num2cycles(2),
    		    num5cycles(5),
    		    num10cycles(10),
    		    num25cycles(25),
    		    num50cycles(50),
    		    num100cycles(100),
    		    num200cycles(200),
    		    num500cycles(500)
    		}
        ACCESS	read-write
        STATUS	mandatory
        DESCRIPTION
                "when loss of synchronization is detected, and CTS is low, start timer; if
                CTS is not high when timer expires, force sync request"
        DEFVAL	{ num200cycles }
        ::= { wfSyncEntry 69 }

    wfSyncKG84ASyncPulse OBJECT-TYPE
        SYNTAX	INTEGER(2..4096)
        ACCESS	read-write
        STATUS	mandatory
        DESCRIPTION
                "interval to pulse KG84a SYNC signal, in milliseconds"
        DEFVAL	{ 10 }
        ::= { wfSyncEntry 70 }

    wfSyncKG84AResyncs OBJECT-TYPE
        SYNTAX	INTEGER
        ACCESS	read-only
        STATUS	mandatory
        DESCRIPTION
                "number of KG84 resyncs performed"
        ::= { wfSyncEntry 71 }

    wfSyncKG84AResyncsDetected OBJECT-TYPE
        SYNTAX	INTEGER
        ACCESS	read-only
        STATUS	mandatory
        DESCRIPTION
                "number of KG84 resyncs detected"
        ::= { wfSyncEntry 72 }

    wfSyncKG84ABsu OBJECT-TYPE
        SYNTAX	INTEGER
        ACCESS	read-only
        STATUS	mandatory
        DESCRIPTION
                "value taken from mk5025 sync chip control block"
        ::= { wfSyncEntry 73 }

    wfSyncKG84AState OBJECT-TYPE
        SYNTAX	INTEGER {
    		    idle(1),
    		    local(2),
    		    remote(3),
    		    sync(4)
    		}
        ACCESS	read-only
        STATUS	mandatory
        DESCRIPTION
                "state of sync"
        DEFVAL	{ idle }
        ::= { wfSyncEntry 74 }

    wfSyncKG84AOkFrames OBJECT-TYPE
        SYNTAX	INTEGER
        ACCESS	read-only
        STATUS	mandatory
        DESCRIPTION
                "count of valid frames received. This value taken from normal sync
                processing, updated by timer routine when FCE error detected"
        ::= { wfSyncEntry 75 }

    wfSyncPollingEnable OBJECT-TYPE
        SYNTAX	INTEGER {
    		    enabled(1),
    		    disabled(2)
    		}
        ACCESS	read-write
        STATUS	mandatory
        DESCRIPTION
                "Enable or Disable Sync Polling. When Sync Polling is enabled, the
                the Sync Driver will be disabled if the DSR lead is dropped. If
                disabled, the DSR lead is ignored."
        DEFVAL	{ disabled }
        ::= { wfSyncEntry 76 }

    wfSyncBackupPool OBJECT-TYPE
        SYNTAX	INTEGER(1..255)
        ACCESS	read-write
        STATUS	mandatory
        DESCRIPTION
                "Backup pool id containing this line driver"
        ::= { wfSyncEntry 77 }

    wfSyncDemandPool OBJECT-TYPE
        SYNTAX	INTEGER(1..255)
        ACCESS	read-write
        STATUS	mandatory
        DESCRIPTION
                "Dial on demand  pool id containing this line driver"
        ::= { wfSyncEntry 78 }

    wfSyncLineNumber OBJECT-TYPE
        SYNTAX	INTEGER
        ACCESS	read-write
        STATUS	mandatory
        DESCRIPTION
                "line number for this line instance"
        ::= { wfSyncEntry 79 }

    wfSyncHoldDownTime OBJECT-TYPE
        SYNTAX	INTEGER
        ACCESS	read-write
        STATUS	mandatory
        DESCRIPTION
                "Wait this number of seconds before bringing the line
                up. This prevents line waffling if this is a
                reactivated primary line in a backup configuration
                and it is a dirty line"
        ::= { wfSyncEntry 80 }

    wfSyncNetworkType OBJECT-TYPE
        SYNTAX	INTEGER {
    		    gosip(1),
    		    net2(2),
    		    c03(3)
    		}
        ACCESS	read-write
        STATUS	mandatory
        DESCRIPTION
                "Specific Network Link Level to be executed, LAPB mode only.
                The types GOSIP and NET2 are used in conjunction with an MK5025
                chip revision C04.  If a customer must be NET2 compliant and is
                using an MK5025 chip revision C03, the C03 option must be used."
        DEFVAL	{ net2 }
        ::= { wfSyncEntry 81 }

    wfSyncActiveCct OBJECT-TYPE
        SYNTAX	INTEGER(1..1023)
        ACCESS	read-only
        STATUS	mandatory
        DESCRIPTION
                "Active CCT number for this line instance"
        ::= { wfSyncEntry 82 }

    wfSyncCableType OBJECT-TYPE
        SYNTAX	INTEGER(0..4)
        ACCESS	read-write
        STATUS	mandatory
        DESCRIPTION
                "Type of Cable attached to the sync port - this is
                needed for V.25bis and Raise DTR to properly
                communicate with the modem"
        ::= { wfSyncEntry 83 }

    wfSyncRxDropPackets OBJECT-TYPE
        SYNTAX	Counter
        ACCESS	read-only
        STATUS	mandatory
        DESCRIPTION
                "Number of Rx packets dropped by driver."
        ::= { wfSyncEntry 84 }

    wfSyncTxDropPackets OBJECT-TYPE
        SYNTAX	Counter
        ACCESS	read-only
        STATUS	mandatory
        DESCRIPTION
                "Number of Tx packets dropped by driver."
        ::= { wfSyncEntry 85 }

    wfSyncModule OBJECT-TYPE
        SYNTAX	INTEGER {
    		    one(1),
    		    two(2),
    		    three(3),
    		    four(4)
    		}
        ACCESS	read-only
        STATUS	mandatory
        DESCRIPTION
                "Module number for ASN platform, filled in by driver. For non-ASN
                platforms this attribute will not be used."
        ::= { wfSyncEntry 86 }

    wfSyncActualConnector OBJECT-TYPE
        SYNTAX	INTEGER {
    		    one(1),
    		    two(2),
    		    three(3),
    		    four(4),
    		    five(5),
    		    six(6),
    		    seven(7),
    		    eight(8)
    		}
        ACCESS	read-only
        STATUS	mandatory
        DESCRIPTION
                "Actual connector number for ASN platform, filled in
                by driver. For non-ASN platforms, this attribute will
                not be used."
        ::= { wfSyncEntry 87 }

    wfSyncLineCoding OBJECT-TYPE
        SYNTAX	INTEGER {
    		    nrz(1),
    		    nrzi(2),
    		    nrzimark(3)
    		}
        ACCESS	read-write
        STATUS	mandatory
        DESCRIPTION
                "Line Coding for sync interface. Can be either NRZ or NRZI."
        DEFVAL	{ nrz }
        ::= { wfSyncEntry 88 }

    wfSyncLastChange OBJECT-TYPE
        SYNTAX	TimeTicks
        ACCESS	read-only
        STATUS	mandatory
        DESCRIPTION
                "The value of SysUpTime at the time the interface entered it's current
                operational state (UP state).  SysUpTime is defined as the time (in
                hundredths of a second) since the network management portion of the
                system was last re-initialized.  Usually the time since boot."
        ::= { wfSyncEntry 89 }

    wfSyncOutQLen OBJECT-TYPE
        SYNTAX	Gauge
        ACCESS	read-only
        STATUS	mandatory
        DESCRIPTION
                "The instantaneous current length of the output packet queue (in packets)."
        ::= { wfSyncEntry 90 }

    wfSyncRemoteLpbkDetection OBJECT-TYPE
        SYNTAX	INTEGER {
    		    enabled(1),
    		    disabled(2)
    		}
        ACCESS	read-write
        STATUS	mandatory
        DESCRIPTION
                "This attribute enables Remote Loopback Detection. When enabled along with
                wfSyncBofl,  the device driver will detect when it is receiving its own
                BOFL packets and will bring the interface down assuming that somewhere
                down stream the link has been put into loopback. "
        DEFVAL	{ disabled }
        ::= { wfSyncEntry 91 }

    wfSyncLastState OBJECT-TYPE
        SYNTAX	INTEGER {
    		    up(1),
    		    down(2),
    		    init(3),
    		    wait(4),
    		    notpresent(5),
    		    dsrwait(6),
    		    holddown(7),
    		    remoteloop(8),
    		    notpres(20)
    		}
        ACCESS	read-only
        STATUS	mandatory
        DESCRIPTION
                "The state which the driver was in prior to the most recent
                re-initialization."
        ::= { wfSyncEntry 92 }

    wfSyncExternalClkSpeed OBJECT-TYPE
        SYNTAX	INTEGER(1200..6000000)
        ACCESS	read-write
        STATUS	mandatory
        DESCRIPTION
                "External Clock Speed. If external clocking is configured, this attribute
                should be set to the clock speed of the externally supplied clock.
                Depending on the protocols configured on this interface,  this value may
                control internal decision making within the router. In some cases,  router
                software uses this attribute for route selection.  If Priority Queuing is
                configured, it chooses queue depths based on this attribute.  This attribute
                has no effect when Internal clocking is configured."
        DEFVAL	{ 64102 }
        ::= { wfSyncEntry 93 }

    wfSyncBChannelOverride OBJECT-TYPE
        SYNTAX	INTEGER {
    		    bchannel1(1),
    		    bchannel2(2),
    		    default(3),
    		    floatingb(4)
    		}
        ACCESS	read-write
        STATUS	mandatory
        DESCRIPTION
                "For ISDN, indicates which B Channel we're using. By default, we'd like
                the B Channel tied to the connector defined in the instance id, but
                the user may override that here, which gives the ability of connecting
                the B Channel to specific SCC's."
        DEFVAL	{ default }
        ::= { wfSyncEntry 94 }

    wfSyncBChannel OBJECT-TYPE
        SYNTAX	INTEGER {
    		    bchannel1(1),
    		    bchannel2(2)
    		}
        ACCESS	read-only
        STATUS	mandatory
        DESCRIPTION
                "Indicates which B Channel is running"
        ::= { wfSyncEntry 95 }

    wfSyncForceIFTF OBJECT-TYPE
        SYNTAX	INTEGER {
    		    default(1),
    		    forcehdlcflags(2),
    		    forceidles(3),
                    flagstreaming(4)
    		}
        ACCESS	read-write
        STATUS	mandatory
        DESCRIPTION
                "Specifies the Inter Frame Time Fill (IFTF) pattern which gets transmitted
                when no data is being transmitted on a particular channel. 
                For SDLC Lines, DEFAULT and FORCE_HDLC_FLAGS both result in
                HDLC Flags (0x7E) as the fill character.
                FLAGSTREAMING will cause the fill character to alternate between 
                Flags (0x7E) and Idles (0xFF), depending upon the current state of the line.
                For ISDN BRI Lines, DEFAULT, FORCE IDLES and FLAGSTREAMING all
                result in Idles (0xFF) as the fill character.

                For all other line types, DEFAULT, FORCE HDLC FLAGS and FLAGSTREAMING all
                result in HDLC Flags (0x7E) as the fill character.

                Leave this field at the default unless required for the attached
                device.  The AS/400 high speed serial controller requires the use of 
                FLAGSTREAMING for error-free operation."
        DEFVAL	{ default }
        ::= { wfSyncEntry 96 }

    wfSyncPriority OBJECT-TYPE
        SYNTAX	INTEGER(1..50)
        ACCESS	read-write
        STATUS	mandatory
        DESCRIPTION
                "Used by dial/switched services to assign priority of lines
                within the same demand or backup pool"
        DEFVAL	{ 1 }
        ::= { wfSyncEntry 97 }

    wfSyncTurboBofl OBJECT-TYPE
        SYNTAX	INTEGER {
    		    enabled(1),
    		    disabled(2)
    		}
        ACCESS	read-write
        STATUS	mandatory
        DESCRIPTION
                "DEBUG parameter - Turbo bofl enabled or disabled"
        DEFVAL	{ disabled }
        ::= { wfSyncEntry 98 }

    wfSyncBoflNum OBJECT-TYPE
        SYNTAX	INTEGER(1..127)
        ACCESS	read-write
        STATUS	mandatory
        DESCRIPTION
                "DEBUG parameter - Number of breath of life packets per breath
                of life"
        DEFVAL	{ 1 }
        ::= { wfSyncEntry 99 }

    wfSyncBoflLen OBJECT-TYPE
        SYNTAX	INTEGER(22..4450)
        ACCESS	read-write
        STATUS	mandatory
        DESCRIPTION
                "DEBUG parameter - breath of life packet length"
        DEFVAL	{ 200 }
        ::= { wfSyncEntry 100 }

    wfSyncTurboBoflMisses OBJECT-TYPE
        SYNTAX	INTEGER
        ACCESS	read-only
        STATUS	mandatory
        DESCRIPTION
                "DEBUG parameter - breath of life allocation failures"
        ::= { wfSyncEntry 101 }

    wfSyncTurboBoflInvocations OBJECT-TYPE
        SYNTAX	INTEGER
        ACCESS	read-only
        STATUS	mandatory
        DESCRIPTION
                "DEBUG parameter - breath of life invocations"
        ::= { wfSyncEntry 102 }

    wfSyncBandwidthOnDemandPool OBJECT-TYPE
        SYNTAX	INTEGER(1..255)
        ACCESS	read-write
        STATUS	mandatory
        DESCRIPTION
                "Bandwidth pool id containing this line driver"
        ::= { wfSyncEntry 103 }

    wfSyncBODRecoverPeriodsToPass OBJECT-TYPE
        SYNTAX	INTEGER(1..100)
        ACCESS	read-write
        STATUS	mandatory
        DESCRIPTION
                "This is the number of consecutive periods where the queue
                depth is below the congestion threshold required to declare
                the line congested.  It is used for recovery.  That is,
                once a line is declared as congested, this is the number of
                consecutive examination periods where the queue depth is
                below the recovery threshold value required to delare that the
                line is no longer congested."
        DEFVAL	{ 10 }
        ::= { wfSyncEntry 104 }

    wfSyncBODHistory OBJECT-TYPE
        SYNTAX	DisplayString
        ACCESS	read-only
        STATUS	mandatory
        DESCRIPTION
                "DEBUG parameter - This is the SBOD history buffer."
        ::= { wfSyncEntry 105 }

    wfSyncBODDebugFlag OBJECT-TYPE
        SYNTAX	INTEGER
        ACCESS	read-write
        STATUS	mandatory
        DESCRIPTION
                "DEBUG parameter - This is the SBOD Debug flag, used to control
                debug code for SBOD."
        ::= { wfSyncEntry 106 }

    wfSyncBChRateAdaption OBJECT-TYPE
        SYNTAX	INTEGER {
    		    adaption64k(1),
    		    adaption128k(2)
    		}
        ACCESS	read-write
        STATUS	mandatory
        DESCRIPTION
                "This attribute is only relevant when this Synchronous device driver
                is performing as an ISDN B channel over a BRI interface in leased
                line mode.  This attribute specifies the piece of ISDN line's bandwidth
                which data from this driver will occupy.  "
        DEFVAL	{ adaption64k }
        ::= { wfSyncEntry 107 }

    wfSyncBChActualRateAdaption OBJECT-TYPE
        SYNTAX	INTEGER {
    		    adaption64k(1),
    		    adaption128k(2),
    		    adaption56kmsb(3),
    		    adaption56klsb(4)
    		}
        ACCESS	read-only
        STATUS	mandatory
        DESCRIPTION
                "Indicates the current B Channel Rate Adaption in use. This attribute
                is only relevant when this Synchronous device driver is performing
                as an ISDN B channel over a BRI interface in leased line or dial-up
                mode. This attribute indicates the speed of this B-channel. It also
                specifies their bit positions for the case of 56K selections."
        ::= { wfSyncEntry 108 }

    wfSyncWanType OBJECT-TYPE
        SYNTAX	INTEGER {
    		    synchronous(1),
    		    asynchronous(2),
                    pasynchronous(3)
    		}
        ACCESS	read-write
        STATUS	mandatory
        DESCRIPTION
                "This attribute indicates whether this port should be
                 configured as a SYNCHRONOUS or UART/ASYNCHRONOUS interface."
        DEFVAL	{ synchronous }
        ::= { wfSyncEntry 109 }

    wfSyncAsyncBaudRate OBJECT-TYPE
        SYNTAX	INTEGER {
                        baudrate1200b(1200),
                        baudrate2400b(2400),
                        baudrate4800b(4800),
                        baudrate7200b(7200),
                        baudrate9600b(9600),
                        baudrate12000b(12000),
                        baudrate14400b(14400),
                        baudrate19200b(19200),
                        baudrate28800b(28800),
                        baudrate38k(38400),
                        baudrate56k(57600),
                        baudrate64k(64000),
                        baudrate76k(76800),
                        baudrate96k(96000),
                        baudrate115k(115200)
                        }
        ACCESS	read-write
        STATUS	mandatory
        DESCRIPTION
                "Indicates the baud rate of the Tx/Rx character stream.
                 This value should always be >= than speed at which the
                 modems connect, but is independent of that speed.

                 For instance, for V34 modems, the maximum modular
                 connection speed is 28800 kbps. If your modems can
                 do V.42 bis or MNP 5 data compression, with high
                 (4 to 1) compression ratios you could fill a 115Kbps
                  pipe."
        DEFVAL	{ baudrate9600b }
        ::= { wfSyncEntry 110 }

    wfSyncCfgAsyncCmndMaxIdles OBJECT-TYPE
        SYNTAX	INTEGER(1..500)
        ACCESS	read-write
        STATUS	mandatory
        DESCRIPTION
                "Maximum number of idles we'll receive (in Command Mode)
                 between ASYNC frames. Values other than zero over-ride the
                 router selected values. A value of zero has a special
                 meaning. Zero causes router based defaults to be used.
                 This attribute is used to delineate frames when the QUICC
                 is configured for UART/ASYNCHRONOUS mode."
        ::= { wfSyncEntry 111 }

    wfSyncAsyncCmndMaxIdles OBJECT-TYPE
        SYNTAX	INTEGER
        ACCESS	read-only
        STATUS	mandatory
        DESCRIPTION
                "Maximum number of idles we'll receive (in Command Mode)
                 (i.e. when the modems have not yet connected & entered
                 data state), before closing the ASYNC frame. This value
                 is used to delineate frames when receiving data when the
                 SYNC port is configured for UART/ASYNCHRONOUS mode."
        ::= { wfSyncEntry 112 }

    wfSyncCfgAsyncDataMaxIdles OBJECT-TYPE
        SYNTAX	INTEGER(1..500)
        ACCESS	read-write
        STATUS	mandatory
        DESCRIPTION
                "Maximum number of idles we'll receive (in Data Mode)
                 between ASYNC frames. Values other than zero over-ride the
                 router selected values. A value of zero has a special
                 meaning. Zero causes router based defaults to be used.
                 This attribute is used to delineate frames when the QUICC
                 is configured for UART/ASYNCHRONOUS mode."
        ::= { wfSyncEntry 113 }

    wfSyncAsyncDataMaxIdles OBJECT-TYPE
        SYNTAX	INTEGER
        ACCESS	read-only
        STATUS	mandatory
        DESCRIPTION
                "Maximum number of idles we'll receive (in Command Mode)
                 (i.e. when the modems have connected & entered data state),
                 before closing the ASYNC frame. This value is used to
                 delineate frames when receiving data when the SYNC port is
                 configured for UART/ASYNCHRONOUS mode."
        ::= { wfSyncEntry 114 }

    wfSyncFramesAbortTx OBJECT-TYPE
        SYNTAX	Counter
        ACCESS	read-only
        STATUS	mandatory
        DESCRIPTION
                "Number of frames where CTS was lost during transmission."
        ::= { wfSyncEntry 115 }

    wfSyncPasyncParityType OBJECT-TYPE
        SYNTAX  INTEGER {
                    odd(1),
                    even(2),
                    high(3),
                    low(4),
                    none(5)
                }
        ACCESS  read-write
        STATUS  mandatory
        DESCRIPTION
                "Type of parity chosen for Polled Async"
        DEFVAL  { even }
        ::= { wfSyncEntry 116 }

    wfSyncPasyncCharacterLength OBJECT-TYPE
        SYNTAX  INTEGER {
                    five(5),
                    six(6),
                    seven(7),
                    eight(8)
                }
        ACCESS  read-write
        STATUS  mandatory
        DESCRIPTION
                "Number of data bits  chosen for Polled Async"
        DEFVAL  { eight }
        ::= { wfSyncEntry 117 }

    wfSyncPasyncStopLength OBJECT-TYPE
        SYNTAX  INTEGER {
                    one(1),
                    two(2)
                }
        ACCESS  read-write
        STATUS  mandatory
        DESCRIPTION
                "Number of stop bits  chosen for Polled Async"
        DEFVAL  { two }
        ::= { wfSyncEntry 118 }

    wfSyncPasyncBaudRate OBJECT-TYPE
        SYNTAX  INTEGER {
                        baudrate150b(150),
                        baudrate300b(300),
                        baudrate600b(600),
                        baudrate1200b(1200),
                        baudrate2400b(2400),
                        baudrate4800b(4800),
                        baudrate7200b(7200),
                        baudrate9600b(9600),
                        baudrate12000b(12000),
                        baudrate14400b(14400),
                        baudrate19200b(19200),
                        baudrate28800b(28800),
                        baudrate38k(38400),
                        baudrate56k(57600),
                        baudrate64k(64000),
                        baudrate76k(76800),
                        baudrate96k(96000),
                        baudrate115k(115200)
                        }
        ACCESS  read-write
        STATUS  mandatory
        DESCRIPTION
                "Indicates the baud rate of the Tx/Rx character stream.
                 This value should always be >= than speed at which the
                 modems connect, but is independent of that speed.

                 For instance, for V34 modems, the maximum modular
                 connection speed is 28800 kbps. If your modems can
                 do V.42 bis or MNP 5 data compression, with high
                 (4 to 1) compression ratios you could fill a 115Kbps
                  pipe."
        DEFVAL  { baudrate600b }
        ::= { wfSyncEntry 119 }

    wfSyncLocalConnectionState OBJECT-TYPE
        SYNTAX  INTEGER {
                    up(1),
                    down(2),
                    unknown(3)
                }
        ACCESS  read-only
        STATUS  mandatory
        DESCRIPTION
                "The state of the cable at the router end."
        DEFVAL  { unknown }
        ::= { wfSyncEntry 120 }

    wfSyncRemoteConnectionState OBJECT-TYPE
        SYNTAX  INTEGER {
                    up(1),
                    down(2),
                    devicestreaming(3),
                    unknown(4)
                }
        ACCESS  read-only
        STATUS  mandatory
        DESCRIPTION
                "The state of the cable at the device end."
        DEFVAL  { unknown }
        ::= { wfSyncEntry 121 }

    wfSyncTimeSlotAssignment OBJECT-TYPE
        SYNTAX  DisplayString
        ACCESS  read-only
        STATUS  mandatory
        DESCRIPTION
                "Lists the time-slots which constitute this channel. Read only
                 attribute that contains a list of time-slots from 1 to 24
                 used by the channel assigned to the FT1 card. It contains
                 a list of the timeslots from 1 to 32 for the G.703 card."
        ::= { wfSyncEntry 122 }

    wfSyncEiaStatus OBJECT-TYPE
        SYNTAX  INTEGER {
                    txd(1),
                    rxd(2),
                    rts(4),
                    cts(8),
                    dsr(16),
                    dcd(32),
                    txc(64),
                    rxc(128),
                    dtr(256),
                    txdToggled(65536),
                    rxdToggled(131072),
                    rtsToggled(262144),
                    ctsToggled(524288),
                    dsrToggled(1048576),
                    dcdToggled(2097152),
                    txcToggled(4194304),
                    rxcToggled(8388608),
                    dtrToggled(16777216)
                }
        ACCESS  read-only
        STATUS  mandatory
        DESCRIPTION
                "The state of the EIA signals at the router interface.
                 The signals are designated as bits in this entry. If the
                 signal is asserted, it is marked as a 1. If not asserted,
                 it is marked as a 0. The state of each signal will be updated
                 every second. Bits 0-15 are reserved for actual signal state.
                 Bits 16-31 are reserved for indicating toggling of the signal.
                 Toggling signals are indicated as a 1. Signals not toggling
                 are indicated with a 0.

                 The following signals are defined and monitored:

                 The bit definition as as follows with bit #0 being the LSB.
                 * signal status - bits 0-15 *
                 bit 0 = TXD transmit data
                     1 = RXD receive data
                     2 = RTS request to send
                     3 = CTS clear to send
                     4 = DSR data set ready
                     5 = DCD data carrier detect
                     6 = TXC transmit clock
                     7 = RXC receive clock
                     8 = DTR data terminal ready.
                 * signal toggle status bits 16-31 *
                 bit 16 = TXD transmit data
                     17 = RXD receive data
                     18 = RTS request to send
                     19 = CTS clear to send
                     20 = DSR data set ready
                     21 = DCD data carrier detect
                     22 = TXC transmit clock
                     23 = RXC receive clock
                     24 = DTR data terminal ready."
        ::= { wfSyncEntry 123 }

    wfSyncEiaStatusReset OBJECT-TYPE
        SYNTAX  INTEGER {
                    reset(1),
                    noaction(21)
                }
        ACCESS  read-write
        STATUS  mandatory
        DESCRIPTION
                "Reset The EIA status for the EIA signals in wfSyncEiaStatus.
                 This is particularly useful for clearing the toggle status. "
        DEFVAL  { noaction }
        ::= { wfSyncEntry 124 }

    wfSyncUcastMap OBJECT-TYPE
        SYNTAX  INTEGER {
                enabled(1),
                disabled(2)
        }
        ACCESS  read-write
        STATUS  mandatory
        DESCRIPTION
                "Used to map ifEntry.ifInUcastPkts to wfSyncRxFrames and
                 ifEntry.ifOutUcastPkts to wfSyncTxFrames."
        DEFVAL  { enabled }
        ::= { wfSyncEntry 125 }

	wfSyncAsyncCfgMaxIdleTimer OBJECT-TYPE
		SYNTAX  INTEGER {	
                baudrate(1),
                threechars(2)
		}
		ACCESS  read-write
        STATUS  mandatory
        DESCRIPTION
                "Determines if Async Max Idle Timer should be based on the
				 baudrate or on the time needed to receive three characters."
		DEFVAL  { baudrate }
        ::= { wfSyncEntry 126 }

		

    END  -- Wellfleet-SYNC-MIB
