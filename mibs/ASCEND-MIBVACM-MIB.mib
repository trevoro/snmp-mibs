--			Ascend mibvacm MIB
--
--			Ascend Communications, Inc
--			1275 Harbor Bay Pkwy
--			Alameda, CA 94502
--			+1 510 769 6001
--			info@ascend.com
--
-- Copyright (c) 1993-1999 Ascend Communications, Inc.
-- All rights reserved.
--
-- Do not edit this file directly.
-- It is generated automatically by mibgen for use with
-- TAOS version 10.0.1 or newer.
--

ASCEND-MIBVACM-MIB DEFINITIONS ::= BEGIN

    IMPORTS

        configuration
            FROM ASCEND-MIB
	IpAddress
	    FROM RFC1155-SMI
	OBJECT-TYPE
	    FROM RFC-1212;

	-- If any of the MIB compilers have problems with the DisplayString
	-- or PhysAddress, uncomment the next two lines.

    DisplayString	::=	OCTET STRING
    -- PhysAddress	::=	OCTET STRING

    mibvacmSecurityGroupProfile  OBJECT IDENTIFIER ::= { configuration 135}
    mibvacmViewTreeProfile  OBJECT IDENTIFIER ::= { configuration 137}
    mibvacmAccessProfile  OBJECT IDENTIFIER ::= { configuration 136}

	-- The mibvacmSecurityGroupProfile table
	--
	-- This table contains parameters for the mibvacmSecurityGroupProfile profile
	--

    mibvacmSecurityGroupProfileTable	OBJECT-TYPE
	SYNTAX		SEQUENCE OF MibvacmSecurityGroupProfileEntry
	ACCESS		not-accessible
	STATUS		mandatory
	DESCRIPTION	"A list of mibvacmSecurityGroupProfile profile entries."
	::= { mibvacmSecurityGroupProfile 1 }

    mibvacmSecurityGroupProfileEntry	OBJECT-TYPE
	SYNTAX		MibvacmSecurityGroupProfileEntry
	ACCESS		not-accessible
	STATUS		mandatory
	DESCRIPTION	"A mibvacmSecurityGroupProfile entry containing objects that
			 maps to the parameters of mibvacmSecurityGroupProfile profile."
	INDEX		{ vacmSecurityGroupProfile-SecurityProperties-SecurityModel, vacmSecurityGroupProfile-SecurityProperties-SecurityName }
	::= { mibvacmSecurityGroupProfileTable 1 }

    MibvacmSecurityGroupProfileEntry ::=
	SEQUENCE {
	    vacmSecurityGroupProfile-SecurityProperties-SecurityModel
		INTEGER,
	    vacmSecurityGroupProfile-SecurityProperties-SecurityName
		OCTET STRING,
	    vacmSecurityGroupProfile-Active
		INTEGER,
	    vacmSecurityGroupProfile-GroupName
		OCTET STRING,
	    vacmSecurityGroupProfile-Action-o
		INTEGER
	}

    vacmSecurityGroupProfile-SecurityProperties-SecurityModel	OBJECT-TYPE
	SYNTAX	INTEGER
	ACCESS	read-only
	STATUS	mandatory
	DESCRIPTION	"Security Model by which the Security Name referenced by this entry is provided."
	::= { mibvacmSecurityGroupProfileEntry 1 }

    vacmSecurityGroupProfile-SecurityProperties-SecurityName	OBJECT-TYPE
	SYNTAX	OCTET STRING
	ACCESS	read-only
	STATUS	mandatory
	DESCRIPTION	"Security Name for the principal that is mapped by this entry to a group name."
	::= { mibvacmSecurityGroupProfileEntry 2 }

    vacmSecurityGroupProfile-Active	OBJECT-TYPE
	SYNTAX	INTEGER {
		    no (1),
		    yes (2)
		}
	ACCESS	read-write
	STATUS	mandatory
	DESCRIPTION	"TRUE if this profile is enabled for message exchange."
	::= { mibvacmSecurityGroupProfileEntry 3 }

    vacmSecurityGroupProfile-GroupName	OBJECT-TYPE
	SYNTAX	OCTET STRING
	ACCESS	read-write
	STATUS	mandatory
	DESCRIPTION	"Name of the group to which this entry (security-model + security-name combination)."
	::= { mibvacmSecurityGroupProfileEntry 4 }

    vacmSecurityGroupProfile-Action-o	OBJECT-TYPE
	SYNTAX	INTEGER {
		    noAction (1),
		    createProfile (2),
		    deleteProfile (3)
		}
	ACCESS	read-write
	STATUS	mandatory
	DESCRIPTION	""
	::= { mibvacmSecurityGroupProfileEntry 5 }


	-- The mibvacmViewTreeProfile table
	--
	-- This table contains parameters for the mibvacmViewTreeProfile profile
	--

    mibvacmViewTreeProfileTable	OBJECT-TYPE
	SYNTAX		SEQUENCE OF MibvacmViewTreeProfileEntry
	ACCESS		not-accessible
	STATUS		mandatory
	DESCRIPTION	"A list of mibvacmViewTreeProfile profile entries."
	::= { mibvacmViewTreeProfile 1 }

    mibvacmViewTreeProfileEntry	OBJECT-TYPE
	SYNTAX		MibvacmViewTreeProfileEntry
	ACCESS		not-accessible
	STATUS		mandatory
	DESCRIPTION	"A mibvacmViewTreeProfile entry containing objects that
			 maps to the parameters of mibvacmViewTreeProfile profile."
	INDEX		{ vacmViewTreeProfile-TreeProperties-ViewName, vacmViewTreeProfile-TreeProperties-ViewTreeOid }
	::= { mibvacmViewTreeProfileTable 1 }

    MibvacmViewTreeProfileEntry ::=
	SEQUENCE {
	    vacmViewTreeProfile-TreeProperties-ViewName
		OCTET STRING,
	    vacmViewTreeProfile-TreeProperties-ViewTreeOid
		DisplayString,
	    vacmViewTreeProfile-Active
		INTEGER,
	    vacmViewTreeProfile-TreeOidMask
		DisplayString,
	    vacmViewTreeProfile-TreeType
		INTEGER,
	    vacmViewTreeProfile-Action-o
		INTEGER
	}

    vacmViewTreeProfile-TreeProperties-ViewName	OBJECT-TYPE
	SYNTAX	OCTET STRING
	ACCESS	read-only
	STATUS	mandatory
	DESCRIPTION	"This field(view-name) acts as the link between vacm-view-tree profile and vacm-acess profile. Any arbitary, human readable string."
	::= { mibvacmViewTreeProfileEntry 1 }

    vacmViewTreeProfile-TreeProperties-ViewTreeOid	OBJECT-TYPE
	SYNTAX	DisplayString
	ACCESS	read-only
	STATUS	mandatory
	DESCRIPTION	"OID that represents the sub tree for allowing or disallowing access."
	::= { mibvacmViewTreeProfileEntry 2 }

    vacmViewTreeProfile-Active	OBJECT-TYPE
	SYNTAX	INTEGER {
		    no (1),
		    yes (2)
		}
	ACCESS	read-write
	STATUS	mandatory
	DESCRIPTION	"TRUE if this profile is enabled for message exchange."
	::= { mibvacmViewTreeProfileEntry 3 }

    vacmViewTreeProfile-TreeOidMask	OBJECT-TYPE
	SYNTAX	DisplayString
	ACCESS	read-write
	STATUS	mandatory
	DESCRIPTION	"Bitmask that would decide if a given sub identifier of the tree OID is to be matched or not."
	::= { mibvacmViewTreeProfileEntry 4 }

    vacmViewTreeProfile-TreeType	OBJECT-TYPE
	SYNTAX	INTEGER {
		    included (2),
		    excluded (3)
		}
	ACCESS	read-write
	STATUS	mandatory
	DESCRIPTION	"Access to this tree would be allowed if this is an 'Including' tree and disallowed if this is an 'Excluding' tree."
	::= { mibvacmViewTreeProfileEntry 5 }

    vacmViewTreeProfile-Action-o	OBJECT-TYPE
	SYNTAX	INTEGER {
		    noAction (1),
		    createProfile (2),
		    deleteProfile (3)
		}
	ACCESS	read-write
	STATUS	mandatory
	DESCRIPTION	""
	::= { mibvacmViewTreeProfileEntry 6 }


	-- The mibvacmAccessProfile table
	--
	-- This table contains parameters for the mibvacmAccessProfile profile
	--

    mibvacmAccessProfileTable	OBJECT-TYPE
	SYNTAX		SEQUENCE OF MibvacmAccessProfileEntry
	ACCESS		not-accessible
	STATUS		mandatory
	DESCRIPTION	"A list of mibvacmAccessProfile profile entries."
	::= { mibvacmAccessProfile 1 }

    mibvacmAccessProfileEntry	OBJECT-TYPE
	SYNTAX		MibvacmAccessProfileEntry
	ACCESS		not-accessible
	STATUS		mandatory
	DESCRIPTION	"A mibvacmAccessProfile entry containing objects that
			 maps to the parameters of mibvacmAccessProfile profile."
	INDEX		{ vacmAccessProfile-AccessProperties-GroupName, vacmAccessProfile-AccessProperties-ContextPrefix, vacmAccessProfile-AccessProperties-SecurityModel, vacmAccessProfile-AccessProperties-SecurityLevel }
	::= { mibvacmAccessProfileTable 1 }

    MibvacmAccessProfileEntry ::=
	SEQUENCE {
	    vacmAccessProfile-AccessProperties-GroupName
		OCTET STRING,
	    vacmAccessProfile-AccessProperties-ContextPrefix
		OCTET STRING,
	    vacmAccessProfile-AccessProperties-SecurityModel
		INTEGER,
	    vacmAccessProfile-AccessProperties-SecurityLevel
		INTEGER,
	    vacmAccessProfile-Active
		INTEGER,
	    vacmAccessProfile-MatchMethod
		INTEGER,
	    vacmAccessProfile-ReadViewName
		OCTET STRING,
	    vacmAccessProfile-WriteViewName
		OCTET STRING,
	    vacmAccessProfile-NotifyViewName
		OCTET STRING,
	    vacmAccessProfile-Action-o
		INTEGER
	}

    vacmAccessProfile-AccessProperties-GroupName	OBJECT-TYPE
	SYNTAX	OCTET STRING
	ACCESS	read-only
	STATUS	mandatory
	DESCRIPTION	"Security group name that was specified in Security Group profile."
	::= { mibvacmAccessProfileEntry 1 }

    vacmAccessProfile-AccessProperties-ContextPrefix	OBJECT-TYPE
	SYNTAX	OCTET STRING
	ACCESS	read-only
	STATUS	mandatory
	DESCRIPTION	"Context Name that would be matched with the context name present in incoming/outgoing PDU"
	::= { mibvacmAccessProfileEntry 2 }

    vacmAccessProfile-AccessProperties-SecurityModel	OBJECT-TYPE
	SYNTAX	INTEGER
	ACCESS	read-only
	STATUS	mandatory
	DESCRIPTION	"Security model that would be matched with the model being used in incoming/outgoing PDU"
	::= { mibvacmAccessProfileEntry 3 }

    vacmAccessProfile-AccessProperties-SecurityLevel	OBJECT-TYPE
	SYNTAX	INTEGER
	ACCESS	read-only
	STATUS	mandatory
	DESCRIPTION	"Security Level being that would be matched with the level being used in incoming/outgoing PDU"
	::= { mibvacmAccessProfileEntry 4 }

    vacmAccessProfile-Active	OBJECT-TYPE
	SYNTAX	INTEGER {
		    no (1),
		    yes (2)
		}
	ACCESS	read-write
	STATUS	mandatory
	DESCRIPTION	"TRUE if this profile is enabled for message exchange."
	::= { mibvacmAccessProfileEntry 5 }

    vacmAccessProfile-MatchMethod	OBJECT-TYPE
	SYNTAX	INTEGER {
		    exactMatch (2),
		    prefixMatch (3)
		}
	ACCESS	read-write
	STATUS	mandatory
	DESCRIPTION	"Deterines if context name would be matched as a prefix or as a absolute value."
	::= { mibvacmAccessProfileEntry 6 }

    vacmAccessProfile-ReadViewName	OBJECT-TYPE
	SYNTAX	OCTET STRING
	ACCESS	read-write
	STATUS	mandatory
	DESCRIPTION	"Read access for the view given by this field is granted for the requests that match with the 'access-properties'"
	::= { mibvacmAccessProfileEntry 7 }

    vacmAccessProfile-WriteViewName	OBJECT-TYPE
	SYNTAX	OCTET STRING
	ACCESS	read-write
	STATUS	mandatory
	DESCRIPTION	"Write access for the view given by this field is granted for the requests that match with the 'access-properties'"
	::= { mibvacmAccessProfileEntry 8 }

    vacmAccessProfile-NotifyViewName	OBJECT-TYPE
	SYNTAX	OCTET STRING
	ACCESS	read-write
	STATUS	mandatory
	DESCRIPTION	"sending Notify messages is allowed for the view given by this field for the outgoing PDUs that match with the 'access-properties'"
	::= { mibvacmAccessProfileEntry 9 }

    vacmAccessProfile-Action-o	OBJECT-TYPE
	SYNTAX	INTEGER {
		    noAction (1),
		    createProfile (2),
		    deleteProfile (3)
		}
	ACCESS	read-write
	STATUS	mandatory
	DESCRIPTION	""
	::= { mibvacmAccessProfileEntry 10 }

END
