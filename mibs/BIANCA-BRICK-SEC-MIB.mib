-- This file is corresponding to Release 6.1.2.100 from 2001/09/26 00:00:00
-- (C)opyright 1991-2000 BinTec Communications AG, All Rights Reserved
--  $RCSfile: mibsec,v $ 
-- $Revision: 1.23 $ 

BIANCA-BRICK-SEC-MIB DEFINITIONS ::= BEGIN
 
        IMPORTS
		DisplayString FROM SNMPv2-TC
            Counter
                FROM RFC1155-SMI
 
            OBJECT-TYPE
                FROM RFC-1212;

    org		OBJECT IDENTIFIER ::= { iso 3 }
    dod		OBJECT IDENTIFIER ::= { org 6 }
    internet	OBJECT IDENTIFIER ::= { dod 1 }
    private	OBJECT IDENTIFIER ::= { internet 4 }
    enterprises	OBJECT IDENTIFIER ::= { private 1 }
    bintec 	OBJECT IDENTIFIER ::= { enterprises 272 }
    bintecsec 	OBJECT IDENTIFIER 
		::= { bintec 254 }
	biboAdmAdminCommunity OBJECT-TYPE
	    SYNTAX  DisplayString (SIZE (0..255))
	    ACCESS  read-write
	    STATUS  mandatory

	    DESCRIPTION
		"The Community name used for admin access"
	::= { bintecsec 1 }

	biboAdmReadCommunity OBJECT-TYPE
	    SYNTAX  DisplayString (SIZE (0..255))
	    ACCESS  read-write
	    STATUS  mandatory

	    DESCRIPTION
		"The Community name used for read-only access."
	::= { bintecsec 2 }

	biboAdmWriteCommunity OBJECT-TYPE
	    SYNTAX  DisplayString (SIZE (0..255))
	    ACCESS  read-write
	    STATUS  mandatory

	    DESCRIPTION
		"The Community name used for read-write access."
	::= { bintecsec 3 }

	biboAdmLicenseTable OBJECT-TYPE
	    SYNTAX  SEQUENCE OF BiboAdmLicenseEntry
	    ACCESS  not-accessible
	    STATUS  mandatory
	    DESCRIPTION
		"This table contains the licenses, purchased for this
		 BIANCA/BRICK. Each entry describes a license. Each
		 license can enable one or more features of the
		 BIANCA/BRICK, when the activation key is correct.
		 Please Note, that a license is only valid for the
		 BIANCA/BRICK it has been purchased for."
	::= { bintecsec 4 }

	biboAdmLicenseEntry OBJECT-TYPE
	    SYNTAX  BiboAdmLicenseEntry
	    ACCESS  not-accessible
	    STATUS  mandatory
	    DESCRIPTION
		""
	    INDEX   { biboAdmLicenseKey }
	::= { biboAdmLicenseTable 1 }

	BiboAdmLicenseEntry ::=
	    SEQUENCE {
		biboAdmLicenseSerialNumber		INTEGER,
		biboAdmLicenseMask			INTEGER,
		biboAdmLicenseKey			DisplayString,
		biboAdmLicenseState			INTEGER,

		biboAdmLicenseSerialId			DisplayString,
		biboAdmLicenseHwSerial			DisplayString,
		biboAdmLicenseLicType			INTEGER
	    }

	biboAdmLicenseSerialNumber OBJECT-TYPE
	    SYNTAX  INTEGER (0..999999) 
	    ACCESS  read-write
	    STATUS  mandatory

	    DESCRIPTION
		"This object specifies the serial number of the license in 
		 case of a numerical license (together with 'Mask' and 'Key')."
	::= { biboAdmLicenseEntry 1 }

	biboAdmLicenseMask OBJECT-TYPE
	    SYNTAX  INTEGER (0..65535)
	    ACCESS  read-write
	    STATUS  mandatory

	    DESCRIPTION
		"The LicenseMask is a bitfield, that specifies the different
		 features enabled by the license. (only used on a numerical 
		 license)."
	::= { biboAdmLicenseEntry 2 }

	biboAdmLicenseKey OBJECT-TYPE
	    SYNTAX  DisplayString 
	    ACCESS  read-write
	    STATUS  mandatory

	    DESCRIPTION
		"This object contains the activation key. A license is only
		 valid, if the activation key is correct."
	::= { biboAdmLicenseEntry 3 }

	biboAdmLicenseState OBJECT-TYPE
	    SYNTAX  INTEGER { ok(1), not-ok(2), delete(3), internal-ok(4), 
			      internal-erase(5), not-supported(6) }
	    ACCESS  read-write
	    STATUS  mandatory

	    DESCRIPTION
		"To delete a license from the system, this object has
		 to be set to delete. In case of an 'internal-ok' license the
		 license can be erased from the modules EEPROM, if it is set
		 to 'internal-erase'.
		 The state will be 'not-supported' if a license refers to 
		 a feature which is not supported by the image loaded.
		 With 'delete' it is only deleted from the main board 
		 flash memory."
	::= { biboAdmLicenseEntry 4 }

	biboAdmLicenseSerialId OBJECT-TYPE
	    SYNTAX  DisplayString 
	    ACCESS  read-write
	    STATUS  mandatory

	    DESCRIPTION
		"This object specifies the serial id string of the license in
		 case of string license (together with 'Key')."
	::= { biboAdmLicenseEntry 5 }

	biboAdmLicenseHwSerial OBJECT-TYPE
	    SYNTAX  DisplayString 
	    ACCESS  read-only
	    STATUS  mandatory

	    DESCRIPTION
		"This object contains the device Hardware serial number
		 for which the license is purchased for."
	::= { biboAdmLicenseEntry 6 }

	biboAdmLicenseLicType OBJECT-TYPE
	    SYNTAX INTEGER {
		ip(1), capi(2), bridge(3), x25(4), ipx(5), stac(6),
		frame-relay(7), tapi(8), ospf(9), extended-lan(10),
		tunneling(11), taf(12), extended-wan(13), leased-line(14),
		ipsec(33),
		ethernet(128), bri(129), g703(130), pri(131), modem(132)
	    } 
	    ACCESS  read-only
	    STATUS  mandatory

	    DESCRIPTION
		"The type of licenseable feature."
	::= { biboAdmLicenseEntry 7 }



	biboAdmRadiusSecret OBJECT-TYPE
	    SYNTAX  DisplayString (SIZE (0..255))
	    ACCESS  read-write
	    STATUS  mandatory

	    DESCRIPTION
		"The shared secret for RADIUS access."
	::= { bintecsec 5 }

	biboAdmHttpPassword OBJECT-TYPE
	    SYNTAX  DisplayString (SIZE (0..255))
	    ACCESS  read-write
	    STATUS  mandatory

	    DESCRIPTION
		"The password for HTTP access."
	::= { bintecsec 6 }


        biboAdmLoginTable OBJECT-TYPE
            SYNTAX  SEQUENCE OF BiboAdmLoginEntry
            ACCESS  not-accessible
            STATUS  mandatory
            DESCRIPTION
                 "The biboAdmLoginTable defines additional users and
                  their passwords, and the commnd to be executed
		  at login."
        ::= { bintecsec 7 }
 
        biboAdmLoginEntry OBJECT-TYPE
            SYNTAX  BiboAdmLoginEntry
            ACCESS  not-accessible
            STATUS  mandatory
            DESCRIPTION
                ""
            INDEX { biboAdmLoginUser }
        ::= { biboAdmLoginTable 1 }
 
        BiboAdmLoginEntry ::=
            SEQUENCE {
                biboAdmLoginUser                        DisplayString,
                biboAdmLoginPassword                    DisplayString,
                biboAdmLoginCommand                     DisplayString,
                biboAdmLoginState                       INTEGER
            }
 
        biboAdmLoginUser OBJECT-TYPE
            SYNTAX  DisplayString
            ACCESS  read-write
            STATUS  mandatory
 
            DESCRIPTION
                "This is the login name."
        ::= { biboAdmLoginEntry 1 }
 
        biboAdmLoginPassword OBJECT-TYPE
            SYNTAX  DisplayString
            ACCESS  read-write
            STATUS  mandatory
 
            DESCRIPTION
                "This is the user password."
        ::= { biboAdmLoginEntry 2 }

        biboAdmLoginCommand OBJECT-TYPE
            SYNTAX  DisplayString
            ACCESS  read-write
            STATUS  mandatory
 
            DESCRIPTION
                "This is the command, which is started at login, 
		 e.g. sh, telnet. All external commands are possible."
        ::= { biboAdmLoginEntry 3 }
 
        biboAdmLoginState OBJECT-TYPE
            SYNTAX  INTEGER { valid(1), delete(2), invalid(3) }
            ACCESS  read-write
            STATUS  mandatory
 
            DESCRIPTION
                "The variable is used to disable or discard the entry."
        ::= { biboAdmLoginEntry 4 }
 
	biboAdmPublicKey OBJECT-TYPE
	    SYNTAX  OCTET STRING
	    ACCESS  read-only
	    STATUS  mandatory

	    DESCRIPTION
		"Generated public key for TAF client access"
	::= { bintecsec 10 }

	biboAdmPrivateKey OBJECT-TYPE
	    SYNTAX  OCTET STRING
	    ACCESS  not-accessible
	    STATUS  mandatory

	    DESCRIPTION
		""
	::= { bintecsec 11 }

	biboAdmActMonPassword OBJECT-TYPE
	    SYNTAX  DisplayString (SIZE (0..255))
	    ACCESS  read-write
	    STATUS  mandatory

	    DESCRIPTION
		"The password for Activity Monitor access."
	::= { bintecsec 12 }

END
