-- 
-- Copyright 1999 by Fore Systems, Inc. 
-- Converted to SMIv2 rfc 2578,2579,2580 - STD 58
--
-- Copyright 1996 by Fore Systems, Inc.



-- This MIB defines TCM related variables for Non ASX1000/ASX1200
-- platforms. FORE-cecplus.mib defines both ECP and ESI (TCM) related
-- variables for ASX-1000 platform (Raven).

Fore-TIMING-MIB DEFINITIONS ::= BEGIN

IMPORTS
	OBJECT-TYPE,
	MODULE-IDENTITY,
	NOTIFICATION-TYPE,
	Integer32				FROM SNMPv2-SMI
	TimeInterval,
	DisplayString				FROM SNMPv2-TC
	hardware 				FROM Fore-Common-MIB
	trapLogIndex				FROM Fore-TrapLog-MIB;

-----------
--  TCM Definitions
-----------

tcmGroup			           MODULE-IDENTITY
          LAST-UPDATED         "9911050000Z"
          ORGANIZATION         "FORE"
          CONTACT-INFO         
               "      Postal:   FORE Systems Inc.
                                 1000 FORE Drive
                                 Warrendale, PA 15086-7502
                       Tel:      +1 724 742 6900
                       Email:    nm_mibs@fore.com
                       Web:      http://www.fore.com"
          DESCRIPTION
           "write something interesting here"
    ::= { hardware 11 }

--
--  TCM Timing Mode
--
TcmTimingMode ::= INTEGER {
			modeFreeRun(1),
			modeExternal(2),
			modeLine(3)
		    }

--
--  TCM Reference Sources
--
TcmReferenceSource ::= INTEGER {
			freerun(1),
			bits1(2),
			bits2(3),
			switchPrimary(4),
			switchSecondary(5)
			}

--
--  TCM Derived DS1/E1 Reference Sources for Transmitting on Bits Interface.
--

DerivedReferenceSource ::= INTEGER {
	                   switchPrimary(4),
                           switchSecondary(5)
                          }

------------
--  TCM hardware definitions
------------

tcmTable  OBJECT-TYPE
	SYNTAX	SEQUENCE OF TcmEntry
	MAX-ACCESS	not-accessible
	STATUS	current
	DESCRIPTION
     		"This table contains the hardware information for the
		Timing Control Module (TCM) s."
	::= { tcmGroup 1 }

tcmEntry	OBJECT-TYPE
	SYNTAX	TcmEntry
   	MAX-ACCESS	not-accessible
	STATUS	current
	DESCRIPTION
		"This table entry contains the hardware information for
		a single Timing Control Module (TCM) ."
	INDEX	{ tcmIndex }
	::= { tcmTable 1 }

TcmEntry ::= SEQUENCE {
		tcmIndex		Integer32,
		tcmHwType		INTEGER,
		tcmHwVersion		Integer32,
		tcmPllStatus   		INTEGER,
		tcmOperationStatus      INTEGER,
		tcmCurrentTimingRef	INTEGER,
		tcmRequestedTimingMode	TcmTimingMode,
		tcmOperatingTimingMode	TcmTimingMode,
		tcmModeFailover		INTEGER,
		tcmPrimaryRefSource     TcmReferenceSource,
		tcmSecondaryRefSource   TcmReferenceSource,
		tcmBitsFramingFormat	INTEGER,
		tcmBitsCodingFormat	INTEGER,
		tcmBitsOutputLevel	INTEGER,
		tcmRevertiveSwitching	INTEGER,
		tcmRevertiveDelay	TimeInterval,
		tcmFailoverDelay	TimeInterval
	}

tcmIndex    OBJECT-TYPE
	SYNTAX	Integer32
   	MAX-ACCESS	not-accessible
	STATUS	current
	DESCRIPTION
		"This is the index for this Timing Control Module (TCM)
		."
	::=  { tcmEntry 1 }

tcmHwType   OBJECT-TYPE
	SYNTAX	INTEGER {
			tcmDs1Stratum3E(1),
			tcmE1Stratum3E(2)
		}
   	MAX-ACCESS	read-only
	STATUS	current
	DESCRIPTION
		"This is the  type for this Timing Control Module (TCM) ."
	::= { tcmEntry 2 }

tcmHwVersion  OBJECT-TYPE
	SYNTAX	Integer32
   	MAX-ACCESS	read-only
	STATUS	current
	DESCRIPTION
		"This is the  version for this Timing Control Module (TCM) ."
	::= { tcmEntry 3 }

tcmPllStatus  OBJECT-TYPE
	SYNTAX	INTEGER {
			pllFreeRun(1),
			pllInitRefQual(2),
			pllLocked(3),
			pllAcquire(4),
			pllHoldover(5),
			pllRefQualFail(6),
			pllQualifyingRef(7)
		}
   	MAX-ACCESS	read-only
	STATUS	current
	DESCRIPTION
		"This is the  phase-locked loop (PLL) status for
		this Timing Control Module (TCM) ."
	::= { tcmEntry 4 }

tcmOperationStatus  OBJECT-TYPE
	SYNTAX	INTEGER {
			enabled(1),
			disabled(2)
		}
	MAX-ACCESS	read-only
	STATUS	current
	DESCRIPTION
		"This is the operation status of the clock output for
		this Timing Control Module (TCM). The status is enabled if
		the switch is configured to use TCM for timing and disabled
		otherwise."
	::= { tcmEntry 5 }

tcmCurrentTimingRef  OBJECT-TYPE
	SYNTAX 	INTEGER	{
			refLocal(1),
			refPrimary(2),
			refSecondary(3)
		}
	MAX-ACCESS	read-only
	STATUS	current
	DESCRIPTION
		"This is the current timing reference in use for this
		Timing Control Module (TCM) ."
	::= { tcmEntry 6 }

tcmRequestedTimingMode  OBJECT-TYPE
	SYNTAX 	TcmTimingMode
	MAX-ACCESS	read-write
	STATUS	current
	DESCRIPTION
		"This is the timing reference requested to be used for
		this Timing Control Module (TCM) ."
	::= { tcmEntry 7 }

tcmOperatingTimingMode	OBJECT-TYPE
        SYNTAX  TcmTimingMode
	MAX-ACCESS read-only
	STATUS	current
	DESCRIPTION
		"This is the operating timing mode, which can be different
		 from the requested timing mode if mode failover is enabled."
	::= { tcmEntry 8 }

tcmModeFailover	OBJECT-TYPE
	SYNTAX	INTEGER {
			enabled(1),
			disabled(2)
		}
	MAX-ACCESS	read-write
	STATUS	current
	DESCRIPTION
		"This is the modefailover that causes the Timing Control
		 Module (TCM) to automatically switch between timing modes
		 (for example external to line) if it is enabled."
	::= { tcmEntry 9 }

tcmPrimaryRefSource  OBJECT-TYPE
	SYNTAX  TcmReferenceSource
	MAX-ACCESS  read-only
	STATUS  current
	DESCRIPTION
		"This is the primary timing reference source for this
		Timing Control Module (TCM) ."
	::= { tcmEntry 10 }

tcmSecondaryRefSource  OBJECT-TYPE
	SYNTAX	TcmReferenceSource
	MAX-ACCESS	read-only
	STATUS  current
	DESCRIPTION
		"This is the secondary timing reference source for this
		Timing Control Module (TCM) ."
	::= { tcmEntry 11 }

tcmBitsFramingFormat  OBJECT-TYPE
	SYNTAX  INTEGER {
			d4(1),		-- DS1 interface
			esf(2),		-- DS1 interface
			mfas(3),        -- E1  interface
			mfascrc4(4),    -- E1  interface
                        fas(5),         -- E1  interface
                        fascrc4(6)      -- E1  interface
		}
	MAX-ACCESS  read-write
	STATUS	current
	DESCRIPTION
		"This is the framing format of the BITS interface for
		this Timing Control Module (TCM) ."
	::= { tcmEntry 12 }

tcmBitsCodingFormat  OBJECT-TYPE
	SYNTAX	INTEGER {
			ami(1),		-- DS1 interface
			b8zs(2),	-- DS1 interface
			hdb3(3)		-- E1  interface
		}
	MAX-ACCESS  read-write
	STATUS  current
	DESCRIPTION
		"This is the coding format of the BITS interface for
		this Timing Control Module (TCM) ."
	::= { tcmEntry 13 }

tcmBitsOutputLevel  OBJECT-TYPE
	SYNTAX	INTEGER {
			tcmDs1Level0-6(1),
			tcmDs1Level1-2(2),
			tcmDs1Level1-8(3),
			tcmDs1Level2-4(4),
			tcmDs1Level3-0(5)
		}
	MAX-ACCESS	read-write
	STATUS	current
	DESCRIPTION
		"This is the output level (dB) of the DS1 BITS interface
		for this Timing Control Module (TCM) ."
	::= { tcmEntry 14 }

tcmRevertiveSwitching  OBJECT-TYPE
	SYNTAX	INTEGER {
			enabled(1),
			disabled(2)
		}
	MAX-ACCESS	read-write
	STATUS	current
	DESCRIPTION
		"This is the status of the revertive switching for timing
		sources on this Timing Control Module (TCM) ."
	::= { tcmEntry 15 }

tcmRevertiveDelay  OBJECT-TYPE
	SYNTAX	TimeInterval
	MAX-ACCESS	read-write
	STATUS	current
	DESCRIPTION
		"This is the amount of time after the restoration of the
		primary timing reference before the Timing Control
		Module (TCM)  will be instructed to return to the
		primary timing reference.  This value is truncated to whole
		seconds."
	::= { tcmEntry 16 }

tcmFailoverDelay  OBJECT-TYPE
	SYNTAX	TimeInterval
	MAX-ACCESS	read-write
	STATUS	current
	DESCRIPTION
		"This is the amount of time after the failure of a timing
		reference before the Timing Control Module (TCM)  will
		be instructed to switch to the next available timing reference.
		This value is truncated to whole seconds."
	::= { tcmEntry 17 }

------------
--  TCM Reference Source definitions
------------

tcmReferenceTable  OBJECT-TYPE
	SYNTAX	SEQUENCE OF TcmReferenceEntry
	MAX-ACCESS	not-accessible
	STATUS	current
	DESCRIPTION
     		"This table contains the timing reference source
		information for the Timing Control Module (TCM)
		."
	::= { tcmGroup 2 }

tcmReferenceEntry  OBJECT-TYPE
	SYNTAX	TcmReferenceEntry
   	MAX-ACCESS	not-accessible
	STATUS	current
	DESCRIPTION
		"This table entry contains the timing reference source
		information for a single Timing Control Module (TCM)
		."
	INDEX	{ tcmIndex, tcmRefSource }
	::= { tcmReferenceTable 1 }

TcmReferenceEntry ::= SEQUENCE {
		tcmRefSource		TcmReferenceSource,
		tcmRefSourceText	DisplayString,
		tcmRefSourceStatus	INTEGER,
		tcmRefSourceAdminStatus	INTEGER,
		tcmRefSourceQualStatus	INTEGER
	}

tcmRefSource  OBJECT-TYPE
	SYNTAX	TcmReferenceSource
	MAX-ACCESS	not-accessible
	STATUS  current
	DESCRIPTION
		"This is the timing reference source index for the
		Timing Control Module (TCM) ."
	::= { tcmReferenceEntry 1 }

tcmRefSourceText  OBJECT-TYPE
	SYNTAX	DisplayString
	MAX-ACCESS  read-only
	STATUS  current
	DESCRIPTION
		"This is a textual description of the timing reference
		 source that is provided to the Timing Control Module (TCM)."
	::= { tcmReferenceEntry 2 }

tcmRefSourceStatus  OBJECT-TYPE
	SYNTAX	INTEGER {
			available(1),
			unavailable(2)
		}
	MAX-ACCESS	read-only
	STATUS	current
	DESCRIPTION
		"This is the status of the timing reference source
		 that is provided to the Timing Control Module (TCM)."
	::= { tcmReferenceEntry 3 }

tcmRefSourceAdminStatus  OBJECT-TYPE
	SYNTAX	INTEGER {
			up(1),
			down(2)
		}
	MAX-ACCESS	read-write
	STATUS	current
	DESCRIPTION
		"This is the admin status of the timing reference source
		 that is provided to the Timing Control Module (TCM)."
	::= { tcmReferenceEntry 4 }

tcmRefSourceQualStatus  OBJECT-TYPE
	SYNTAX	INTEGER {
			ok(1),
			fail(2)
		}
	MAX-ACCESS	read-only
	STATUS	current
	DESCRIPTION
		"This is the RefQual status of the timing reference source
		 that is provided to the Timing Control Module (TCM) ."
	::= { tcmReferenceEntry 5 }


tcmTxBits1RefSource OBJECT-TYPE
        SYNTAX  DerivedReferenceSource
        MAX-ACCESS  read-write
        STATUS  current
        DESCRIPTION
                "This object is the timing source that is used to derive
		DS1 or E1 signal transmitted out on the BITS1 interface."
        ::= { tcmGroup 3 }


tcmTxBits2RefSource OBJECT-TYPE
        SYNTAX  DerivedReferenceSource
        MAX-ACCESS  read-write
        STATUS  current
        DESCRIPTION
                "This object is the timing source that is used to derive
		 DS1 or E1 signal transmitted out on the BITS2 interface."
        ::= { tcmGroup 4 }

tcmTxBitsOperMode OBJECT-TYPE
	SYNTAX  INTEGER {
			automatic(1),
			thresholdAIS(2)
		}
	MAX-ACCESS  read-write
	STATUS  current
	DESCRIPTION 
		"This object refers to the mode of operation for the derived
		DS1 or E1 outputs. In thresholdAIS mode, AIS is transmitted
		on the derived DS1 or E1 signal when the transmit reference
		source becomes unacceptable. In automatic mode, synchronization
		status messages are passed through on the derived DS1 or E1 
		output if SSM Automatic Reference Switching is enabled and 
		the DS1 or E1 frame format supports SSM. Otherwise, AIS is 
		transmitted when the reference becomes unacceptable."
	::= { tcmGroup 5 }

-- TRAP Definitions

tcmTimingSourceChange  NOTIFICATION-TYPE
        OBJECTS { tcmIndex, tcmCurrentTimingRef, tcmRefSource,
		    trapLogIndex }
        STATUS      current
        DESCRIPTION
		"This trap is generated whenever the Timing Control Module
		 (TCM) timing source (tcmCurrentTimingRef) is changed
		 either manually or by the system due to failure detection."
        ::= { tcmGroup 0 1 }

tcmTimingSourceFailed  NOTIFICATION-TYPE
        OBJECTS { tcmIndex, tcmCurrentTimingRef, tcmRefSource,
                    trapLogIndex }
        STATUS      current
        DESCRIPTION
		"This trap is generated whenever the Timing Control Module
		 (TCM) timing source (tcmCurrentTimingRef) fails."
        ::= { tcmGroup 0 2 }

END
