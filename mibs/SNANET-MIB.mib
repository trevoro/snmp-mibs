--
-- This enterprise specific MIB is for the Unisys SNA Networking
-- product "SNA/net". It can be used to manage platforms which
-- contain the 5R2 release version of this software product. These
-- include the Distributed Communication Processor (DCP) Series
-- Systems, Communications Access Processor (CAP), and the  
-- Architecture Gateway (ARCH).
--
-- This MIB provides support for SNA objects which do not
-- have Internet standard MIB definitions. It provides
-- for the gathering of statistics and monitoring of the
-- operational state of various SNA/net entities. It also
-- allows for control of network entities by writing the   
-- AdminState variable to change the operational state of 
-- the entity.
-- 
-- This MIB may be periodically updated or expanded.
--
-- The definitions were influenced by a review of the various 
-- Internet Drafts of the Internet Engineering Task Force(IETF) 
-- titled "Definitions of Managed Objects for SNA NAUs" and 
-- "Definitions of Managed Object for SNA Data Link Control".
--


SNANET-MIB DEFINITIONS ::= BEGIN

IMPORTS
	Counter, enterprises, Gauge, TimeTicks
		FROM RFC1155-SMI
	DisplayString
		FROM RFC1213-MIB
	OBJECT-TYPE
		FROM RFC-1212
	TRAP-TYPE
		FROM RFC-1215;


	   

unisys  OBJECT IDENTIFIER ::= { enterprises 223 }

dcp     OBJECT IDENTIFIER ::= { unisys 8 }

snanet  OBJECT IDENTIFIER ::= { dcp 3 }

-- groups in the SNA/net MIB

prodInfo OBJECT IDENTIFIER ::= { snanet 1 }

t5node  OBJECT IDENTIFIER ::= { snanet 2 }

subarea OBJECT IDENTIFIER ::= { snanet 3 }

snaNau  OBJECT IDENTIFIER ::= { snanet 4 }

snaSession OBJECT IDENTIFIER ::= { snanet 5 }

snaLink OBJECT IDENTIFIER ::= { snanet 6 }

-- *********** The SNA/net Product Information Group ************
						       
-- The productInfo group provides information about the Software
-- Program Product Release

prodInfoDesc   OBJECT-TYPE
     SYNTAX DisplayString (SIZE(0..255))
     ACCESS read-only
     STATUS mandatory
     DESCRIPTION
	  "A textual description of the software release.
	  Includes the release level and the internal revision level
	  (example: SNA/net  Release 5R2  Revision 5.2.10
			     Installed    06/03/94 07:10 )."
     ::= { prodInfo 1 } 

prodInfoFeatures  OBJECT-TYPE
     SYNTAX INTEGER
     ACCESS read-only
     STATUS mandatory
     DESCRIPTION
	  "A value which indicates the features included in the 
	  software release.

	  The value is a sum. This sum initially takes the value
	  zero, then for each feature a value is assigned
	  corresponding to a power of 2, such that a unique number
	  is generated for each combination of features.

	  Feature
	       1  Cross-Domain Resource Manager
	       2  Terminal Connect
	       4  PU T2.0 Inverted
	       8  Node Type 2.1 Low Entry Node (len)
	       16 Network Packet-Switching Interface (NPSI)
	       32 Remote Batch File Transfer Extended (RBFTE)"
     ::= { prodInfo 2 }



-- *********** The Type 5 Node Group ************
--
-- The t5node group provides information about the System Services
-- Control Point (SSCP).

t5nodeTable OBJECT-TYPE
     SYNTAX SEQUENCE OF T5nodeEntry
     ACCESS not-accessible
     STATUS mandatory
     DESCRIPTION
	  "This table contains information about the Type 5 node
	  functionality (SSCP) provided by the SNA/net product.
	  Multiple nodes can be provided by a single SNA/net
	  product."
     ::= { t5node 1 }

t5nodeEntry OBJECT-TYPE
     SYNTAX T5nodeEntry
     ACCESS not-accessible
     STATUS mandatory
     DESCRIPTION
	  "Entry contains information about the Type 5 node
	  functionality (SSCP)."
     INDEX     { t5nodeIndex }
     ::= { t5nodeTable 1 }

T5nodeEntry ::= SEQUENCE {
     t5nodeIndex
	  INTEGER,
     t5nodeDomainName
	  DisplayString,
     t5nodeOperState
	  INTEGER,
     t5nodeSubareaNumber
	  INTEGER (1..65535),
     t5nodeSscpName
	  DisplayString,
     t5nodeNetworkName
	  DisplayString,
     t5nodeSscpId
	  INTEGER (0..65535),
     t5nodePuName
	  DisplayString
     }

t5nodeIndex         OBJECT-TYPE
     SYNTAX INTEGER
     ACCESS read-only
     STATUS mandatory
     DESCRIPTION
	  "SNA/net can appear as more than one t5node. Used to
	  index instances of this object. Value is assigned by the
	  agent and remains constant."
     ::= { t5nodeEntry 1 }

t5nodeDomainName         OBJECT-TYPE
     SYNTAX DisplayString (SIZE (1..8))
     ACCESS read-only
     STATUS mandatory
     DESCRIPTION
	  "The configured name for this domain. This is also the
	  t5nodeSscpName, if t5nodeSscpName is a 0 length string."
     ::= { t5nodeEntry 2 }

t5nodeOperState    OBJECT-TYPE
     SYNTAX INTEGER {
	  other(1),      -- A transition state, or not initialized
	  up(2),         -- Operational
	  down(3),       -- Not Operational
	  standby(4)     -- Online standby mode
	  }
     ACCESS read-only
     STATUS mandatory
     DESCRIPTION
	  "The operational state of the Type 5 Domain."
     ::= { t5nodeEntry 3 }

t5nodeSubareaNumber      OBJECT-TYPE
     SYNTAX INTEGER (1..65535)
     ACCESS read-only
     STATUS mandatory
     DESCRIPTION
	  "The subarea number for this domain."
     ::= { t5nodeEntry 4 }

t5nodeSscpName      OBJECT-TYPE
     SYNTAX DisplayString (SIZE (0..8))
     ACCESS read-only
     STATUS mandatory
     DESCRIPTION
	  "The name of the SSCP. Must be unique in the SNA
	  subnetwork. It must match the name of the VTAM CDRM macro
	  that defines this t5node as a CDRM to VTAM. May be
	  a zero length string, in which case, the t5nodeDomainName
	  is the name of the SSCP."
     ::= { t5nodeEntry 5 }

t5nodeNetworkName   OBJECT-TYPE
     SYNTAX DisplayString (SIZE (1..8))
     ACCESS read-only
     STATUS mandatory
     DESCRIPTION
	  "The SNA network name."
     ::= { t5nodeEntry 6 }

t5nodeSscpId   OBJECT-TYPE
     SYNTAX INTEGER (0..65535)
     ACCESS read-only
     STATUS mandatory
     DESCRIPTION
	  "This value is used in ACTCDRM messages sent to VTAM."

     ::= { t5nodeEntry 7 }

t5nodePuName   OBJECT-TYPE
     SYNTAX DisplayString (SIZE (1..8))
     ACCESS read-only
     STATUS mandatory
     DESCRIPTION
	  "The PU identifier of this node."

     ::= { t5nodeEntry 8 }


t5CdrmTable    OBJECT-TYPE
     SYNTAX SEQUENCE OF T5CdrmEntry
     ACCESS not-accessible
     STATUS mandatory
     DESCRIPTION
	  "This table contains information about other Crossdomain
	  Resource Managers known to this type 5 node."
     ::= { t5node 2 }

t5CdrmEntry    OBJECT-TYPE
     SYNTAX T5CdrmEntry
     ACCESS not-accessible
     STATUS mandatory
     DESCRIPTION
	  "The entry contains information about CDRMs. Variables
	  have read-only access. The variable t5CdrmAdminState has
	  read-write access and is used to control a CDRM."

     INDEX     { t5CdrmT5nodeIndex, 
		 t5CdrmName }
     ::= { t5CdrmTable 1 }

T5CdrmEntry ::= SEQUENCE {
     t5CdrmT5nodeIndex
	  INTEGER,
     t5CdrmName
	  DisplayString,
     t5CdrmSnaName
	  DisplayString,
     t5CdrmType
	  INTEGER,
     t5CdrmAdminState
	  INTEGER,
     t5CdrmOperState
	  INTEGER,
     t5CdrmSubareaNumber
	  INTEGER (1..65535),
     t5CdrmNetworkName
	  DisplayString,
     t5CdrmElementAddress
	  INTEGER (1..32767)
     }

t5CdrmT5nodeIndex   OBJECT-TYPE
     SYNTAX INTEGER
     ACCESS read-only
     STATUS mandatory
     DESCRIPTION
	  "Index in the t5nodetable of the t5node this CDRM is
	  associated with." 
     ::= { t5CdrmEntry 1 }

t5CdrmName          OBJECT-TYPE
     SYNTAX DisplayString (SIZE (1..8))
     ACCESS read-only
     STATUS mandatory
     DESCRIPTION
	  "The configured name of the CDRM."
     ::= { t5CdrmEntry 2 }

t5CdrmSnaName       OBJECT-TYPE
     SYNTAX DisplayString (SIZE (0..8))
     ACCESS read-only
     STATUS mandatory
     DESCRIPTION
	  "The name of the CDRM as it is known in the SNA 
	  network. May be a zero length string, in which
	  case, the t5CdrmName is the SNA name."
     ::= { t5CdrmEntry 3 }


t5CdrmType          OBJECT-TYPE
     SYNTAX INTEGER {
	       external (1),  -- Non SNA/net CDRM
	       snanet (2)     -- SNA/net CDRM
	       }
     ACCESS read-only
     STATUS mandatory
     DESCRIPTION
	  "Identifies the type of CDRM."
     ::= { t5CdrmEntry 4 }

t5CdrmAdminState        OBJECT-TYPE
     SYNTAX INTEGER {
	       other (1),
	       up (2),
	       down (3)
	       }    
     ACCESS read-write
     STATUS mandatory
     DESCRIPTION
	  "Used by the Management Station to control the CDRM.
	  Values up (2) and down (3) can be read or written,
	  while value other (1) is read-only and indicates that
	  this variable has not been set since reboot."
     ::= { t5CdrmEntry 5 }

t5CdrmOperState    OBJECT-TYPE
     SYNTAX INTEGER {
	       up(1),         -- Ready to accept session activation
	       down(2),       -- Not ready to accept session
			      -- activation
	       active(3)      -- Session has been activated
	       }
     ACCESS read-only
     STATUS mandatory
     DESCRIPTION
	  "The current operational state of the CDRM in relation to
	  this Type 5 node SSCP."
     ::= { t5CdrmEntry 6 }

t5CdrmSubareaNumber      OBJECT-TYPE
     SYNTAX INTEGER (1..65535)
     ACCESS read-only
     STATUS mandatory
     DESCRIPTION
	  "The subarea number for the CDRM."
     ::= { t5CdrmEntry 7}

t5CdrmNetworkName   OBJECT-TYPE
     SYNTAX DisplayString (SIZE (1..8))
     ACCESS read-only
     STATUS mandatory
     DESCRIPTION
	  "The SNA network name for the CDRM."
     ::= { t5CdrmEntry 8 }

t5CdrmElementAddress          OBJECT-TYPE
     SYNTAX INTEGER (1..32767)
     ACCESS read-only
     STATUS mandatory
     DESCRIPTION
	  "Element Address assigned to this CDRM. "
     ::= { t5CdrmEntry 9 }

t5CdrscTable   OBJECT-TYPE
     SYNTAX SEQUENCE OF T5CdrscEntry
     ACCESS not-accessible
     STATUS mandatory
     DESCRIPTION
	  "This table contains information about other Crossdomain
	  Resources known to this type 5 node."
     ::= { t5node 3 }

t5CdrscEntry   OBJECT-TYPE
     SYNTAX T5CdrscEntry
     ACCESS not-accessible
     STATUS mandatory
     DESCRIPTION
	  "The entry contains information about a CDRSC. Variables
	  have read-only access. The variable t5CdrscAdminState has
	  read-write access and is used to control a CDRSC."

     INDEX     { t5CdrscT5nodeIndex,
		 t5CdrscName }
     ::= { t5CdrscTable 1 }

T5CdrscEntry ::= SEQUENCE {
     t5CdrscT5nodeIndex
	  INTEGER,
     t5CdrscName
	  DisplayString,
     t5CdrscSnaName
	  DisplayString,
     t5CdrscCdrmName
	  DisplayString,
     t5CdrscAdminState
	  INTEGER,
     t5CdrscOperState
	  INTEGER,
     t5CdrscSessions
	  Counter,
     t5CdrscDlmName
	  DisplayString,
     t5CdrscCosName
	  DisplayString
     }

t5CdrscT5nodeIndex  OBJECT-TYPE
     SYNTAX INTEGER
     ACCESS read-only
     STATUS mandatory
     DESCRIPTION
	  "Index in the t5nodetable of the t5node this CDRSC is
	  associated with." 
     ::= { t5CdrscEntry 1 }

t5CdrscName    OBJECT-TYPE
     SYNTAX DisplayString (SIZE (1..8))
     ACCESS read-only
     STATUS mandatory
     DESCRIPTION
	  "The configured name of the CDRSC."
     ::= { t5CdrscEntry 2 }

t5CdrscSnaName    OBJECT-TYPE
     SYNTAX DisplayString (SIZE (0..8))
     ACCESS read-only
     STATUS mandatory
     DESCRIPTION
	  "The name of the CDRSC as it is known in the SNA
	  Network. The SnaName is the same a the t5CdrscName
	  when this value is a zero length string."
     ::= { t5CdrscEntry 3 }


t5CdrscCdrmName     OBJECT-TYPE
     SYNTAX DisplayString (SIZE (1..8))
     ACCESS read-only
     STATUS mandatory
     DESCRIPTION
	  "The name the CDRM which owns this CDRSC."
     ::= { t5CdrscEntry 4 }

t5CdrscAdminState       OBJECT-TYPE
     SYNTAX INTEGER {
	       other (1),
	       up (2),
	       down (3)
	       }
     ACCESS read-write
     STATUS mandatory
     DESCRIPTION
	  "Used by the Management Station to control the use
	  of the CDRSC. Values up (2) and down (3) may be read
	  or written, while the value other(1) read-only and
	  indicates this variable has not been set since the last
	  reboot."
     ::= { t5CdrscEntry 5 }

t5CdrscOperState   OBJECT-TYPE
     SYNTAX INTEGER {
	       up (1),        -- Ready to accept session activation
	       down (2),      -- Not ready to accept session activation
	       active(3)      -- Sessions active
	       }
     ACCESS read-only
     STATUS mandatory
     DESCRIPTION
	  "The current operational state of the CDRSC in relation
	  to this Type 5 node SSCP."
     ::= { t5CdrscEntry 6 }

t5CdrscSessions OBJECT-TYPE
     SYNTAX Counter
     ACCESS read-only
     STATUS mandatory
     DESCRIPTION
	  "The number of active SNA LU-LU sessions for this CDRSC."
     ::= { t5CdrscEntry 7}

t5CdrscDlmName OBJECT-TYPE
     SYNTAX DisplayString (SIZE (1..8))
     ACCESS read-only
     STATUS mandatory
     DESCRIPTION
	  "The name of the Default Logon mode table used by this
	  CDRSC."
     ::= { t5CdrscEntry 8 }

t5CdrscCosName OBJECT-TYPE
     SYNTAX DisplayString (SIZE (1..8))
     ACCESS read-only
     STATUS mandatory
     DESCRIPTION
	  "The name of the Class of Service table used by this
	  CDRSC."
     ::= { t5CdrscEntry 9 }

t5DlmTable     OBJECT-TYPE
     SYNTAX SEQUENCE OF T5DlmEntry
     ACCESS not-accessible
     STATUS mandatory
     DESCRIPTION
	  "This table contains information about Default Logon Mode
	  Tables used by the SSCP for LU-LU session establishment."
     ::= { t5node 4 }

t5DlmEntry     OBJECT-TYPE
     SYNTAX T5DlmEntry
     ACCESS not-accessible
     STATUS mandatory
     DESCRIPTION
	  "The entry contains a Default Logon Mode Table entry. All
	  variables are read-only."

     INDEX     { t5DlmT5nodeIndex,
		    t5DlmName }
     ::= { t5DlmTable 1 }

T5DlmEntry ::= SEQUENCE {
     t5DlmT5nodeIndex
	  INTEGER,
     t5DlmName
	  DisplayString,
     t5DlmSnaName
	  DisplayString,
     t5DlmFmprof
	  OCTET STRING,
     t5DlmTsprof
	  OCTET STRING,
     t5DlmPriprot
	  OCTET STRING,
     t5DlmSecprot
	  OCTET STRING,
     t5DlmComprot
	  OCTET STRING,
     t5DlmRusizes
	  OCTET STRING,
     t5DlmPservic
	  OCTET STRING,
     t5DlmPsndpac
	  OCTET STRING,
     t5DlmPrcvpac
	  OCTET STRING,
     t5DlmSsndpac
	  OCTET STRING,
     t5DlmSrcvpac
	  OCTET STRING,
     t5DlmEncr
	  INTEGER (0..15),
     t5DlmBindType
	  INTEGER (0..1),
     t5DlmCos
	  DisplayString
     }

t5DlmT5nodeIndex    OBJECT-TYPE
     SYNTAX INTEGER
     ACCESS read-only
     STATUS mandatory
     DESCRIPTION
	  "Index in the t5nodetable of the t5node this DLM is
	  associated with." 
     ::= { t5DlmEntry 1 }

t5DlmName OBJECT-TYPE
     SYNTAX DisplayString (SIZE (1..8))
     ACCESS read-only
     STATUS mandatory
     DESCRIPTION
	  "The configured name of the Default Logon Mode."
     ::= { t5DlmEntry 2 }

t5DlmSnaName OBJECT-TYPE
     SYNTAX DisplayString (SIZE (0..8))
     ACCESS read-only
     STATUS mandatory
     DESCRIPTION
	  "The name of the Default Logon Mode as it is
	  known in the SNA network. May contain a zero
	  length string, in which case, the t5DlmName
	  is the SNA name."
     ::= { t5DlmEntry 3 }


t5DlmFmprof    OBJECT-TYPE
     SYNTAX OCTET STRING (SIZE (1))
     ACCESS read-only
     STATUS mandatory
     DESCRIPTION
	  "The Function Management Profile type, a value from 0 to
	  18 hexadecimal(byte 1 in the session parameter
	  field)."  
     ::= { t5DlmEntry 4 }

t5DlmTsprof    OBJECT-TYPE
     SYNTAX OCTET STRING (SIZE (1))
     ACCESS read-only
     STATUS mandatory
     DESCRIPTION
	  "The Transmission Services profile type, a value from 1
	  to 17 hexadecimal(byte 2 in the session parameter
	  field)."
     ::= { t5DlmEntry 5 }

t5DlmPriprot   OBJECT-TYPE
     SYNTAX OCTET STRING (SIZE (1)) 
     ACCESS read-only
     STATUS mandatory
     DESCRIPTION
	  "The primary logical unit protocol, a value from 0 to
	  0FF hexadecimal(byte 3 in the session parameter
	  field)."  
     ::= { t5DlmEntry 6 }

t5DlmSecprot   OBJECT-TYPE
     SYNTAX OCTET STRING (SIZE (1))
     ACCESS read-only
     STATUS mandatory
     DESCRIPTION
	  "The secondary logical unit protocol, a value from 0 to
	  0FF hexadecimal(byte 4 in the session parameter
	  field)."  
     ::= { t5DlmEntry 7 }

t5DlmComprot   OBJECT-TYPE
     SYNTAX OCTET STRING (SIZE (2))
     ACCESS read-only
     STATUS mandatory
     DESCRIPTION
	  "The common logical unit protocol, a value from 0 to
	  0FFFF hexadecimal(byte 5 and 6 in the session parameter
	  field)."  
     ::= { t5DlmEntry 8 }

t5DlmRusizes   OBJECT-TYPE
     SYNTAX OCTET STRING (SIZE (2))
     ACCESS read-only
     STATUS mandatory
     DESCRIPTION
	  "The maximum length of data request units in bytes. A
	  four digit hexadecimal value is provided in the same
	  format as for the ACF/VTAM generation(bytes 9 and 10 in
	  the session parameter field." 
     ::= { t5DlmEntry 9 }

t5DlmPservic   OBJECT-TYPE
     SYNTAX OCTET STRING (SIZE(12))
     ACCESS read-only
     STATUS mandatory
     DESCRIPTION
	  "The logical unit presentation services profile and usage
	  field(bytes 13 through 24 in the session parameter
	  field). A 24 digit hexadecimal number." 
     ::= { t5DlmEntry 10 }

t5DlmPsndpac   OBJECT-TYPE
     SYNTAX OCTET STRING (SIZE (1))
     ACCESS read-only
     STATUS mandatory
     DESCRIPTION
	  "The primary send pacing count(byte 11 in the session
	  parameter field), a value from 0 to 63 decimal."  
     ::= { t5DlmEntry 11 }

t5DlmPrcvpac   OBJECT-TYPE
     SYNTAX OCTET STRING (SIZE (1))
     ACCESS read-only
     STATUS mandatory
     DESCRIPTION
	  "The primary receive pacing count(byte 12 in the session
	  parameter field), a value from 0 to 63 decimal."  
     ::= { t5DlmEntry 12 }

t5DlmSsndpac   OBJECT-TYPE
     SYNTAX OCTET STRING (SIZE (1))
     ACCESS read-only
     STATUS mandatory
     DESCRIPTION
	  "The secondary send pacing count(byte 7 in the session
	  parameter field), a value from 0 to 63 decimal."  
     ::= { t5DlmEntry 13 }

t5DlmSrcvpac   OBJECT-TYPE
     SYNTAX OCTET STRING (SIZE (1))
     ACCESS read-only
     STATUS mandatory
     DESCRIPTION
	  "The secondary receive pacing count(byte 8 in the session
	  parameter field), a value from 0 to 63 decimal."  
     ::= { t5DlmEntry 14 }

t5DlmEncr      OBJECT-TYPE
     SYNTAX INTEGER (0..15)
     ACCESS read-only
     STATUS mandatory
     DESCRIPTION
	  "The encryption/decryption type expected by the logical
	  unit(first four bits of byte 26 in the session parameter
	  field), a value from 0 to F hexadecimal."    
     ::= { t5DlmEntry 15 }

t5DlmBindType  OBJECT-TYPE
     SYNTAX INTEGER (0..1)
     ACCESS read-only
     STATUS mandatory
     DESCRIPTION
	  "The BIND type, a value of 0 or 1.
	  0  means a negotiable BIND
	  1  means a non-negotiable BIND."   
     ::= { t5DlmEntry 16 }

t5DlmCos  OBJECT-TYPE
     SYNTAX DisplayString(SIZE (1..8))
     ACCESS read-only
     STATUS mandatory
     DESCRIPTION
	  "The name of the class of service to be used for a
	  session that uses this logon mode."
     ::= { t5DlmEntry 17 }

t5CosTable     OBJECT-TYPE
     SYNTAX SEQUENCE OF T5CosEntry
     ACCESS not-accessible
     STATUS mandatory
     DESCRIPTION
	  "This table contain class of service (COS) entries."
     ::= { t5node 5 }

t5CosEntry     OBJECT-TYPE
     SYNTAX T5CosEntry
     ACCESS not-accessible
     STATUS mandatory
     DESCRIPTION
	  "The entry contains a class of service entry. All
	  variables are read-only."

     INDEX     { t5CosT5nodeIndex,
		    t5CosName }
     ::= { t5CosTable 1 }

T5CosEntry ::= SEQUENCE {
     t5CosT5nodeIndex
	  INTEGER,
     t5CosName
	  DisplayString,
     t5CosSnaName
	  DisplayString,
     t5CosVrids
	  OCTET STRING
     }

t5CosT5nodeIndex    OBJECT-TYPE
     SYNTAX INTEGER
     ACCESS read-only
     STATUS mandatory
     DESCRIPTION
	  "Index in the t5nodetable of the t5node this COS is
	  associated with." 

     ::= { t5CosEntry 1 }

t5CosName OBJECT-TYPE
     SYNTAX DisplayString (SIZE (1..8))
     ACCESS read-only
     STATUS mandatory
     DESCRIPTION
	  "The configured name of the class of service entry."
     ::= { t5CosEntry 2 }

t5CosSnaName OBJECT-TYPE
     SYNTAX DisplayString (SIZE (0..8))
     ACCESS read-only
     STATUS mandatory
     DESCRIPTION
	  "The name of the class of service entry as
	  it is known in the SNA Network. May be a zero
	  length string, in which case, the t5CosName
	  is the SNA name."
     ::= { t5CosEntry 3 }


t5CosVrids     OBJECT-TYPE
     SYNTAX OCTET STRING (SIZE (2..48))
     ACCESS read-only
     STATUS mandatory
     DESCRIPTION
	  "A list of virtual routes, in hierarchical order, that
	  are used for LU-LU session traffic. The list is octet
	  pairs in the form x,y where x is the virtual route number
	  from 0 to 7, and y is the transmission priority from 0 to
	  3. Up to 24 ordered pairs are possible
	  (vr1,tp1 vr2,tp2 ...vr24,tp24)."   
     ::= { t5CosEntry 4 }

t5AliasTable     OBJECT-TYPE
     SYNTAX SEQUENCE OF T5AliasEntry
     ACCESS not-accessible
     STATUS mandatory
     DESCRIPTION
	  "This table is a crossreference for alias names 
	  to SNA/net resource names. The current use of
	  this table is for alternate logon names for 
	  Crossdomain resources."
     ::= { t5node 6 }

t5AliasEntry     OBJECT-TYPE
     SYNTAX T5AliasEntry
     ACCESS not-accessible
     STATUS mandatory
     DESCRIPTION
	  "The entry contains the alias name and a 
	  reference to the SNA (CDRSC) resource it refers
	  to. All variables are read-only."

     INDEX     { t5AliasT5nodeIndex,
		    t5AliasName }
     ::= { t5AliasTable 1 }

T5AliasEntry ::= SEQUENCE {
     t5AliasT5nodeIndex
	  INTEGER,
     t5AliasName
	  DisplayString,
     t5AliasResourceId
	  OBJECT IDENTIFIER 
     }

t5AliasT5nodeIndex    OBJECT-TYPE
     SYNTAX INTEGER
     ACCESS read-only
     STATUS mandatory
     DESCRIPTION
	  "Index in the t5nodetable of the t5node this Alias 
	  Name is associated with." 

     ::= { t5AliasEntry 1 }

t5AliasName OBJECT-TYPE
     SYNTAX DisplayString (SIZE (1..8))
     ACCESS read-only
     STATUS mandatory
     DESCRIPTION
	  "The configured alias name."
     ::= { t5AliasEntry 2 }

t5AliasResourceId OBJECT-TYPE
     SYNTAX OBJECT IDENTIFIER
     ACCESS read-only
     STATUS mandatory
     DESCRIPTION
	  "A reference to the SNA resource (CDRSC) identified
	  by this Alias Name. It is the object identifier
	  representing the instance of the index variable
	  of the resource."
     ::= { t5AliasEntry 3 }


-- *********** The Subarea Information Group ************
-- Includes information about connections to other subareas
-- (explicit routes, virtual routes, and transmission groups)
--
--
--
-- The Explicit Route Table

saErTable      OBJECT-TYPE
     SYNTAX SEQUENCE OF SaErEntry
     ACCESS not-accessible
     STATUS mandatory
     DESCRIPTION
	  "This table contains information about explicit routes
	  between this subarea and other network subareas."
     ::= { subarea 1}

saErEntry      OBJECT-TYPE
     SYNTAX SaErEntry
     ACCESS not-accessible
     STATUS mandatory
     DESCRIPTION
	  "This entry contain information about an explicit route."

     INDEX     { saErT5nodeIndex, 
		 saErDestinationSubarea,
		 saErNumber }
     ::= { saErTable 1 }

SaErEntry ::= SEQUENCE {
     saErT5nodeIndex
	  INTEGER,
     saErDestinationSubarea 
	  INTEGER (1..65535),
     saErNumber
	  INTEGER (1..15),
     saErTgNumber
	  INTEGER (0..255),
     saErOperState
	  INTEGER 
     }

saErT5nodeIndex     OBJECT-TYPE
     SYNTAX INTEGER
     ACCESS read-only
     STATUS mandatory
     DESCRIPTION
	  "Index in the t5nodetable of the t5node this explicit
	  route is associated with." 
     ::= { saErEntry 1 }

saErDestinationSubarea     OBJECT-TYPE
     SYNTAX INTEGER (1..65535)
     ACCESS read-only
     STATUS mandatory
     DESCRIPTION
	  "The destination subarea number for this Expicit Route."
     ::= { saErEntry 2 }

saErNumber     OBJECT-TYPE
     SYNTAX INTEGER (0..15)
     ACCESS read-only
     STATUS mandatory
     DESCRIPTION
	  "The number of the Explicit Route."
     ::= { saErEntry 3 }

saErTgNumber    OBJECT-TYPE
     SYNTAX INTEGER (0..255)
     ACCESS read-only
     STATUS mandatory
     DESCRIPTION
	  "The Transmission Group number associated with this
	  Explicit Route."
     ::= { saErEntry 4 }

saErOperState      OBJECT-TYPE
     SYNTAX INTEGER {
	       other(1),            -- None of the following
	       inoperative(2),      -- Not operational   
	       operative(3),        -- NC-ER-OP sent
	       actPend(4),          -- NC-ER-ACT sent, reply pending
	       innActPend(5),       -- Forwarded NC-ER-ACT, reply pending
	       innAct(6),           -- NC-ER-ACT-REPLY received
	       actNoSend(7),        -- Received NC-ER-ACT, sent reply
	       active(8)            -- Sent NC-ER-ACT, received reply
	       }
     ACCESS read-only
     STATUS mandatory
     DESCRIPTION
	  "The current operational state of the Explicit Route."
     ::= { saErEntry 5 }


-- The Virtual Routing Table

saVrTable      OBJECT-TYPE
     SYNTAX SEQUENCE OF SaVrEntry
     ACCESS not-accessible
     STATUS mandatory
     DESCRIPTION
	  "This table contains information about virtual routes
	  between this subarea and other network subareas. Virtual
	  routes are logical connections between subareas and are
	  mapped to explicit routes."
     ::= { subarea 2 }

saVrEntry      OBJECT-TYPE
     SYNTAX SaVrEntry
     ACCESS not-accessible
     STATUS mandatory
     DESCRIPTION
	  "This entry contains information about a virtual route.
	  All variables are read-only." 
     INDEX     { saVrT5nodeIndex,
		 saVrErNumber,
		 saVrNumber,
		 saVrTransmissionPriority }
     ::= { saVrTable 1 }

SaVrEntry ::= SEQUENCE {
     saVrT5nodeIndex
	  INTEGER,
     saVrErNumber
	  INTEGER (0..15),
     saVrNumber
	  INTEGER (1..15),
     saVrTransmissionPriority
	  INTEGER (0..2),
     saVrWindowSize
	  INTEGER (0..255),
     saVrMinWindowSize
	  INTEGER (0..255),
     saVrMaxWindowSize
	  INTEGER (0..255),
     saVrPacingCount
	  INTEGER (0..255)

     }

saVrT5nodeIndex     OBJECT-TYPE
     SYNTAX INTEGER
     ACCESS read-only
     STATUS mandatory
     DESCRIPTION
	  "Index in the t5nodetable of the t5node this virtual
	  route is associated with." 
     ::= { saVrEntry 1 }

saVrErNumber   OBJECT-TYPE
     SYNTAX INTEGER (0..15)
     ACCESS read-only
     STATUS mandatory
     DESCRIPTION
	  "The expicit route to which this virtual route belongs."
     ::= { saVrEntry 2 }

saVrNumber     OBJECT-TYPE
     SYNTAX INTEGER (1..15)
     ACCESS read-only
     STATUS mandatory
     DESCRIPTION
	  "The number of the Virtual Route."
     ::= { saVrEntry 3 }

saVrTransmissionPriority OBJECT-TYPE
     SYNTAX INTEGER (0..2)
     ACCESS read-only
     STATUS mandatory
     DESCRIPTION
	  "The transmission priority for this virtual route."
     ::= { saVrEntry 4 }

saVrWindowSize      OBJECT-TYPE
     SYNTAX INTEGER (0..255)
     ACCESS read-only
     STATUS mandatory
     DESCRIPTION
	  "The initial window size for this virtual route."
     ::= { saVrEntry 5 }

saVrMinWindowSize        OBJECT-TYPE
     SYNTAX INTEGER (0..255)
     ACCESS read-only
     STATUS mandatory
     DESCRIPTION
	  "The minimum window size for this virtual route."
     ::= { saVrEntry 6 }

saVrMaxWindowSize        OBJECT-TYPE
     SYNTAX INTEGER (0..255)
     ACCESS read-only
     STATUS mandatory
     DESCRIPTION
	  "The maximum window size for this virtual route."
     ::= { saVrEntry 7 }

saVrPacingCount     OBJECT-TYPE
     SYNTAX INTEGER (0..255)
     ACCESS read-only
     STATUS mandatory
     DESCRIPTION
	  "The pacing count for this virtual route."
     ::= { saVrEntry 8 }

-- ******** The Transmission Group ********       

saTransmissionGroup OBJECT IDENTIFIER ::= { subarea 3 }


-- ******** The Transmission Group Table ********

saTgTable      OBJECT-TYPE
     SYNTAX SEQUENCE OF SaTgEntry
     ACCESS not-accessible
     STATUS mandatory
     DESCRIPTION
	  "This table contains information about transmission
	  groups between this subarea and other network subareas.
	  Entries are dynamically added to this table as they are
	  learned from TG link activations."
     ::= { saTransmissionGroup 1}

saTgEntry      OBJECT-TYPE
     SYNTAX SaTgEntry
     ACCESS not-accessible
     STATUS mandatory
     DESCRIPTION
	  "This entry contains information about a transmission
	  group."
     INDEX     { saTgT5nodeIndex,
		 saTgNumber,
		 saTgAdjacentSubarea }  
     ::= { saTgTable 1 }

SaTgEntry ::= SEQUENCE {
     saTgT5nodeIndex
	  INTEGER,
     saTgNumber
	  INTEGER (1..255),
     saTgAdjacentSubarea
	  INTEGER (1..65535),
     saTgOperState 
	  INTEGER, 
     saTgMaxSendPiuSize
	  INTEGER (1..65535),
     saTgMaxReceivePiuSize
	  INTEGER (1..65535),
     saTgActiveTime
	  TimeTicks,
     saTgLastStateChange
	  TimeTicks,
     saTgSentBytes
	  Counter,
     saTgReceivedBytes
	  Counter,
     saTgSentBtus
	  Counter,
     saTgReceivedBtus
	  Counter 
     }

saTgT5nodeIndex     OBJECT-TYPE
     SYNTAX INTEGER
     ACCESS read-only
     STATUS mandatory
     DESCRIPTION
	  "Index in the t5nodetable of the t5node this transmission
	  group is associated with." 
     ::= { saTgEntry 1 }

saTgNumber     OBJECT-TYPE
     SYNTAX INTEGER (1..255)
     ACCESS read-only
     STATUS mandatory
     DESCRIPTION
	  "The number of this transmission group."
     ::= { saTgEntry 2 }

saTgAdjacentSubarea     OBJECT-TYPE
     SYNTAX INTEGER (1..65535)
     ACCESS read-only
     STATUS mandatory
     DESCRIPTION
	  "The adjacent subarea number with which this transmission
	  group is associated."
     ::= { saTgEntry 3 }
			     
saTgOperState     OBJECT-TYPE
     SYNTAX INTEGER {
	 inactive(1),
	 active(2),
	 pendActive(3),
	 pendInactive(4)
	 }
     ACCESS read-only
     STATUS mandatory
     DESCRIPTION
	  "The current operational state of this transmission group."
     ::= { saTgEntry 4 }
			     


saTgMaxSendPiuSize  OBJECT-TYPE
     SYNTAX INTEGER (1..65565) 
     ACCESS read-only
     STATUS mandatory
     DESCRIPTION
	  "The maximum Path Information Unit size in bytes that may
	  be sent on this Tranmission Group."
     ::= { saTgEntry 5}

saTgMaxReceivePiuSize    OBJECT-TYPE
     SYNTAX INTEGER (1..65535) 
     ACCESS read-only
     STATUS mandatory
     DESCRIPTION
	  "The maximum Path Information Unit size in bytes that may
	  be received on this Tranmission Group."
     ::= { saTgEntry 6}

saTgActiveTime OBJECT-TYPE
     SYNTAX  TimeTicks
     ACCESS  read-only
     STATUS  mandatory
     DESCRIPTION
	  "The value of sysUpTime when this transmission group 
	  became active."
     ::= { saTgEntry 7 }

saTgLastStateChange OBJECT-TYPE
     SYNTAX  TimeTicks
     ACCESS  read-only
     STATUS  mandatory
     DESCRIPTION
	  "The value of sysUpTime when the last state change 
	  occurred."
     ::= { saTgEntry 8 }

saTgSentBytes OBJECT-TYPE
     SYNTAX    Counter
     ACCESS    read-only
     STATUS    mandatory
     DESCRIPTION
	  "The number of bytes sent on this transmission group." 
     ::= { saTgEntry 9 }

saTgReceivedBytes OBJECT-TYPE
     SYNTAX    Counter
     ACCESS    read-only
     STATUS    mandatory
     DESCRIPTION
	  "The number of bytes received on transmission group."
     ::= { saTgEntry 10 }

saTgSentBtus OBJECT-TYPE
     SYNTAX    Counter
     ACCESS    read-only
     STATUS    mandatory
     DESCRIPTION
	  "The number of Basic Transmission Units sent on this
	  transmission group."
    ::= { saTgEntry 11 }

saTgReceivedBtus OBJECT-TYPE
     SYNTAX    Counter
     ACCESS    read-only
     STATUS    mandatory
     DESCRIPTION
	  "The number of Basic Transmission Units  received on this
	  transmission group."
     ::= { saTgEntry 12 }

-- ***************************************************************
-- The following table contains configuration information and 
-- state information about links used for transmission groups.
-- ***************************************************************

saTgLinkTable OBJECT-TYPE
     SYNTAX  SEQUENCE OF SaTgLinkEntry
     ACCESS  not-accessible
     STATUS  mandatory
     DESCRIPTION
	  "This table contains an entry for each link which may be
	  used for a transmission group. The links are not
	  associated with a transmission group until
	  saTgLinkOperState is active (2)."
     ::= { saTransmissionGroup 2 }

saTgLinkEntry OBJECT-TYPE
     SYNTAX  SaTgLinkEntry
     ACCESS  not-accessible
     STATUS  mandatory
     DESCRIPTION
	  "Contains configuration and state information about
	  TG links. Variables have read-only access. The variable 
	  saTgLinkAdminState has read-write access and is used 
	  to control a TG link."
     INDEX   { saTgLinkT5nodeIndex,
		saTgLinkIndex }
     ::= { saTgLinkTable 1 }

SaTgLinkEntry ::= SEQUENCE {
     saTgLinkT5nodeIndex
	  INTEGER,
     saTgLinkIndex
	  INTEGER,
     saTgLinkTgNumber
	  INTEGER (0..255),
     saTgLinkAdjacentSubarea
	  INTEGER (1..65535),
     saTgLinkName
	  DisplayString,
     saTgLinkOperState
	  INTEGER,
     saTgLinkAdminState
	  INTEGER,
     saTgLinkType
	  INTEGER,
     saTgLinkSpecific
	  OBJECT IDENTIFIER,
     saTgLinkActiveTime
	  TimeTicks,
     saTgLinkLastStateChange
	  TimeTicks,
     saTgLinkSentBytes
	  Counter,
     saTgLinkReceivedBytes
	  Counter,
     saTgLinkSentBtus
	  Counter,
     saTgLinkReceivedBtus
	  Counter 
     }

saTgLinkT5nodeIndex OBJECT-TYPE
     SYNTAX  INTEGER
     ACCESS  read-only
     STATUS  mandatory
     DESCRIPTION
	  "Identifies the Type 5 node with which this transmission
	  group link is associated."
     ::= { saTgLinkEntry 1 }

saTgLinkIndex OBJECT-TYPE
     SYNTAX  INTEGER
     ACCESS  read-only
     STATUS  mandatory
     DESCRIPTION
	  "Unique index of this transmisson group link. The value
	  is assigned by the agent and is unique among TG and PU
	  links."
     ::= { saTgLinkEntry 2 }

saTgLinkTgNumber    OBJECT-TYPE
     SYNTAX INTEGER (0..255)
     ACCESS read-only
     STATUS mandatory
     DESCRIPTION
	  "The transmission group number to which this link is
	  associated. Contains a value of zero (0) when
	  saTgLinkOperState is inactive(1)."
     ::= { saTgLinkEntry 3 }

saTgLinkAdjacentSubarea  OBJECT-TYPE
     SYNTAX INTEGER (1..65535)
     ACCESS read-only
     STATUS mandatory
     DESCRIPTION
	  "The adjacent subarea number with which this transmission
	  group is associated. Contains a value of zero when
	  saTgLinkOperState in inactive(1)."
     ::= { saTgLinkEntry 4 }

saTgLinkName OBJECT-TYPE
     SYNTAX  DisplayString (SIZE(1..8))
     ACCESS  read-only
     STATUS  mandatory
     DESCRIPTION
	  "The administratively assigned name of the transmission
	  group link."
     ::= { saTgLinkEntry 5 }

saTgLinkOperState OBJECT-TYPE
     SYNTAX  INTEGER {
	  inactive(1),
	  active(2)
	  }
     ACCESS  read-only
     STATUS  mandatory
     DESCRIPTION
	  "The current operational state of this transmission
	  group link."
     ::= { saTgLinkEntry 6 }

saTgLinkAdminState OBJECT-TYPE
     SYNTAX  INTEGER {
	  other (1),
	  up (2),
	  down (3)
	  }
     ACCESS  read-write
     STATUS  mandatory
     DESCRIPTION
	  "Used by the Management Station to control the
	  transmission group Link. Values up (2) and down (3) can
	  be read or written, while value other (1) is read-only
	  and indicates that this variable has not been set since
	  reboot."
     ::= { saTgLinkEntry 7 }

saTgLinkType   OBJECT-TYPE
     SYNTAX INTEGER {
	  internal(1),
	  link8022(2),
	  qllc(3),
	  sdlc(4),
	  channel(5)
	  }
     ACCESS read-only
     STATUS mandatory
     DESCRIPTION
	  "The type of transmission group link."

     ::= { saTgLinkEntry 8 }

saTgLinkSpecific    OBJECT-TYPE
     SYNTAX OBJECT IDENTIFIER
     ACCESS read-only
     STATUS mandatory
     DESCRIPTION
	  "A row in a table specific for the link. It is the object
	  identifier representing the instance of the index
	  variable in one of the snaLink tables from this MIB."
     ::= { saTgLinkEntry 9 }

saTgLinkActiveTime OBJECT-TYPE
     SYNTAX  TimeTicks
     ACCESS  read-only
     STATUS  mandatory
     DESCRIPTION
	  "The value of sysUpTime when this TG link became    
	  active."
     ::= { saTgLinkEntry 10 }

saTgLinkLastStateChange OBJECT-TYPE
     SYNTAX  TimeTicks
     ACCESS  read-only
     STATUS  mandatory
     DESCRIPTION
	  "The value of sysUptime when the last state change 
	  occurred."
     ::= { saTgLinkEntry 11 }


saTgLinkSentBytes OBJECT-TYPE
     SYNTAX    Counter
     ACCESS    read-only
     STATUS    mandatory
     DESCRIPTION
	  "The number of bytes sent on this TG link." 
     ::= { saTgLinkEntry 12 }
			   
saTgLinkReceivedBytes OBJECT-TYPE
     SYNTAX    Counter
     ACCESS    read-only
     STATUS    mandatory
     DESCRIPTION
	  "The number of bytes received on this TG link."
     ::= { saTgLinkEntry 13 }

saTgLinkSentBtus OBJECT-TYPE
     SYNTAX    Counter
     ACCESS    read-only
     STATUS    mandatory
     DESCRIPTION
	  "The number of Basic Transmission Units sent on this
	  TG link."
    ::= { saTgLinkEntry 14 }

saTgLinkReceivedBtus OBJECT-TYPE
     SYNTAX    Counter
     ACCESS    read-only
     STATUS    mandatory
     DESCRIPTION
	  "The number of Basic Transmission Units  received on this
	  TG link."
     ::= { saTgLinkEntry 15 }

-- ***************************************************************
-- Traps - The traps identified here may be implemented in
--         the future.
-- ***************************************************************

-- saTgLinkTraps OBJECT IDENTIFIER ::= { saTransmissionGroup 3 }

-- saTgLinkStateChangeTrap TRAP-TYPE
--     ENTERPRISE      saTgLinkTrap
--     VARIABLES   { saTgLinkName
--                    saTgLinkOperState }
--   STATUS  mandatory
--     DESCRIPTION
--         "The operational state of a TG Link changed. The following
--          variables are returned:
--          saTgLinkName      - name of the TG link
--          saTgLinkOperState - the current state after the change."
--     ::= { saTgLinkTraps 1 }
--


-- ***************** The SNA NAU group ******************** 
-- The definition of this group was heavily influenced by
-- reviewing the various Internet Drafts of the Internet 
-- Engineering Task Force titled "Definitions of Managed
-- Objects for SNA NAUs". An attempt was made to allow for 
-- an easy transition to the use of an eventual standard MIB 
-- for some of the objects in this group.
--

t2node OBJECT IDENTIFIER ::= { snaNau 1 }
snaLu OBJECT IDENTIFIER ::= { snaNau 2 }
applicationLu OBJECT IDENTIFIER ::= { snaNau 3 }

-- ***************************************************************
-- t2node group
--
-- It contains Managed Objects related to a remote type 2.0 PUs,   
-- emulated type 2.0 PU controllers (IBF), 
-- and  type 2.1 low entry nodes (len).
-- ***************************************************************

t2nodeTable OBJECT-TYPE
     SYNTAX  SEQUENCE OF T2nodeEntry
     ACCESS  not-accessible
     STATUS  mandatory
     DESCRIPTION
	  "This table contains all configured and dynamic parameters
	  of type 2 nodes  have read-only access. There is also one 
	  control  parameter,  t2nodeAdminState which has
	  read-write access.  The link specific parameters are contained
	  in a row of a separate table referenced by the
	  snaLinkSpecific object."     
     ::= { t2node 1 }

t2nodeEntry OBJECT-TYPE
     SYNTAX  T2nodeEntry
     ACCESS  not-accessible
     STATUS  mandatory
     DESCRIPTION
	  "Entry contains all parameters of one type 2 node.
	  They have read-only access.  The entry is created by the 
	  Agent. The variable t2nodeAdminState has read-write
	  access and is used to start or stop the node."
 
     INDEX   { t2nodeT5nodeIndex,
	       t2nodeIndex }
     ::= { t2nodeTable 1 }

T2nodeEntry ::= SEQUENCE {
     t2nodeT5nodeIndex
	  INTEGER,
     t2nodeIndex
	  INTEGER,
     t2nodeName
	  DisplayString,
     t2nodeType
	  INTEGER,
     t2nodeBlockNum
	  DisplayString,
     t2nodeIdNum
	  DisplayString,
     t2nodeMaxPiu
	  INTEGER,
     t2nodeLinkType
	  INTEGER,
     t2nodeLinkSpecific
	  OBJECT IDENTIFIER,
     t2nodeOperState
	  INTEGER,
     t2nodeAdminState
	  INTEGER,
     t2nodeStartTime
	  TimeTicks,
     t2nodeLastStateChange
	  TimeTicks,
     t2nodeActFailureReason
	  INTEGER 
  
   }

t2nodeT5nodeIndex OBJECT-TYPE
     SYNTAX  INTEGER
     ACCESS  read-only
     STATUS  mandatory
     DESCRIPTION
	  "Index in the t5nodeTable to which this t2node is
	  associated."
     ::= { t2nodeEntry 1 }

t2nodeIndex OBJECT-TYPE
     SYNTAX  INTEGER
     ACCESS  read-only
     STATUS  mandatory
     DESCRIPTION
	  "Used to index the instances of objects assigned by the 
	  Agent."
     ::= { t2nodeEntry 2 }

t2nodeName OBJECT-TYPE
     SYNTAX  DisplayString (SIZE(1..8))
     ACCESS  read-only
     STATUS  mandatory
     DESCRIPTION
	  "The value identifies the name of the Node."
     ::= { t2nodeEntry 3 }

t2nodeType OBJECT-TYPE
     SYNTAX  INTEGER {
	  other(1),
	  pu20prim(2),  -- A remote or internal PU 2.0 connection
	  pu20sec(3),   -- Emulation of a PU 2.0 device
	  t21LEN(4)     -- Type 2.1 Low Entry Node (LEN)   
	  }
     ACCESS  read-only
     STATUS  mandatory
     DESCRIPTION
	  "This value identifies the type of Node."
     ::= { t2nodeEntry 4 }

t2nodeBlockNum OBJECT-TYPE
     SYNTAX  DisplayString(SIZE(3))
     ACCESS  read-only
     STATUS  mandatory
     DESCRIPTION
	  "The value identifies the block number for this Node
	  instance. It is the first 3 hexadecimal digits of
	  the t2node id."
     ::= { t2nodeEntry 5 }

t2nodeIdNum OBJECT-TYPE
     SYNTAX  OCTET STRING (SIZE(5))
     ACCESS  read-only
     STATUS  mandatory
     DESCRIPTION
	  "The value identifies the ID number for this Node instance.
	  This is the last 5 hexadecimal digits of the t2node id."
     ::= { t2nodeEntry 6 }

t2nodeMaxPiu OBJECT-TYPE
     SYNTAX  INTEGER
     ACCESS  read-only
     STATUS  mandatory
     DESCRIPTION
	  "Maximum number of octets that can be exchanged by this
	  PU in one Pathcontrol Information Unit (PIU)."
     ::= { t2nodeEntry 7 }

t2nodeLinkType OBJECT-TYPE
     SYNTAX  INTEGER {
	  internal (1),
	  link8022 (2),
	  qllc (3),
	  sdlc (4),
	  channelAttach (5),
	  tcpip (6)
	  }
     ACCESS  read-only
     STATUS  mandatory
     DESCRIPTION
	  "The type of link protocol used for this PU."
     ::= { t2nodeEntry 8 }

t2nodeLinkSpecific OBJECT-TYPE
     SYNTAX  OBJECT IDENTIFIER
     ACCESS  read-only
     STATUS  mandatory
     DESCRIPTION
	  "The row in a table specific for
	  the link. It is the object identifier representing
	  the instance of the index variable in one of the
	  snaLink tables from this MIB."
     ::= { t2nodeEntry 9 }

t2nodeOperState OBJECT-TYPE
     SYNTAX  INTEGER {
	  other (1),      -- none of the following
	  disabled (2),   -- cannot operate for some reason
	  enabled (3),    -- in ready state but not operating
	  active (4),     -- ready and operating
	  busy (5)        -- operating but cannot accept more traffic
	  }
     ACCESS  read-only
     STATUS  mandatory
     DESCRIPTION
	  "The operational state of the type 2 Node."
     ::= { t2nodeEntry 10 }

t2nodeAdminState OBJECT-TYPE
     SYNTAX  INTEGER {
	  other (1),
	  start (2),
	  stop (3)
	  }

     ACCESS  read-write
     STATUS  mandatory
     DESCRIPTION
	  "The administrative state of the type 2 Node and is 
	  used by the Management Station to start or stop the 
	  Node. The values that can be read and written are:
	    start (2) - this value has to be used to start,
	    stop (3) - this value has to be used to stop.
	  The values that can be read only are:
	    other (1) - this value indicates that the
	    variable has not been set after reboot."
     ::= { t2nodeEntry 11 }

t2nodeStartTime OBJECT-TYPE
     SYNTAX  TimeTicks
     ACCESS  read-only
     STATUS  mandatory
     DESCRIPTION
	  "The value of sysUpTime at type 2 Node activation."
     ::= { t2nodeEntry 12 }

t2nodeLastStateChange OBJECT-TYPE
     SYNTAX  TimeTicks
     ACCESS  read-only
     STATUS  mandatory
     DESCRIPTION
	  "The value of sysUpTime at the last state change 
	  of the type 2 Node."
     ::= { t2nodeEntry 13 }

t2nodeActFailureReason OBJECT-TYPE
     SYNTAX  INTEGER
     ACCESS  read-only
     STATUS  mandatory
     DESCRIPTION
	  "The sense code for the activation failure. It will be
	  sent in the trap t2NodeActFailTrap."
     ::= { t2nodeEntry 14 }

-- ***************************************************************
-- The following table contains PU statistics dynamic parameters.
-- ***************************************************************

t2nodeStatsTable OBJECT-TYPE
     SYNTAX  SEQUENCE OF T2nodeStatsEntry
     ACCESS  not-accessible
     STATUS  mandatory
     DESCRIPTION
	  "This table contains the dynamic parameters which have
	  read-only access. The entries in this table augment the
	  entries in the t2nodeTable and cannot be created by
	  Management Station."
     ::= { t2node 2 }

t2nodeStatsEntry OBJECT-TYPE
     SYNTAX  T2nodeStatsEntry
     ACCESS  not-accessible
     STATUS  mandatory
     DESCRIPTION
	  "The entry contains parameters which describe the statistics
	  of one t2node. They have read-only access. The counters represent
	  traffic for all kinds of sessions: LU-LU, SSCP-PU, and SSCP-LU. 
	  The entry is created by the Agent."
     INDEX   { t2nodeStatsT5nodeIndex,
	       t2nodeStatsIndex }
     ::= { t2nodeStatsTable 1 }

T2nodeStatsEntry ::= SEQUENCE {
     t2nodeStatsT5nodeIndex
	  INTEGER (1..65535),
     t2nodeStatsIndex
	  INTEGER (1..65535),
     t2nodeStatsSentBytes
	  Counter,
     t2nodeStatsReceivedBytes
	  Counter,
     t2nodeStatsSentPius
	  Counter,
     t2nodeStatsReceivedPius
	  Counter,
     t2nodeStatsSentNegativeResps
	  Counter,
     t2nodeStatsReceivedNegativeResps
	  Counter,
     t2nodeStatsActiveLus
	  Gauge,
     t2nodeStatsActLus
	  Gauge,
     t2nodeStatsInActLus
	  Gauge,
     t2nodeStatsBindLus
	  Gauge
     }
t2nodeStatsT5nodeIndex OBJECT-TYPE
     SYNTAX  INTEGER
     ACCESS  read-only
     STATUS  mandatory
     DESCRIPTION
	  " Index in the t5nodeTable to which this t2node is
	  associated."
     ::= { t2nodeStatsEntry 1 }

t2nodeStatsIndex OBJECT-TYPE
     SYNTAX  INTEGER
     ACCESS  read-only
     STATUS  mandatory
     DESCRIPTION
	  "The instance of the entry parameters. The index value is
	  taken by the Agent from t2nodeIndex."
     ::= { t2nodeStatsEntry 2 }

t2nodeStatsSentBytes OBJECT-TYPE
     SYNTAX    Counter
     ACCESS    read-only
     STATUS    mandatory
     DESCRIPTION
	  "The number of bytes sent by this Node."         
     ::= { t2nodeStatsEntry 3 }

t2nodeStatsReceivedBytes OBJECT-TYPE
     SYNTAX    Counter
     ACCESS    read-only
     STATUS    mandatory
     DESCRIPTION
	  "The number of bytes received by this Node."
     ::= { t2nodeStatsEntry 4 }

t2nodeStatsSentPius OBJECT-TYPE
     SYNTAX    Counter
     ACCESS    read-only
     STATUS    mandatory
     DESCRIPTION
	  "The number of PIUs sent by this Node."               
  ::= { t2nodeStatsEntry 5 }

t2nodeStatsReceivedPius OBJECT-TYPE
     SYNTAX    Counter
     ACCESS    read-only
     STATUS    mandatory
     DESCRIPTION
	  "The number of PIUs received by this Node."          
     ::= { t2nodeStatsEntry 6 }

t2nodeStatsSentNegativeResps OBJECT-TYPE
     SYNTAX    Counter
     ACCESS    read-only
     STATUS    mandatory
     DESCRIPTION
	  "The number of negative responses sent by this Node."
     ::= { t2nodeStatsEntry 7 }

t2nodeStatsReceivedNegativeResps OBJECT-TYPE
     SYNTAX    Counter
     ACCESS    read-only
     STATUS    mandatory
     DESCRIPTION
	  "The number of negative responses received by this Node."
     ::= { t2nodeStatsEntry 8 }

t2nodeStatsActiveLus OBJECT-TYPE
     SYNTAX  Gauge
     ACCESS  read-only
     STATUS  mandatory
     DESCRIPTION
	  "The number of LUs currently active on this PU."
     ::= { t2nodeStatsEntry 9 }

t2nodeStatsActLus OBJECT-TYPE
     SYNTAX  Gauge
     ACCESS  read-only
     STATUS  mandatory
     DESCRIPTION
	  "The number of LUs on this type 2 Node which have 
	  active SSCP-LU  sessions."
     ::= { t2nodeStatsEntry 10 }

t2nodeStatsInActLus OBJECT-TYPE
     SYNTAX  Gauge
     ACCESS  read-only
     STATUS  mandatory
     DESCRIPTION
	  "The number of LUs on this type 2 Node which do not have 
	  active SSCP-LU sessions."
     ::= { t2nodeStatsEntry 11 }

t2nodeStatsBindLus OBJECT-TYPE
     SYNTAX  Gauge
     ACCESS  read-only
     STATUS  mandatory
     DESCRIPTION
	  "The number of LUs on this type 2 Node which have received and
	  acknowledged a BIND request."
     ::= { t2nodeStatsEntry 12 }


-- ***************************************************************
-- Traps - The traps identified here may be implemented in
--         the future.
-- ***************************************************************

-- t2nodeTraps OBJECT IDENTIFIER ::= { t2node 4 }

-- t2nodeStateChangeTrap TRAP-TYPE
--     ENTERPRISE      t2nodeTrap
--     VARIABLES   { t2nodeName
--                    t2nodeOperState }
--   STATUS  mandatory
--     DESCRIPTION
--         "The operational state of a type 2 Node changed. The following
--          variables are returned:
--          t2nodeName      - name of the Node
--          t2nodeOperState - the current state after the change."
--     ::= { t2nodeTraps 1 }
--
-- t2nodeActFailTrap TRAP-TYPE
--     ENTERPRISE      t2nodeTrap
--     VARIABLES   { t2nodeName,
--                   t2nodeOperState,
--                   t2nodeActFailureReason }
--   STATUS  mandatory
--     DESCRIPTION
--          "The trap sent to indicates a Node activation failure. Value
--          t2nodeOperState indicates the current state after
--          change. Value t2nodeActFailureReason indicates the
--          failure reason."
--     ::=  { t2nodeTraps 2 }

-- ***************************************************************
-- snaLu group
--
-- Implementation of the snaLu group is mandatory.
--
-- It contains Managed Objects for LUs of types 0, 1, 2, 3, 
-- and 6.2. 
-- ***************************************************************

snaLuTable OBJECT-TYPE
     SYNTAX  SEQUENCE OF SnaLuEntry
     ACCESS  not-accessible
     STATUS  mandatory
     DESCRIPTION
	"This table contains configuration and state information relating
	 to LUs."
     ::= { snaLu 1 }

snaLuEntry OBJECT-TYPE
     SYNTAX  SnaLuEntry
     ACCESS  not-accessible
     STATUS  mandatory
     DESCRIPTION
	  "Contains configuration and state objects relating to an LU. All 
	  have read-only access with the exeption of snaLuAdminState 
	  which has read-write access and is used by the Management
	  station to control the state of the LU."
     INDEX   { snaLuT5nodeIndex,
		snaLuT2nodeIndex,
		snaLuIndex }
     ::= { snaLuTable 1 }

SnaLuEntry ::= SEQUENCE {
     snaLuT5nodeIndex
	  INTEGER,
     snaLuT2nodeIndex
	  INTEGER,
     snaLuIndex
	  INTEGER,
     snaLuName
	  DisplayString,
     snaLuType
	  INTEGER,
     snaLuLocalAddress
	  OCTET STRING,
     snaLuUserName
	  DisplayString,
     snaLuPoolName
	  DisplayString,
     snaLuOperState
	  INTEGER,
     snaLuAdminState
	  INTEGER,
     snaLuLastStateChange
	  TimeTicks,
     snaLuActiveTime
	  TimeTicks,
     snaLuBindFailureReason
	  INTEGER
     }

snaLuT5nodeIndex OBJECT-TYPE
     SYNTAX  INTEGER
     ACCESS  read-only
     STATUS  mandatory
     DESCRIPTION
	  "Index in the t5nodeTable to which this LU is
	  associated."
     ::= { snaLuEntry 1 }

snaLuT2nodeIndex OBJECT-TYPE
     SYNTAX  INTEGER
     ACCESS  read-only
     STATUS  mandatory
     DESCRIPTION
	  "Index in the t2nodeTable of the type 2 Node with which this
	  LU is associated."
     ::= { snaLuEntry 2 }

snaLuIndex OBJECT-TYPE
     SYNTAX  INTEGER
     ACCESS  read-only
     STATUS  mandatory
     DESCRIPTION
	  "This value identifies a unique index for an LU instance within
	  a type 2 Node."
     ::= { snaLuEntry 3 }

snaLuName OBJECT-TYPE
     SYNTAX  DisplayString (SIZE(1..8))
     ACCESS  read-only
     STATUS  mandatory
     DESCRIPTION
	  "The SNA name for this LU. "
     ::= { snaLuEntry 4 }

snaLuType OBJECT-TYPE
     SYNTAX  INTEGER {
	  other(1),
	  lu0(2),
	  lu1(3),
	  lu2(4),
	  lu3(5),
	  lu62(6)
	   }
     ACCESS  read-only
     STATUS  mandatory
     DESCRIPTION
	  "Identifies whether the LU is Type 0, 1, 2, 3 or 6.2"
     ::= { snaLuEntry 5 }

snaLuLocalAddress OBJECT-TYPE
     SYNTAX  OCTET STRING (SIZE(1)) 
     ACCESS  read-only
     STATUS  mandatory
     DESCRIPTION
	  "The local address for this LU. It is a byte with a value ranging 
	  in size from 0 to 255. For dependent LUs this value ranges from
	  1 to 255. For independent Lus this value is always 0."
     ::= { snaLuEntry 6 }

snaLuUserName OBJECT-TYPE
     SYNTAX  DisplayString (SIZE(0..8))
     ACCESS  read-only
     STATUS  mandatory
     DESCRIPTION
	  "The name of the non-sna terminal or SNA LU that 
	  is using this LU. This value does not apply to 
	  all LUs and contains a zero length string if 
	  not known or does not apply."
     ::= { snaLuEntry 7 }

snaLuPoolName OBJECT-TYPE
     SYNTAX  DisplayString (SIZE(0..8))
     ACCESS  read-only
     STATUS  mandatory
     DESCRIPTION
	  "The name of the LU pool to which this LU belongs. An LU
	  Pool is configured by the user.  It contains a group of
	  LUs any of which can be assigned to a user requesting an
	  LU by the Pool name.  May be  a zero length string if
	  this LU does not belong  to a pool."
   ::= { snaLuEntry 8 }

snaLuOperState OBJECT-TYPE
     SYNTAX  INTEGER {
	  inactive(1),
	  active(2)
	  }
     ACCESS  read-only
     STATUS  mandatory
     DESCRIPTION
	  "The current operational state of this LU: For dependent LUs active(2) 
	  indicates the SSCP-LU session is active. For Independent LUs active(2)
	  indicates that the LU is able to send or receive BINDs."
     ::= { snaLuEntry 9 }

snaLuAdminState OBJECT-TYPE
     SYNTAX  INTEGER {
	  other(1),
	  up(2),
	  down(3)
	  }
     ACCESS  read-write
     STATUS  mandatory
     DESCRIPTION
	  "This object is used by a management station to control 
	  the LU. Values up(2) and down(3) can be read or written,
	  while a value other(1) is read-only and indicates that
	  this variable has not been set since reboot."
     ::= { snaLuEntry 10 }

snaLuLastStateChange OBJECT-TYPE
     SYNTAX  TimeTicks
     ACCESS  read-only
     STATUS  mandatory
     DESCRIPTION
	  "The value of sysUpTime when the last state change 
	  occurred."
     ::= { snaLuEntry 11 }

snaLuActiveTime OBJECT-TYPE
     SYNTAX  TimeTicks
     ACCESS  read-only
     STATUS  mandatory
     DESCRIPTION
	  "The value of sysUpTime when this LU becomes active."
     ::= { snaLuEntry 12 }

snaLuBindFailureReason OBJECT-TYPE
     SYNTAX  INTEGER
     ACCESS  read-only
     STATUS  mandatory
     DESCRIPTION
	  "The sense code when there is a bind failure."
     ::= { snaLuEntry 13 }

-- *************************************************************** 
-- Traps - The traps identified here may be implemented in
--         the future.
-- ***************************************************************

-- snaLuTrap OBJECT IDENTIFIER ::= { snaLu 3 }
--     snaLuStateChangeTrap TRAP-TYPE
--     ENTERPRISE     snaLuTrap
--     VARIABLES { snaLuName,
--                  snaLuOperState }
--   STATUS    mandatory
--     DESCRIPTION
--          "The operational state of the LU has changed. Value
--          snaLuOperState indicates the operational state after
--          the change."
--     ::= 0
--
--     snaLuBindFailTrap TRAP-TYPE
--     ENTERPRISE      snaLuTrap
--     VARIABLES   { snaLuName,                       
--                    snaLuBindFailureReason }
--   STATUS  mandatory
--     DESCRIPTION
--          "The trap sent to indicate the failure of BIND.        
--          Value snaLuName SNA LU name.  Value
--          snaLuBindFailureReason indicates
--          the failure reason."
--     ::= 1


-- ***************************************************************
-- ApplicationLu group
--
-- It contains Managed Objects for Application LUs.
-- ***************************************************************

applicationLuTable OBJECT-TYPE
     SYNTAX  SEQUENCE OF AppLuEntry
     ACCESS  not-accessible
     STATUS  mandatory
     DESCRIPTION
	"Table of application LUs configuration and
	operational information."
     ::= { applicationLu 1 }

appLuEntry OBJECT-TYPE
     SYNTAX  AppLuEntry
     ACCESS  not-accessible
     STATUS  mandatory
     DESCRIPTION
	  "Contains configuration and operational variables 
	  of an application LU. Variables are read-only with
	  the exception of appLuAdminState which has read-write
	  access and is used by the Management station to control  
	  the state of the Application LU."
     INDEX   { appLuT5nodeIndex,
		appLuIndex }
     ::= { applicationLuTable 1 }

AppLuEntry ::= SEQUENCE {
     appLuT5nodeIndex
	  INTEGER,
     appLuIndex
	  INTEGER,
     appLuName
	  DisplayString,
     appLuConversionType
	  INTEGER,
     appLuHostInterfaceType
	  INTEGER,
     appLuApplicationName
	  DisplayString,
     appLuGatewayName
	  DisplayString,
     appLuAdminState
	  INTEGER,
     appLuOperState
	  INTEGER,
     appLuActiveTime
	  TimeTicks,
     appLuLastStateChange
	  TimeTicks,
     appLuBindFailureReason
	  INTEGER
     }

appLuT5nodeIndex OBJECT-TYPE
     SYNTAX  INTEGER
     ACCESS  read-only
     STATUS  mandatory
     DESCRIPTION
	  "Index in the t5nodeTable to which this application 
	  LU is associated."
     ::= { appLuEntry 1 }

appLuIndex OBJECT-TYPE
     SYNTAX  INTEGER
     ACCESS  read-only
     STATUS  mandatory
     DESCRIPTION
	  "Unique index of an application LU."
     ::= { appLuEntry 2 }

appLuName OBJECT-TYPE
     SYNTAX  DisplayString (SIZE(1..8))
     ACCESS  read-only
     STATUS  mandatory
     DESCRIPTION
	  "Configured name for this application LU."
     ::= { appLuEntry 3 }

appLuConversionType OBJECT-TYPE
     SYNTAX  INTEGER {
	  interactive (1),    -- Unisys host interactive
	  transparent (2),    -- EBCDIC passthrough mode
	  native (3),         -- 3270 ASCII native datastream
	  netvOper (4)        -- Netview operator control 
	  }
     ACCESS  read-only
     STATUS  mandatory
     DESCRIPTION
	  "Indicates the type of protocol conversion being
	  performed on behalf of the application LU."
     ::= { appLuEntry 4 }

appLuHostInterfaceType OBJECT-TYPE
     SYNTAX  INTEGER {
	  interactive (1),    -- Interactive interface
	  outbound (2),       -- Outbound (from Host) only
	  appc (3),           -- Unisys host APPC interface
	  batch (4),          -- Unisys host batch interface
	  rbfte(5)            -- Remote batch filetransfer extented
	   }
     ACCESS  read-only
     STATUS  mandatory
     DESCRIPTION
	  "Identifies the type of application interface used by
	  this application LU."
     ::= { appLuEntry 5 }

appLuApplicationName OBJECT-TYPE
     SYNTAX  DisplayString (SIZE (1..8))
     ACCESS  read-only
     STATUS  mandatory
     DESCRIPTION
	  "The name of the host application which uses this
	  application LU."
     ::= { appLuEntry 6 }

appLuGatewayName OBJECT-TYPE
     SYNTAX  DisplayString (SIZE(1..8))
     ACCESS  read-only
     STATUS  mandatory
     DESCRIPTION
	  "The name of the application gateway. The gateway is used
	  to group application LUs together for management
	  purposes."
   ::= { appLuEntry 7 }

appLuAdminState OBJECT-TYPE
     SYNTAX  INTEGER {
	  other (1),
	  up (2),
	  down (3)
	  }
     ACCESS  read-write
     STATUS  mandatory
     DESCRIPTION
	  "Used by the Management Station to control the
	  Application LU. Values up (2) and down (3) can be read or
	  written, while value other (1) is read-only and indicates
	  that this variable has not been set since reboot."
     ::= { appLuEntry 8 }

appLuOperState OBJECT-TYPE
     SYNTAX  INTEGER {
	  other (1),     -- none of the following
	  disabled (2),  -- not operational
	  inactive (3),  -- operational, no active sessions
	  active (4),    -- operational, active sessions
	  busy (5)       -- operational, but unable to accept sessions
	  }
     ACCESS  read-only
     STATUS  mandatory
     DESCRIPTION
	  "The current operational state of this application LU:
	  whether it is inactive, active, or has one of more active
	  sessions."
     ::= { appLuEntry 9 }

appLuActiveTime OBJECT-TYPE
     SYNTAX  TimeTicks
     ACCESS  read-only
     STATUS  mandatory
     DESCRIPTION
	  "The value of sysUpTime when this application LU 
	  becomes active."
     ::= { appLuEntry 10 }

appLuLastStateChange OBJECT-TYPE
     SYNTAX  TimeTicks
     ACCESS  read-only
     STATUS  mandatory
     DESCRIPTION
	  "The value of sysUpTime when the last state change 
	  occurred."
     ::= { appLuEntry 11 }

appLuBindFailureReason OBJECT-TYPE
     SYNTAX  INTEGER
     ACCESS  read-only
     STATUS  mandatory
     DESCRIPTION
	  "The sense code when there is a bind failure."
     ::= { appLuEntry 12 }

-- Application LU Batch device table
-- This table augments the applicationLuTable for application
-- LUs which have an appLuHostInterfaceType of batch (4) or
-- rbfte (5). It identifies the configured batch device names and
-- characteristics known to the application.

appLuBatchDeviceTable OBJECT-TYPE
     SYNTAX  SEQUENCE OF AppLuBatchDeviceEntry
     ACCESS  not-accessible
     STATUS  mandatory
     DESCRIPTION
	  "Table of configuration information for batch devices
	  associated with a batch type application LU."
     ::= { applicationLu 2 }

appLuBatchDeviceEntry OBJECT-TYPE
     SYNTAX  AppLuBatchDeviceEntry
     ACCESS  not-accessible
     STATUS  mandatory
     DESCRIPTION
	  "The entry contains configuration variables for batch
	  devices associated with batch type application LUs."
     INDEX   { appLuBatchDeviceT5nodeIndex,
	       appLuBatchDeviceLuIndex,
	       appLuBatchDeviceName }
     ::= { appLuBatchDeviceTable 1 }

AppLuBatchDeviceEntry ::= SEQUENCE {
     appLuBatchDeviceT5nodeIndex
	  INTEGER,
     appLuBatchDeviceLuIndex
	  INTEGER,
     appLuBatchDeviceName
	  DisplayString,
     appLuBatchDeviceType
	  INTEGER,
     appLuBatchDeviceNumber
	  INTEGER
     }

appLuBatchDeviceT5nodeIndex OBJECT-TYPE
     SYNTAX  INTEGER
     ACCESS  read-only
     STATUS  mandatory
     DESCRIPTION
	  "Index in the t5nodeTable to which this batch device is
	  associated."
     ::= { appLuBatchDeviceEntry 1 }

appLuBatchDeviceLuIndex OBJECT-TYPE
     SYNTAX  INTEGER
     ACCESS  read-only
     STATUS  mandatory
     DESCRIPTION
	  "The index of an application LU to which this batch
	  device is associated."
     ::= { appLuBatchDeviceEntry 2 }

appLuBatchDeviceName OBJECT-TYPE
     SYNTAX  DisplayString (SIZE(1..8))
     ACCESS  read-only
     STATUS  mandatory
     DESCRIPTION
	  "The configured name for this batch device."
     ::= { appLuBatchDeviceEntry 3 }

appLuBatchDeviceType OBJECT-TYPE
     SYNTAX  INTEGER {
	  console (1),
	  cardreader (2),
	  cardpunch (3),
	  printer (4)
	  }
     ACCESS  read-only
     STATUS  mandatory
     DESCRIPTION
	  "Indicates the type of batch device."
     ::= { appLuBatchDeviceEntry 4 }

appLuBatchDeviceNumber OBJECT-TYPE
     SYNTAX  INTEGER (1..14)
     ACCESS  read-only
     STATUS  mandatory
     DESCRIPTION
	  "A device number used to identify multiple devices of the
	  same type."
     ::= { appLuBatchDeviceEntry 5 }

-- *************************************************************** 
-- Traps - The traps identified here may be implemented in
--         the future.
-- ***************************************************************

-- AppLuTrap OBJECT IDENTIFIER ::= { applicationLu 3 }
--     snaLuStateChangeTrap TRAP-TYPE
--     ENTERPRISE     applLuTrap
--     VARIABLES { snaLuName,
--                  snaLuOperState }
--   STATUS    mandatory
--     DESCRIPTION
--          "The operational state of the Application LU has
--          changed. Value snaLuStateOperState indicates the 
--          operational state of the Application LU after
--          the change."
--     ::= 0
--
--     snaLuBindFailTrap TRAP-TYPE
--     ENTERPRISE      snaLuTrap
--     VARIABLES   { snaLuName,                       
--                    snaLuBindFailureReason }
--   STATUS  mandatory
--     DESCRIPTION
--          "The trap sent to indicate the failure of BIND.        
--          Value snaLuName is the SNA LU name.  Value
--          snaLuBindFailureReason indicates
--          the failure reason."
--     ::= 1



-- ***************** The snaSession group ********************
-- This group contains a table for SNA sessions. It contains
-- state and statistic information about active sessions, or
-- sessions that are initiating, queued, or terminating.
-- It is a representation of a session as seen from a network
-- addressable unit owned by an SNA/net Type 5 node.

snaSessionTable OBJECT-TYPE
     SYNTAX    SEQUENCE OF SnaSessionEntry
     ACCESS    not-accessible
     STATUS    mandatory
     DESCRIPTION
	  "Table containing dynamic statistics information relating
	  to SNA sessions."
     ::= { snaSession 1 }

snaSessionEntry OBJECT-TYPE
     SYNTAX    SnaSessionEntry
     ACCESS    not-accessible
     STATUS    mandatory
     DESCRIPTION
	  "Contains information about an SNA session. Objects in
	  this table have read-only access."

     INDEX     { snaSessT5nodeIndex,
		    snaSessNauName,
		    snaSessNauSessNumber }
     ::= { snaSessionTable 1 }

SnaSessionEntry ::= SEQUENCE {
     snaSessT5nodeIndex
	  INTEGER,
     snaSessNauName
	  DisplayString,
     snaSessNauSessNumber
	  INTEGER (1..65535),
     snaSessType
	  INTEGER,
     snaSessNauElementAddress
	  INTEGER (1..65535),
     snaSessState
	  INTEGER,
     snaSessActiveTime
	  Counter,
     snaSessSentBytes
	  Counter,
     snaSessReceivedBytes
	  Counter,
     snaSessSentRus
	  Counter,
     snaSessReceivedRus
	  Counter,
     snaSessSentNegativeResps
	  Counter,
     snaSessReceivedNegativeResps
	  Counter,
     snaSessPartnerNauName
	  DisplayString,
     snaSessPartnerNauSubarea
	  INTEGER,
     snaSessPartnerNauElementAddress
	  INTEGER (1..65535),
     snaSessVirtualRouteNumber
	 INTEGER (0..7),
     snaSessTransmissionPriority
	 INTEGER (0..2),
     snaSessProcCorrelationId
	  OCTET STRING,
     snaSessPluIndicator
	  INTEGER,
     snaSessModeName
	  DisplayString
     }

snaSessT5nodeIndex OBJECT-TYPE
     SYNTAX    INTEGER
     ACCESS    read-only
     STATUS    mandatory
     DESCRIPTION
	  "Identifies the Type 5 node which is associated with this
	  SNA session."
     ::= { snaSessionEntry 1 }

snaSessNauName OBJECT-TYPE
     SYNTAX    DisplayString (SIZE(1..8))
     ACCESS    read-only
     STATUS    mandatory
     DESCRIPTION
	  "The name of the SNA network addressable unit (NAU)."
     ::= { snaSessionEntry 2 }

snaSessNauSessNumber OBJECT-TYPE
     SYNTAX    INTEGER (1..65535)
     ACCESS    read-only
     STATUS    mandatory
     DESCRIPTION
	  "A number identifying the session number within the NAU."
     ::= { snaSessionEntry 3 }

snaSessType OBJECT-TYPE
     SYNTAX    INTEGER {
	  sscp-sscp (1),
	  lu-lu (2)
	  }
     ACCESS    read-only
     STATUS    mandatory
     DESCRIPTION
	  "Identifies the type of SNA session."
     ::= { snaSessionEntry 4 }

snaSessNauElementAddress OBJECT-TYPE
     SYNTAX    INTEGER
     ACCESS    read-only
     STATUS    mandatory
     DESCRIPTION
	  "The element address assigned to the SNA NAU by the Type
	  5 node."
     ::= { snaSessionEntry 5 }

snaSessState OBJECT-TYPE
     SYNTAX    INTEGER {
	  initiating (1),
	  terminating (2),
	  queued (3),
	  active (4)
	  }
     ACCESS    read-only
     STATUS    mandatory
     DESCRIPTION
	  "The state of the session.  Valid values for all session
	  types are: initiating (1), terminating (2), and active
	  (4). The value queued (3) is valid only for snaSessType
	  value of lu-lu (2). Some variables are unknown when the
	  session state is initiating (1) or queued (2). "
     ::= { snaSessionEntry 6 }

snaSessActiveTime OBJECT-TYPE
     SYNTAX    TimeTicks
     ACCESS    read-only
     STATUS    mandatory
     DESCRIPTION
	  "The value of sysUpTime when session becomes active."
     ::= { snaSessionEntry 7 }

snaSessSentBytes OBJECT-TYPE
     SYNTAX    Counter
     ACCESS    read-only
     STATUS    mandatory
     DESCRIPTION
	  "The number of bytes sent on this SNA session."         
     ::= { snaSessionEntry 8 }

snaSessReceivedBytes OBJECT-TYPE
     SYNTAX    Counter
     ACCESS    read-only
     STATUS    mandatory
     DESCRIPTION
	  "The number of bytes received on this session."
     ::= { snaSessionEntry 9 }

snaSessSentRus OBJECT-TYPE
     SYNTAX    Counter
     ACCESS    read-only
     STATUS    mandatory
     DESCRIPTION
	  "The number of RUs sent on this session."               
  ::= { snaSessionEntry 10 }

snaSessReceivedRus OBJECT-TYPE
     SYNTAX    Counter
     ACCESS    read-only
     STATUS    mandatory
     DESCRIPTION
	  "The number of RUs received on this session."          
     ::= { snaSessionEntry 11 }

snaSessSentNegativeResps OBJECT-TYPE
     SYNTAX    Counter
     ACCESS    read-only
     STATUS    mandatory
     DESCRIPTION
	  "The number of negative responses sent on 
	  this session."
     ::= { snaSessionEntry 12 }

snaSessReceivedNegativeResps OBJECT-TYPE
     SYNTAX    Counter
     ACCESS    read-only
     STATUS    mandatory
     DESCRIPTION
	  "The number of negative responses received 
	  on this session."
     ::= { snaSessionEntry 13 }

snaSessPartnerNauName OBJECT-TYPE
     SYNTAX    DisplayString (SIZE (0..8))
     ACCESS    read-only
     STATUS    mandatory
     DESCRIPTION
	  "The name of the session partner NAU. May be a zero
	  length string if not known."
     ::= { snaSessionEntry 14 }

snaSessPartnerNauSubarea OBJECT-TYPE
     SYNTAX    INTEGER (0..65535)
     ACCESS    read-only
     STATUS    mandatory
     DESCRIPTION
	  "The subarea number of the session partner NAU. Will be
	  zero if not known."
     ::= { snaSessionEntry 15 }

snaSessPartnerNauElementAddress OBJECT-TYPE
     SYNTAX    INTEGER (0..65536)
     ACCESS    read-only
     STATUS    mandatory
     DESCRIPTION
	  "The element address of the session partner NAU. Will be
	  zero if not known."
     ::= { snaSessionEntry 16 }

snaSessVirtualRouteNumber  OBJECT-TYPE
     SYNTAX INTEGER (0..7)
     ACCESS read-only
     STATUS mandatory
     DESCRIPTION
	  "A value indicating the virtual route number for this
	  session. Will be zero if not known."
     ::= { snaSessionEntry 17 }

snaSessTransmissionPriority     OBJECT-TYPE
     SYNTAX INTEGER (0..2)
     ACCESS read-only
     STATUS mandatory
     DESCRIPTION
	  "A transmission priority for this session. Will be zero
	  if not known."
     ::= { snaSessionEntry 18 }

-- The following variables apply only when snaSessType value is
-- lu-lu (2).

snaSessProcCorrelationId OBJECT-TYPE
     SYNTAX    OCTET STRING (SIZE (0..8))
     ACCESS    read-only
     STATUS    mandatory
     DESCRIPTION
	  "This variable uniquely identifies this lu-lu session.
	  Will contain a zero length string if snaSessType value is
	  not lu-lu (2)."
     ::= { snaSessionEntry 19 }

snaSessPluIndicator OBJECT-TYPE
     SYNTAX    INTEGER {
	  other (1),            
	  plu (2),            -- NAU is primary LU for session
	  slu (3)             -- NAU is secondary LU for session
	  }
     ACCESS    read-only
     STATUS    mandatory
     DESCRIPTION
	  "It indicates whether LU is primary or secondary for this
	  session. Will be other (1) if snaSessType value is not lu-lu
	  (2)."
     ::= { snaSessionEntry 20 }

snaSessModeName OBJECT-TYPE
     SYNTAX    DisplayString (SIZE(0..8))
     ACCESS    read-only
     STATUS    mandatory
     DESCRIPTION
	  "The name of the mode used for this session. Contains a
	  zero length string if snaSessType value is not lu-lu
	  (2)."
     ::= { snaSessionEntry 21 }


-- ******************* The snaLink information group ************
-- This group provides link specific configuration information
-- about links used for PU type 2 or PU type 4 (TGs).
-- ***************************************************************
-- The following table contains 802.2 specific configuration      
-- parameters.
-- ***************************************************************
snaLink802Dot2Table OBJECT-TYPE
     SYNTAX    SEQUENCE OF SnaLink802Dot2Entry
     ACCESS    not-accessible
     STATUS    mandatory
     DESCRIPTION
	  "This table contains Managed Objects which describe    
	  basic configuration parameters for PUs or TGs using
	  802.2 links."
     ::= { snaLink 1 }

snaLink802Dot2Entry OBJECT-TYPE
     SYNTAX    SnaLink802Dot2Entry
     ACCESS    not-accessible
     STATUS    mandatory
     DESCRIPTION
	  "Entry contains all link configuration parameters      
	  for one PU or TG. The objects in the entry have        
	  read-only access."
     INDEX     { snaLink802Dot2T5nodeIndex,
		    snaLink802Dot2Index }
     ::= { snaLink802Dot2Table 1 }

SnaLink802Dot2Entry ::= SEQUENCE {
     snaLink802Dot2T5nodeIndex
	  INTEGER (1..65535),
     snaLink802Dot2Index
	  INTEGER (1..65535),
     snaLink802Dot2SourceAddress
	  OCTET STRING,
     snaLink802Dot2SourceSAP
	  INTEGER,
     snaLink802Dot2DestinationAddress
	  OCTET STRING,
     snaLink802Dot2DestinationSAP
	  INTEGER,
     snaLink802Dot2MediaType
	  DisplayString,
     snaLink802Dot2Role
	  INTEGER,
     snaLink802Dot2LineName
	  DisplayString,
     snaLink802Dot2Port
	  INTEGER,
     snaLink802Dot2IfIndex
	  INTEGER
     }

snaLink802Dot2T5nodeIndex OBJECT-TYPE
     SYNTAX  INTEGER (1..65535)
     ACCESS  read-only
     STATUS  mandatory
     DESCRIPTION
	  "The index of the Type 5 node associated with this link."
     ::= { snaLink802Dot2Entry 1 }

snaLink802Dot2Index OBJECT-TYPE
     SYNTAX  INTEGER (1..65535)
     ACCESS  read-only
     STATUS  mandatory
     DESCRIPTION
	  "The index variable assigned by Agent."
     ::= { snaLink802Dot2Entry 2 }

snaLink802Dot2SourceAddress OBJECT-TYPE
     SYNTAX  OCTET STRING (SIZE(0..12))
     ACCESS  read-only
     STATUS  mandatory
     DESCRIPTION
	  "Medium Access Control (MAC) address of the source node
	  of this logical link."
     ::= { snaLink802Dot2Entry 3 }

snaLink802Dot2SourceSAP OBJECT-TYPE
     SYNTAX  INTEGER
     ACCESS  read-only
     STATUS  mandatory
     DESCRIPTION
	  "The source node's Service Access Point (SSAP)."
     ::= { snaLink802Dot2Entry 4 }

snaLink802Dot2DestinationAddress OBJECT-TYPE
     SYNTAX  OCTET STRING (SIZE(0..12))
     ACCESS  read-only
     STATUS  mandatory
     DESCRIPTION
	  "Medium Access Control (MAC) address of the destination
	  node of this logical link."
     ::= { snaLink802Dot2Entry 5 }

snaLink802Dot2DestinationSAP OBJECT-TYPE
     SYNTAX  INTEGER
     ACCESS  read-only
     STATUS  mandatory
     DESCRIPTION
	  "The Service Access Point used by the remote node
	  (DSAP)."
     ::= { snaLink802Dot2Entry 6 }

snaLink802Dot2MediaType OBJECT-TYPE
     SYNTAX  DisplayString (SIZE(1..10))
     ACCESS  read-only
     STATUS  mandatory
     DESCRIPTION
	  "The underlying physical media type: token-ring or
	  ethernet."
     ::= { snaLink802Dot2Entry 7 }

snaLink802Dot2Role OBJECT-TYPE
     SYNTAX  INTEGER {
	  secondary (1),
	  primary (2),
	  negotiable (3)
	  }
     ACCESS  read-only
     STATUS  mandatory
     DESCRIPTION
	  "The role of the PU used for the 802.2 link."
     ::= { snaLink802Dot2Entry 8 }

snaLink802Dot2LineName OBJECT-TYPE
     SYNTAX  DisplayString (SIZE(1..8))
     ACCESS  read-only
     STATUS  mandatory
     DESCRIPTION
	  "The configured name of the associated line."
     ::= { snaLink802Dot2Entry 9 }

snaLink802Dot2Port OBJECT-TYPE
     SYNTAX  OCTET STRING (SIZE (2))
     ACCESS  read-only
     STATUS  mandatory
     DESCRIPTION
	  "The physical port location in the system. The first 
	  octet contains the port processor id (0 to 255) and 
	  the second octet contains the line number (0-8) 
	  for line modules which support multiple lines. "
     ::= { snaLink802Dot2Entry 10 }

snaLink802Dot2IfIndex OBJECT-TYPE
     SYNTAX  INTEGER
     ACCESS  read-only
     STATUS  mandatory
     DESCRIPTION
	  "The IfIndex value of the interface used by this link."
     ::= { snaLink802Dot2Entry 11 }

-- ************************************************************
-- The following table contains SDLC-specific configuration
-- parameters.
-- ***************************************************************

snaLinkSdlcTable OBJECT-TYPE
     SYNTAX  SEQUENCE OF SnaLinkSdlcEntry
     ACCESS  not-accessible
     STATUS  mandatory
     DESCRIPTION
	  "This table contains Managed Objects which describe basic
	  configuration parameters for PUs using SDLC link."
      ::= { snaLink 2 }

snaLinkSdlcEntry OBJECT-TYPE
     SYNTAX  SnaLinkSdlcEntry
     ACCESS  not-accessible
     STATUS  mandatory
     DESCRIPTION
	  "Entry contains all link configuration parameters for one
	  PU. The objects in the entry have read-only access."

     INDEX   { snaLinkSdlcT5nodeIndex,
	    snaLinkSdlcIndex }
     ::= { snaLinkSdlcTable 1 }

SnaLinkSdlcEntry ::= SEQUENCE {
     snaLinkSdlcT5nodeIndex
	  INTEGER,
     snaLinkSdlcIndex
	  INTEGER,
     snaLinkSdlcDestinationStationAddr
	  OCTET STRING,
     snaLinkSdlcStationRole
	  INTEGER,
     snaLinkSdlcLineName
	  DisplayString,
     snaLinkSdlcPort
	  OCTET STRING,
     snaLinkSdlcIfIndex
	  INTEGER 
     }

snaLinkSdlcT5nodeIndex OBJECT-TYPE
     SYNTAX  INTEGER (1..65535)
     ACCESS  read-only
     STATUS  mandatory
     DESCRIPTION
	  "The index of the Type 5 node associated with this link."
     ::= { snaLinkSdlcEntry 1 }

snaLinkSdlcIndex OBJECT-TYPE
	  SYNTAX  INTEGER
	  ACCESS  read-only
	  STATUS  mandatory
	  DESCRIPTION
	  "The index variable assigned by Agent."
     ::= { snaLinkSdlcEntry 2 }

snaLinkSdlcDestinationStationAddr OBJECT-TYPE
     SYNTAX  OCTET STRING (SIZE(0..1))
     ACCESS  read-only
     STATUS  mandatory
     DESCRIPTION
	  "Station Address (1 byte) of the destination node."
     ::= { snaLinkSdlcEntry 3 }

snaLinkSdlcStationRole OBJECT-TYPE
     SYNTAX  INTEGER {
	  secondary (1),
	  primary (2),
	  negotiable (3)
	  }
	  ACCESS  read-only
	  STATUS  mandatory
	  DESCRIPTION
	  "The role of the local station in relation to a remote
	  one."
     ::= { snaLinkSdlcEntry 4 }

snaLinkSdlcLineName OBJECT-TYPE
     SYNTAX  DisplayString
     ACCESS  read-only
     STATUS  mandatory
     DESCRIPTION
	  "The configured name of the associated line."
     ::= { snaLinkSdlcEntry 5 }

snaLinkSdlcPort OBJECT-TYPE
     SYNTAX  OCTET STRING (SIZE (2))
     ACCESS  read-only
     STATUS  mandatory
     DESCRIPTION
	  "The physical port location in the system. The first 
	  octet contains the port processor id (0 to 255) and 
	  the second octet contains the line number (0-8) for 
	  line modules which support multiple lines. "
     ::= { snaLinkSdlcEntry 6 }

snaLinkSdlcIfIndex OBJECT-TYPE
     SYNTAX  INTEGER
     ACCESS  read-only
     STATUS  mandatory
     DESCRIPTION
	  "The IfIndex value of the interface used by this link."
     ::= { snaLinkSdlcEntry 7 }

-- ***************************************************************
-- The following table contains QLLC specific configuration
-- parameters.
-- ***************************************************************

snaLinkQllcTable OBJECT-TYPE
     SYNTAX  SEQUENCE OF SnaLinkQllcEntry
     ACCESS  not-accessible
     STATUS  mandatory
     DESCRIPTION
	  "This table contains Managed Objects which describe    
	  basic configuration parameters for PUs using QLLC      
	  links." 
      ::= { snaLink 3 }

snaLinkQllcEntry OBJECT-TYPE
     SYNTAX  SnaLinkQllcEntry
     ACCESS  not-accessible
     STATUS  mandatory
     DESCRIPTION
	  "Entry contains all link configuration parameters
	  for one PU. The objects in the entry have read-only
	  access."

     INDEX   { snaLinkQllcT5nodeIndex,
	    snaLinkQllcIndex }
     ::= { snaLinkQllcTable 1 }

SnaLinkQllcEntry ::= SEQUENCE {
     snaLinkQllcT5nodeIndex
	  INTEGER (1..65535),
     snaLinkQllcIndex
	  INTEGER (1..65535),
     snaLinkQllcLcn
	  INTEGER,
     snaLinkQllcSourceDteAddr
	  OCTET STRING,
     snaLinkQllcDestinationDteAddr
	  OCTET STRING,
     snaLinkQllcRole
	  INTEGER,
     snaLinkQllcPdnGroupName
	  DisplayString,
     snaLinkQllcLineName
	  DisplayString,
     snaLinkQllcPort
	  OCTET STRING,
     snaLinkQllcIfIndex
	  INTEGER
     }

snaLinkQllcT5nodeIndex OBJECT-TYPE
     SYNTAX  INTEGER (1..65535)
     ACCESS  read-only
     STATUS  mandatory
     DESCRIPTION
	  "The index of the Type 5 node associated with this link."
     ::= { snaLinkQllcEntry 1 }

snaLinkQllcIndex OBJECT-TYPE
     SYNTAX  INTEGER (1..65535)
     ACCESS  read-only
     STATUS  mandatory
     DESCRIPTION
	  "The index variable assigned by Agent."
      ::= { snaLinkQllcEntry 2 }

snaLinkQllcLcn OBJECT-TYPE
     SYNTAX  INTEGER
     ACCESS  read-only
     STATUS  mandatory
     DESCRIPTION
	  "The Logical Channel Number (LCN) used by the source node
	  in the case of SVC. Identifies the Circuit number in the
	  case of PVC."
     ::= { snaLinkQllcEntry 3 }

snaLinkQllcSourceDteAddr OBJECT-TYPE
     SYNTAX  OCTET STRING (SIZE(0..15))
     ACCESS  read-only
     STATUS  mandatory
     DESCRIPTION
	  "The DTE Address (15 bytes) of the source node."
     ::= { snaLinkQllcEntry 4 }

snaLinkQllcDestinationDteAddr OBJECT-TYPE
     SYNTAX  OCTET STRING (SIZE(0..15))
     ACCESS  read-only
     STATUS  mandatory
     DESCRIPTION
	  "The DTE Address (15 bytes) of the destination node."
     ::= { snaLinkQllcEntry 5 }

snaLinkQllcRole OBJECT-TYPE
     SYNTAX  INTEGER {
	  secondary (1),
	  primary (2),
	  negotiable (3)
	  }
	  ACCESS  read-only
	  STATUS  mandatory
	  DESCRIPTION
	       "The role of the QLLC PU in relation to a remote
	       one."
     ::= { snaLinkQllcEntry 6 }


snaLinkQllcPdnGroupName OBJECT-TYPE  
     SYNTAX  DisplayString (SIZE(1..8))
     ACCESS  read-only
     STATUS  mandatory
     DESCRIPTION
	  "Name of the associated PDNGROUP."
     ::= { snaLinkQllcEntry 7 }

snaLinkQllcLineName OBJECT-TYPE
     SYNTAX  DisplayString (SIZE(1..8))
     ACCESS  read-only
     STATUS  mandatory
     DESCRIPTION
	  "The configured name of the associated line."
     ::= { snaLinkQllcEntry 8 }

snaLinkQllcPort OBJECT-TYPE
     SYNTAX  OCTET STRING (SIZE (2))
     ACCESS  read-only
     STATUS  mandatory
     DESCRIPTION
	  "The physical port location in the system. The first 
	  octet contains the port processor id (0 to 255) and 
	  the second octet contains the line number (0-8) for 
	  line modules which support multiple lines. "
     ::= { snaLinkQllcEntry 9 }

snaLinkQllcIfIndex OBJECT-TYPE
     SYNTAX  INTEGER
     ACCESS  read-only
     STATUS  mandatory
     DESCRIPTION
	  "The IfIndex value of the interface used by this link."
     ::= { snaLinkQllcEntry 10 }

-- ************************************************************
-- The following table contains CHANNEL-specific configuration
-- parameters.
-- ***************************************************************

snaLinkChannelTable OBJECT-TYPE
     SYNTAX  SEQUENCE OF SnaLinkChannelEntry
     ACCESS  not-accessible
     STATUS  mandatory
     DESCRIPTION
	  "This table contains Managed Objects which describe basic
	  configuration parameters for PUs using Channel link."
      ::= { snaLink 4 }

snaLinkChannelEntry OBJECT-TYPE
     SYNTAX  SnaLinkChannelEntry
     ACCESS  not-accessible
     STATUS  mandatory
     DESCRIPTION
	  "Entry contains all link configuration parameters for one
	  PU. The objects in the entry have read-only access."

     INDEX   { snaLinkChannelT5nodeIndex,
	    snaLinkChannelIndex }
     ::= { snaLinkChannelTable 1 }

SnaLinkChannelEntry ::= SEQUENCE {
     snaLinkChannelT5nodeIndex
	  INTEGER,
     snaLinkChannelIndex
	  INTEGER,
     snaLinkChannelLineName
	  DisplayString,
     snaLinkChannelPort
	  OCTET STRING,
     snaLinkChannelIfIndex
	  INTEGER
	  }

snaLinkChannelT5nodeIndex OBJECT-TYPE
     SYNTAX  INTEGER (1..65535)
     ACCESS  read-only
     STATUS  mandatory
     DESCRIPTION
	  "The index of the Type 5 node associated with this link."
     ::= { snaLinkChannelEntry 1 }

snaLinkChannelIndex OBJECT-TYPE
	  SYNTAX  INTEGER
	  ACCESS  read-only
	  STATUS  mandatory
	  DESCRIPTION
	  "The index variable assigned by Agent."
     ::= { snaLinkChannelEntry 2 }

snaLinkChannelLineName OBJECT-TYPE
     SYNTAX  DisplayString (SIZE(1..8))
     ACCESS  read-only
     STATUS  mandatory
     DESCRIPTION
	  "The configured name of the associated line."
     ::= { snaLinkChannelEntry 3 }

snaLinkChannelPort OBJECT-TYPE
     SYNTAX  OCTET STRING (SIZE (2))
     ACCESS  read-only
     STATUS  mandatory
     DESCRIPTION
	  "The physical port location in the system. The first 
	  octet contains the port processor id (0 to 255) and 
	  the second octet contains the line number (0-8) for 
	  line modules which support multiple lines. "
     ::= { snaLinkChannelEntry 4 }

snaLinkChannelIfIndex OBJECT-TYPE
     SYNTAX  INTEGER
     ACCESS  read-only
     STATUS  mandatory
     DESCRIPTION
	  "The IfIndex value of the interface used by this link."
     ::= { snaLinkChannelEntry 5 }

-- ************************************************************
-- The following table contains Internal Link-specific
-- configuration parameters.
-- ***************************************************************

snaLinkIntTable OBJECT-TYPE
     SYNTAX  SEQUENCE OF SnaLinkIntEntry
     ACCESS  not-accessible
     STATUS  mandatory
     DESCRIPTION
	  "This table contains Managed Objects which describe basic
	  configuration parameters Internal links."
      ::= { snaLink 5 }

snaLinkIntEntry OBJECT-TYPE
     SYNTAX  SnaLinkIntEntry
     ACCESS  not-accessible
     STATUS  mandatory
     DESCRIPTION
	  "Entry contains all link configuration parameters for one
	  PU. The objects in the entry have read-only access."
     INDEX   { snaLinkIntT5nodeIndex,
	    snaLinkIntIndex }
     ::= { snaLinkIntTable 1 }

SnaLinkIntEntry ::= SEQUENCE {
     snaLinkIntT5nodeIndex
	  INTEGER,
     snaLinkIntIndex
	  INTEGER,
     snaLinkIntServiceType
	  INTEGER,
     snaLinkIntOutputCredit
	  INTEGER (1..15),
     snaLinkIntOutputPacing
	  INTEGER (1..15)
     }

snaLinkIntT5nodeIndex OBJECT-TYPE
     SYNTAX  INTEGER (1..65535)
     ACCESS  read-only
     STATUS  mandatory
     DESCRIPTION
	  "The index of the Type 5 node associated with this link."
     ::= { snaLinkIntEntry 1 }

snaLinkIntIndex OBJECT-TYPE
	  SYNTAX  INTEGER
	  ACCESS  read-only
	  STATUS  mandatory
	  DESCRIPTION
	  "The index variable assigned by Agent."
     ::= { snaLinkIntEntry 2 }

snaLinkIntServiceType OBJECT-TYPE
     SYNTAX  INTEGER {
	  tglink (1),    -- TG between SNA/net nodes
	  uniscope (2),  -- Uniscope terminal SNA access(PU T2.0)
	  ds3270 (3)     -- 3270 datastream SNA access(PU T2.0) 
			 -- Provides:
			 -- Conversion of Bi-sync 3270 or TN3270 
			 -- data streams to SNA. Also Terminal 
			 -- Operator Menu Facility (TOMF) 
			 -- access to IBM applications for 3270
			 -- devices.
	 
	  }               

     ACCESS  read-only
     STATUS  mandatory
     DESCRIPTION
	  "The type of the internal link."
     ::= { snaLinkIntEntry 3 }

snaLinkIntOutputCredit OBJECT-TYPE
     SYNTAX  INTEGER (1..15)
     ACCESS  read-only
     STATUS  mandatory
     DESCRIPTION
	  "This value is used to control the flow of data on
	  the internal link."
     ::= { snaLinkIntEntry 4 }

snaLinkIntOutputPacing OBJECT-TYPE
     SYNTAX  INTEGER (1..15)
     ACCESS  read-only
     STATUS  mandatory
     DESCRIPTION
	  "This value is used to control the flow of data on
	  the internal link."
     ::= { snaLinkIntEntry 5 }
END
