-- This file is the MIB file for a  V.34 modem.
-- This file, and the associated modem.cdl file, 
-- were created to manage the internal modem for NEPTUNE.
-- Last modified 12/10/96 PCK
Wellfleet-Modem-MIB DEFINITIONS ::= BEGIN

   IMPORTS

      Counter
        FROM RFC1155-SMI
      OBJECT-TYPE
        FROM RFC-1212
      DisplayString
        FROM RFC1213-MIB
      wfModemGroup
        FROM Wellfleet-COMMON-MIB;

      wfModemTable OBJECT-TYPE
          SYNTAX   SEQUENCE OF WfModemEntry
          ACCESS   not-accessible
          STATUS   mandatory
          DESCRIPTION
                  "Modem line record."
          ::= { wfModemGroup 1 }

      wfModemEntry OBJECT-TYPE
          SYNTAX   WfModemEntry
          ACCESS   not-accessible
          STATUS   mandatory
          DESCRIPTION
                  " An entry in the MODEM table"
          INDEX    { wfModemSlot,
                     wfModemConnector }
          ::= { wfModemTable 1 }

       WfModemEntry ::= SEQUENCE {
    	  wfModemDelete
              INTEGER,
          wfModemSlot
              INTEGER,
          wfModemConnector
              INTEGER,
          wfModemIdSwRev
              DisplayString,
          wfModemIdHwRev
              DisplayString,
          wfModemLineState
              INTEGER,
          wfModemConnectionFailReason
              INTEGER,
          wfModemCfgFactoryDefaults
              INTEGER,
          wfModemCfgInitString
              DisplayString,
          wfModemCfgDefaultString
              DisplayString,
          wfModemCfgResultCodeString
              DisplayString,
          wfModemCfgState
              INTEGER,
          wfModemCfgCountry
              INTEGER,
          wfModemV54Lpbk
              INTEGER,
          wfModemV54Timer
              INTEGER,
          wfModemV54Errors
              Counter,
          wfModemV54RemLpbkDetect
              INTEGER,
          wfModemPhoneNumber
              DisplayString,
          wfModemInitState
              INTEGER,
          wfModemUnitReset
              INTEGER,
	  wfModemType
	      INTEGER
       }  

      wfModemDelete OBJECT-TYPE
        SYNTAX	INTEGER {
    		    created(1),
    		    deleted(2)
    		}
        ACCESS	read-write
        STATUS	mandatory
        DESCRIPTION
                "Create/Delete parameter"
        DEFVAL	{ created }
        ::= { wfModemEntry 1 }

      wfModemSlot OBJECT-TYPE
          SYNTAX  INTEGER
          ACCESS  read-only
          STATUS  mandatory
          DESCRIPTION
             "Instance ID Slot, filled in by driver"
          ::= { wfModemEntry 2}

      wfModemConnector OBJECT-TYPE
          SYNTAX  INTEGER
          ACCESS  read-only
          STATUS  mandatory
          DESCRIPTION
             "Instance ID Connector, filled in by the driver."
          ::= { wfModemEntry 3 }

       wfModemIdSwRev OBJECT-TYPE
          SYNTAX   DisplayString (SIZE (0..79))
          ACCESS   read-only
          STATUS   mandatory
          DESCRIPTION
                  "A textual description of the modem's
                   firmware version number."
          ::= { wfModemEntry 4 }

       wfModemIdHwRev OBJECT-TYPE
          SYNTAX   DisplayString (SIZE (0..79))
          ACCESS   read-only
          STATUS   mandatory
          DESCRIPTION
                  "A textual description of the revision
                   number of the modem daughter card."
          ::= { wfModemEntry 5 }

       wfModemLineState OBJECT-TYPE
          SYNTAX  INTEGER {
                       unknown(1),
                       onHook(2),
                       offHook(3),
                       connected(4),
                       busiedOut(5),
                       reset(6)
                  }
          ACCESS  read-only
          STATUS  mandatory
          DESCRIPTION
                  "Indicates the state of the modem."
          DEFVAL { unknown }
          ::= { wfModemEntry 6 } 

       wfModemConnectionFailReason OBJECT-TYPE
          SYNTAX  INTEGER {
                       normal(1),
                       lossOfCarrier(2),
                       v42NegotiationFailed(3),  
                       noCommonProtocol(4),
                       remoteDisconnect(5),
                       noResponseFromRemote(6),
                       protocolViolation(7)
                  }
          ACCESS  read-only
          STATUS  mandatory
          DESCRIPTION
                  "indicates the reason for the last failed connection"
          ::= { wfModemEntry 7 }

       wfModemCfgFactoryDefaults OBJECT-TYPE
          SYNTAX  INTEGER {
                       enabled(1),
                       disabled(2)
                  }
          ACCESS  read-write
          STATUS  mandatory
          DESCRIPTION
                  "This object indicates if factory defaults are to be loaded.
                   If set to enabled(1), factory defaults are loaded. If set
                   to disabled(2), the initialization string in 
                   wfModemCfgInitString is sent to the modem."
          DEFVAL { enabled }
          ::= { wfModemEntry 8 }

       wfModemCfgInitString OBJECT-TYPE
          SYNTAX  DisplayString
          ACCESS  read-write
          STATUS  mandatory
          DESCRIPTION
                  "An initialization string that will be sent to the modem
                   each time the modem is rebooted."
          ::= { wfModemEntry 9 }

       wfModemCfgDefaultString OBJECT-TYPE
          SYNTAX  DisplayString
          ACCESS  read-only
          STATUS  mandatory
          DESCRIPTION
                  "The string contains AT comands for initializing the
                   modem every time the modem comes up, regardless of 
                   configuration."
          ::= { wfModemEntry 10 }

       wfModemCfgResultCodeString OBJECT-TYPE
          SYNTAX  DisplayString
          ACCESS  read-only
          STATUS  mandatory
          DESCRIPTION
                  "The ASCII response string returned by the modem.
                   Response strings will be returned in response to
                   last command to the modem and in response to activity
                   on the line."
          ::= { wfModemEntry 11 }

       wfModemCfgState OBJECT-TYPE
          SYNTAX  INTEGER {
                       cfgIdle(1),
                       cfgInProgress(2),
                       cfgResponseReturned(3)
                  }
          ACCESS  read-write
          STATUS  mandatory
          DESCRIPTION
                  "Indicates the state of AT command processing. When a
                   new initialization string is to be sent to the modem, 
                   the sender sets the state to cfgInProgress(2). After the
                   command has been sent to the modem, and a result code
                   has been returned, the state is set to 
                   cfgResponseReturned(3). Once the sender
                   has received the return code, the sender sets the state
                   to cfgIdle(1)."
           DEFVAL { cfgIdle }
           ::= { wfModemEntry 12 }

       wfModemCfgCountry OBJECT-TYPE
          SYNTAX   INTEGER {
                        northAmerica(1),
                        japan(2),
                        uk(3),
                        germany(4)
                    }
          ACCESS    read-write
          STATUS    mandatory
          DESCRIPTION
                   "Identifies the country the modem is designed to operate
                    in. This object is not read from the modem directly.
                    It must be entered manually when configuring the modem."
          DEFVAL { northAmerica }
          ::= { wfModemEntry 13 }

      wfModemV54Lpbk OBJECT-TYPE
          SYNTAX      INTEGER 
          {
               noLpbk(1),
               localAnlgLpbk(2),
               localDigLpbk(3),
               remDigLpbk(4),
               remDigLpbkWPattern(5),
               localAnlgLpbkWPattern(6)
          }
          ACCESS      read-write
          STATUS      mandatory
          DESCRIPTION
             "Enables the operator to control, and examine the 
             state of, V.54 loopbacks within the modem. This object
             equates to the AT&Tn command."
          DEFVAL { noLpbk }
          ::= { wfModemEntry 14 }

       wfModemV54Timer OBJECT-TYPE
          SYNTAX       INTEGER (0..255)
          ACCESS       read-write
          STATUS       mandatory
          DESCRIPTION
             "Duration in seconds that a test specified in wfModemV.54Lpbk
              is to execute."
          DEFVAL { 0 }
          ::= { wfModemEntry 15 }

       wfModemV54Errors OBJECT-TYPE
          SYNTAX       Counter
          ACCESS       read-only
          STATUS       mandatory
          DESCRIPTION
             "Indicates the number of errors reported during the last
              loopback test. This count will only be updated for 
              loopbacks with test pattern."
          ::= { wfModemEntry 16 }

        wfModemV54RemLpbkDetect OBJECT-TYPE
          SYNTAX  INTEGER {
                       enabled(1),
                       disabled(2)
                  }
          ACCESS  read-write
          STATUS  mandatory
          DESCRIPTION
                  "This object controls whether or not this modem will
                   acknowledge V.54 Remote Loop 2 requests from a remote
                   Site. When ENABLED, this modem can be put into a
                   digital loopback from a remote site. When DISABLED,
                   the modem will reject requests from the remote site."
          DEFVAL { enabled }
          ::= { wfModemEntry 17 }

        wfModemPhoneNumber OBJECT-TYPE
          SYNTAX       DisplayString
          ACCESS       read-write
          STATUS       mandatory
          DESCRIPTION
             "Contains the phone number for the modem to dial."
          ::= { wfModemEntry 18 }

        wfModemInitState OBJECT-TYPE
          SYNTAX       INTEGER {
                            startup(1),
                            sccInit(2),
                            getInfo(3),
                            setDefaults(4),
                            initialization(5),
                            phoneNumber(6),
                            loopback(7),
                            initComplete(8)
                       }
          ACCESS       read-only
          STATUS       mandatory
          DESCRIPTION
             "Indictes the state of the modem initialization sequence. The state will
              freeze in the state that fails when a failure is detected. Otherwise,
              the state will be set to initComplete when initialization completes
              successfully."
          ::= {wfModemEntry 19 }

      wfModemUnitReset OBJECT-TYPE
          SYNTAX  INTEGER {
                      resetUnit(1)
                  }
          ACCESS  read-write
          STATUS  mandatory
          DESCRIPTION
             "Enables the operator to remotely reset the unit.
              Using this command will cause the unit to terminate
              all its connections and drop data."
          ::= { wfModemEntry 20 }

      wfModemType OBJECT-TYPE
	  SYNTAX  INTEGER (0..255)
	  ACCESS  read-write
	  STATUS  mandatory
	  DESCRIPTION
	     "Enables a user to specify a modem type attached to the port
	      thus enabling Site Manager to put a preconfigured modem init
	      string in the wfModemInitString entry. The list of modems and
	      init strings are stored in Site Manager for flexibility. This
	      type can be set to Custom and a user defined string can be
	      entered in wfModemInitString field."
	   ::= { wfModemEntry 21 }

    END -- Wellfleet-MODEM-MIB
