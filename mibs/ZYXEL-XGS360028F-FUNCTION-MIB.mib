ZYXEL-XGS360028F-FUNCTION-MIB DEFINITIONS ::= BEGIN

IMPORTS
    DisplayString,MacAddress FROM SNMPv2-TC
    MODULE-COMPLIANCE,OBJECT-GROUP, NOTIFICATION-GROUP       FROM SNMPv2-CONF
    ifIndex    FROM RFC1213-MIB
    enterprises,MODULE-IDENTITY,OBJECT-TYPE,NOTIFICATION-TYPE,Counter32,Counter64,IpAddress        FROM SNMPv2-SMI
    InetAddress                   FROM INET-ADDRESS-MIB
    MacAddress FROM BRIDGE-MIB;

zyxel MODULE-IDENTITY
        LAST-UPDATED "201205150000Z"
        ORGANIZATION "Corp."
        CONTACT-INFO
            ""
        DESCRIPTION
            ""
        ::= { enterprises 890 }

products                                                         OBJECT IDENTIFIER ::= { zyxel 1 }

accessSwitch                                                    OBJECT IDENTIFIER ::= { products 5 }

esSeries                                                        OBJECT IDENTIFIER ::= { accessSwitch 8 }

xgs360028fProductId                                             OBJECT IDENTIFIER ::= { esSeries 78 }

xgs360028fSystem                                                OBJECT IDENTIFIER ::= { xgs360028fProductId 1 }

xgs360028fSystemInformation                                     OBJECT IDENTIFIER ::= { xgs360028fSystem 1 }

xgs360028fModelName OBJECT-TYPE
   SYNTAX       DisplayString
   MAX-ACCESS   read-only
   STATUS       current
   DESCRIPTION
       ""
 ::= { xgs360028fSystemInformation 1 }

xgs360028fBIOSVersion OBJECT-TYPE
   SYNTAX       DisplayString
   MAX-ACCESS   read-only
   STATUS       current
   DESCRIPTION
       ""
   ::= { xgs360028fSystemInformation 2 }

xgs360028fFirmwareVersion OBJECT-TYPE
   SYNTAX       DisplayString
   MAX-ACCESS   read-only
   STATUS       current
   DESCRIPTION
       ""
   ::= { xgs360028fSystemInformation 3 }

xgs360028fHardwareMechanicalVersion OBJECT-TYPE
   SYNTAX       DisplayString
   MAX-ACCESS   read-only
   STATUS       current
   DESCRIPTION
       ""
   ::= { xgs360028fSystemInformation 4 }

xgs360028fSeriesNumber OBJECT-TYPE
   SYNTAX       DisplayString
   MAX-ACCESS   read-only
   STATUS       current
   DESCRIPTION
       ""
   ::= { xgs360028fSystemInformation 5 }

xgs360028fHostMACAddress OBJECT-TYPE
   SYNTAX       MacAddress
   MAX-ACCESS   read-only
   STATUS       current
   DESCRIPTION
       ""
   ::= { xgs360028fSystemInformation 6 }

xgs360028fConsoleBaudrate OBJECT-TYPE
   SYNTAX       DisplayString
   MAX-ACCESS   read-only
   STATUS       current
   DESCRIPTION
       ""
   ::= { xgs360028fSystemInformation 7 }

xgs360028fRAMSize OBJECT-TYPE
   SYNTAX       DisplayString
   MAX-ACCESS   read-only
   STATUS       current
   DESCRIPTION
       ""
   ::= { xgs360028fSystemInformation 8 }

xgs360028fFlashSize OBJECT-TYPE
   SYNTAX       DisplayString
   MAX-ACCESS   read-only
   STATUS       current
   DESCRIPTION
       ""
   ::= { xgs360028fSystemInformation 9 }

xgs360028fBridgeFBDSize OBJECT-TYPE
   SYNTAX       DisplayString
   MAX-ACCESS   read-only
   STATUS       current
   DESCRIPTION
       ""
   ::= { xgs360028fSystemInformation 10 }

xgs360028fTransmitQueue OBJECT-TYPE
   SYNTAX       DisplayString
   MAX-ACCESS   read-only
   STATUS       current
   DESCRIPTION
       ""
   ::= { xgs360028fSystemInformation 11 }

xgs360028fMaximumFrameSize OBJECT-TYPE
   SYNTAX       DisplayString
   MAX-ACCESS   read-only
   STATUS       current
   DESCRIPTION
       ""
   ::= { xgs360028fSystemInformation 12 }

xgs360028fCPULoad OBJECT-TYPE
   SYNTAX       DisplayString
   MAX-ACCESS   read-only
   STATUS       current
   DESCRIPTION
       ""
   ::= { xgs360028fSystemInformation 13 }
   
xgs360028fFanSpeed OBJECT-TYPE
   SYNTAX       DisplayString
   MAX-ACCESS   read-only
   STATUS       current
   DESCRIPTION
       ""
   ::= { xgs360028fSystemInformation 14 }

xgs360028fPowers OBJECT-TYPE
   SYNTAX       DisplayString
   MAX-ACCESS   read-only
   STATUS       current
   DESCRIPTION
       ""
   ::= { xgs360028fSystemInformation 15 }
      
xgs360028fTemperature1 OBJECT-TYPE
   SYNTAX       DisplayString
   MAX-ACCESS   read-only
   STATUS       current
   DESCRIPTION
       ""
   ::= { xgs360028fSystemInformation 16 }

xgs360028fTemperature2 OBJECT-TYPE
   SYNTAX       DisplayString
   MAX-ACCESS   read-only
   STATUS       current
   DESCRIPTION
       ""
   ::= { xgs360028fSystemInformation 17 }
   
xgs360028fTemperature3 OBJECT-TYPE
   SYNTAX       DisplayString
   MAX-ACCESS   read-only
   STATUS       current
   DESCRIPTION
       ""
   ::= { xgs360028fSystemInformation 18 }

xgs360028fTemperature4 OBJECT-TYPE
   SYNTAX       DisplayString
   MAX-ACCESS   read-only
   STATUS       current
   DESCRIPTION
       ""
   ::= { xgs360028fSystemInformation 19 }   
    

xgs360028fSystemTime                                            OBJECT IDENTIFIER ::= { xgs360028fSystem 2 }

xgs360028fSystemTimeManual                                      OBJECT IDENTIFIER ::= { xgs360028fSystemTime 1 }

xgs360028fSystemTimeManualClockSource OBJECT-TYPE
   SYNTAX       INTEGER(0|1)
   MAX-ACCESS   read-write
   STATUS       current
   DESCRIPTION
       "default: 0,
        0 : Use Local Settings,
        1 : Use NTP Server."
   ::= { xgs360028fSystemTimeManual 1 }
   
xgs360028fSystemTimeManualLocaltime OBJECT-TYPE
   SYNTAX       DisplayString
   MAX-ACCESS   read-write
   STATUS       current
   DESCRIPTION
       "Get/Set the system time of the device.
        The input format is 'Year-Month-Day Hour:Minute:Second'.
        ex: 2011-01-01 05:43:05  means 2011/1/1 - 05:43:05 .
        The value range:
        Year    : 2010 - 2090,
        Mouth   : 1 - 12,
        Day     : 1 - 31,
        Hour    : 0 - 23,
        Minute  : 0 - 59,
        Sec     : 0 - 59."
   ::= { xgs360028fSystemTimeManual 2 }

xgs360028fSystemTimeManualTimeZoneOffset OBJECT-TYPE
   SYNTAX       INTEGER(-720..780)
   MAX-ACCESS   read-write
   STATUS       current
   DESCRIPTION
       "Get/Set the NTP Time Zone.
        The value range is between -720 and 780 (minutes)."
   ::= { xgs360028fSystemTimeManual 3 }
   
xgs360028fSystemTimeManualDaylightSavings OBJECT-TYPE
   SYNTAX       INTEGER(0|1)
   MAX-ACCESS   read-write
   STATUS       current
   DESCRIPTION
       "default: 0,
        0 : Disable,
        1 : Enable."
   ::= { xgs360028fSystemTimeManual 4 }
   
xgs360028fSystemTimeManualTimeSetOffset OBJECT-TYPE
   SYNTAX       INTEGER(1..1440)
   MAX-ACCESS   read-write
   STATUS       current
   DESCRIPTION
       "Get/Set the Daylight Saving Time.
        The value range is between 1 and 1440 (minutes),
        Default : 60 (minutes)."
   ::= { xgs360028fSystemTimeManual 5 }
   
xgs360028fSystemTimeManualDaylightSavingsType OBJECT-TYPE
   SYNTAX       INTEGER(0|1)
   MAX-ACCESS   read-write
   STATUS       current
   DESCRIPTION
       "default: 0,
        0 : By dates,
        1 : Recurring."
   ::= { xgs360028fSystemTimeManual 6 }
   
xgs360028fSystemTimeManualDaylightSavingsBydatesFrom OBJECT-TYPE
   SYNTAX       DisplayString
   MAX-ACCESS   read-write
   STATUS       current
   DESCRIPTION
       "Get/Set the Start time of By dates Daylight Savings.
        The input format is 'Year-Month-Day Hour:Minute'.
        ex: 2011-01-01 05:43  means 2011/1/1 - 05:43 .
        The value range:
        Year    : 2010 - 2090,
        Mouth   : 1 - 12,
        Day     : 1 - 31,
        Hour    : 0 - 23,
        Minute  : 0 - 59."
   ::= { xgs360028fSystemTimeManual 7 }
   
xgs360028fSystemTimeManualDaylightSavingsBydatesTo OBJECT-TYPE
   SYNTAX       DisplayString
   MAX-ACCESS   read-write
   STATUS       current
   DESCRIPTION
       "Get/Set the End time of By dates Daylight Savings.
        The input format is 'Year-Month-Day Hour:Minute'.
        ex: 2011-01-01 05:43  means 2011/1/1 - 05:43 .
        The value range:
        Year    : 2010 - 2090,
        Mouth   : 1 - 12,
        Day     : 1 - 31,
        Hour    : 0 - 23,
        Minute  : 0 - 59."
   ::= { xgs360028fSystemTimeManual 8 }

xgs360028fSystemTimeManualDaylightSavingsRecurringDayFrom OBJECT-TYPE
   SYNTAX       INTEGER(0..6)
   MAX-ACCESS   read-write
   STATUS       current
   DESCRIPTION
       "Get/Set the Daylight Saving Time Day From.
        0 : Sun, 1 : Mon, 2 : Tue, 3 : Wed, 4 : Thu, 5 : Fri, 6 : Sat."
   ::= { xgs360028fSystemTimeManual 9 }

xgs360028fSystemTimeManualDaylightSavingsRecurringWeekFrom OBJECT-TYPE
   SYNTAX       INTEGER(1..5)
   MAX-ACCESS   read-write
   STATUS       current
   DESCRIPTION
       "Get/Set the Daylight Saving Time Week From.
        1 : first week, 2, 3, 4, 5 : last week"
   ::= { xgs360028fSystemTimeManual 10 }
   
xgs360028fSystemTimeManualDaylightSavingsRecurringMonthFrom OBJECT-TYPE
   SYNTAX       INTEGER(0..11)
   MAX-ACCESS   read-write
   STATUS       current
   DESCRIPTION
       "Get/Set the Daylight Saving Time Month From.
        1 : Jan, 2 : Feb, 3 : Mar, 4 : Apr, 5 : May, 6 : Jun,
        7 : Jul, 8 : Aug, 9 : Sep, 10 : Oct, 11 : Nov, 12 : Dec."
   ::= { xgs360028fSystemTimeManual 11 }

xgs360028fSystemTimeManualDaylightSavingsRecurringTimeFrom OBJECT-TYPE
   SYNTAX       DisplayString
   MAX-ACCESS   read-write
   STATUS       current
   DESCRIPTION
       "Get/Set the Start time of By dates Daylight Savings.
        The input format is 'Hour:Minute'.
        ex: 05:43.
        The value range:
        Hour    : 0 - 23,
        Minute  : 0 - 59."
   ::= { xgs360028fSystemTimeManual 12 }
   
xgs360028fSystemTimeManualDaylightSavingsRecurringDayTo OBJECT-TYPE
   SYNTAX       INTEGER(0..6)
   MAX-ACCESS   read-write
   STATUS       current
   DESCRIPTION
       "Get/Set the Daylight Saving Time Day To.
        0 : Sun, 1 : Mon, 2 : Tue, 3 : Wed, 4 : Thu, 5 : Fri, 6 : Sat."
   ::= { xgs360028fSystemTimeManual 13 }

xgs360028fSystemTimeManualDaylightSavingsRecurringWeekTo OBJECT-TYPE
   SYNTAX       INTEGER(1..5)
   MAX-ACCESS   read-write
   STATUS       current
   DESCRIPTION
       "Get/Set the Daylight Saving Time Week To.
        1 : first week, 2, 3, 4, 5 : last week"
   ::= { xgs360028fSystemTimeManual 14 }
   
xgs360028fSystemTimeManualDaylightSavingsRecurringMonthTo OBJECT-TYPE
   SYNTAX       INTEGER(0..11)
   MAX-ACCESS   read-write
   STATUS       current
   DESCRIPTION
       "Get/Set the Daylight Saving Time Month To.
        1 : Jan, 2 : Feb, 3 : Mar, 4 : Apr, 5 : May, 6 : Jun,
        7 : Jul, 8 : Aug, 9 : Sep, 10 : Oct, 11 : Nov, 12 : Dec."
   ::= { xgs360028fSystemTimeManual 15 }

xgs360028fSystemTimeManualDaylightSavingsRecurringTimeTo OBJECT-TYPE
   SYNTAX       DisplayString
   MAX-ACCESS   read-write
   STATUS       current
   DESCRIPTION
       "Get/Set the Start time of By dates Daylight Savings.
        The input format is 'Hour:Minute'.
        ex: 05:43.
        The value range:
        Hour    : 0 - 23,
        Minute  : 0 - 59."
   ::= { xgs360028fSystemTimeManual 16 }

xgs360028fSystemTimeNTP                                     OBJECT IDENTIFIER ::= { xgs360028fSystemTime 2 }

xgs360028fSystemTimeNTPTable OBJECT-TYPE
   SYNTAX      SEQUENCE OF XGS360028FSystemTimeNTPEntry
   MAX-ACCESS  not-accessible
   STATUS      current
   DESCRIPTION
       " "
   ::= { xgs360028fSystemTimeNTP 1 }

xgs360028fSystemTimeNTPEntry OBJECT-TYPE
   SYNTAX      XGS360028FSystemTimeNTPEntry
   MAX-ACCESS  not-accessible
   STATUS      current
   DESCRIPTION
       ""
   INDEX    { xgs360028fSystemTimeNTPIndex  }
   ::= { xgs360028fSystemTimeNTPTable 1 }

XGS360028FSystemTimeNTPEntry ::= SEQUENCE {
   xgs360028fSystemTimeNTPIndex             INTEGER,
   xgs360028fSystemTimeNTPServerIPType      INTEGER,
   xgs360028fSystemTimeNTPServer            DisplayString,
   xgs360028fSystemTimeNTPCurrentMode       INTEGER
}

xgs360028fSystemTimeNTPIndex OBJECT-TYPE
   SYNTAX      INTEGER (1..5)
   MAX-ACCESS  not-accessible
   STATUS      current
   DESCRIPTION
       " The index of the ntp entry. "
   ::= { xgs360028fSystemTimeNTPEntry 1 }

xgs360028fSystemTimeNTPServerIPType OBJECT-TYPE
   SYNTAX       INTEGER(0|1)
   MAX-ACCESS   read-write
   STATUS       current
   DESCRIPTION
       "Default: 0,
        0 : IPv4,
        1 : IPv6."
   ::= { xgs360028fSystemTimeNTPEntry 2 }

xgs360028fSystemTimeNTPServer OBJECT-TYPE
   SYNTAX       DisplayString
   MAX-ACCESS   read-write
   STATUS       current
   DESCRIPTION
       "Get/Set the NTP Time Server1. You can use the IP address or domain name."
   ::= { xgs360028fSystemTimeNTPEntry 3 }

xgs360028fSystemTimeNTPCurrentMode OBJECT-TYPE
   SYNTAX      INTEGER (0..3)
   MAX-ACCESS  read-write
   STATUS      current
   DESCRIPTION
       " 0: Empty
        1: Active
        2: Edit
        3: Delete"
   ::= { xgs360028fSystemTimeNTPEntry 4 }
    

xgs360028fSystemAccount                                         OBJECT IDENTIFIER ::= { xgs360028fSystem 3 }

xgs360028fSystemAccountUsers                                    OBJECT IDENTIFIER ::= { xgs360028fSystemAccount 1 }

xgs360028fSystemAccountUserCreate OBJECT-TYPE
   SYNTAX       INTEGER(0|1)
   MAX-ACCESS   read-write
   STATUS       current
   DESCRIPTION
       "default: 0
        0 : None  (read only)
        1 : Create a user account"
   ::= { xgs360028fSystemAccountUsers 1 }

xgs360028fSystemAccountUsersTable OBJECT-TYPE
   SYNTAX      SEQUENCE OF XGS360028FSystemAccountUsersEntry
   MAX-ACCESS  not-accessible
   STATUS      current
   DESCRIPTION
       " "
   ::= { xgs360028fSystemAccountUsers 2 }

xgs360028fSystemAccountUsersEntry OBJECT-TYPE
   SYNTAX      XGS360028FSystemAccountUsersEntry
   MAX-ACCESS  not-accessible
   STATUS      current
   DESCRIPTION
       ""
   INDEX    { xgs360028fUserIndex  }
   ::= { xgs360028fSystemAccountUsersTable 1 }


XGS360028FSystemAccountUsersEntry ::= SEQUENCE {
   xgs360028fUserIndex              INTEGER,
   xgs360028fUserName               DisplayString,
   xgs360028fPassword               DisplayString,
   xgs360028fUserPrivilegeLevel     INTEGER,
   xgs360028fAccountUserRowStatus   INTEGER
}


xgs360028fUserIndex OBJECT-TYPE
   SYNTAX      INTEGER (1..20)
   MAX-ACCESS  not-accessible
   STATUS      current
   DESCRIPTION
       " "
   ::= { xgs360028fSystemAccountUsersEntry 1 }

xgs360028fUserName OBJECT-TYPE
   SYNTAX      DisplayString (SIZE (1..32))
   MAX-ACCESS  read-write
   STATUS      current
   DESCRIPTION
       " "
   ::= { xgs360028fSystemAccountUsersEntry 2 }

xgs360028fPassword OBJECT-TYPE
   SYNTAX      DisplayString (SIZE (1..32))
   MAX-ACCESS  read-write
   STATUS      current
   DESCRIPTION
       " "
   ::= { xgs360028fSystemAccountUsersEntry 3 }

xgs360028fUserPrivilegeLevel OBJECT-TYPE
   SYNTAX      INTEGER (1..15)
   MAX-ACCESS  read-write
   STATUS      current
   DESCRIPTION
       "default:1 
        User privilege level range : 1 - 15"
   ::= { xgs360028fSystemAccountUsersEntry 4 }

xgs360028fAccountUserRowStatus OBJECT-TYPE
   SYNTAX      INTEGER (1..5)
   MAX-ACCESS  read-write
   STATUS      current
   DESCRIPTION
       " 1: active
        2: notInservice
        3: edit
        4: destroy
        5: undo"
   ::= { xgs360028fSystemAccountUsersEntry 5 }

xgs360028fSystemAccountPrivilegeLevel                           OBJECT IDENTIFIER ::= { xgs360028fSystemAccount 2 }

xgs360028fAccountPrivilegeLevel OBJECT-TYPE
   SYNTAX      INTEGER (1..15)
   MAX-ACCESS  read-write
   STATUS      current
   DESCRIPTION
       "Default:10, Range : 1-15. "
   ::= { xgs360028fSystemAccountPrivilegeLevel 1 }

xgs360028fAggregationPrivilegeLevel OBJECT-TYPE
   SYNTAX      INTEGER (1..15)
   MAX-ACCESS  read-write
   STATUS      current
   DESCRIPTION
       "Default:10, Range : 1-15. "
   ::= { xgs360028fSystemAccountPrivilegeLevel 2 }

xgs360028fDiagnosticsPrivilegeLevel OBJECT-TYPE
   SYNTAX      INTEGER (1..15)
   MAX-ACCESS  read-write
   STATUS      current
   DESCRIPTION
       "Default:10, Range : 1-15. "
   ::= { xgs360028fSystemAccountPrivilegeLevel 3 }

xgs360028fEPSPrivilegeLevel OBJECT-TYPE
   SYNTAX      INTEGER (1..15)
   MAX-ACCESS  read-write
   STATUS      current
   DESCRIPTION
       "Default:10, Range : 1-15. "
   ::= { xgs360028fSystemAccountPrivilegeLevel 5 }

xgs360028fERPSPrivilegeLevel OBJECT-TYPE
   SYNTAX      INTEGER (1..15)
   MAX-ACCESS  read-write
   STATUS      current
   DESCRIPTION
       "Default:10, Range : 1-15. "
   ::= { xgs360028fSystemAccountPrivilegeLevel 6 }

xgs360028fETHLinkOAMPrivilegeLevel OBJECT-TYPE
   SYNTAX      INTEGER (1..15)
   MAX-ACCESS  read-write
   STATUS      current
   DESCRIPTION
       "Default:10, Range : 1-15. "
   ::= { xgs360028fSystemAccountPrivilegeLevel 7 }

xgs360028fEVCPrivilegeLevel OBJECT-TYPE
   SYNTAX      INTEGER (1..15)
   MAX-ACCESS  read-write
   STATUS      current
   DESCRIPTION
       "Default:10, Range : 1-15. "
   ::= { xgs360028fSystemAccountPrivilegeLevel 8 }

xgs360028fGARPPrivilegeLevel OBJECT-TYPE
   SYNTAX      INTEGER (1..15)
   MAX-ACCESS  read-write
   STATUS      current
   DESCRIPTION
       "Default:10, Range : 1-15. "
   ::= { xgs360028fSystemAccountPrivilegeLevel 10 }

xgs360028fGVRPPrivilegeLevel OBJECT-TYPE
   SYNTAX      INTEGER (1..15)
   MAX-ACCESS  read-write
   STATUS      current
   DESCRIPTION
       "Default:10, Range : 1-15. "
   ::= { xgs360028fSystemAccountPrivilegeLevel 11 }

xgs360028fIPPrivilegeLevel OBJECT-TYPE
   SYNTAX      INTEGER (1..15)
   MAX-ACCESS  read-write
   STATUS      current
   DESCRIPTION
       "Default:10, Range : 1-15. "
   ::= { xgs360028fSystemAccountPrivilegeLevel 12 }

xgs360028fIPMCSnoopingPrivilegeLevel OBJECT-TYPE
   SYNTAX      INTEGER (1..15)
   MAX-ACCESS  read-write
   STATUS      current
   DESCRIPTION
       "Default:10, Range : 1-15. "
   ::= { xgs360028fSystemAccountPrivilegeLevel 13 }

xgs360028fLACPPrivilegeLevel OBJECT-TYPE
   SYNTAX      INTEGER (1..15)
   MAX-ACCESS  read-write
   STATUS      current
   DESCRIPTION
       "Default:10, Range : 1-15. "
   ::= { xgs360028fSystemAccountPrivilegeLevel 14 }

xgs360028fLLDPPrivilegeLevel OBJECT-TYPE
   SYNTAX      INTEGER (1..15)
   MAX-ACCESS  read-write
   STATUS      current
   DESCRIPTION
       "Default:10, Range : 1-15. "
   ::= { xgs360028fSystemAccountPrivilegeLevel 15 }

xgs360028fLLDPMEDPrivilegeLevel OBJECT-TYPE
   SYNTAX      INTEGER (1..15)
   MAX-ACCESS  read-write
   STATUS      current
   DESCRIPTION
       "Default:10, Range : 1-15. "
   ::= { xgs360028fSystemAccountPrivilegeLevel 16 }

xgs360028fLoopProtectPrivilegeLevel OBJECT-TYPE
   SYNTAX      INTEGER (1..15)
   MAX-ACCESS  read-write
   STATUS      current
   DESCRIPTION
       "Default:10, Range : 1-15. "
   ::= { xgs360028fSystemAccountPrivilegeLevel 17 }

xgs360028fMACTablePrivilegeLevel OBJECT-TYPE
   SYNTAX      INTEGER (1..15)
   MAX-ACCESS  read-write
   STATUS      current
   DESCRIPTION
       "Default:10, Range : 1-15. "
   ::= { xgs360028fSystemAccountPrivilegeLevel 18 }

xgs360028fMEPPrivilegeLevel OBJECT-TYPE
   SYNTAX      INTEGER (1..15)
   MAX-ACCESS  read-write
   STATUS      current
   DESCRIPTION
       "Default:10, Range : 1-15. "
   ::= { xgs360028fSystemAccountPrivilegeLevel 20 }

xgs360028fMRSTPPrivilegeLevel OBJECT-TYPE
   SYNTAX      INTEGER (1..15)
   MAX-ACCESS  read-write
   STATUS      current
   DESCRIPTION
       "Default:10, Range : 1-15. "
   ::= { xgs360028fSystemAccountPrivilegeLevel 21 }

xgs360028fMVRPrivilegeLevel OBJECT-TYPE
   SYNTAX      INTEGER (1..15)
   MAX-ACCESS  read-write
   STATUS      current
   DESCRIPTION
       "Default:10, Range : 1-15. "
   ::= { xgs360028fSystemAccountPrivilegeLevel 22 }

xgs360028fMaintenancePrivilegeLevel OBJECT-TYPE
   SYNTAX      INTEGER (1..15)
   MAX-ACCESS  read-write
   STATUS      current
   DESCRIPTION
       "Default:10, Range : 1-15. "
   ::= { xgs360028fSystemAccountPrivilegeLevel 24 }

xgs360028fMirroringPrivilegeLevel OBJECT-TYPE
   SYNTAX      INTEGER (1..15)
   MAX-ACCESS  read-write
   STATUS      current
   DESCRIPTION
       "Default:10, Range : 1-15. "
   ::= { xgs360028fSystemAccountPrivilegeLevel 25 }

xgs360028fPTPPrivilegeLevel OBJECT-TYPE
   SYNTAX      INTEGER (1..15)
   MAX-ACCESS  read-write
   STATUS      current
   DESCRIPTION
       "Default:10, Range : 1-15. "
   ::= { xgs360028fSystemAccountPrivilegeLevel 26 }

xgs360028fPortsPrivilegeLevel OBJECT-TYPE
   SYNTAX      INTEGER (1..15)
   MAX-ACCESS  read-write
   STATUS      current
   DESCRIPTION
       "Default:10, Range : 1-15. "
   ::= { xgs360028fSystemAccountPrivilegeLevel 27 }

xgs360028fPrivateVLANsPrivilegeLevel OBJECT-TYPE
   SYNTAX      INTEGER (1..15)
   MAX-ACCESS  read-write
   STATUS      current
   DESCRIPTION
       "Default:10, Range : 1-15. "
   ::= { xgs360028fSystemAccountPrivilegeLevel 28 }

xgs360028fQoSPrivilegeLevel OBJECT-TYPE
   SYNTAX      INTEGER (1..15)
   MAX-ACCESS  read-write
   STATUS      current
   DESCRIPTION
       "Default:10, Range : 1-15. "
   ::= { xgs360028fSystemAccountPrivilegeLevel 29 }

xgs360028fSMTPPrivilegeLevel OBJECT-TYPE
   SYNTAX      INTEGER (1..15)
   MAX-ACCESS  read-write
   STATUS      current
   DESCRIPTION
       "Default:10, Range : 1-15. "
   ::= { xgs360028fSystemAccountPrivilegeLevel 31 }

xgs360028fSNMPPrivilegeLevel OBJECT-TYPE
   SYNTAX      INTEGER (1..15)
   MAX-ACCESS  read-write
   STATUS      current
   DESCRIPTION
       "Default:10, Range : 1-15. "
   ::= { xgs360028fSystemAccountPrivilegeLevel 32 }

xgs360028fSecurityPrivilegeLevel OBJECT-TYPE
   SYNTAX      INTEGER (1..15)
   MAX-ACCESS  read-write
   STATUS      current
   DESCRIPTION
       "Default:10, Range : 1-15. "
   ::= { xgs360028fSystemAccountPrivilegeLevel 33 }

xgs360028fSpanningTreePrivilegeLevel OBJECT-TYPE
   SYNTAX      INTEGER (1..15)
   MAX-ACCESS  read-write
   STATUS      current
   DESCRIPTION
       "Default:10, Range : 1-15. "
   ::= { xgs360028fSystemAccountPrivilegeLevel 35 }

xgs360028fSystemPrivilegeLevel OBJECT-TYPE
   SYNTAX      INTEGER (1..15)
   MAX-ACCESS  read-write
   STATUS      current
   DESCRIPTION
       "Default:10, Range : 1-15. "
   ::= { xgs360028fSystemAccountPrivilegeLevel 36 }

xgs360028fTrapEventPrivilegeLevel OBJECT-TYPE
   SYNTAX      INTEGER (1..15)
   MAX-ACCESS  read-write
   STATUS      current
   DESCRIPTION
       "Default:10, Range : 1-15. "
   ::= { xgs360028fSystemAccountPrivilegeLevel 37 }

xgs360028fVCLPrivilegeLevel OBJECT-TYPE
   SYNTAX      INTEGER (1..15)
   MAX-ACCESS  read-write
   STATUS      current
   DESCRIPTION
       "Default:10, Range : 1-15. "
   ::= { xgs360028fSystemAccountPrivilegeLevel 39 }

xgs360028fVLANTranslationPrivilegeLevel OBJECT-TYPE
   SYNTAX      INTEGER (1..15)
   MAX-ACCESS  read-write
   STATUS      current
   DESCRIPTION
       "Default:10, Range : 1-15. "
   ::= { xgs360028fSystemAccountPrivilegeLevel 40 }

xgs360028fVLANsPrivilegeLevel OBJECT-TYPE
   SYNTAX      INTEGER (1..15)
   MAX-ACCESS  read-write
   STATUS      current
   DESCRIPTION
       "Default:10, Range : 1-15. "
   ::= { xgs360028fSystemAccountPrivilegeLevel 41 }


xgs360028fIP                                                    OBJECT IDENTIFIER ::= { xgs360028fSystem 4 }

xgs360028fIPv4                                                  OBJECT IDENTIFIER ::= { xgs360028fIP 1 }

xgs360028fIPv4Configured                                                  OBJECT IDENTIFIER ::= { xgs360028fIPv4 1 }

xgs360028fIpv4DHCPClient OBJECT-TYPE
   SYNTAX      INTEGER (0|1)
   MAX-ACCESS  read-write
   STATUS      current
   DESCRIPTION
       "default:0
       0: disable
       1: enable"
   ::= { xgs360028fIPv4Configured 1 }

xgs360028fIPv4Address OBJECT-TYPE
   SYNTAX      IpAddress
   MAX-ACCESS  read-write
   STATUS      current
   DESCRIPTION
       ""
   ::= { xgs360028fIPv4Configured 2 }

xgs360028fIPv4Mask OBJECT-TYPE
   SYNTAX      IpAddress
   MAX-ACCESS  read-write
   STATUS      current
   DESCRIPTION
       ""
   ::= { xgs360028fIPv4Configured 3 }

xgs360028fIPv4Router OBJECT-TYPE
   SYNTAX      IpAddress
   MAX-ACCESS  read-write
   STATUS      current
   DESCRIPTION
       ""
   ::= { xgs360028fIPv4Configured 4 }

xgs360028fIPv4VLANId OBJECT-TYPE
   SYNTAX      INTEGER (1..4094)
   MAX-ACCESS  read-write
   STATUS      current
   DESCRIPTION
       "default:1"
   ::= { xgs360028fIPv4Configured 5 }

xgs360028fIPv4DNSServer OBJECT-TYPE
   SYNTAX      IpAddress
   MAX-ACCESS  read-write
   STATUS      current
   DESCRIPTION
       ""
   ::= { xgs360028fIPv4Configured 6 }

xgs360028fIPv4DNSProxy OBJECT-TYPE
   SYNTAX      INTEGER (0|1)
   MAX-ACCESS  read-write
   STATUS      current
   DESCRIPTION
       " "
   ::= { xgs360028fIPv4Configured 7 }

xgs360028fIPv4Current                                                  OBJECT IDENTIFIER ::= { xgs360028fIPv4 2 }

xgs360028fIpv4CurrentDHCPClient OBJECT-TYPE
   SYNTAX      INTEGER (0|1)
   MAX-ACCESS  read-write
   STATUS      current
   DESCRIPTION
       "default:0
       0: none (for read)
       1: renew"
   ::= { xgs360028fIPv4Current 1 }

xgs360028fIPv4CurrentAddress OBJECT-TYPE
   SYNTAX      IpAddress
   MAX-ACCESS  read-only
   STATUS      current
   DESCRIPTION
       ""
   ::= { xgs360028fIPv4Current 2 }

xgs360028fIPv4CurrentMask OBJECT-TYPE
   SYNTAX      IpAddress
   MAX-ACCESS  read-only
   STATUS      current
   DESCRIPTION
       ""
   ::= { xgs360028fIPv4Current 3 }

xgs360028fIPv4CurrentRouter OBJECT-TYPE
   SYNTAX      IpAddress
   MAX-ACCESS  read-only
   STATUS      current
   DESCRIPTION
       ""
   ::= { xgs360028fIPv4Current 4 }

xgs360028fIPv4CurrentVLANId OBJECT-TYPE
   SYNTAX      INTEGER (1..4094)
   MAX-ACCESS  read-only
   STATUS      current
   DESCRIPTION
       "default:1"
   ::= { xgs360028fIPv4Current 5 }

xgs360028fIPv4CurrentDNSServer OBJECT-TYPE
   SYNTAX      IpAddress
   MAX-ACCESS  read-only
   STATUS      current
   DESCRIPTION
       ""
   ::= { xgs360028fIPv4Current 6 }


xgs360028fIPv6                                                  OBJECT IDENTIFIER ::= { xgs360028fIP 2 }

xgs360028fIPv6Configured                                                  OBJECT IDENTIFIER ::= { xgs360028fIPv6 1 }

xgs360028fIpv6AutoConfiguration OBJECT-TYPE
   SYNTAX      INTEGER (0|1)
   MAX-ACCESS  read-write
   STATUS      current
   DESCRIPTION
       "default:0
       0: disable
       1: enable"
   ::= { xgs360028fIPv6Configured 1 }

xgs360028fIpv6Address OBJECT-TYPE
   SYNTAX      DisplayString (SIZE (0..30))
   MAX-ACCESS  read-write
   STATUS      current
   DESCRIPTION
       ""
   ::= { xgs360028fIPv6Configured 2 }

xgs360028fIpv6Prefix OBJECT-TYPE
   SYNTAX      INTEGER (1..128)
   MAX-ACCESS  read-write
   STATUS      current
   DESCRIPTION
       "default: 96"
   ::= { xgs360028fIPv6Configured 3 }

xgs360028fIpv6Router OBJECT-TYPE
   SYNTAX      DisplayString (SIZE (0..30))
   MAX-ACCESS  read-write
   STATUS      current
   DESCRIPTION
       " "
   ::= { xgs360028fIPv6Configured 4 }

xgs360028fIPv6Current                                                  OBJECT IDENTIFIER ::= { xgs360028fIPv6 2 }

xgs360028fIpv6CurrentAutoConfiguration OBJECT-TYPE
   SYNTAX      INTEGER (0|1)
   MAX-ACCESS  read-only
   STATUS      current
   DESCRIPTION
       "default:0
       0: disable
       1: enable"
   ::= { xgs360028fIPv6Current 1 }

xgs360028fIpv6CurrentAddress OBJECT-TYPE
   SYNTAX      DisplayString (SIZE (0..30))
   MAX-ACCESS  read-only
   STATUS      current
   DESCRIPTION
       ""
   ::= { xgs360028fIPv6Current 2 }


xgs360028fIpv6CurrentLinkLocalAddress OBJECT-TYPE
   SYNTAX      DisplayString(SIZE (0..30))
   MAX-ACCESS  read-only
   STATUS      current
   DESCRIPTION
       ""
   ::= { xgs360028fIPv6Current 3 }


xgs360028fIpv6CurrentPrefix OBJECT-TYPE
   SYNTAX      INTEGER (1..128)
   MAX-ACCESS  read-only
   STATUS      current
   DESCRIPTION
       ""
   ::= { xgs360028fIPv6Current 4 }

xgs360028fIpv6CurrentRouter OBJECT-TYPE
   SYNTAX      DisplayString (SIZE (0..30))
   MAX-ACCESS  read-only
   STATUS      current
   DESCRIPTION
       " "
   ::= { xgs360028fIPv6Current 5 }

xgs360028fSyslog                                                OBJECT IDENTIFIER ::= { xgs360028fSystem 5 }

xgs360028fSyslogConf                                            OBJECT IDENTIFIER ::= { xgs360028fSyslog 1 }

xgs360028fServerMode OBJECT-TYPE
   SYNTAX      INTEGER (0|1)
   MAX-ACCESS  read-write
   STATUS      current
   DESCRIPTION
       "default: 0
       0: disable
       1: enable "
   ::= { xgs360028fSyslogConf 1 }

xgs360028fServerAddress1 OBJECT-TYPE
   SYNTAX      IpAddress
   MAX-ACCESS  read-write
   STATUS      current
   DESCRIPTION
       " "
   ::= { xgs360028fSyslogConf 2 }

xgs360028fServerAddress2 OBJECT-TYPE
   SYNTAX      IpAddress
   MAX-ACCESS  read-write
   STATUS      current
   DESCRIPTION
       " "
   ::= { xgs360028fSyslogConf 3 }

xgs360028fSyslogLevel OBJECT-TYPE
   SYNTAX      INTEGER(0..7)
   MAX-ACCESS  read-write
   STATUS      current
   DESCRIPTION
       "default: 6 (Info)
       0: Emergency
       1: Alert
       2: Critical
       3: Error
       4: Warning
       5: Notice
       6: Info
       7: Debug"
   ::= { xgs360028fSyslogConf 4 }

xgs360028fSyslogDetailedInfo                                    OBJECT IDENTIFIER ::= { xgs360028fSyslog 2 }

xgs360028fSyslogDetailedInfoClear OBJECT-TYPE
   SYNTAX      INTEGER(0|1)
   MAX-ACCESS  read-write
   STATUS      current
   DESCRIPTION
      "default: 0
       0 : None  (read only)
       1 : Clear Syslog"
   ::= { xgs360028fSyslogDetailedInfo 1 }

xgs360028fSyslogDetailedInfoTable OBJECT-TYPE
  SYNTAX      SEQUENCE OF XGS360028FSyslogDetailedInfoEntry
  MAX-ACCESS  not-accessible
  STATUS      current
  DESCRIPTION
           " "
       ::= { xgs360028fSyslogDetailedInfo 2 }

xgs360028fSyslogDetailedInfoEntry OBJECT-TYPE
   SYNTAX      XGS360028FSyslogDetailedInfoEntry
   MAX-ACCESS  not-accessible
   STATUS      current
   DESCRIPTION
           ""
   INDEX    { xgs360028fSyslogDetailedInfoIndex  }
   ::= { xgs360028fSyslogDetailedInfoTable 1 }

XGS360028FSyslogDetailedInfoEntry ::= SEQUENCE {
   xgs360028fSyslogDetailedInfoIndex       INTEGER,
   xgs360028fSyslogDetailedInfoLevel       DisplayString,
   xgs360028fSyslogDetailedInfoTime        DisplayString,
   xgs360028fSyslogDetailedInfoMessage     DisplayString
}

xgs360028fSyslogDetailedInfoIndex OBJECT-TYPE
   SYNTAX      INTEGER (1..1024)
   MAX-ACCESS  not-accessible
   STATUS      current
   DESCRIPTION
       " "
   ::= { xgs360028fSyslogDetailedInfoEntry 1 }
   
xgs360028fSyslogDetailedInfoLevel OBJECT-TYPE
   SYNTAX      DisplayString
   MAX-ACCESS  read-only
   STATUS      current
   DESCRIPTION
       " "
   ::= { xgs360028fSyslogDetailedInfoEntry 2 }

xgs360028fSyslogDetailedInfoTime OBJECT-TYPE
   SYNTAX      DisplayString(SIZE (0..20))
   MAX-ACCESS  read-only
   STATUS      current
   DESCRIPTION
       " "
   ::= { xgs360028fSyslogDetailedInfoEntry 3 }

xgs360028fSyslogDetailedInfoMessage OBJECT-TYPE
   SYNTAX      DisplayString
   MAX-ACCESS  read-only
   STATUS      current
   DESCRIPTION
       " "
   ::= { xgs360028fSyslogDetailedInfoEntry 4 }


xgs360028fSnmp                                                OBJECT IDENTIFIER ::= { xgs360028fSystem 6 }

xgs360028fSnmpConf                                            OBJECT IDENTIFIER ::= { xgs360028fSnmp 1 }

xgs360028fGetCommunity OBJECT-TYPE
   SYNTAX       DisplayString
   MAX-ACCESS   read-write
   STATUS       current
   DESCRIPTION
       "Get/Set the get-community of the SNMP."
   ::= { xgs360028fSnmpConf 1 }

xgs360028fSetCommunityMode OBJECT-TYPE
   SYNTAX       INTEGER(0|1) 
   MAX-ACCESS   read-write
   STATUS       current
   DESCRIPTION
       "Get/Set the set-community mode of the SNMP.
        default : 1, 0: disable, 1: enable. "
   ::= { xgs360028fSnmpConf 2 }

xgs360028fSetCommunity OBJECT-TYPE
   SYNTAX       DisplayString
   MAX-ACCESS   read-write
   STATUS       current
   DESCRIPTION
       "Get/Set the set-community of the SNMP."
   ::= { xgs360028fSnmpConf 3 }

xgs360028fTrapHostConfTable OBJECT-TYPE
   SYNTAX      SEQUENCE OF XGS360028FTrapHostConfEntry
   MAX-ACCESS  not-accessible
   STATUS      current
   DESCRIPTION
       "A list of trap host entry. The numbers of entries are given by the value of xgs360028fTrapHostConfNumber."
   ::= { xgs360028fSnmpConf 4 }
   
xgs360028fTrapHostConfEntry OBJECT-TYPE
   SYNTAX      XGS360028FTrapHostConfEntry
   MAX-ACCESS  not-accessible
   STATUS      current
   DESCRIPTION
       "This is the entry information for trap host."
   INDEX    { xgs360028fTrapHostConfIndex  }
   ::= { xgs360028fTrapHostConfTable 1 }

XGS360028FTrapHostConfEntry ::= SEQUENCE {
    xgs360028fTrapHostConfIndex             INTEGER,
    xgs360028fTrapHostConfVersion           INTEGER,
    xgs360028fTrapHostConfIPType            INTEGER,
    xgs360028fTrapHostConfIP                DisplayString,
    xgs360028fTrapHostConfPort              INTEGER,
    xgs360028fTrapHostConfCommunity         DisplayString,
    xgs360028fTrapHostConfSeverityLevel     INTEGER,
    xgs360028fTrapHostConfSecurityLevel     INTEGER,
    xgs360028fTrapHostConfAuthPtc           INTEGER,
    xgs360028fTrapHostConfAuthPassword      DisplayString,
    xgs360028fTrapHostConfPrivPtc           INTEGER,
    xgs360028fTrapHostConfPrivPassword      DisplayString,
    xgs360028fTrapHostConfCurrentMode       INTEGER
}
   
xgs360028fTrapHostConfIndex OBJECT-TYPE
   SYNTAX      INTEGER (1..6)
   MAX-ACCESS  not-accessible
   STATUS      current
   DESCRIPTION
       " The index of the trap host entry. "
   ::= { xgs360028fTrapHostConfEntry 1 }

xgs360028fTrapHostConfVersion OBJECT-TYPE
   SYNTAX       INTEGER(2..3)
   MAX-ACCESS   read-write
   STATUS       current
   DESCRIPTION
       "The version of the Trap PDU. Version : 2(SNMPv2c), 3(SNMPv3)"
   ::= { xgs360028fTrapHostConfEntry 2 }

xgs360028fTrapHostConfIPType OBJECT-TYPE
   SYNTAX       INTEGER(4|6)
   MAX-ACCESS   read-write
   STATUS       current
   DESCRIPTION
       "Server IP Type. Default: 4,
        4 : IPv4,
        6 : IPv6."
   ::= { xgs360028fTrapHostConfEntry 3 }

xgs360028fTrapHostConfIP OBJECT-TYPE
   SYNTAX       DisplayString
   MAX-ACCESS   read-write
   STATUS       current
   DESCRIPTION
       "This is the IP of the trap host."
   ::= { xgs360028fTrapHostConfEntry 4 }

xgs360028fTrapHostConfPort OBJECT-TYPE
   SYNTAX       INTEGER(1..65535)
   MAX-ACCESS   read-write
   STATUS       current
   DESCRIPTION
       "This is the receiving-port number of the trap host.
        range : 1 - 65535."
   ::= { xgs360028fTrapHostConfEntry 5 }

xgs360028fTrapHostConfCommunity OBJECT-TYPE
   SYNTAX       DisplayString (SIZE (1..32))
   MAX-ACCESS   read-write
   STATUS       current
   DESCRIPTION
       "The community/security name for the trap PDU."
   ::= { xgs360028fTrapHostConfEntry 6 }

xgs360028fTrapHostConfSeverityLevel	OBJECT-TYPE
   SYNTAX       INTEGER(0..7)
   MAX-ACCESS   read-write
   STATUS       current
   DESCRIPTION
       "The Severity Level.
        0 : Emerg, 1 : Alert, 2 : Crit, 3 : Error, 4 : Warning, 5 : Notice, 6 : Info, 7 : Debug."
	::= { xgs360028fTrapHostConfEntry 7 }

xgs360028fTrapHostConfSecurityLevel	OBJECT-TYPE
   SYNTAX       INTEGER(1..3)
   MAX-ACCESS   read-write
   STATUS       current
   DESCRIPTION
       "The Security Level, NoAuthNoPriv, AuthNoPriv, and AuthPriv.
        1 : NoAuthNoPriv, 2 : AuthNoPriv, 3 : AuthPriv.
        Privacy protocol will be configured as 'DES' automatically if security level is 3(AuthPriv)."
	::= { xgs360028fTrapHostConfEntry 8 }

xgs360028fTrapHostConfAuthPtc	OBJECT-TYPE
   SYNTAX       INTEGER(1..2)
   MAX-ACCESS   read-write
   STATUS       current
   DESCRIPTION
       "Authentication Protocol, there are SHA and MD5 supported presently.
        1 : MD5, 2 : SHA."
	::= { xgs360028fTrapHostConfEntry 9 }

xgs360028fTrapHostConfAuthPassword	OBJECT-TYPE
   SYNTAX      DisplayString
   MAX-ACCESS  read-write
   STATUS		current
   DESCRIPTION
       "Authentication Password, is used for authenticating. The return value is always '********'.
        If the authentication protocol is MD5, the length of password should be 8 ~ 32 characters.
        If the authentication protocol is SHA, the length of password should be 8 ~ 40 characters."
   ::= { xgs360028fTrapHostConfEntry 10 }

xgs360028fTrapHostConfPrivPtc	OBJECT-TYPE
   SYNTAX       INTEGER(1)
   MAX-ACCESS   read-write
   STATUS       current
   DESCRIPTION
       "This is the Privacy Protocol, which is used in AuthPriv. Only supports DES.
        An empty string will be returned if the security level is not 3(AuthPriv).
        1 : DES."
	::= { xgs360028fTrapHostConfEntry 11 }

xgs360028fTrapHostConfPrivPassword	OBJECT-TYPE
   SYNTAX       DisplayString
   MAX-ACCESS   read-write
   STATUS       current
   DESCRIPTION
       "The password is Privacy Key.  The return value is always '********'.  This Key
        must be more than 8 characters, and less than 32 characters."
   ::= { xgs360028fTrapHostConfEntry 12 }

xgs360028fTrapHostConfCurrentMode OBJECT-TYPE
   SYNTAX       INTEGER(0..2)
   MAX-ACCESS   read-write
   STATUS       current
   DESCRIPTION
       "0:Empty, 1:Active mode, 2:Edit mode, 3:Delete."
   ::= { xgs360028fTrapHostConfEntry 13 }


----------------------------------------------------------------------------------------------------

xgs360028fConfiguration                                         OBJECT IDENTIFIER ::= { xgs360028fProductId 2 }

xgs360028fPort                                                  OBJECT IDENTIFIER ::= { xgs360028fConfiguration 1 }

xgs360028fPortConfigurationTable OBJECT-TYPE
   SYNTAX      SEQUENCE OF XGS360028FPortConfigurationEntry
   MAX-ACCESS  not-accessible
   STATUS      current
   DESCRIPTION
       " Show port configurations. "
   ::= { xgs360028fPort 1 }

xgs360028fPortConfigurationEntry OBJECT-TYPE
   SYNTAX      XGS360028FPortConfigurationEntry
   MAX-ACCESS  not-accessible
   STATUS      current
   DESCRIPTION
       ""
   INDEX    { xgs360028fPortConfPort  }
   ::= { xgs360028fPortConfigurationTable 1 }

XGS360028FPortConfigurationEntry ::= SEQUENCE {
   xgs360028fPortConfPort                     INTEGER,
   xgs360028fPortConfPortMedia                DisplayString,
   xgs360028fPortConfLink                     DisplayString,
   xgs360028fPortConfCurrentSpeed             DisplayString,
   xgs360028fPortConfSpeed                    INTEGER,
   xgs360028fPortConfCurrentFlowControlRx     INTEGER,
   xgs360028fPortConfCurrentFlowControlTx     INTEGER,
   xgs360028fPortConfFlowControl              INTEGER,
   xgs360028fPortConfMaxFrameSize             INTEGER,
   xgs360028fPortConfExcessiveCollisionMode   INTEGER,
   xgs360028fPortConfPowerControl             INTEGER,
   xgs360028fPortConfDescription              DisplayString
}

xgs360028fPortConfPort OBJECT-TYPE
   SYNTAX      INTEGER (1..4095)
   MAX-ACCESS  not-accessible
   STATUS      current
   DESCRIPTION
       " port, range : 1 - port number. "
   ::= { xgs360028fPortConfigurationEntry 1 }

xgs360028fPortConfPortMedia OBJECT-TYPE
   SYNTAX      DisplayString(SIZE (1..4))
   MAX-ACCESS  read-only
   STATUS      current
   DESCRIPTION
       " Show port media. "
   ::= { xgs360028fPortConfigurationEntry 2 }

xgs360028fPortConfLink OBJECT-TYPE
   SYNTAX      DisplayString(SIZE (2..4))
   MAX-ACCESS  read-only
   STATUS      current
   DESCRIPTION
       " The current link state. "
   ::= { xgs360028fPortConfigurationEntry 3 }

xgs360028fPortConfCurrentSpeed OBJECT-TYPE
   SYNTAX      DisplayString(SIZE (6..12))
   MAX-ACCESS  read-only
   STATUS      current
   DESCRIPTION
       " The current link speed of the port. "
   ::= { xgs360028fPortConfigurationEntry 4 }

xgs360028fPortConfSpeed OBJECT-TYPE
   SYNTAX      INTEGER (0..11)
   MAX-ACCESS  read-write
   STATUS      current
   DESCRIPTION
       "default: 1,
        0: disable state, 
        1: auto, 
        2: 10 Half, 
        3: 10 Full, 
        4: 100 Half, 
        5: 100 Full, 
        6: 1G full, 
        only 'Dual Media' port have 7-11 option. 
        Dual Media port default: 7,  
        7: SFP_Auto_AMS, 
        8: 100FX_AMS, 
        9: 1000X_AMS, 
        10: 100FX, 
        11: 1000X "
   ::= { xgs360028fPortConfigurationEntry 5 }

xgs360028fPortConfCurrentFlowControlRx OBJECT-TYPE
   SYNTAX      INTEGER (0|1)
   MAX-ACCESS  read-only
   STATUS      current
   DESCRIPTION
       "0: disable
        1: enable
        2: not support.  "
   ::= { xgs360028fPortConfigurationEntry 6 }

xgs360028fPortConfCurrentFlowControlTx OBJECT-TYPE
   SYNTAX      INTEGER (0|1)
   MAX-ACCESS  read-only
   STATUS      current
   DESCRIPTION
       "0: disable
        1: enable
        2: not support.  "
   ::= { xgs360028fPortConfigurationEntry 7 }

xgs360028fPortConfFlowControl OBJECT-TYPE
   SYNTAX      INTEGER (0|1)
   MAX-ACCESS  read-write
   STATUS      current
   DESCRIPTION
       "default: 0,
        0: disable
        1: enable
        2: not support. "
   ::= { xgs360028fPortConfigurationEntry 8 }

xgs360028fPortConfMaxFrameSize OBJECT-TYPE
   SYNTAX      INTEGER (1518..9600)
   MAX-ACCESS  read-write
   STATUS      current
   DESCRIPTION
       "default: 9600 , range : 1518 - 9600 "
   ::= { xgs360028fPortConfigurationEntry 9 }

xgs360028fPortConfExcessiveCollisionMode OBJECT-TYPE
   SYNTAX      INTEGER (0|1)
   MAX-ACCESS  read-write
   STATUS      current
   DESCRIPTION
       "default: 0,
        Excessive Collision Mode : 
        0: Discard,
        1: Restart, 
        2: not support.
       "
   ::= { xgs360028fPortConfigurationEntry 10 }

xgs360028fPortConfPowerControl OBJECT-TYPE
   SYNTAX      INTEGER (0..3)
   MAX-ACCESS  read-write
   STATUS      current
   DESCRIPTION
       "default: 0,
        PowerControl : 
        0: disable,
        1: Actiphy, 
        2: Dynamic (perfectReach),
        3: Enable,
        4: not support.
       "
   ::= { xgs360028fPortConfigurationEntry 11 }

xgs360028fPortConfDescription OBJECT-TYPE
   SYNTAX      DisplayString
   MAX-ACCESS  read-write
   STATUS      current
   DESCRIPTION
       " Interface specific description.
         Up to 47 characters describing this interface. "
   ::= { xgs360028fPortConfigurationEntry 12 }


xgs360028fPortTrafficStatisticsTable OBJECT-TYPE
   SYNTAX      SEQUENCE OF XGS360028FPortTrafficStatisticsEntry
   MAX-ACCESS  not-accessible
   STATUS      current
   DESCRIPTION
       " "
   ::= { xgs360028fPort 2 }

xgs360028fPortTrafficStatisticsEntry OBJECT-TYPE
   SYNTAX      XGS360028FPortTrafficStatisticsEntry
   MAX-ACCESS  not-accessible
   STATUS      current
   DESCRIPTION
       ""
   INDEX    { xgs360028fPortTrafficStatisticsPort  }
   ::= { xgs360028fPortTrafficStatisticsTable 1 }

XGS360028FPortTrafficStatisticsEntry ::= SEQUENCE {
   xgs360028fPortTrafficStatisticsPort          INTEGER,
   xgs360028fPortTrafficStatisticsClear         INTEGER,
   xgs360028fPortTrafficRxPackets               Counter64,
   xgs360028fPortTrafficRxOctets                Counter64,
   xgs360028fPortTrafficRxUnicast               Counter64,
   xgs360028fPortTrafficRxMulticast             Counter64,
   xgs360028fPortTrafficRxBroadcast             Counter64,
   xgs360028fPortTrafficRxPause                 Counter64,
   xgs360028fPortTrafficRx64Bytes               Counter64,
   xgs360028fPortTrafficRx65to127Bytes          Counter64,
   xgs360028fPortTrafficRx128to255Bytes         Counter64,
   xgs360028fPortTrafficRx256to511Bytes         Counter64,
   xgs360028fPortTrafficRx512to1023Bytes        Counter64,
   xgs360028fPortTrafficRx1024to1526Bytes       Counter64,
   xgs360028fPortTrafficRxExceecd1527Bytes      Counter64,
   xgs360028fPortTrafficRxQ0                    Counter64,
   xgs360028fPortTrafficRxQ1                    Counter64,
   xgs360028fPortTrafficRxQ2                    Counter64,
   xgs360028fPortTrafficRxQ3                    Counter64,
   xgs360028fPortTrafficRxQ4                    Counter64,
   xgs360028fPortTrafficRxQ5                    Counter64,
   xgs360028fPortTrafficRxQ6                    Counter64,
   xgs360028fPortTrafficRxQ7                    Counter64,
   xgs360028fPortTrafficRxDrops                 Counter64,
   xgs360028fPortTrafficRxCRCorAlignment        Counter64,
   xgs360028fPortTrafficRxUndersize             Counter64,
   xgs360028fPortTrafficRxOversize              Counter64,
   xgs360028fPortTrafficRxFragments             Counter64,
   xgs360028fPortTrafficRxJabber                Counter64,
   xgs360028fPortTrafficRxFiltered              Counter64,
   xgs360028fPortTrafficTxPackets               Counter64,
   xgs360028fPortTrafficTxOctets                Counter64,
   xgs360028fPortTrafficTxUnicast               Counter64,
   xgs360028fPortTrafficTxMulticast             Counter64,
   xgs360028fPortTrafficTxBroadcast             Counter64,
   xgs360028fPortTrafficTxPause                 Counter64,
   xgs360028fPortTrafficTx64Bytes               Counter64,
   xgs360028fPortTrafficTx65to127Bytes          Counter64,
   xgs360028fPortTrafficTx128to255Bytes         Counter64,
   xgs360028fPortTrafficTx256to511Bytes         Counter64,
   xgs360028fPortTrafficTx512to1023Bytes        Counter64,
   xgs360028fPortTrafficTx1024to1526Bytes       Counter64,
   xgs360028fPortTrafficTxExceecd1527Bytes      Counter64,
   xgs360028fPortTrafficTxQ0                    Counter64,
   xgs360028fPortTrafficTxQ1                    Counter64,
   xgs360028fPortTrafficTxQ2                    Counter64,
   xgs360028fPortTrafficTxQ3                    Counter64,
   xgs360028fPortTrafficTxQ4                    Counter64,
   xgs360028fPortTrafficTxQ5                    Counter64,
   xgs360028fPortTrafficTxQ6                    Counter64,
   xgs360028fPortTrafficTxQ7                    Counter64,
   xgs360028fPortTrafficTxDrops                 Counter64,
   xgs360028fPortTrafficTxLateOrExcColl         Counter64
}

xgs360028fPortTrafficStatisticsPort OBJECT-TYPE
   SYNTAX      INTEGER (1..4095)
   MAX-ACCESS  not-accessible
   STATUS      current
   DESCRIPTION
       " "
   ::= { xgs360028fPortTrafficStatisticsEntry 1 }

xgs360028fPortTrafficStatisticsClear OBJECT-TYPE
   SYNTAX      INTEGER(0|1)
   MAX-ACCESS  read-write
   STATUS      current
   DESCRIPTION
       " "
   ::= { xgs360028fPortTrafficStatisticsEntry 2 }

xgs360028fPortTrafficRxPackets OBJECT-TYPE
   SYNTAX      Counter64
   MAX-ACCESS  read-only
   STATUS      current
   DESCRIPTION
       " "
   ::= { xgs360028fPortTrafficStatisticsEntry 3 }

xgs360028fPortTrafficRxOctets OBJECT-TYPE
   SYNTAX      Counter64
   MAX-ACCESS  read-only
   STATUS      current
   DESCRIPTION
       " "
   ::= { xgs360028fPortTrafficStatisticsEntry 4 }

xgs360028fPortTrafficRxUnicast OBJECT-TYPE
   SYNTAX      Counter64
   MAX-ACCESS  read-only
   STATUS      current
   DESCRIPTION
       " "
   ::= { xgs360028fPortTrafficStatisticsEntry 5 }

xgs360028fPortTrafficRxMulticast OBJECT-TYPE
   SYNTAX      Counter64
   MAX-ACCESS  read-only
   STATUS      current
   DESCRIPTION
       " "
   ::= { xgs360028fPortTrafficStatisticsEntry 6 }

xgs360028fPortTrafficRxBroadcast OBJECT-TYPE
   SYNTAX      Counter64
   MAX-ACCESS  read-only
   STATUS      current
   DESCRIPTION
       " "
   ::= { xgs360028fPortTrafficStatisticsEntry 7 }

xgs360028fPortTrafficRxPause OBJECT-TYPE
   SYNTAX      Counter64
   MAX-ACCESS  read-only
   STATUS      current
   DESCRIPTION
       " "
   ::= { xgs360028fPortTrafficStatisticsEntry 8 }

xgs360028fPortTrafficRx64Bytes OBJECT-TYPE
   SYNTAX      Counter64
   MAX-ACCESS  read-only
   STATUS      current
   DESCRIPTION
       " "
   ::= { xgs360028fPortTrafficStatisticsEntry 9 }

xgs360028fPortTrafficRx65to127Bytes OBJECT-TYPE
   SYNTAX      Counter64
   MAX-ACCESS  read-only
   STATUS      current
   DESCRIPTION
       " "
   ::= { xgs360028fPortTrafficStatisticsEntry 10 }

xgs360028fPortTrafficRx128to255Bytes OBJECT-TYPE
   SYNTAX      Counter64
   MAX-ACCESS  read-only
   STATUS      current
   DESCRIPTION
       " "
   ::= { xgs360028fPortTrafficStatisticsEntry 11 }

xgs360028fPortTrafficRx256to511Bytes OBJECT-TYPE
   SYNTAX      Counter64
   MAX-ACCESS  read-only
   STATUS      current
   DESCRIPTION
       " "
   ::= { xgs360028fPortTrafficStatisticsEntry 12 }

xgs360028fPortTrafficRx512to1023Bytes OBJECT-TYPE
   SYNTAX      Counter64
   MAX-ACCESS  read-only
   STATUS      current
   DESCRIPTION
       " "
   ::= { xgs360028fPortTrafficStatisticsEntry 13 }

xgs360028fPortTrafficRx1024to1526Bytes OBJECT-TYPE
   SYNTAX      Counter64
   MAX-ACCESS  read-only
   STATUS      current
   DESCRIPTION
       " "
   ::= { xgs360028fPortTrafficStatisticsEntry 14 }

xgs360028fPortTrafficRxExceecd1527Bytes OBJECT-TYPE
   SYNTAX      Counter64
   MAX-ACCESS  read-only
   STATUS      current
   DESCRIPTION
       " "
   ::= { xgs360028fPortTrafficStatisticsEntry 15 }

xgs360028fPortTrafficRxQ0 OBJECT-TYPE
   SYNTAX      Counter64
   MAX-ACCESS  read-only
   STATUS      current
   DESCRIPTION
       " "
   ::= { xgs360028fPortTrafficStatisticsEntry 16 }

xgs360028fPortTrafficRxQ1 OBJECT-TYPE
   SYNTAX      Counter64
   MAX-ACCESS  read-only
   STATUS      current
   DESCRIPTION
       " "
   ::= { xgs360028fPortTrafficStatisticsEntry 17 }

xgs360028fPortTrafficRxQ2 OBJECT-TYPE
   SYNTAX      Counter64
   MAX-ACCESS  read-only
   STATUS      current
   DESCRIPTION
       " "
   ::= { xgs360028fPortTrafficStatisticsEntry 18 }

xgs360028fPortTrafficRxQ3 OBJECT-TYPE
   SYNTAX      Counter64
   MAX-ACCESS  read-only
   STATUS      current
   DESCRIPTION
       " "
   ::= { xgs360028fPortTrafficStatisticsEntry 19 }

xgs360028fPortTrafficRxQ4 OBJECT-TYPE
   SYNTAX      Counter64
   MAX-ACCESS  read-only
   STATUS      current
   DESCRIPTION
       " "
   ::= { xgs360028fPortTrafficStatisticsEntry 20 }

xgs360028fPortTrafficRxQ5 OBJECT-TYPE
   SYNTAX      Counter64
   MAX-ACCESS  read-only
   STATUS      current
   DESCRIPTION
       " "
   ::= { xgs360028fPortTrafficStatisticsEntry 21 }

xgs360028fPortTrafficRxQ6 OBJECT-TYPE
   SYNTAX      Counter64
   MAX-ACCESS  read-only
   STATUS      current
   DESCRIPTION
       " "
   ::= { xgs360028fPortTrafficStatisticsEntry 22 }

xgs360028fPortTrafficRxQ7 OBJECT-TYPE
   SYNTAX      Counter64
   MAX-ACCESS  read-only
   STATUS      current
   DESCRIPTION
       " "
   ::= { xgs360028fPortTrafficStatisticsEntry 23 }

xgs360028fPortTrafficRxDrops OBJECT-TYPE
   SYNTAX      Counter64
   MAX-ACCESS  read-only
   STATUS      current
   DESCRIPTION
       " "
   ::= { xgs360028fPortTrafficStatisticsEntry 24 }

xgs360028fPortTrafficRxCRCorAlignment OBJECT-TYPE
   SYNTAX      Counter64
   MAX-ACCESS  read-only
   STATUS      current
   DESCRIPTION
       " "
   ::= { xgs360028fPortTrafficStatisticsEntry 25 }

xgs360028fPortTrafficRxUndersize OBJECT-TYPE
   SYNTAX      Counter64
   MAX-ACCESS  read-only
   STATUS      current
   DESCRIPTION
       " "
   ::= { xgs360028fPortTrafficStatisticsEntry 26 }

xgs360028fPortTrafficRxOversize OBJECT-TYPE
   SYNTAX      Counter64
   MAX-ACCESS  read-only
   STATUS      current
   DESCRIPTION
       " "
   ::= { xgs360028fPortTrafficStatisticsEntry 27 }

xgs360028fPortTrafficRxFragments OBJECT-TYPE
   SYNTAX      Counter64
   MAX-ACCESS  read-only
   STATUS      current
   DESCRIPTION
       " "
   ::= { xgs360028fPortTrafficStatisticsEntry 28 }

xgs360028fPortTrafficRxJabber OBJECT-TYPE
   SYNTAX      Counter64
   MAX-ACCESS  read-only
   STATUS      current
   DESCRIPTION
       " "
   ::= { xgs360028fPortTrafficStatisticsEntry 29 }

xgs360028fPortTrafficRxFiltered OBJECT-TYPE
   SYNTAX      Counter64
   MAX-ACCESS  read-only
   STATUS      current
   DESCRIPTION
       " "
   ::= { xgs360028fPortTrafficStatisticsEntry 30 }

xgs360028fPortTrafficTxPackets OBJECT-TYPE
   SYNTAX      Counter64
   MAX-ACCESS  read-only
   STATUS      current
   DESCRIPTION
       " "
   ::= { xgs360028fPortTrafficStatisticsEntry 31 }

xgs360028fPortTrafficTxOctets OBJECT-TYPE
   SYNTAX      Counter64
   MAX-ACCESS  read-only
   STATUS      current
   DESCRIPTION
       " "
   ::= { xgs360028fPortTrafficStatisticsEntry 32 }

xgs360028fPortTrafficTxUnicast OBJECT-TYPE
   SYNTAX      Counter64
   MAX-ACCESS  read-only
   STATUS      current
   DESCRIPTION
       " "
   ::= { xgs360028fPortTrafficStatisticsEntry 33 }

xgs360028fPortTrafficTxMulticast OBJECT-TYPE
   SYNTAX      Counter64
   MAX-ACCESS  read-only
   STATUS      current
   DESCRIPTION
       " "
   ::= { xgs360028fPortTrafficStatisticsEntry 34 }

xgs360028fPortTrafficTxBroadcast OBJECT-TYPE
   SYNTAX      Counter64
   MAX-ACCESS  read-only
   STATUS      current
   DESCRIPTION
       " "
   ::= { xgs360028fPortTrafficStatisticsEntry 35 }

xgs360028fPortTrafficTxPause OBJECT-TYPE
   SYNTAX      Counter64
   MAX-ACCESS  read-only
   STATUS      current
   DESCRIPTION
       " "
   ::= { xgs360028fPortTrafficStatisticsEntry 36 }

xgs360028fPortTrafficTx64Bytes OBJECT-TYPE
   SYNTAX      Counter64
   MAX-ACCESS  read-only
   STATUS      current
   DESCRIPTION
       " "
   ::= { xgs360028fPortTrafficStatisticsEntry 37 }

xgs360028fPortTrafficTx65to127Bytes OBJECT-TYPE
   SYNTAX      Counter64
   MAX-ACCESS  read-only
   STATUS      current
   DESCRIPTION
       " "
   ::= { xgs360028fPortTrafficStatisticsEntry 38 }

xgs360028fPortTrafficTx128to255Bytes OBJECT-TYPE
   SYNTAX      Counter64
   MAX-ACCESS  read-only
   STATUS      current
   DESCRIPTION
       " "
   ::= { xgs360028fPortTrafficStatisticsEntry 39 }

xgs360028fPortTrafficTx256to511Bytes OBJECT-TYPE
   SYNTAX      Counter64
   MAX-ACCESS  read-only
   STATUS      current
   DESCRIPTION
       " "
   ::= { xgs360028fPortTrafficStatisticsEntry 40 }

xgs360028fPortTrafficTx512to1023Bytes OBJECT-TYPE
   SYNTAX      Counter64
   MAX-ACCESS  read-only
   STATUS      current
   DESCRIPTION
       " "
   ::= { xgs360028fPortTrafficStatisticsEntry 41 }

xgs360028fPortTrafficTx1024to1526Bytes OBJECT-TYPE
   SYNTAX      Counter64
   MAX-ACCESS  read-only
   STATUS      current
   DESCRIPTION
       " "
   ::= { xgs360028fPortTrafficStatisticsEntry 42 }

xgs360028fPortTrafficTxExceecd1527Bytes OBJECT-TYPE
   SYNTAX      Counter64
   MAX-ACCESS  read-only
   STATUS      current
   DESCRIPTION
       " "
   ::= { xgs360028fPortTrafficStatisticsEntry 43 }

xgs360028fPortTrafficTxQ0 OBJECT-TYPE
   SYNTAX      Counter64
   MAX-ACCESS  read-only
   STATUS      current
   DESCRIPTION
       " "
   ::= { xgs360028fPortTrafficStatisticsEntry 44 }

xgs360028fPortTrafficTxQ1 OBJECT-TYPE
   SYNTAX      Counter64
   MAX-ACCESS  read-only
   STATUS      current
   DESCRIPTION
       " "
   ::= { xgs360028fPortTrafficStatisticsEntry 45 }

xgs360028fPortTrafficTxQ2 OBJECT-TYPE
   SYNTAX      Counter64
   MAX-ACCESS  read-only
   STATUS      current
   DESCRIPTION
       " "
   ::= { xgs360028fPortTrafficStatisticsEntry 46 }

xgs360028fPortTrafficTxQ3 OBJECT-TYPE
   SYNTAX      Counter64
   MAX-ACCESS  read-only
   STATUS      current
   DESCRIPTION
       " "
   ::= { xgs360028fPortTrafficStatisticsEntry 47 }

xgs360028fPortTrafficTxQ4 OBJECT-TYPE
   SYNTAX      Counter64
   MAX-ACCESS  read-only
   STATUS      current
   DESCRIPTION
       " "
   ::= { xgs360028fPortTrafficStatisticsEntry 48 }

xgs360028fPortTrafficTxQ5 OBJECT-TYPE
   SYNTAX      Counter64
   MAX-ACCESS  read-only
   STATUS      current
   DESCRIPTION
       " "
   ::= { xgs360028fPortTrafficStatisticsEntry 49 }

xgs360028fPortTrafficTxQ6 OBJECT-TYPE
   SYNTAX      Counter64
   MAX-ACCESS  read-only
   STATUS      current
   DESCRIPTION
       " "
   ::= { xgs360028fPortTrafficStatisticsEntry 50 }


xgs360028fPortTrafficTxQ7 OBJECT-TYPE
   SYNTAX      Counter64
   MAX-ACCESS  read-only
   STATUS      current
   DESCRIPTION
       " "
   ::= { xgs360028fPortTrafficStatisticsEntry 51 }

xgs360028fPortTrafficTxDrops OBJECT-TYPE
   SYNTAX      Counter64
   MAX-ACCESS  read-only
   STATUS      current
   DESCRIPTION
       " "
   ::= { xgs360028fPortTrafficStatisticsEntry 52 }

xgs360028fPortTrafficTxLateOrExcColl OBJECT-TYPE
   SYNTAX      Counter64
   MAX-ACCESS  read-only
   STATUS      current
   DESCRIPTION
       " "
   ::= { xgs360028fPortTrafficStatisticsEntry 53 }


xgs360028fPortQoSStatistics                                     OBJECT IDENTIFIER ::= { xgs360028fPort 3 }

xgs360028fPortQoSStatisticsClear OBJECT-TYPE
   SYNTAX      INTEGER(0|1)
   MAX-ACCESS  read-only
   STATUS      current
   DESCRIPTION
       "default: 0
       0: none
       1: clear "
   ::= { xgs360028fPortQoSStatistics 1 }

xgs360028fPortQoSStatisticsTable OBJECT-TYPE
   SYNTAX      SEQUENCE OF XGS360028FPortQoSStatisticsEntry
   MAX-ACCESS  not-accessible
   STATUS      current
   DESCRIPTION
       " "
   ::= { xgs360028fPortQoSStatistics 2 }

xgs360028fPortQoSStatisticsEntry OBJECT-TYPE
   SYNTAX      XGS360028FPortQoSStatisticsEntry
   MAX-ACCESS  not-accessible
   STATUS      current
   DESCRIPTION
       ""
   INDEX    { xgs360028fPortQoSStatisticsPort  }
   ::= { xgs360028fPortQoSStatisticsTable 1 }

XGS360028FPortQoSStatisticsEntry ::= SEQUENCE {
   xgs360028fPortQoSStatisticsPort   INTEGER,
   xgs360028fPortQoSQ0Rx	            Counter64,
   xgs360028fPortQoSQ0Tx	            Counter64,
   xgs360028fPortQoSQ1Rx	            Counter64,
   xgs360028fPortQoSQ1Tx	            Counter64,
   xgs360028fPortQoSQ2Rx	            Counter64,
   xgs360028fPortQoSQ2Tx	            Counter64,
   xgs360028fPortQoSQ3Rx	            Counter64,
   xgs360028fPortQoSQ3Tx	            Counter64,
   xgs360028fPortQoSQ4Rx	            Counter64,
   xgs360028fPortQoSQ4Tx	            Counter64,
   xgs360028fPortQoSQ5Rx	            Counter64,
   xgs360028fPortQoSQ5Tx	            Counter64,
   xgs360028fPortQoSQ6Rx	            Counter64,
   xgs360028fPortQoSQ6Tx	            Counter64,
   xgs360028fPortQoSQ7Rx	            Counter64,
   xgs360028fPortQoSQ7Tx	            Counter64
}

xgs360028fPortQoSStatisticsPort OBJECT-TYPE
   SYNTAX      INTEGER (1..4095)
   MAX-ACCESS  not-accessible
   STATUS      current
   DESCRIPTION
       " "
   ::= { xgs360028fPortQoSStatisticsEntry 1 }

xgs360028fPortQoSQ0Rx OBJECT-TYPE
   SYNTAX      Counter64
   MAX-ACCESS  read-only
   STATUS      current
   DESCRIPTION
       " "
   ::= { xgs360028fPortQoSStatisticsEntry 2 }

xgs360028fPortQoSQ0Tx OBJECT-TYPE
   SYNTAX      Counter64
   MAX-ACCESS  read-only
   STATUS      current
   DESCRIPTION
       " "
   ::= { xgs360028fPortQoSStatisticsEntry 3 }

xgs360028fPortQoSQ1Rx OBJECT-TYPE
   SYNTAX      Counter64
   MAX-ACCESS  read-only
   STATUS      current
   DESCRIPTION
       " "
   ::= { xgs360028fPortQoSStatisticsEntry 4 }

xgs360028fPortQoSQ1Tx OBJECT-TYPE
   SYNTAX      Counter64
   MAX-ACCESS  read-only
   STATUS      current
   DESCRIPTION
       " "
   ::= { xgs360028fPortQoSStatisticsEntry 5 }

xgs360028fPortQoSQ2Rx OBJECT-TYPE
   SYNTAX      Counter64
   MAX-ACCESS  read-only
   STATUS      current
   DESCRIPTION
       " "
   ::= { xgs360028fPortQoSStatisticsEntry 6 }

xgs360028fPortQoSQ2Tx OBJECT-TYPE
   SYNTAX      Counter64
   MAX-ACCESS  read-only
   STATUS      current
   DESCRIPTION
       " "
   ::= { xgs360028fPortQoSStatisticsEntry 7 }

xgs360028fPortQoSQ3Rx OBJECT-TYPE
   SYNTAX      Counter64
   MAX-ACCESS  read-only
   STATUS      current
   DESCRIPTION
       " "
   ::= { xgs360028fPortQoSStatisticsEntry 8 }

xgs360028fPortQoSQ3Tx OBJECT-TYPE
   SYNTAX      Counter64
   MAX-ACCESS  read-only
   STATUS      current
   DESCRIPTION
       " "
   ::= { xgs360028fPortQoSStatisticsEntry 9 }

xgs360028fPortQoSQ4Rx OBJECT-TYPE
   SYNTAX      Counter64
   MAX-ACCESS  read-only
   STATUS      current
   DESCRIPTION
       " "
   ::= { xgs360028fPortQoSStatisticsEntry 10 }

xgs360028fPortQoSQ4Tx OBJECT-TYPE
   SYNTAX      Counter64
   MAX-ACCESS  read-only
   STATUS      current
   DESCRIPTION
       " "
   ::= { xgs360028fPortQoSStatisticsEntry 11 }

xgs360028fPortQoSQ5Rx OBJECT-TYPE
   SYNTAX      Counter64
   MAX-ACCESS  read-only
   STATUS      current
   DESCRIPTION
       " "
   ::= { xgs360028fPortQoSStatisticsEntry 12 }

xgs360028fPortQoSQ5Tx OBJECT-TYPE
   SYNTAX      Counter64
   MAX-ACCESS  read-only
   STATUS      current
   DESCRIPTION
       " "
   ::= { xgs360028fPortQoSStatisticsEntry 13 }

xgs360028fPortQoSQ6Rx OBJECT-TYPE
   SYNTAX      Counter64
   MAX-ACCESS  read-only
   STATUS      current
   DESCRIPTION
       " "
   ::= { xgs360028fPortQoSStatisticsEntry 14 }

xgs360028fPortQoSQ6Tx OBJECT-TYPE
   SYNTAX      Counter64
   MAX-ACCESS  read-only
   STATUS      current
   DESCRIPTION
       " "
   ::= { xgs360028fPortQoSStatisticsEntry 15 }

xgs360028fPortQoSQ7Rx OBJECT-TYPE
   SYNTAX      Counter64
   MAX-ACCESS  read-only
   STATUS      current
   DESCRIPTION
       " "
   ::= { xgs360028fPortQoSStatisticsEntry 16 }

xgs360028fPortQoSQ7Tx OBJECT-TYPE
   SYNTAX      Counter64
   MAX-ACCESS  read-only
   STATUS      current
   DESCRIPTION
       " "
   ::= { xgs360028fPortQoSStatisticsEntry 17 }

xgs360028fSFPInfoTable OBJECT-TYPE
   SYNTAX      SEQUENCE OF XGS360028FSFPInfoEntry
   MAX-ACCESS  not-accessible
   STATUS      current
   DESCRIPTION
       " "
   ::= { xgs360028fPort 4 }

xgs360028fSFPInfoEntry OBJECT-TYPE
   SYNTAX      XGS360028FSFPInfoEntry
   MAX-ACCESS  not-accessible
   STATUS      current
   DESCRIPTION
       ""
   INDEX    { xgs360028fSFPInfoIndex }
   ::= { xgs360028fSFPInfoTable 1 }

XGS360028FSFPInfoEntry ::= SEQUENCE {
   xgs360028fSFPInfoIndex               INTEGER,
   xgs360028fSFPInfoPort                DisplayString,
   xgs360028fSFPConnectorType           DisplayString,
   xgs360028fSFPFiberType               DisplayString,
   xgs360028fSFPTxCentralWavelength     DisplayString,
   xgs360028fSFPBaudRate                DisplayString,
   xgs360028fSFPVendorOUI               DisplayString,
   xgs360028fSFPVendorName              DisplayString,
   xgs360028fSFPVendorPN                DisplayString,
   xgs360028fSFPVendorRev               DisplayString,
   xgs360028fSFPVendorSN                DisplayString,
   xgs360028fSFPDateCode                DisplayString,
   xgs360028fSFPTemperature             DisplayString,
   xgs360028fSFPVcc                     DisplayString,
   xgs360028fSFPMon1Bias                DisplayString,
   xgs360028fSFPMon2TxPWR               DisplayString,
   xgs360028fSFPMon3RxPWR               DisplayString
}

xgs360028fSFPInfoIndex OBJECT-TYPE
   SYNTAX      INTEGER (1..4095)
   MAX-ACCESS  not-accessible
   STATUS      current
   DESCRIPTION
       " "
   ::= { xgs360028fSFPInfoEntry 1 }

xgs360028fSFPInfoPort OBJECT-TYPE
   SYNTAX      DisplayString
   MAX-ACCESS  read-only
   STATUS      current
   DESCRIPTION
       " "
   ::= { xgs360028fSFPInfoEntry 2 }

xgs360028fSFPConnectorType OBJECT-TYPE
   SYNTAX      DisplayString
   MAX-ACCESS  read-only
   STATUS      current
   DESCRIPTION
       " "
   ::= { xgs360028fSFPInfoEntry 3 }

xgs360028fSFPFiberType OBJECT-TYPE
   SYNTAX      DisplayString
   MAX-ACCESS  read-only
   STATUS      current
   DESCRIPTION
       " "
   ::= { xgs360028fSFPInfoEntry 4 }

xgs360028fSFPTxCentralWavelength OBJECT-TYPE
   SYNTAX      DisplayString
   MAX-ACCESS  read-only
   STATUS      current
   DESCRIPTION
       " "
   ::= { xgs360028fSFPInfoEntry 5 }

xgs360028fSFPBaudRate OBJECT-TYPE
   SYNTAX      DisplayString
   MAX-ACCESS  read-only
   STATUS      current
   DESCRIPTION
       " "
   ::= { xgs360028fSFPInfoEntry 6 }

xgs360028fSFPVendorOUI OBJECT-TYPE
   SYNTAX      DisplayString
   MAX-ACCESS  read-only
   STATUS      current
   DESCRIPTION
       " "
   ::= { xgs360028fSFPInfoEntry 7 }

xgs360028fSFPVendorName OBJECT-TYPE
   SYNTAX      DisplayString
   MAX-ACCESS  read-only
   STATUS      current
   DESCRIPTION
       " "
   ::= { xgs360028fSFPInfoEntry 8 }

xgs360028fSFPVendorPN OBJECT-TYPE
   SYNTAX      DisplayString
   MAX-ACCESS  read-only
   STATUS      current
   DESCRIPTION
       " "
   ::= { xgs360028fSFPInfoEntry 9 }

xgs360028fSFPVendorRev OBJECT-TYPE
   SYNTAX      DisplayString
   MAX-ACCESS  read-only
   STATUS      current
   DESCRIPTION
       " "
   ::= { xgs360028fSFPInfoEntry 10 }

xgs360028fSFPVendorSN OBJECT-TYPE
   SYNTAX      DisplayString
   MAX-ACCESS  read-only
   STATUS      current
   DESCRIPTION
       " "
   ::= { xgs360028fSFPInfoEntry 11 }

xgs360028fSFPDateCode OBJECT-TYPE
   SYNTAX      DisplayString
   MAX-ACCESS  read-only
   STATUS      current
   DESCRIPTION
       " "
   ::= { xgs360028fSFPInfoEntry 12 }

xgs360028fSFPTemperature OBJECT-TYPE
   SYNTAX      DisplayString
   MAX-ACCESS  read-only
   STATUS      current
   DESCRIPTION
       " "
   ::= { xgs360028fSFPInfoEntry 13 }

xgs360028fSFPVcc OBJECT-TYPE
   SYNTAX      DisplayString
   MAX-ACCESS  read-only
   STATUS      current
   DESCRIPTION
       " "
   ::= { xgs360028fSFPInfoEntry 14 }
   
xgs360028fSFPMon1Bias OBJECT-TYPE
   SYNTAX      DisplayString
   MAX-ACCESS  read-only
   STATUS      current
   DESCRIPTION
       " "
   ::= { xgs360028fSFPInfoEntry 15 }
   
xgs360028fSFPMon2TxPWR OBJECT-TYPE
   SYNTAX      DisplayString
   MAX-ACCESS  read-only
   STATUS      current
   DESCRIPTION
       " "
   ::= { xgs360028fSFPInfoEntry 16 }

xgs360028fSFPMon3RxPWR OBJECT-TYPE
   SYNTAX      DisplayString
   MAX-ACCESS  read-only
   STATUS      current
   DESCRIPTION
       " "
   ::= { xgs360028fSFPInfoEntry 17 }


xgs360028fGARP                                                   OBJECT IDENTIFIER ::= { xgs360028fConfiguration 3 }

xgs360028fGARPConfTable OBJECT-TYPE
   SYNTAX      SEQUENCE OF XGS360028FGARPConfEntry
   MAX-ACCESS  not-accessible
   STATUS      current
   DESCRIPTION
       " "
   ::= { xgs360028fGARP 1 }

xgs360028fGARPConfEntry OBJECT-TYPE
   SYNTAX      XGS360028FGARPConfEntry
   MAX-ACCESS  not-accessible
   STATUS      current
   DESCRIPTION
       ""
   INDEX    { xgs360028fGARPConfPort  }
   ::= { xgs360028fGARPConfTable 1 }

XGS360028FGARPConfEntry ::= SEQUENCE {
   xgs360028fGARPConfPort            INTEGER,
   xgs360028fGARPJoinTimer           INTEGER,
   xgs360028fGARPLeaveTimer          INTEGER,
   xgs360028fGARPLeaveAllTimer		INTEGER,
   xgs360028fGARPApplicantion		INTEGER,
   xgs360028fGARPAttributeType		INTEGER,
   xgs360028fGARPApplicant		    INTEGER
}

xgs360028fGARPConfPort OBJECT-TYPE
   SYNTAX      INTEGER (1..4095)
   MAX-ACCESS  not-accessible
   STATUS      current
   DESCRIPTION
       " "
   ::= { xgs360028fGARPConfEntry 1 }

xgs360028fGARPJoinTimer OBJECT-TYPE
   SYNTAX      INTEGER (200..1000)
   MAX-ACCESS  read-write
   STATUS      current
   DESCRIPTION
       "default: 200, range : 200 - 1000 "
   ::= { xgs360028fGARPConfEntry 2 }

xgs360028fGARPLeaveTimer OBJECT-TYPE
   SYNTAX      INTEGER (600..3000)
   MAX-ACCESS  read-write
   STATUS      current
   DESCRIPTION
       "default: 600 , range : 600 - 3000"
   ::= { xgs360028fGARPConfEntry 3 }

xgs360028fGARPLeaveAllTimer OBJECT-TYPE
   SYNTAX      INTEGER (10000..50000)
   MAX-ACCESS  read-write
   STATUS      current
   DESCRIPTION
       "default: 10000, range : 10000 - 50000 "
   ::= { xgs360028fGARPConfEntry 4 }

xgs360028fGARPApplicantion OBJECT-TYPE
   SYNTAX      INTEGER(1)
   MAX-ACCESS  read-write
   STATUS      current
   DESCRIPTION
       "default: 1
       1: GVRP"
   ::= { xgs360028fGARPConfEntry 5 }

xgs360028fGARPAttributeType OBJECT-TYPE
   SYNTAX      INTEGER(1)
   MAX-ACCESS  read-write
   STATUS      current
   DESCRIPTION
       "default: 1
       1: VLAN"
   ::= { xgs360028fGARPConfEntry 6 }

xgs360028fGARPApplicant OBJECT-TYPE
   SYNTAX      INTEGER(0|1)
   MAX-ACCESS  read-write
   STATUS      current
   DESCRIPTION
       "default: 0
       0: normal-participant
       1: non-participant"
   ::= { xgs360028fGARPConfEntry 7 }

xgs360028fGARPStatisticsTable OBJECT-TYPE
   SYNTAX      SEQUENCE OF XGS360028FGARPStatisticsEntry
   MAX-ACCESS  not-accessible
   STATUS      current
   DESCRIPTION
       " Show the basic GARP port statistics. "
   ::= { xgs360028fGARP 2 }

xgs360028fGARPStatisticsEntry OBJECT-TYPE
   SYNTAX      XGS360028FGARPStatisticsEntry
   MAX-ACCESS  not-accessible
   STATUS      current
   DESCRIPTION
       ""
   INDEX    { xgs360028fGARPStatisticsPort  }
   ::= { xgs360028fGARPStatisticsTable 1 }

XGS360028FGARPStatisticsEntry ::= SEQUENCE {
   xgs360028fGARPStatisticsPort          INTEGER,
   xgs360028fGARPStatisticsPeerMAC		DisplayString,
   xgs360028fGARPStatisticsFailedCount   Counter32
}

xgs360028fGARPStatisticsPort OBJECT-TYPE
   SYNTAX      INTEGER (1..4095)
   MAX-ACCESS  not-accessible
   STATUS      current
   DESCRIPTION
       " port, range : 1 - port number. "
   ::= { xgs360028fGARPStatisticsEntry 1 }

xgs360028fGARPStatisticsPeerMAC OBJECT-TYPE
   SYNTAX      DisplayString
   MAX-ACCESS  read-only
   STATUS      current
   DESCRIPTION
       " Peer MAC is MAC address of the neighbour Switch from with GARP frame is received.  "
   ::= { xgs360028fGARPStatisticsEntry 2 }

xgs360028fGARPStatisticsFailedCount OBJECT-TYPE
   SYNTAX      Counter32
   MAX-ACCESS  read-only
   STATUS      current
   DESCRIPTION
       " explain Failed count here. "
   ::= { xgs360028fGARPStatisticsEntry 3 }

xgs360028fGVRP                                                   OBJECT IDENTIFIER ::= { xgs360028fConfiguration 4 }

xgs360028fGVRPConf                                                   OBJECT IDENTIFIER ::= { xgs360028fGVRP 1 }

xgs360028fGVRPMode OBJECT-TYPE
   SYNTAX      INTEGER(0|1)
   MAX-ACCESS  read-write
   STATUS      current
   DESCRIPTION
       "default: 0,
        0: disable, 
        1: enable. "
   ::= { xgs360028fGVRPConf 1 }

xgs360028fGVRPConfTable OBJECT-TYPE
   SYNTAX      SEQUENCE OF XGS360028FGVRPConfEntry
   MAX-ACCESS  not-accessible
   STATUS      current
   DESCRIPTION
       " "
   ::= { xgs360028fGVRPConf 2 }

xgs360028fGVRPConfEntry OBJECT-TYPE
   SYNTAX      XGS360028FGVRPConfEntry
   MAX-ACCESS  not-accessible
   STATUS      current
   DESCRIPTION
       ""
   INDEX    { xgs360028fGVRPConfPort  }
   ::= { xgs360028fGVRPConfTable 1 }

XGS360028FGVRPConfEntry ::= SEQUENCE {
   xgs360028fGVRPConfPort        INTEGER,
   xgs360028fGVRPConfPortMode	INTEGER,
   xgs360028fGVRPConfPortRRole	INTEGER
}

xgs360028fGVRPConfPort OBJECT-TYPE
   SYNTAX      INTEGER (1..4095)
   MAX-ACCESS  not-accessible
   STATUS      current
   DESCRIPTION
       " "
   ::= { xgs360028fGVRPConfEntry 1 }

xgs360028fGVRPConfPortMode OBJECT-TYPE
   SYNTAX      INTEGER(0|1)
   MAX-ACCESS  read-write
   STATUS      current
   DESCRIPTION
       "default: 0
       1: enable
       0: disable"
   ::= { xgs360028fGVRPConfEntry 2 }

xgs360028fGVRPConfPortRRole OBJECT-TYPE
   SYNTAX      INTEGER(0|1)
   MAX-ACCESS  read-write
   STATUS      current
   DESCRIPTION
       "default: 0
       1: enable
       0: disable"
   ::= { xgs360028fGVRPConfEntry 3 }

xgs360028fGVRPStatisticsTable OBJECT-TYPE
   SYNTAX      SEQUENCE OF XGS360028FGVRPStatisticsEntry
   MAX-ACCESS  not-accessible
   STATUS      current
   DESCRIPTION
       " "
   ::= { xgs360028fGVRP 2 }

xgs360028fGVRPStatisticsEntry OBJECT-TYPE
   SYNTAX      XGS360028FGVRPStatisticsEntry
   MAX-ACCESS  not-accessible
   STATUS      current
   DESCRIPTION
       ""
   INDEX    { xgs360028fGVRPStatisticsPort  }
   ::= { xgs360028fGVRPStatisticsTable 1 }

XGS360028FGVRPStatisticsEntry ::= SEQUENCE {
   xgs360028fGVRPStatisticsPort          INTEGER,
   xgs360028fGVRPStatisticsJoinTxCnt		Counter32,
   xgs360028fGVRPStatisticsLeaveTxCnt    Counter32
}

xgs360028fGVRPStatisticsPort OBJECT-TYPE
   SYNTAX      INTEGER (1..4095)
   MAX-ACCESS  not-accessible
   STATUS      current
   DESCRIPTION
       " "
   ::= { xgs360028fGVRPStatisticsEntry 1 }

xgs360028fGVRPStatisticsJoinTxCnt OBJECT-TYPE
   SYNTAX      Counter32
   MAX-ACCESS  read-only
   STATUS      current
   DESCRIPTION
       ""
   ::= { xgs360028fGVRPStatisticsEntry 2 }

xgs360028fGVRPStatisticsLeaveTxCnt OBJECT-TYPE
   SYNTAX      Counter32
   MAX-ACCESS  read-only
   STATUS      current
   DESCRIPTION
       ""
   ::= { xgs360028fGVRPStatisticsEntry 3 }

xgs360028fThermalProtection                                     OBJECT IDENTIFIER ::= { xgs360028fConfiguration 5 }

xgs360028fPriority0Temperature OBJECT-TYPE
   SYNTAX      INTEGER(0..255)
   MAX-ACCESS  read-write
   STATUS      current
   DESCRIPTION
       "default: 255, range : 0 - 255 "
   ::= { xgs360028fThermalProtection 1 }

xgs360028fPriority1Temperature OBJECT-TYPE
   SYNTAX      INTEGER(0..255)
   MAX-ACCESS  read-write
   STATUS      current
   DESCRIPTION
       "default: 255, range : 0 - 255 "
   ::= { xgs360028fThermalProtection 2 }

xgs360028fPriority2Temperature OBJECT-TYPE
   SYNTAX      INTEGER(0..255)
   MAX-ACCESS  read-write
   STATUS      current
   DESCRIPTION
       "default: 255, range : 0 - 255 "
   ::= { xgs360028fThermalProtection 3 }

xgs360028fPriority3Temperature OBJECT-TYPE
   SYNTAX      INTEGER(0..255)
   MAX-ACCESS  read-write
   STATUS      current
   DESCRIPTION
       "default: 255, range : 0 - 255 "
   ::= { xgs360028fThermalProtection 4 }

xgs360028fThermalProtectionTable OBJECT-TYPE
   SYNTAX      SEQUENCE OF XGS360028FThermalProtectionEntry
   MAX-ACCESS  not-accessible
   STATUS      current
   DESCRIPTION
       " "
   ::= { xgs360028fThermalProtection 5 }

xgs360028fThermalProtectionEntry OBJECT-TYPE
   SYNTAX      XGS360028FThermalProtectionEntry
   MAX-ACCESS  not-accessible
   STATUS      current
   DESCRIPTION
       ""
   INDEX    { xgs360028fThermalProtectionPort  }
   ::= { xgs360028fThermalProtectionTable 1 }

XGS360028FThermalProtectionEntry ::= SEQUENCE {
   xgs360028fThermalProtectionPort               INTEGER,
   xgs360028fThermalProtectionPortTemperature    INTEGER,
   xgs360028fThermalProtectionPortPriority		INTEGER,
   xgs360028fThermalProtectionPortStatus         DisplayString
}

xgs360028fThermalProtectionPort OBJECT-TYPE
   SYNTAX      INTEGER (1..4095)
   MAX-ACCESS  not-accessible
   STATUS      current
   DESCRIPTION
       " "
   ::= { xgs360028fThermalProtectionEntry 1 }
   
xgs360028fThermalProtectionPortTemperature OBJECT-TYPE
   SYNTAX      INTEGER(0..255)
   MAX-ACCESS  read-only
   STATUS      current
   DESCRIPTION
       ""
   ::= { xgs360028fThermalProtectionEntry 2 }
   
xgs360028fThermalProtectionPortPriority OBJECT-TYPE
   SYNTAX      INTEGER(0..3)
   MAX-ACCESS  read-write
   STATUS      current
   DESCRIPTION
       "default: 0, range : 0 - 3"
   ::= { xgs360028fThermalProtectionEntry 3 }

xgs360028fThermalProtectionPortStatus OBJECT-TYPE
   SYNTAX      DisplayString
   MAX-ACCESS  read-only
   STATUS      current
   DESCRIPTION
       ""
   ::= { xgs360028fThermalProtectionEntry 4 }


xgs360028fMirroring                                             OBJECT IDENTIFIER ::= { xgs360028fConfiguration 6 }

xgs360028fPortToMirrorOn OBJECT-TYPE
   SYNTAX      INTEGER(0..10)
   MAX-ACCESS  read-write
   STATUS      current
   DESCRIPTION
       "default: 0 
        0: disable,
        range : 1 - port number. "
   ::= { xgs360028fMirroring 1 }

xgs360028fMirrorTable OBJECT-TYPE
   SYNTAX      SEQUENCE OF XGS360028FMirrorEntry
   MAX-ACCESS  not-accessible
   STATUS      current
   DESCRIPTION
       " "
   ::= { xgs360028fMirroring 2 }

xgs360028fMirrorEntry OBJECT-TYPE
   SYNTAX      XGS360028FMirrorEntry
   MAX-ACCESS  not-accessible
   STATUS      current
   DESCRIPTION
       ""
   INDEX    { xgs360028fMirrorPort  }
   ::= { xgs360028fMirrorTable 1 }

XGS360028FMirrorEntry ::= SEQUENCE {
   xgs360028fMirrorPort		INTEGER,
   xgs360028fMirrorMode		INTEGER
}

xgs360028fMirrorPort OBJECT-TYPE
   SYNTAX      INTEGER (1..4095)
   MAX-ACCESS  not-accessible
   STATUS      current
   DESCRIPTION
       " "
   ::= { xgs360028fMirrorEntry 1 }

xgs360028fMirrorMode OBJECT-TYPE
   SYNTAX      INTEGER(0..3)
   MAX-ACCESS  read-write
   STATUS      current
   DESCRIPTION
       "default: 0
       0: disable
       1: enable
       2: rx only
       3: tx only
       Setting Tx mirroring for analyzer port has no effect. Tx mirroring ignored"
   ::= { xgs360028fMirrorEntry 2 }

xgs360028fTrapEventSeverity                                             OBJECT IDENTIFIER ::= { xgs360028fConfiguration 7 }

xgs360028fTrapEventSeverityACL OBJECT-TYPE
   SYNTAX      INTEGER (0..7)
   MAX-ACCESS  read-write
   STATUS      current
   DESCRIPTION
       " default:  6(Info)
        0: Emergency
        1: Alert
        2: Critical
        3: Error
        4: Warning
        5: Notice
        6: Info
        7: Debug"
   ::= { xgs360028fTrapEventSeverity 1 }

xgs360028fTrapEventSeverityACLLog OBJECT-TYPE
   SYNTAX      INTEGER (0..7)
   MAX-ACCESS  read-write
   STATUS      current
   DESCRIPTION
       " default:  7(Debug)
        0: Emergency
        1: Alert
        2: Critical
        3: Error
        4: Warning
        5: Notice
        6: Info
        7: Debug"
   ::= { xgs360028fTrapEventSeverity 2 }

xgs360028fTrapEventSeverityAccessMgmt OBJECT-TYPE
   SYNTAX      INTEGER (0..7)
   MAX-ACCESS  read-write
   STATUS      current
   DESCRIPTION
       " default:  6(Info)
        0: Emergency
        1: Alert
        2: Critical
        3: Error
        4: Warning
        5: Notice
        6: Info
        7: Debug"
   ::= { xgs360028fTrapEventSeverity 3 }

xgs360028fTrapEventSeverityAuthFailed OBJECT-TYPE
   SYNTAX      INTEGER (0..7)
   MAX-ACCESS  read-write
   STATUS      current
   DESCRIPTION
       " default:  4(Warning)
        0: Emergency
        1: Alert
        2: Critical
        3: Error
        4: Warning
        5: Notice
        6: Info
        7: Debug"
   ::= { xgs360028fTrapEventSeverity 4 }

xgs360028fTrapEventSeverityColdStart OBJECT-TYPE
   SYNTAX      INTEGER (0..7)
   MAX-ACCESS  read-write
   STATUS      current
   DESCRIPTION
       " default:  4(Warning)
        0: Emergency
        1: Alert
        2: Critical
        3: Error
        4: Warning
        5: Notice
        6: Info
        7: Debug"
   ::= { xgs360028fTrapEventSeverity 5 }

xgs360028fTrapEventSeverityConfigInfo OBJECT-TYPE
   SYNTAX      INTEGER (0..7)
   MAX-ACCESS  read-write
   STATUS      current
   DESCRIPTION
       " default:  6(Info)
        0: Emergency
        1: Alert
        2: Critical
        3: Error
        4: Warning
        5: Notice
        6: Info
        7: Debug"
   ::= { xgs360028fTrapEventSeverity 6 }

xgs360028fTrapEventSeverityFirmwareUpgrade OBJECT-TYPE
   SYNTAX      INTEGER (0..7)
   MAX-ACCESS  read-write
   STATUS      current
   DESCRIPTION
       " default:  6(Info)
        0: Emergency
        1: Alert
        2: Critical
        3: Error
        4: Warning
        5: Notice
        6: Info
        7: Debug"
   ::= { xgs360028fTrapEventSeverity 7 }

xgs360028fTrapEventSeverityImportExport OBJECT-TYPE
   SYNTAX      INTEGER (0..7)
   MAX-ACCESS  read-write
   STATUS      current
   DESCRIPTION
       " default:  6(Info)
        0: Emergency
        1: Alert
        2: Critical
        3: Error
        4: Warning
        5: Notice
        6: Info
        7: Debug"
   ::= { xgs360028fTrapEventSeverity 8 }

xgs360028fTrapEventSeverityLACP OBJECT-TYPE
   SYNTAX      INTEGER (0..7)
   MAX-ACCESS  read-write
   STATUS      current
   DESCRIPTION
       " default:  6(Info)
        0: Emergency
        1: Alert
        2: Critical
        3: Error
        4: Warning
        5: Notice
        6: Info
        7: Debug"
   ::= { xgs360028fTrapEventSeverity 9 }

xgs360028fTrapEventSeverityLinkStatus OBJECT-TYPE
   SYNTAX      INTEGER (0..7)
   MAX-ACCESS  read-write
   STATUS      current
   DESCRIPTION
       " default:  4(Warning)
        0: Emergency
        1: Alert
        2: Critical
        3: Error
        4: Warning
        5: Notice
        6: Info
        7: Debug"
   ::= { xgs360028fTrapEventSeverity 10 }

xgs360028fTrapEventSeverityLogin OBJECT-TYPE
   SYNTAX      INTEGER (0..7)
   MAX-ACCESS  read-write
   STATUS      current
   DESCRIPTION
       " default:  6(Info)
        0: Emergency
        1: Alert
        2: Critical
        3: Error
        4: Warning
        5: Notice
        6: Info
        7: Debug"
   ::= { xgs360028fTrapEventSeverity 11 }

xgs360028fTrapEventSeverityLogout OBJECT-TYPE
   SYNTAX      INTEGER (0..7)
   MAX-ACCESS  read-write
   STATUS      current
   DESCRIPTION
       " default:  6(Info)
        0: Emergency
        1: Alert
        2: Critical
        3: Error
        4: Warning
        5: Notice
        6: Info
        7: Debug"
   ::= { xgs360028fTrapEventSeverity 12 }

xgs360028fTrapEventSeverityLoopProtect OBJECT-TYPE
   SYNTAX      INTEGER (0..7)
   MAX-ACCESS  read-write
   STATUS      current
   DESCRIPTION
       " default:  6(Info)
        0: Emergency
        1: Alert
        2: Critical
        3: Error
        4: Warning
        5: Notice
        6: Info
        7: Debug"
   ::= { xgs360028fTrapEventSeverity 13 }

xgs360028fTrapEventSeverityMgmtIPChange OBJECT-TYPE
   SYNTAX      INTEGER (0..7)
   MAX-ACCESS  read-write
   STATUS      current
   DESCRIPTION
       " default:  6(Info)
        0: Emergency
        1: Alert
        2: Critical
        3: Error
        4: Warning
        5: Notice
        6: Info
        7: Debug"
   ::= { xgs360028fTrapEventSeverity 14 }

xgs360028fTrapEventSeverityModuleChange OBJECT-TYPE
   SYNTAX      INTEGER (0..7)
   MAX-ACCESS  read-write
   STATUS      current
   DESCRIPTION
       " default:  5(Notice)
        0: Emergency
        1: Alert
        2: Critical
        3: Error
        4: Warning
        5: Notice
        6: Info
        7: Debug"
   ::= { xgs360028fTrapEventSeverity 15 }

xgs360028fTrapEventSeverityNAS OBJECT-TYPE
   SYNTAX      INTEGER (0..7)
   MAX-ACCESS  read-write
   STATUS      current
   DESCRIPTION
       " default:  6(Info)
        0: Emergency
        1: Alert
        2: Critical
        3: Error
        4: Warning
        5: Notice
        6: Info
        7: Debug"
   ::= { xgs360028fTrapEventSeverity 16 }

xgs360028fTrapEventSeverityPasswdChange OBJECT-TYPE
   SYNTAX      INTEGER (0..7)
   MAX-ACCESS  read-write
   STATUS      current
   DESCRIPTION
       " default:  6(Info)
        0: Emergency
        1: Alert
        2: Critical
        3: Error
        4: Warning
        5: Notice
        6: Info
        7: Debug"
   ::= { xgs360028fTrapEventSeverity 17 }

xgs360028fTrapEventSeverityPortSecurity OBJECT-TYPE
   SYNTAX      INTEGER (0..7)
   MAX-ACCESS  read-write
   STATUS      current
   DESCRIPTION
       " default:  6(Info)
        0: Emergency
        1: Alert
        2: Critical
        3: Error
        4: Warning
        5: Notice
        6: Info
        7: Debug"
   ::= { xgs360028fTrapEventSeverity 18 }

xgs360028fTrapEventSeverityThermalProtect OBJECT-TYPE
   SYNTAX      INTEGER (0..7)
   MAX-ACCESS  read-write
   STATUS      current
   DESCRIPTION
       " default:  6(Info)
        0: Emergency
        1: Alert
        2: Critical
        3: Error
        4: Warning
        5: Notice
        6: Info
        7: Debug"
   ::= { xgs360028fTrapEventSeverity 19 }

xgs360028fTrapEventSeverityVLAN OBJECT-TYPE
   SYNTAX      INTEGER (0..7)
   MAX-ACCESS  read-write
   STATUS      current
   DESCRIPTION
       " default:  6(Info)
        0: Emergency
        1: Alert
        2: Critical
        3: Error
        4: Warning
        5: Notice
        6: Info
        7: Debug"
   ::= { xgs360028fTrapEventSeverity 20 }

xgs360028fTrapEventSeverityWarmStart OBJECT-TYPE
   SYNTAX      INTEGER (0..7)
   MAX-ACCESS  read-write
   STATUS      current
   DESCRIPTION
       " default:  4(Warning)
        0: Emergency
        1: Alert
        2: Critical
        3: Error
        4: Warning
        5: Notice
        6: Info
        7: Debug"
   ::= { xgs360028fTrapEventSeverity 21 }


xgs360028fSMTP                                             OBJECT IDENTIFIER ::= { xgs360028fConfiguration 8 }

xgs360028fSMTPMailServer OBJECT-TYPE
   SYNTAX      DisplayString
   MAX-ACCESS  read-write
   STATUS      current
   DESCRIPTION
       " Up to 47 characters describing email server. "
   ::= { xgs360028fSMTP 1 }

xgs360028fSMTPUserName OBJECT-TYPE
   SYNTAX      DisplayString
   MAX-ACCESS  read-write
   STATUS      current
   DESCRIPTION
       " Up to 47 characters describing user name. "
   ::= { xgs360028fSMTP 2 }

xgs360028fSMTPPassword OBJECT-TYPE
   SYNTAX      DisplayString
   MAX-ACCESS  read-write
   STATUS      current
   DESCRIPTION
       " Up to 47 characters describing password. "
   ::= { xgs360028fSMTP 3 }

xgs360028fSMTPServeriryLevel OBJECT-TYPE
   SYNTAX      INTEGER(0..7)
   MAX-ACCESS  read-write
   STATUS      current
   DESCRIPTION
       "default: 6
       0: Emergency
       1: Alert
       2: Critical
       3: Error
       4: Warning
       5: Notice
       6: Info
       7: Debug"
   ::= { xgs360028fSMTP 4 }

xgs360028fSMTPSender OBJECT-TYPE
   SYNTAX      DisplayString
   MAX-ACCESS  read-write
   STATUS      current
   DESCRIPTION
       " Up to 47 characters describing sender. "
   ::= { xgs360028fSMTP 5 }

xgs360028fSMTPReturnPath OBJECT-TYPE
   SYNTAX      DisplayString
   MAX-ACCESS  read-write
   STATUS      current
   DESCRIPTION
       " Up to 47 characters describing return path. "
   ::= { xgs360028fSMTP 6 }

xgs360028fSMTPEmailAddress1 OBJECT-TYPE
   SYNTAX      DisplayString
   MAX-ACCESS  read-write
   STATUS      current
   DESCRIPTION
       " Up to 47 characters describing mail address. "
   ::= { xgs360028fSMTP 7 }

xgs360028fSMTPEmailAddress2 OBJECT-TYPE
   SYNTAX      DisplayString
   MAX-ACCESS  read-write
   STATUS      current
   DESCRIPTION
       " Up to 47 characters describing mail address. "
   ::= { xgs360028fSMTP 8 }

xgs360028fSMTPEmailAddress3 OBJECT-TYPE
   SYNTAX      DisplayString
   MAX-ACCESS  read-write
   STATUS      current
   DESCRIPTION
       " Up to 47 characters describing mail address. "
   ::= { xgs360028fSMTP 9 }

xgs360028fSMTPEmailAddress4 OBJECT-TYPE
   SYNTAX      DisplayString
   MAX-ACCESS  read-write
   STATUS      current
   DESCRIPTION
       " Up to 47 characters describing mail address. "
   ::= { xgs360028fSMTP 10 }

xgs360028fSMTPEmailAddress5 OBJECT-TYPE
   SYNTAX      DisplayString
   MAX-ACCESS  read-write
   STATUS      current
   DESCRIPTION
       " Up to 47 characters describing mail address. "
   ::= { xgs360028fSMTP 11 }

xgs360028fSMTPEmailAddress6 OBJECT-TYPE
   SYNTAX      DisplayString
   MAX-ACCESS  read-write
   STATUS      current
   DESCRIPTION
       " Up to 47 characters describing mail address. "
   ::= { xgs360028fSMTP 12 }


xgs360028fACL                                                   OBJECT IDENTIFIER ::= { xgs360028fConfiguration 9 }

xgs360028fACLPortsConfTable OBJECT-TYPE
   SYNTAX      SEQUENCE OF XGS360028FACLPortsConfEntry
   MAX-ACCESS  not-accessible
   STATUS      current
   DESCRIPTION
       " "
   ::= { xgs360028fACL 1 }

xgs360028fACLPortsConfEntry OBJECT-TYPE
   SYNTAX      XGS360028FACLPortsConfEntry
   MAX-ACCESS  not-accessible
   STATUS      current
   DESCRIPTION
       ""
   INDEX    { xgs360028fACLPortsConfPort  }
   ::= { xgs360028fACLPortsConfTable 1 }

XGS360028FACLPortsConfEntry ::= SEQUENCE {
   xgs360028fACLPortsConfPort               INTEGER,
   xgs360028fACLPortsConfPolicyID           INTEGER,
   xgs360028fACLPortsConfAction             INTEGER,
   xgs360028fACLPortsConfRateLimiterID      INTEGER,
   xgs360028fACLPortsConfPortRedirect       INTEGER,
   xgs360028fACLPortsConfLogging            INTEGER,
   xgs360028fACLPortsConfShutdown           INTEGER,
   xgs360028fACLPortsConfState              INTEGER,
   xgs360028fACLPortsConfCounter            Counter32
}

xgs360028fACLPortsConfPort OBJECT-TYPE
   SYNTAX      INTEGER (1..4095)
   MAX-ACCESS  not-accessible
   STATUS      current
   DESCRIPTION
       " "
   ::= { xgs360028fACLPortsConfEntry 1 }

xgs360028fACLPortsConfPolicyID OBJECT-TYPE
   SYNTAX      INTEGER (0..255)
   MAX-ACCESS  read-write
   STATUS      current
   DESCRIPTION
       "default: 0, range : 0 - 255 "
   ::= { xgs360028fACLPortsConfEntry 2 }

xgs360028fACLPortsConfAction OBJECT-TYPE
   SYNTAX      INTEGER(0|1)
   MAX-ACCESS  read-write
   STATUS      current
   DESCRIPTION
       "default: 1,
        0: Deny
        1: Permit"
   ::= { xgs360028fACLPortsConfEntry 3 }

xgs360028fACLPortsConfRateLimiterID OBJECT-TYPE
   SYNTAX      INTEGER (0..16)
   MAX-ACCESS  read-write
   STATUS      current
   DESCRIPTION
       "default: 0,
        0: Disable
        range : 0 - 16 "
   ::= { xgs360028fACLPortsConfEntry 4 }

xgs360028fACLPortsConfPortRedirect OBJECT-TYPE
   SYNTAX      INTEGER (0..4095)
   MAX-ACCESS  read-write
   STATUS      current
   DESCRIPTION
       "default: 0
        0: Disable
        range : 0 - end port number "
   ::= { xgs360028fACLPortsConfEntry 5 }

xgs360028fACLPortsConfLogging OBJECT-TYPE
   SYNTAX      INTEGER(0|1)
   MAX-ACCESS  read-write
   STATUS      current
   DESCRIPTION
       "default: 0
        0: Disable
        1: Enable "
   ::= { xgs360028fACLPortsConfEntry 7 }

xgs360028fACLPortsConfShutdown OBJECT-TYPE
   SYNTAX      INTEGER(0|1)
   MAX-ACCESS  read-write
   STATUS      current
   DESCRIPTION
       "default: 0
        0: Disable
        1: Enable "
   ::= { xgs360028fACLPortsConfEntry 8 }
   
xgs360028fACLPortsConfState OBJECT-TYPE
   SYNTAX      INTEGER(0|1)
   MAX-ACCESS  read-write
   STATUS      current
   DESCRIPTION
       "default: 1
        0: Disable
        1: Enable "
   ::= { xgs360028fACLPortsConfEntry 9 }

xgs360028fACLPortsConfCounter OBJECT-TYPE
   SYNTAX      Counter32
   MAX-ACCESS  read-only
   STATUS      current
   DESCRIPTION
       "Counts the number of frames that match this ACE. "
   ::= { xgs360028fACLPortsConfEntry 10 }


xgs360028fACLRateLimiterTable OBJECT-TYPE
   SYNTAX      SEQUENCE OF XGS360028FACLRateLimiterEntry
   MAX-ACCESS  not-accessible
   STATUS      current
   DESCRIPTION
       " "
   ::= { xgs360028fACL 2 }

xgs360028fACLRateLimiterEntry OBJECT-TYPE
   SYNTAX      XGS360028FACLRateLimiterEntry
   MAX-ACCESS  not-accessible
   STATUS      current
   DESCRIPTION
       ""
   INDEX    { xgs360028fACLRateLimiterID  }
   ::= { xgs360028fACLRateLimiterTable 1 }

XGS360028FACLRateLimiterEntry ::= SEQUENCE {
   xgs360028fACLRateLimiterID       INTEGER,
   xgs360028fACLRateLimiterRate     INTEGER
}

xgs360028fACLRateLimiterID OBJECT-TYPE
   SYNTAX      INTEGER (1..16)
   MAX-ACCESS  not-accessible
   STATUS      current
   DESCRIPTION
       " Rate Limiter ID.
         range : 1-16 "
   ::= { xgs360028fACLRateLimiterEntry 1 }

xgs360028fACLRateLimiterRate OBJECT-TYPE
   SYNTAX      INTEGER (0..3276700)
   MAX-ACCESS  read-write
   STATUS      current
   DESCRIPTION
       "default: 1, 
        range : <0-3276700> pps
       "
   ::= { xgs360028fACLRateLimiterEntry 3 }


xgs360028fACLACE                                          OBJECT IDENTIFIER ::= { xgs360028fACL 3 }

xgs360028fACLACECreate OBJECT-TYPE
   SYNTAX       INTEGER(0|1)
   MAX-ACCESS   read-write
   STATUS       current
   DESCRIPTION
       "default: 0
        0 : None  (read only)
        1 : Create an ACE entry"
   ::= { xgs360028fACLACE 1 }

xgs360028fACLACETable OBJECT-TYPE
   SYNTAX      SEQUENCE OF XGS360028FACLACEEntry
   MAX-ACCESS  not-accessible
   STATUS      current
   DESCRIPTION
       " Create ACL ACE entry. "
   ::= { xgs360028fACLACE 2 }

xgs360028fACLACEEntry OBJECT-TYPE
   SYNTAX      XGS360028FACLACEEntry
   MAX-ACCESS  not-accessible
   STATUS      current
   DESCRIPTION
       ""
   INDEX    { xgs360028fACLACEIndex  }
   ::= { xgs360028fACLACETable 1 }

XGS360028FACLACEEntry ::= SEQUENCE {
   xgs360028fACLACEIndex                INTEGER,
   xgs360028fACLACEID                   INTEGER,
   xgs360028fACLACENextID               INTEGER,
   xgs360028fACLACEIngressPort          DisplayString,
   xgs360028fACLACEPortPolicyNumber     INTEGER,
   
   xgs360028fACLACEPortPolicyBitmask    INTEGER,
   xgs360028fACLACEFrameType            INTEGER,
   xgs360028fACLACEAction               INTEGER,
   xgs360028fACLACEDenyPortRedirect     DisplayString,
   xgs360028fACLACELogging              INTEGER,
   
   xgs360028fACLACERateLimiter          INTEGER,
   xgs360028fACLACEShutdown             INTEGER,
   xgs360028fACLACEVLANTagPriority      INTEGER,
   
   xgs360028fACLACEVLANVID              INTEGER,
   xgs360028fACLACEEtherType            INTEGER,
   xgs360028fACLACESMAC                 DisplayString,
   xgs360028fACLACEDMACType             INTEGER,
   xgs360028fACLACEDMAC                 DisplayString,
   
   xgs360028fACLACEArpOpcode            INTEGER,
   xgs360028fACLACEArpFlagsRequestReply INTEGER,
   xgs360028fACLACEArpFlagsArpSmac      INTEGER,
   xgs360028fACLACEArpFlagsRarpDmac     INTEGER,
   xgs360028fACLACEArpFlagsLength       INTEGER,
   
   xgs360028fACLACEArpFlagsIp           INTEGER,
   xgs360028fACLACEArpFlagsEthernet     INTEGER,
   xgs360028fACLACESIPType              INTEGER,
   xgs360028fACLACESIPIPAddress         IpAddress,                      
   xgs360028fACLACESIPNetworkPrefix     INTEGER,
   
   xgs360028fACLACEDIPType              INTEGER,
   xgs360028fACLACEDIPIPAddress         IpAddress,                      
   xgs360028fACLACEDIPNetworkPrefix     INTEGER,
   
   xgs360028fACLACEIPProtocol           INTEGER,
   xgs360028fACLACEIPFlagsTTL           INTEGER,
   xgs360028fACLACEIPFlagsOptions       INTEGER,
   xgs360028fACLACEIPFlagsFragment      INTEGER,
   xgs360028fACLACEICMPType             INTEGER,
   
   xgs360028fACLACEICMPCode             INTEGER,
   xgs360028fACLACESourcePortMin        INTEGER,
   xgs360028fACLACESourcePortMax        INTEGER,
   xgs360028fACLACEDestPortMin          INTEGER,
   xgs360028fACLACEDestPortMax          INTEGER,
   
   xgs360028fACLACETCPFlagsFin          INTEGER,
   xgs360028fACLACETCPFlagsSyn          INTEGER,
   xgs360028fACLACETCPFlagsRst          INTEGER,
   xgs360028fACLACETCPFlagsPsh          INTEGER,
   xgs360028fACLACETCPFlagsAck          INTEGER,
   
   xgs360028fACLACETCPFlagsUrg          INTEGER,
   
   xgs360028fACLACERowStatus            INTEGER
}

xgs360028fACLACEIndex OBJECT-TYPE
   SYNTAX      INTEGER (1..256)
   MAX-ACCESS  not-accessible
   STATUS      current
   DESCRIPTION
       " "
   ::= { xgs360028fACLACEEntry 1 }

xgs360028fACLACEID OBJECT-TYPE
   SYNTAX      INTEGER (1..256)
   MAX-ACCESS  read-write
   STATUS      current
   DESCRIPTION
       " If the ACE ID is specified and an entry with this ACE ID
         already exists, the ACE will be modified. Otherwise, a
         new ACE will be added.
         range : 1 - 256. "
   ::= { xgs360028fACLACEEntry 2 }

xgs360028fACLACENextID OBJECT-TYPE
   SYNTAX      INTEGER (0..256)
   MAX-ACCESS  read-write
   STATUS      current
   DESCRIPTION
       " If the next ACE ID is non zero, the ACE will be placed
         before this ACE in the list. If the next ACE ID is zero,
         the ACE will be placed last in the list.
         range : 0 - 256. "
   ::= { xgs360028fACLACEEntry 3 }

xgs360028fACLACEIngressPort OBJECT-TYPE
   SYNTAX      DisplayString
   MAX-ACCESS  read-write
   STATUS      current
   DESCRIPTION
       " Indicates the ingress port of the ACE. Possible values are: 
         All: The ACE will match all ingress port. 
         Port: The ACE will match a specific ingress port.Format: 1,3,6."
   ::= { xgs360028fACLACEEntry 4 }

xgs360028fACLACEPortPolicyNumber OBJECT-TYPE
   SYNTAX      INTEGER (0..255)
   MAX-ACCESS  read-write
   STATUS      current
   DESCRIPTION
       " policy value.
         range : 0 - 255. "
   ::= { xgs360028fACLACEEntry 5 }
   
xgs360028fACLACEPortPolicyBitmask OBJECT-TYPE
   SYNTAX      INTEGER (0..255)
   MAX-ACCESS  read-write
   STATUS      current
   DESCRIPTION
       " policy bitmask.
         range : 0 - 255(0xff). "
   ::= { xgs360028fACLACEEntry 6 }

xgs360028fACLACEFrameType OBJECT-TYPE
   SYNTAX      INTEGER (0..6)
   MAX-ACCESS  read-write
   STATUS      current
   DESCRIPTION
       " 0: any,
         1: arp,
         2: etype,
         3: icmp,
         4: ipv4,
         5: tcp,
         6: udp."
   ::= { xgs360028fACLACEEntry 7 }

xgs360028fACLACEAction OBJECT-TYPE
   SYNTAX      INTEGER(0|1)
   MAX-ACCESS  read-write
   STATUS      current
   DESCRIPTION
       "default: 1,
        0: Deny
        1: Permit"
   ::= { xgs360028fACLACEEntry 8 }

xgs360028fACLACEDenyPortRedirect OBJECT-TYPE
   SYNTAX      DisplayString
   MAX-ACCESS  read-write
   STATUS      current
   DESCRIPTION
       " Frames that hit the ACE are redirected to the port number specified here.  
         Disabled: indicates that the port redirect operation is disabled. 
         Port Format: 1,3,6."
   ::= { xgs360028fACLACEEntry 9 }

xgs360028fACLACELogging OBJECT-TYPE
   SYNTAX      INTEGER(0|1)
   MAX-ACCESS  read-write
   STATUS      current
   DESCRIPTION
       "default: 0,
        0: disable - Frames matching the ACE are not logged.
        1: enable - Frames matching the ACE are stored in the system log."
   ::= { xgs360028fACLACEEntry 10 }

xgs360028fACLACERateLimiter OBJECT-TYPE
   SYNTAX      INTEGER (0..16)
   MAX-ACCESS  read-write
   STATUS      current
   DESCRIPTION
       "default: 0,
        0: Disable
        range : 0 - 16 "
   ::= { xgs360028fACLACEEntry 12 }

xgs360028fACLACEShutdown OBJECT-TYPE
   SYNTAX      INTEGER(0|1)
   MAX-ACCESS  read-write
   STATUS      current
   DESCRIPTION
       "default: 0,
        0: disable - Port shut down is disabled for the AC.
        1: enable - If a frame matches the ACE, the ingress port will be disabled."
   ::= { xgs360028fACLACEEntry 13 }

xgs360028fACLACEVLANTagPriority OBJECT-TYPE
   SYNTAX      INTEGER (0..8)
   MAX-ACCESS  read-write
   STATUS      current
   DESCRIPTION
       "Specify the tag priority for this ACE.
        The tag priority can't be set when 802.1Q Tagged is disabled
        default: 8,
        8: Any,
        range : 0 - 8 "
   ::= { xgs360028fACLACEEntry 15 }

xgs360028fACLACEVLANVID OBJECT-TYPE
   SYNTAX      INTEGER (0..4094)
   MAX-ACCESS  read-write
   STATUS      current
   DESCRIPTION
       "Specify the VLAN ID filter for this ACE.
        The vid can't be set when 802.1Q Tagged is disabled. 
        default: 0,
        0: Any - No VLAN ID filter is specified.
        range : 0 - 4094 "
   ::= { xgs360028fACLACEEntry 16 }

xgs360028fACLACEEtherType OBJECT-TYPE
   SYNTAX      INTEGER (0..65535)
   MAX-ACCESS  read-write
   STATUS      current
   DESCRIPTION
       " 0: Any - Any but excluding 0x0800(IPv4) 0x0806(ARP) and 0x86DD(IPv6).
         range : 0 or 1536(0x0600)- 65535(0xffff). "
   ::= { xgs360028fACLACEEntry 17 }

xgs360028fACLACESMAC OBJECT-TYPE
   SYNTAX      DisplayString
   MAX-ACCESS  read-write
   STATUS      current
   DESCRIPTION
       " Configure source MAC address for this ACE.
         <mac-address>: A frame that hits this ACE matches this source MAC address value. 
         Any: Don't care."
   ::= { xgs360028fACLACEEntry 18 }

xgs360028fACLACEDMACType OBJECT-TYPE
   SYNTAX      INTEGER (0..4)
   MAX-ACCESS  read-write
   STATUS      current
   DESCRIPTION
       "DMAC Type.
        default: 0,
        0: Any - Don't care.
        1: Broadcast - Frame must be broadcast.
        2: Unicast - Frame must be unicast.
        3: Multicast - Frame must be multicast.
        4: mac address
        range : 0 - 4 "
   ::= { xgs360028fACLACEEntry 19 }

xgs360028fACLACEDMAC OBJECT-TYPE
   SYNTAX      DisplayString
   MAX-ACCESS  read-write
   STATUS      current
   DESCRIPTION
       " Configure destination MAC address for this ACE. 
         <mac-address>: A frame that hits this ACE matches this destination MAC address value.            
         Any: Don't care.
         Broadcast: Frame must be broadcast.
         Unicast: Frame must be unicast.
         Multicast: Frame must be multicast. "
   ::= { xgs360028fACLACEEntry 20 }

xgs360028fACLACEArpOpcode OBJECT-TYPE
   SYNTAX      INTEGER (0..3)
   MAX-ACCESS  read-write
   STATUS      current
   DESCRIPTION
       "Configure ARP opcode for this ACE.
        default: 0,
        0: Any - Don't care.
        1: arp.
        2: rarp.
        3: other.
        4: No data.
        range : 0 - 3 "
   ::= { xgs360028fACLACEEntry 21 }

xgs360028fACLACEArpFlagsRequestReply OBJECT-TYPE
   SYNTAX      INTEGER (0..2)
   MAX-ACCESS  read-write
   STATUS      current
   DESCRIPTION
       "Specify the available ARP/RARP opcode (OP) flag for this ACE.
        default: 2,
        0: Frame must have ARP Reply or RARP Reply OP flag.
        1: Frame must have ARP Request or RARP Request OP flag set.
        2: Any - Don't care.
        3: No data.
        range : 0 - 2 "
   ::= { xgs360028fACLACEEntry 22 }

xgs360028fACLACEArpFlagsArpSmac OBJECT-TYPE
   SYNTAX      INTEGER (0..2)
   MAX-ACCESS  read-write
   STATUS      current
   DESCRIPTION
       "Specify whether frames can hit the action according to their sender hardware address field (SHA) settings.
        default: 2,
        0: ARP frames where SHA is not equal to the SMAC address.
        1: ARP frames where SHA is equal to the SMAC address.
        2: Any - Don't care.
        3: No data.
        range : 0 - 2 "
   ::= { xgs360028fACLACEEntry 23 }   

xgs360028fACLACEArpFlagsRarpDmac OBJECT-TYPE
   SYNTAX      INTEGER (0..2)
   MAX-ACCESS  read-write
   STATUS      current
   DESCRIPTION
       "Specify whether frames can hit the action according to their target hardware address field (THA) settings.
        default: 2,
        0: RARP frames where THA is not equal to the DMAC address.
        1: RARP frames where THA is equal to the DMAC address.
        2: Any - Don't care.
        3: No data.
        range : 0 - 2 "
   ::= { xgs360028fACLACEEntry 24 }

xgs360028fACLACEArpFlagsLength OBJECT-TYPE
   SYNTAX      INTEGER (0..2)
   MAX-ACCESS  read-write
   STATUS      current
   DESCRIPTION
       "Specify whether frames can hit the action according to their ARP/RARP hardware address length (HLN) and
        protocol address length (PLN) settings.
        default: 2,
        0: ARP/RARP frames where the HLN is not equal to Ethernet(0x06) or the (PLN) is not equal to IPv4(0x04).
        1: ARP/RARP frames where the HLN is equal to Ethernet (0x06) and the (PLN) is equal to IPv4(0x04).
        2: Any - Don't care.
        3: No data.
        range : 0 - 2 "
   ::= { xgs360028fACLACEEntry 25 }

xgs360028fACLACEArpFlagsIp OBJECT-TYPE
   SYNTAX      INTEGER (0..2)
   MAX-ACCESS  read-write
   STATUS      current
   DESCRIPTION
       "Specify whether frames can hit the action according to their ARP/RARP hardware address space (HRD) settings.
        default: 2,
        0: ARP/RARP frames where the HLD is not equal to Ethernet(1).
        1: ARP/RARP frames where the HLD is equal to Ethernet(1).
        2: Any - Don't care.
        3: No data.
        range : 0 - 2 "
   ::= { xgs360028fACLACEEntry 26 }

xgs360028fACLACEArpFlagsEthernet OBJECT-TYPE
   SYNTAX      INTEGER (0..2)
   MAX-ACCESS  read-write
   STATUS      current
   DESCRIPTION
       "Specify whether frames can hit the action according to their ARP/RARP protocol address space (PRO) settings.
        default: 2,
        0: ARP/RARP frames where the PRO is not equal to IP\n(0x800).
        1: ARP/RARP frames where the PRO is equal to IP(0x800).
        2: Any - Don't care.
        3: No data.
        range : 0 - 2 "
   ::= { xgs360028fACLACEEntry 27 }
   
xgs360028fACLACESIPType OBJECT-TYPE
   SYNTAX      INTEGER(0|1)
   MAX-ACCESS  read-write
   STATUS      current
   DESCRIPTION
       "Configure source IP address for this ACE.
        default: 0,
        0: Any - Don't care.
        1: IP Address.
        2: No data.
        range : 0 - 1"
   ::= { xgs360028fACLACEEntry 28 }   
   
xgs360028fACLACESIPIPAddress OBJECT-TYPE
   SYNTAX      IpAddress
   MAX-ACCESS  read-write
   STATUS      current
   DESCRIPTION
       "A frame that hits this ACE matches this source IP address value."
   ::= { xgs360028fACLACEEntry 29 }      
   
xgs360028fACLACESIPNetworkPrefix OBJECT-TYPE
   SYNTAX      INTEGER (1..32)
   MAX-ACCESS  read-write
   STATUS      current
   DESCRIPTION
       "Network prefix.
        default: 32,
        0: No data.
        range : 1 - 32"
   ::= { xgs360028fACLACEEntry 30 }   
   

xgs360028fACLACEDIPType OBJECT-TYPE
   SYNTAX      INTEGER(0|1)
   MAX-ACCESS  read-write
   STATUS      current
   DESCRIPTION
       "Configure destination IP address for this ACE.
        default: 0,
        0: Any - Don't care.
        1: IP Address.
        2: No data.
        range : 0 - 1"
   ::= { xgs360028fACLACEEntry 32 }   
   
xgs360028fACLACEDIPIPAddress OBJECT-TYPE
   SYNTAX      IpAddress
   MAX-ACCESS  read-write
   STATUS      current
   DESCRIPTION
       "A frame that hits this ACE matches this destination IP address value."
   ::= { xgs360028fACLACEEntry 33 }      
   
xgs360028fACLACEDIPNetworkPrefix OBJECT-TYPE
   SYNTAX      INTEGER (1..32)
   MAX-ACCESS  read-write
   STATUS      current
   DESCRIPTION
       "Network prefix.
        default: 32,
        0: No data.
        range : 1 - 32"
   ::= { xgs360028fACLACEEntry 34 }  
   
   
xgs360028fACLACEIPProtocol OBJECT-TYPE
   SYNTAX      INTEGER (0..256)
   MAX-ACCESS  read-write
   STATUS      current
   DESCRIPTION
       "Configure IP protocol for this ACE.
        default: 256,
        256: Any - Don't care.
        257: No data.
        range : 0 - 256"
   ::= { xgs360028fACLACEEntry 36 } 

xgs360028fACLACEIPFlagsTTL OBJECT-TYPE
   SYNTAX      INTEGER (0..2)
   MAX-ACCESS  read-write
   STATUS      current
   DESCRIPTION
       "Configure IP Time-to-Live flags for this ACE.
        default: 2,
        0: IPv4 frames with a Time-to-Live field is equal to zero.
        1: IPv4 frames with a Time-to-Live field greater than zero.
        2: Any - Don't care.
        3: No data.
        range : 0 - 2 "
   ::= { xgs360028fACLACEEntry 37 }   
   
xgs360028fACLACEIPFlagsOptions OBJECT-TYPE
   SYNTAX      INTEGER (0..2)
   MAX-ACCESS  read-write
   STATUS      current
   DESCRIPTION
       "Configure IP options flag for this ACE.
        default: 2,
        0: IPv4 frames where the options flag is unset.
        1: IPv4 frames where the options flag is set.
        2: Any - Don't care.
        3: No data.
        range : 0 - 2 "
   ::= { xgs360028fACLACEEntry 38 }

xgs360028fACLACEIPFlagsFragment OBJECT-TYPE
   SYNTAX      INTEGER (0..2)
   MAX-ACCESS  read-write
   STATUS      current
   DESCRIPTION
       "Configure IP fragment offset flags for this ACE.
        default: 2,
        0: IPv4 frames where the MF bit is unset and the FRAG OFFSET field is equal zero.
        1: IPv4 frames where the MF bit is set or the FRAG OFFSET field is greater than zero.
        2: Any - Don't care.
        3: No data.
        range : 0 - 2 "
   ::= { xgs360028fACLACEEntry 39 }

xgs360028fACLACEICMPType OBJECT-TYPE
   SYNTAX      INTEGER (0..256)
   MAX-ACCESS  read-write
   STATUS      current
   DESCRIPTION
       "Configure ICMP type for this ACE.
        default: 256,
        256: Any - Don't care.
        257: No data.
        range : 0 - 256"
   ::= { xgs360028fACLACEEntry 40 }   

xgs360028fACLACEICMPCode OBJECT-TYPE
   SYNTAX      INTEGER (0..256)
   MAX-ACCESS  read-write
   STATUS      current
   DESCRIPTION
       "Configure ICMP code for this ACE.
        default: 256,
        256: Any - Don't care.
        257: No data.
        range : 0 - 256"
   ::= { xgs360028fACLACEEntry 41 } 

xgs360028fACLACESourcePortMin OBJECT-TYPE
   SYNTAX      INTEGER (0..65535)
   MAX-ACCESS  read-write
   STATUS      current
   DESCRIPTION
       "Configure Source UDP/TCP port range for this ACE.
        default: 0,
        65536: No data.
        range : 0 - 65535"
   ::= { xgs360028fACLACEEntry 42 }     
   
xgs360028fACLACESourcePortMax OBJECT-TYPE
   SYNTAX      INTEGER (0..65535)
   MAX-ACCESS  read-write
   STATUS      current
   DESCRIPTION
       "Configure Source UDP/TCP port range for this ACE.
        default: 0,
        65536: No data.
        range : 0 - 65535"
   ::= { xgs360028fACLACEEntry 43 } 
      
xgs360028fACLACEDestPortMin OBJECT-TYPE
   SYNTAX      INTEGER (0..65535)
   MAX-ACCESS  read-write
   STATUS      current
   DESCRIPTION
       "Configure Destination UDP/TCP port range for this ACE.
        default: 0,
        65536: No data.
        range : 0 - 65535"
   ::= { xgs360028fACLACEEntry 44 }     

xgs360028fACLACEDestPortMax OBJECT-TYPE
   SYNTAX      INTEGER (0..65535)
   MAX-ACCESS  read-write
   STATUS      current
   DESCRIPTION
       "Configure Destination UDP/TCP port range for this ACE.
        default: 0,
        65536: No data.
        range : 0 - 65535"
   ::= { xgs360028fACLACEEntry 45 }

xgs360028fACLACETCPFlagsFin OBJECT-TYPE
   SYNTAX      INTEGER (0..2)
   MAX-ACCESS  read-write
   STATUS      current
   DESCRIPTION
       "Configure TCP (FIN) flags for this ACE.
        default: 2,
        0: TCP frames where the FIN field is unset.
        1: TCP frames where the FIN field is set.
        2: Any - Don't care.
        3: No data.
        range : 0 - 2 "
   ::= { xgs360028fACLACEEntry 46 }

xgs360028fACLACETCPFlagsSyn OBJECT-TYPE
   SYNTAX      INTEGER (0..2)
   MAX-ACCESS  read-write
   STATUS      current
   DESCRIPTION
       "Configure TCP (SYN) flags for this ACE.
        default: 2,
        0: TCP frames where the SYN field is unset.
        1: TCP frames where the SYN field is set.
        2: Any - Don't care.
        3: No data.
        range : 0 - 2 "
   ::= { xgs360028fACLACEEntry 47 }

xgs360028fACLACETCPFlagsRst OBJECT-TYPE
   SYNTAX      INTEGER (0..2)
   MAX-ACCESS  read-write
   STATUS      current
   DESCRIPTION
       "Configure TCP (RST) flags for this ACE.
        default: 2,
        0: TCP frames where the RST field is unset.
        1: TCP frames where the RST field is set.
        2: Any - Don't care.
        3: No data.
        range : 0 - 2 "
   ::= { xgs360028fACLACEEntry 48 }

xgs360028fACLACETCPFlagsPsh OBJECT-TYPE
   SYNTAX      INTEGER (0..2)
   MAX-ACCESS  read-write
   STATUS      current
   DESCRIPTION
       "Configure TCP (PSH) flags for this ACE.
        default: 2,
        0: TCP frames where the PSH field is unset.
        1: TCP frames where the PSH field is set.
        2: Any - Don't care.
        3: No data.
        range : 0 - 2 "
   ::= { xgs360028fACLACEEntry 49 }

xgs360028fACLACETCPFlagsAck OBJECT-TYPE
   SYNTAX      INTEGER (0..2)
   MAX-ACCESS  read-write
   STATUS      current
   DESCRIPTION
       "Configure TCP (ACK) flags for this ACE.
        default: 2,
        0: TCP frames where the ACK field is unset.
        1: TCP frames where the ACK field is set.
        2: Any - Don't care.
        3: No data.
        range : 0 - 2 "
   ::= { xgs360028fACLACEEntry 50 }

xgs360028fACLACETCPFlagsUrg OBJECT-TYPE
   SYNTAX      INTEGER (0..2)
   MAX-ACCESS  read-write
   STATUS      current
   DESCRIPTION
       "Configure TCP (URG) flags for this ACE.
        default: 2,
        0: TCP frames where the URG field is unset.
        1: TCP frames where the URG field is set.
        2: Any - Don't care.
        3: No data.
        range : 0 - 2 "
   ::= { xgs360028fACLACEEntry 51 }

xgs360028fACLACERowStatus OBJECT-TYPE
   SYNTAX      INTEGER (1..5)
   MAX-ACCESS  read-write
   STATUS      current
   DESCRIPTION
       " 1: active
         2: notInservice
         4: destroy
         5: undo"
   ::= { xgs360028fACLACEEntry 66 }


xgs360028fACLACEClear OBJECT-TYPE
   SYNTAX       INTEGER(0|1)
   MAX-ACCESS   read-write
   STATUS       current
   DESCRIPTION
       "default: 0
        0 : No action
        1 : Clear all ACL counters."
   ::= { xgs360028fACLACE 3 }

xgs360028fACLACEMoveACEID OBJECT-TYPE
   SYNTAX       INTEGER (1..256)
   MAX-ACCESS   read-write
   STATUS       current
   DESCRIPTION
       "Move ACE,
        default: 0
        ACE ID must be exist.
        range : 1 - 256."
   ::= { xgs360028fACLACE 4 }

xgs360028fACLACEMoveNextACEID OBJECT-TYPE
   SYNTAX       INTEGER (0..256)
   MAX-ACCESS   read-write
   STATUS       current
   DESCRIPTION
       "Move ACE,
        default: 0
        If the next ACE ID is non zero, the ACE will be placed before this ACE in the list. If the next ACE ID is zero,
        the ACE will be placed last in the list.
        range : 0 - 256."
   ::= { xgs360028fACLACE 5 }

xgs360028fACLACEStatusTable OBJECT-TYPE
   SYNTAX      SEQUENCE OF XGS360028FACLACEStatusEntry
   MAX-ACCESS  not-accessible
   STATUS      current
   DESCRIPTION
       " ACL ACE Status entry. "
   ::= { xgs360028fACLACE 6 }

xgs360028fACLACEStatusEntry OBJECT-TYPE
   SYNTAX      XGS360028FACLACEStatusEntry
   MAX-ACCESS  not-accessible
   STATUS      current
   DESCRIPTION
       ""
   INDEX    { xgs360028fACLACEStatusIndex  }
   ::= { xgs360028fACLACEStatusTable 1 }

XGS360028FACLACEStatusEntry ::= SEQUENCE {
   xgs360028fACLACEStatusIndex          INTEGER,
   xgs360028fACLACEStatusUser           DisplayString,
   xgs360028fACLACEStatusID             INTEGER,
   xgs360028fACLACEStatusIngressPort    DisplayString,
   xgs360028fACLACEStatusFrameType      DisplayString,
   xgs360028fACLACEStatusAction         DisplayString,
   xgs360028fACLACEStatusRateLimiter    DisplayString,
   xgs360028fACLACEStatusPortCopy       DisplayString,
   xgs360028fACLACEStatusMirror         DisplayString,
   xgs360028fACLACEStatusCPU            DisplayString,
   xgs360028fACLACEStatusCounter        Counter32,
   xgs360028fACLACEStatusConflict       DisplayString
}

xgs360028fACLACEStatusIndex OBJECT-TYPE
   SYNTAX      INTEGER (1..256)
   MAX-ACCESS  not-accessible
   STATUS      current
   DESCRIPTION
       " "
   ::= { xgs360028fACLACEStatusEntry 1 }

xgs360028fACLACEStatusUser OBJECT-TYPE
   SYNTAX      DisplayString
   MAX-ACCESS  read-only
   STATUS      current
   DESCRIPTION
       " Indicates the ACL user. 
         S : Static.  
         IPMG : IP Management.  
         IPSG : IP Source Guard.  
         IPMC : IPMC.  
         ARPI : Arp Inspection.  
         UPnP : UPnP.  
         DHCP : DHCP. "
   ::= { xgs360028fACLACEStatusEntry 2 }

xgs360028fACLACEStatusID OBJECT-TYPE
   SYNTAX      INTEGER (1..256)
   MAX-ACCESS  read-only
   STATUS      current
   DESCRIPTION
       " ACE ID.
         range : 1 - 256. "
   ::= { xgs360028fACLACEStatusEntry 3 }

xgs360028fACLACEStatusIngressPort OBJECT-TYPE
   SYNTAX      DisplayString
   MAX-ACCESS  read-only
   STATUS      current
   DESCRIPTION
       " Indicates the ingress port of the ACE. Possible values are: 
         All: The ACE will match all ingress port. 
         Port: The ACE will match a specific ingress port. "
   ::= { xgs360028fACLACEStatusEntry 4 }

xgs360028fACLACEStatusFrameType OBJECT-TYPE
   SYNTAX      DisplayString
   MAX-ACCESS  read-only
   STATUS      current
   DESCRIPTION
       " Indicates the frame type of the ACE. "
   ::= { xgs360028fACLACEStatusEntry 5 }

xgs360028fACLACEStatusAction OBJECT-TYPE
   SYNTAX      DisplayString
   MAX-ACCESS  read-only
   STATUS      current
   DESCRIPTION
       " Indicates the forwarding action of the ACE. "
   ::= { xgs360028fACLACEStatusEntry 6 }

xgs360028fACLACEStatusRateLimiter OBJECT-TYPE
   SYNTAX      DisplayString
   MAX-ACCESS  read-only
   STATUS      current
   DESCRIPTION
       " Indicates the rate limiter number of the ACE. "
   ::= { xgs360028fACLACEStatusEntry 7 }

xgs360028fACLACEStatusPortCopy OBJECT-TYPE
   SYNTAX      DisplayString
   MAX-ACCESS  read-only
   STATUS      current
   DESCRIPTION
       " Indicates the port redirect operation of the ACE. Frames matching the ACE are redirected to the port number. "
   ::= { xgs360028fACLACEStatusEntry 8 }

xgs360028fACLACEStatusMirror OBJECT-TYPE
   SYNTAX      DisplayString
   MAX-ACCESS  read-only
   STATUS      current
   DESCRIPTION
       " Specify the mirror operation of this port. "
   ::= { xgs360028fACLACEStatusEntry 9 }

xgs360028fACLACEStatusCPU OBJECT-TYPE
   SYNTAX      DisplayString
   MAX-ACCESS  read-only
   STATUS      current
   DESCRIPTION
       " Forward packet that matched the specific ACE to CPU. "
   ::= { xgs360028fACLACEStatusEntry 10 }

xgs360028fACLACEStatusCounter OBJECT-TYPE
   SYNTAX      Counter32
   MAX-ACCESS  read-only
   STATUS      current
   DESCRIPTION
       " The counter indicates the number of times the ACE was hit by a frame. "
   ::= { xgs360028fACLACEStatusEntry 11 }
   
xgs360028fACLACEStatusConflict OBJECT-TYPE
   SYNTAX      DisplayString
   MAX-ACCESS  read-only
   STATUS      current
   DESCRIPTION
       " Indicates the hardware status of the specific ACE. The specific ACE is not applied to the hardware due to hardware limitations. "
   ::= { xgs360028fACLACEStatusEntry 12 }   


xgs360028fERPS                                             OBJECT IDENTIFIER ::= { xgs360028fConfiguration 10 }

xgs360028fERPSConf                                          OBJECT IDENTIFIER ::= { xgs360028fERPS 1 }

xgs360028fERPSConfCreate OBJECT-TYPE
   SYNTAX       INTEGER(0|1)
   MAX-ACCESS   read-write
   STATUS       current
   DESCRIPTION
       "default: 0
        0 : None  (read only)
        1 : Create an ERPS entry"
   ::= { xgs360028fERPSConf 1 }

xgs360028fERPSConfTable OBJECT-TYPE
   SYNTAX      SEQUENCE OF XGS360028FERPSConfEntry
   MAX-ACCESS  not-accessible
   STATUS      current
   DESCRIPTION
       " Create one ERPS group. "
   ::= { xgs360028fERPSConf 2 }

xgs360028fERPSConfEntry OBJECT-TYPE
   SYNTAX      XGS360028FERPSConfEntry
   MAX-ACCESS  not-accessible
   STATUS      current
   DESCRIPTION
       ""
   INDEX    { xgs360028fERPSConfIndex  }
   ::= { xgs360028fERPSConfTable 1 }

XGS360028FERPSConfEntry ::= SEQUENCE {
   xgs360028fERPSConfIndex                  INTEGER,
   xgs360028fERPSConfERPSID                 INTEGER,
   xgs360028fERPSConfPort0                  INTEGER,
   xgs360028fERPSConfPort1                  INTEGER,
   xgs360028fERPSConfPort0SFMEP             INTEGER,
   xgs360028fERPSConfPort1SFMEP             INTEGER,
   xgs360028fERPSConfPort0APSMEP            INTEGER,
   xgs360028fERPSConfPort1APSMEP            INTEGER,
   xgs360028fERPSConfRingType               INTEGER,    
   xgs360028fERPSConfInterconnectedNode     INTEGER,
   xgs360028fERPSConfVirtualChannel         INTEGER,
   xgs360028fERPSConfMajorRingID            INTEGER,
   xgs360028fERPSConfAlarm                  DisplayString,
   
   xgs360028fERPSInstanceConfConfigured     DisplayString,
   xgs360028fERPSInstanceConfGuardTime      INTEGER,
   xgs360028fERPSInstanceConfWTRTime        INTEGER,
   xgs360028fERPSInstanceConfHoldOffTime    INTEGER,
   xgs360028fERPSInstanceConfVersion        INTEGER,
   xgs360028fERPSInstanceConfRevertive      INTEGER,
   xgs360028fERPSInstanceConfVLANconfig     DisplayString,  
   
   xgs360028fERPSConfRowStatus              INTEGER
}

xgs360028fERPSConfIndex OBJECT-TYPE
   SYNTAX      INTEGER (1..64)
   MAX-ACCESS  not-accessible
   STATUS      current
   DESCRIPTION
       " "
   ::= { xgs360028fERPSConfEntry 1 }

xgs360028fERPSConfERPSID OBJECT-TYPE
   SYNTAX      INTEGER (1..64)
   MAX-ACCESS  read-write
   STATUS      current
   DESCRIPTION
       " Protection group ID.
         range : 1 - 64. "
   ::= { xgs360028fERPSConfEntry 2 }

xgs360028fERPSConfPort0 OBJECT-TYPE
   SYNTAX      INTEGER (1..26)
   MAX-ACCESS  read-write
   STATUS      current
   DESCRIPTION
       " East port of the switch in the ring.
         range : 1 - 26. "
   ::= { xgs360028fERPSConfEntry 3 }

xgs360028fERPSConfPort1 OBJECT-TYPE
   SYNTAX      INTEGER (0..26)
   MAX-ACCESS  read-write
   STATUS      current
   DESCRIPTION
       " West port of the switch in the Ring. 
         As interconnected sub-ring will have only one ring port, W port is configured as 0 for interconnected sub-ring. 
         0: in this field indicates that no west port is associated with this instance.
         range : 0 - 26. "
   ::= { xgs360028fERPSConfEntry 4 }

xgs360028fERPSConfPort0SFMEP OBJECT-TYPE
   SYNTAX      INTEGER (1..32)
   MAX-ACCESS  read-write
   STATUS      current
   DESCRIPTION
       " The East Signal Fail reporting MEP.
         range : 1 - 32. "
   ::= { xgs360028fERPSConfEntry 5 }

xgs360028fERPSConfPort1SFMEP OBJECT-TYPE
   SYNTAX      INTEGER (0..32)
   MAX-ACCESS  read-write
   STATUS      current
   DESCRIPTION
       " The West Signal Fail reporting MEP. As only one SF MEP is associated with interconnected sub-ring without virtual channel,
         it is configured as 0 for such ring instances. 0: in this field indicates that no west SF MEP is associated with this instance. 
         range : 0 - 32. "
   ::= { xgs360028fERPSConfEntry 6 }

xgs360028fERPSConfPort0APSMEP OBJECT-TYPE
   SYNTAX      INTEGER (1..32)
   MAX-ACCESS  read-write
   STATUS      current
   DESCRIPTION
       " The East APS PDU handling MEP. 
         range : 1 - 32. "
   ::= { xgs360028fERPSConfEntry 7 }

xgs360028fERPSConfPort1APSMEP OBJECT-TYPE
   SYNTAX      INTEGER (0..32)
   MAX-ACCESS  read-write
   STATUS      current
   DESCRIPTION
       " The West APS PDU handling MEP. As only one APS MEP is associated with interconnected sub-ring without virtual channel,
         it is configured as 0 for such ring instances. 0: in this field indicates that no west APS MEP is associated with this instance. 
         range : 0 - 32. "
   ::= { xgs360028fERPSConfEntry 8 }

xgs360028fERPSConfRingType OBJECT-TYPE
   SYNTAX      INTEGER (0|1)
   MAX-ACCESS  read-write
   STATUS      current
   DESCRIPTION
       " Type of Protectiong ring. It can be either major ring or sub-ring. 
         default: 0,
         0: Major
         1: Sub"
   ::= { xgs360028fERPSConfEntry 9 }

xgs360028fERPSConfInterconnectedNode OBJECT-TYPE
   SYNTAX      INTEGER (0|1)
   MAX-ACCESS  read-write
   STATUS      current
   DESCRIPTION
       " Interconnected Node indicates that the ring instance is interconnected.   
         default: 0,
         0: No - indicates that the configured instance is not interconnected.
         1: Yes - indicates it is an interconnected node for this instance. "
   ::= { xgs360028fERPSConfEntry 10 }

xgs360028fERPSConfVirtualChannel OBJECT-TYPE
   SYNTAX      INTEGER (0|1)
   MAX-ACCESS  read-write
   STATUS      current
   DESCRIPTION
       " Sub-rings can either have virtual channel or not on the interconnected node.  
         default: 0,
         0: No - indicates, sub-ring doesn't have virtual channel.
         1: Yes - indicates it is a sub-ring with virtual channel. "
   ::= { xgs360028fERPSConfEntry 11 }

xgs360028fERPSConfMajorRingID OBJECT-TYPE
   SYNTAX      INTEGER (1..64)
   MAX-ACCESS  read-only
   STATUS      current
   DESCRIPTION
       " Major ring group ID for the interconnected sub-ring. 
         It is used to send topology change updates on major ring. 
         If ring is major, this value is same as the protection group ID of this ring. "
   ::= { xgs360028fERPSConfEntry 12 }

xgs360028fERPSConfAlarm OBJECT-TYPE
   SYNTAX      DisplayString (SIZE (1..32))
   MAX-ACCESS  read-only
   STATUS      current
   DESCRIPTION
       " There is an active alarm on the ERPS. "
   ::= { xgs360028fERPSConfEntry 13 }

xgs360028fERPSInstanceConfConfigured OBJECT-TYPE
   SYNTAX      DisplayString (SIZE (1..32))
   MAX-ACCESS  read-only
   STATUS      current
   DESCRIPTION
       " Down: This ERPS is only created and has not yet been configured - is not active.
         Up: This ERPS is configured - is active. "
   ::= { xgs360028fERPSConfEntry 14 }

xgs360028fERPSInstanceConfGuardTime OBJECT-TYPE
   SYNTAX      INTEGER (10..2000)
   MAX-ACCESS  read-write
   STATUS      current
   DESCRIPTION
       " Guard timeout value to be used to prevent ring nodes from receiving outdated R-APS messages.
         default : 500(ms).
         range : 10 - 2000(ms). "
   ::= { xgs360028fERPSConfEntry 15 }
   
xgs360028fERPSInstanceConfWTRTime OBJECT-TYPE
   SYNTAX      INTEGER (1..12)
   MAX-ACCESS  read-write
   STATUS      current
   DESCRIPTION
       " The Wait To Restore timing value to be used in revertive switching.
         default : 5(minutes).
         range : 1 - 12(minutes). "
   ::= { xgs360028fERPSConfEntry 16 }
   
xgs360028fERPSInstanceConfHoldOffTime OBJECT-TYPE
   SYNTAX      INTEGER (0..10000)
   MAX-ACCESS  read-write
   STATUS      current
   DESCRIPTION
       " The timing value to be used to make persistent check on Signal Fail before switching. 
         default : 0(seconds).
         range : 0 - 10000(ms). "
   ::= { xgs360028fERPSConfEntry 17 }

xgs360028fERPSInstanceConfVersion OBJECT-TYPE
   SYNTAX      INTEGER (0|1)
   MAX-ACCESS  read-write
   STATUS      current
   DESCRIPTION
       " ERPS version of a group. 
         default : 1.
         0: v1
         1: v2 "
   ::= { xgs360028fERPSConfEntry 18 }
   
xgs360028fERPSInstanceConfRevertive OBJECT-TYPE
   SYNTAX      INTEGER (0|1)
   MAX-ACCESS  read-write
   STATUS      current
   DESCRIPTION
       " ERPS revertibility of a group. 
         default : 1.
         0: non-revertible
         1: revertible "
   ::= { xgs360028fERPSConfEntry 19 }
   
xgs360028fERPSInstanceConfVLANconfig OBJECT-TYPE
   SYNTAX      DisplayString (SIZE (1..255))
   MAX-ACCESS  read-write
   STATUS      current
   DESCRIPTION
       " VID of the protected vlan. "
   ::= { xgs360028fERPSConfEntry 20 }      

xgs360028fERPSConfRowStatus OBJECT-TYPE
   SYNTAX      INTEGER (1..5)
   MAX-ACCESS  read-write
   STATUS      current
   DESCRIPTION
       " 1: active
        2: notInservice
        3: edit
        4: destroy
        5: undo"
   ::= { xgs360028fERPSConfEntry 21 }


xgs360028fMRSTP                                             OBJECT IDENTIFIER ::= { xgs360028fConfiguration 11 }

xgs360028fMRSTPInstance                                          OBJECT IDENTIFIER ::= { xgs360028fMRSTP 1 }

xgs360028fMRSTPInstanceConf                                          OBJECT IDENTIFIER ::= { xgs360028fMRSTPInstance 1 }

xgs360028fMRSTPInstanceConfGlobalState OBJECT-TYPE
   SYNTAX      INTEGER(0|1)
   MAX-ACCESS  read-write
   STATUS      current
   DESCRIPTION
       "default: 0
       0: disable
       1: enable"
   ::= { xgs360028fMRSTPInstanceConf 1 }

xgs360028fMRSTPInstanceConfigurationTable OBJECT-TYPE
   SYNTAX      SEQUENCE OF XGS360028FMRSTPInstanceConfigurationEntry
   MAX-ACCESS  not-accessible
   STATUS      current
   DESCRIPTION
       " show instance configuration. "
   ::= { xgs360028fMRSTPInstanceConf 2 }

xgs360028fMRSTPInstanceConfigurationEntry OBJECT-TYPE
   SYNTAX      XGS360028FMRSTPInstanceConfigurationEntry
   MAX-ACCESS  not-accessible
   STATUS      current
   DESCRIPTION
       ""
   INDEX    { xgs360028fMRSTPInstanceConfigurationInstance  }
   ::= { xgs360028fMRSTPInstanceConfigurationTable 1 }
   
XGS360028FMRSTPInstanceConfigurationEntry ::= SEQUENCE {
   xgs360028fMRSTPInstanceConfigurationInstance         INTEGER,
   xgs360028fMRSTPInstanceConfigurationState            INTEGER,
   xgs360028fMRSTPInstanceConfigurationVersion          INTEGER,
   xgs360028fMRSTPInstanceConfigurationPriority         INTEGER,
   xgs360028fMRSTPInstanceConfigurationHelloTime        INTEGER,
   xgs360028fMRSTPInstanceConfigurationMaxAge           INTEGER,
   xgs360028fMRSTPInstanceConfigurationFWDelay          INTEGER
}

xgs360028fMRSTPInstanceConfigurationInstance OBJECT-TYPE
   SYNTAX      INTEGER(1..12)
   MAX-ACCESS  not-accessible
   STATUS      current
   DESCRIPTION
       " mrstp instance id, range : 1-12 "
   ::= { xgs360028fMRSTPInstanceConfigurationEntry 1 }

xgs360028fMRSTPInstanceConfigurationState OBJECT-TYPE
   SYNTAX      INTEGER (0|1)
   MAX-ACCESS  read-write
   STATUS      current
   DESCRIPTION
       " MRSTP instance state. To really enable an MRSTP instance, the MRSTP Global State must also be enabled. 
         default: 0,
         0: disable
         1: enable"
   ::= { xgs360028fMRSTPInstanceConfigurationEntry 2 }

xgs360028fMRSTPInstanceConfigurationVersion OBJECT-TYPE
   SYNTAX      INTEGER (0|1)
   MAX-ACCESS  read-write
   STATUS      current
   DESCRIPTION
       " The STP protocol version.
         default: 1,
         0: stp
         1: rstp"
   ::= { xgs360028fMRSTPInstanceConfigurationEntry 3 }

xgs360028fMRSTPInstanceConfigurationPriority OBJECT-TYPE
   SYNTAX      INTEGER(0..61440)
   MAX-ACCESS  read-write
   STATUS      current
   DESCRIPTION
       " The instance priority would be truncated to a multiple of 4096.
         range : 0 - 61440, default: 32768."
   ::= { xgs360028fMRSTPInstanceConfigurationEntry 4 }

xgs360028fMRSTPInstanceConfigurationHelloTime OBJECT-TYPE
   SYNTAX      INTEGER(1..10)
   MAX-ACCESS  read-write
   STATUS      current
   DESCRIPTION
       " The interval between periodic transmissions of STP Configuration Messages by Designated Ports when the Bridge Instance is the Root Bridge.
         range : 1 - 10 (seconds), and (HelloTime+1)*2 must be <= MaxAge.
         default: 2."
   ::= { xgs360028fMRSTPInstanceConfigurationEntry 5 }

xgs360028fMRSTPInstanceConfigurationMaxAge OBJECT-TYPE
   SYNTAX      INTEGER(6..40)
   MAX-ACCESS  read-write
   STATUS      current
   DESCRIPTION
       " The maximum age of the information transmitted by the Bridge Instance when it is the Root Bridge.  
         range : 6 - 40 (seconds), and MaxAge must be <= (FwdDelay-1)*2.
         default: 20."
   ::= { xgs360028fMRSTPInstanceConfigurationEntry 6 }

xgs360028fMRSTPInstanceConfigurationFWDelay OBJECT-TYPE
   SYNTAX      INTEGER(4..30)
   MAX-ACCESS  read-write
   STATUS      current
   DESCRIPTION
       " The delay used by an MRSTP Bridge Instance to transit Root and Designated Ports to Forwarding 
        (used in STP compatible mode).
         range : 4 - 30 (seconds), and MaxAge must be <= (FwdDelay-1)*2.
         default: 15."
   ::= { xgs360028fMRSTPInstanceConfigurationEntry 7 }

xgs360028fMRSTPInstanceStatus                                          OBJECT IDENTIFIER ::= { xgs360028fMRSTPInstance 2 }

xgs360028fMRSTPInstanceStatusTable OBJECT-TYPE
   SYNTAX      SEQUENCE OF XGS360028FMRSTPInstanceStatusEntry
   MAX-ACCESS  not-accessible
   STATUS      current
   DESCRIPTION
       " show mrstp status of instance(s). "
   ::= { xgs360028fMRSTPInstanceStatus 1 }

xgs360028fMRSTPInstanceStatusEntry OBJECT-TYPE
   SYNTAX      XGS360028FMRSTPInstanceStatusEntry
   MAX-ACCESS  not-accessible
   STATUS      current
   DESCRIPTION
       ""
   INDEX    { xgs360028fMRSTPInstanceStatusInstance  }
   ::= { xgs360028fMRSTPInstanceStatusTable 1 }
   
XGS360028FMRSTPInstanceStatusEntry ::= SEQUENCE {
   xgs360028fMRSTPInstanceStatusInstance                        INTEGER,
   xgs360028fMRSTPInstanceStatusGlobalState                     INTEGER,
   xgs360028fMRSTPInstanceStatusInstanceConfigState             INTEGER,
   xgs360028fMRSTPInstanceStatusInstanceCurrentState            INTEGER,
   xgs360028fMRSTPInstanceStatusBridgeID                        MacAddress,
   xgs360028fMRSTPInstanceStatusBridgePrioriry                  INTEGER,
   xgs360028fMRSTPInstanceStatusRootID                          MacAddress,
   xgs360028fMRSTPInstanceStatusRootPriority                    INTEGER,
   xgs360028fMRSTPInstanceStatusRootPort                        INTEGER,
   xgs360028fMRSTPInstanceStatusRootPathCost                    INTEGER,
   xgs360028fMRSTPInstanceStatusCurrentMaxAge                   INTEGER,
   xgs360028fMRSTPInstanceStatusCurrentForwardDelay             INTEGER,
   xgs360028fMRSTPInstanceStatusHelloTime                       INTEGER,
   xgs360028fMRSTPInstanceStatusTopologyChangeCount             INTEGER,
   xgs360028fMRSTPInstanceStatusTimeSinceLastTopologyChange     INTEGER
}

xgs360028fMRSTPInstanceStatusInstance OBJECT-TYPE
   SYNTAX      INTEGER(1..12)
   MAX-ACCESS  not-accessible
   STATUS      current
   DESCRIPTION
       " mrstp instance id, range : 1-12 "
   ::= { xgs360028fMRSTPInstanceStatusEntry 1 }

xgs360028fMRSTPInstanceStatusGlobalState OBJECT-TYPE
   SYNTAX      INTEGER (0|1)
   MAX-ACCESS  read-only
   STATUS      current
   DESCRIPTION
       " The global state of MRSTP. If disabled,all instances won't be in an active state.
         0: disable
         1: enable"
   ::= { xgs360028fMRSTPInstanceStatusEntry 2 }

xgs360028fMRSTPInstanceStatusInstanceConfigState OBJECT-TYPE
   SYNTAX      INTEGER (0|1)
   MAX-ACCESS  read-only
   STATUS      current
   DESCRIPTION
       " The configured state of an MRSTP instance. 
         0: disable
         1: enable"
   ::= { xgs360028fMRSTPInstanceStatusEntry 3 }

xgs360028fMRSTPInstanceStatusInstanceCurrentState OBJECT-TYPE
   SYNTAX      INTEGER (0|1)
   MAX-ACCESS  read-only
   STATUS      current
   DESCRIPTION
       " The operational state of an MRSTP Bridge Instance.  
         0: disable
         1: enable"
   ::= { xgs360028fMRSTPInstanceStatusEntry 4 }

xgs360028fMRSTPInstanceStatusBridgeID OBJECT-TYPE
   SYNTAX       MacAddress
   MAX-ACCESS   read-only
   STATUS       current
   DESCRIPTION
       " The Bridge ID of this Bridge instance. "
   ::= { xgs360028fMRSTPInstanceStatusEntry 5 }
   
xgs360028fMRSTPInstanceStatusBridgePrioriry OBJECT-TYPE
   SYNTAX      INTEGER(0..61440)
   MAX-ACCESS  read-only
   STATUS      current
   DESCRIPTION
       " The Bridge Priority of this Bridge instance. Value is shown in decimal. 
         range : 0 - 61440 "
   ::= { xgs360028fMRSTPInstanceStatusEntry 6 }
   
xgs360028fMRSTPInstanceStatusRootID OBJECT-TYPE
   SYNTAX       MacAddress
   MAX-ACCESS   read-only
   STATUS       current
   DESCRIPTION
       " The Bridge ID of the currently elected root bridge. "
   ::= { xgs360028fMRSTPInstanceStatusEntry 7 }   

xgs360028fMRSTPInstanceStatusRootPriority OBJECT-TYPE
   SYNTAX      INTEGER(0..61440)
   MAX-ACCESS  read-only
   STATUS      current
   DESCRIPTION
       " The Bridge Priority of the currently elected root bridge. Value is shown in decimal.  
         range : 0 - 61440 "
   ::= { xgs360028fMRSTPInstanceStatusEntry 8 }

xgs360028fMRSTPInstanceStatusRootPort OBJECT-TYPE
   SYNTAX      INTEGER
   MAX-ACCESS  read-only
   STATUS      current
   DESCRIPTION
       " The switch port currently assigned the root port role. "
   ::= { xgs360028fMRSTPInstanceStatusEntry 9 }

xgs360028fMRSTPInstanceStatusRootPathCost OBJECT-TYPE
   SYNTAX      INTEGER
   MAX-ACCESS  read-only
   STATUS      current
   DESCRIPTION
       " For the Root Bridge it is zero. For all other Bridges, it is the sum of the Port Path Costs on the least cost path to the Root Bridge. "
   ::= { xgs360028fMRSTPInstanceStatusEntry 10 }

xgs360028fMRSTPInstanceStatusCurrentMaxAge OBJECT-TYPE
   SYNTAX      INTEGER(6..40)
   MAX-ACCESS  read-only
   STATUS      current
   DESCRIPTION
       " The Max Age inherited from the Root Bridge.   
         range : 6 - 40 (seconds)"
   ::= { xgs360028fMRSTPInstanceStatusEntry 11 }
   
xgs360028fMRSTPInstanceStatusCurrentForwardDelay OBJECT-TYPE
   SYNTAX      INTEGER(4..30)
   MAX-ACCESS  read-only
   STATUS      current
   DESCRIPTION
       " The Forward Delay time inherited from the Root Bridge.    
         range : 4 - 30 (seconds) "
   ::= { xgs360028fMRSTPInstanceStatusEntry 12 }
      
xgs360028fMRSTPInstanceStatusHelloTime OBJECT-TYPE
   SYNTAX      INTEGER(1..10)
   MAX-ACCESS  read-only
   STATUS      current
   DESCRIPTION
       " The Hello Time inherited from the Root Bridge.   
         range : 1 - 10 (seconds) "
   ::= { xgs360028fMRSTPInstanceStatusEntry 13 }
      
xgs360028fMRSTPInstanceStatusTopologyChangeCount OBJECT-TYPE
   SYNTAX      INTEGER
   MAX-ACCESS  read-only
   STATUS      current
   DESCRIPTION
       " The Topology Change Count since the MRSTP Bridge Instance is actually enabled. "
   ::= { xgs360028fMRSTPInstanceStatusEntry 14 }         

xgs360028fMRSTPInstanceStatusTimeSinceLastTopologyChange OBJECT-TYPE
   SYNTAX      INTEGER
   MAX-ACCESS  read-only
   STATUS      current
   DESCRIPTION
       " The time since last Topology Change occurred. "
   ::= { xgs360028fMRSTPInstanceStatusEntry 15 }

xgs360028fMRSTPPort                                          OBJECT IDENTIFIER ::= { xgs360028fMRSTP 2 }

xgs360028fMRSTPPortConfiguration                                          OBJECT IDENTIFIER ::= { xgs360028fMRSTPPort 1 }

xgs360028fMRSTPPortConfigurationTable OBJECT-TYPE
   SYNTAX      SEQUENCE OF XGS360028FMRSTPPortConfigurationEntry
   MAX-ACCESS  not-accessible
   STATUS      current
   DESCRIPTION
       " current MRSTP port configurations. "
   ::= { xgs360028fMRSTPPortConfiguration 1 }

xgs360028fMRSTPPortConfigurationEntry OBJECT-TYPE
   SYNTAX      XGS360028FMRSTPPortConfigurationEntry
   MAX-ACCESS  not-accessible
   STATUS      current
   DESCRIPTION
       ""
   INDEX    { xgs360028fMRSTPPortConfigurationPort  }
   ::= { xgs360028fMRSTPPortConfigurationTable 1 }
   
XGS360028FMRSTPPortConfigurationEntry ::= SEQUENCE {
   xgs360028fMRSTPPortConfigurationPort             INTEGER,
   xgs360028fMRSTPPortConfigurationInstance         INTEGER,
   xgs360028fMRSTPPortConfigurationPathCost         INTEGER,
   xgs360028fMRSTPPortConfigurationPriority         INTEGER,   
   xgs360028fMRSTPPortConfigurationAdminEdge        INTEGER,   
   xgs360028fMRSTPPortConfigurationAdminP2P         INTEGER,
   xgs360028fMRSTPPortConfigurationMigrateCheck     INTEGER
}

xgs360028fMRSTPPortConfigurationPort OBJECT-TYPE
   SYNTAX      INTEGER(1..4095)
   MAX-ACCESS  not-accessible
   STATUS      current
   DESCRIPTION
       " The switch port number of the MRSTP port. "
   ::= { xgs360028fMRSTPPortConfigurationEntry 1 }

xgs360028fMRSTPPortConfigurationInstance OBJECT-TYPE
   SYNTAX      INTEGER(0..61440)
   MAX-ACCESS  read-write
   STATUS      current
   DESCRIPTION
       " MRSTP Bridge Instance. default: 0
         range : 0 - 12, 0: None "
   ::= { xgs360028fMRSTPPortConfigurationEntry 2 }

xgs360028fMRSTPPortConfigurationPathCost OBJECT-TYPE
   SYNTAX      INTEGER(0..200000000)
   MAX-ACCESS  read-write
   STATUS      current
   DESCRIPTION
       " port path cost;when the value is 0,path cost is determined by physical port speed. 
         default: 0
         range : 0 - 200000000, 0: Auto"
   ::= { xgs360028fMRSTPPortConfigurationEntry 3 }

xgs360028fMRSTPPortConfigurationPriority OBJECT-TYPE
   SYNTAX      INTEGER(0..240)
   MAX-ACCESS  read-write
   STATUS      current
   DESCRIPTION
       " Port Priority; would be truncated to a multiple of 16. 
         default: 128
         range : 0 - 240"
   ::= { xgs360028fMRSTPPortConfigurationEntry 4 }
   
xgs360028fMRSTPPortConfigurationAdminEdge OBJECT-TYPE
   SYNTAX      INTEGER(0|1)
   MAX-ACCESS  read-write
   STATUS      current
   DESCRIPTION
       " port(s) as edge or non-edge.
         default: 1
         0: non-edge
         1: edge "
   ::= { xgs360028fMRSTPPortConfigurationEntry 5 }
   
xgs360028fMRSTPPortConfigurationAdminP2P OBJECT-TYPE
   SYNTAX      INTEGER(0..2)
   MAX-ACCESS  read-write
   STATUS      current
   DESCRIPTION
       " administrative point-to-point (p2p) port. 
         range : 0 - 2, default: 2
         0: force to be p2p port(s)
         1: force to be non-p2p port(s) 
         2: auto-detected according to port duplex "
   ::= { xgs360028fMRSTPPortConfigurationEntry 6 }
   
xgs360028fMRSTPPortConfigurationMigrateCheck OBJECT-TYPE
   SYNTAX      INTEGER(0|1)
   MAX-ACCESS  read-write
   STATUS      current
   DESCRIPTION
       " default: 0
         0: none
         1: perform migration check on port(s) "
   ::= { xgs360028fMRSTPPortConfigurationEntry 7 } 

xgs360028fMRSTPPortStatus                                          OBJECT IDENTIFIER ::= { xgs360028fMRSTPPort 2 }

xgs360028fMRSTPPortStatusTable OBJECT-TYPE
   SYNTAX      SEQUENCE OF XGS360028FMRSTPPortStatusEntry
   MAX-ACCESS  not-accessible
   STATUS      current
   DESCRIPTION
       " show mrstp port information. "
   ::= { xgs360028fMRSTPPortStatus 1 }

xgs360028fMRSTPPortStatusEntry OBJECT-TYPE
   SYNTAX      XGS360028FMRSTPPortStatusEntry
   MAX-ACCESS  not-accessible
   STATUS      current
   DESCRIPTION
       ""
   INDEX    { xgs360028fMRSTPPortStatusPort  }
   ::= { xgs360028fMRSTPPortStatusTable 1 }
   
XGS360028FMRSTPPortStatusEntry ::= SEQUENCE {
   xgs360028fMRSTPPortStatusPort                INTEGER,
   xgs360028fMRSTPPortStatusInstance            DisplayString,
   xgs360028fMRSTPPortStatusState               DisplayString,
   xgs360028fMRSTPPortStatusRole                DisplayString,   
   xgs360028fMRSTPPortStatusPathCost            INTEGER,   
   xgs360028fMRSTPPortStatusPathCostConfig      INTEGER,
   xgs360028fMRSTPPortStatusPriority            INTEGER,
   xgs360028fMRSTPPortStatusAdminEdge           DisplayString,
   xgs360028fMRSTPPortStatusAdminP2P            DisplayString
}

xgs360028fMRSTPPortStatusPort OBJECT-TYPE
   SYNTAX      INTEGER(1..4095)
   MAX-ACCESS  not-accessible
   STATUS      current
   DESCRIPTION
       " The switch port number of the MRSTP port. "
   ::= { xgs360028fMRSTPPortStatusEntry 1 }

xgs360028fMRSTPPortStatusInstance OBJECT-TYPE
   SYNTAX      DisplayString
   MAX-ACCESS  read-only
   STATUS      current
   DESCRIPTION
       " MRSTP Bridge Instance. "
   ::= { xgs360028fMRSTPPortStatusEntry 2 }

xgs360028fMRSTPPortStatusState OBJECT-TYPE
   SYNTAX      DisplayString
   MAX-ACCESS  read-only
   STATUS      current
   DESCRIPTION
       " The current RSTP port state. The port state can be one of the following values: DISCARDING LISTENING FORWARDING NON-MRSTP INST-DSBL. 
         INST-DSBL indicates that the Bridge Instance the port belongs to is disabled. "
   ::= { xgs360028fMRSTPPortStatusEntry 3 }

xgs360028fMRSTPPortStatusRole OBJECT-TYPE
   SYNTAX      DisplayString
   MAX-ACCESS  read-only
   STATUS      current
   DESCRIPTION
       " The current MRSTP port role. The port role can be one of the following values: disable alternate backup ROOT DSGN none. 
         none indicates that the Bridge Instance the port belongs to is disabled or the port is not an MRSTP port. 
         DSGN indicates a Designated port role. "
   ::= { xgs360028fMRSTPPortStatusEntry 4 }

xgs360028fMRSTPPortStatusPathCost OBJECT-TYPE
   SYNTAX      INTEGER(0..200000000)
   MAX-ACCESS  read-only
   STATUS      current
   DESCRIPTION
       " path cost. "
   ::= { xgs360028fMRSTPPortStatusEntry 5 }
   
xgs360028fMRSTPPortStatusPathCostConfig OBJECT-TYPE
   SYNTAX      INTEGER(0..200000000)
   MAX-ACCESS  read-only
   STATUS      current
   DESCRIPTION
       " port path cost config. "
   ::= { xgs360028fMRSTPPortStatusEntry 6 }
   
xgs360028fMRSTPPortStatusPriority OBJECT-TYPE
   SYNTAX      INTEGER(0..240)
   MAX-ACCESS  read-only
   STATUS      current
   DESCRIPTION
       " port priority. "
   ::= { xgs360028fMRSTPPortStatusEntry 7 }
   
xgs360028fMRSTPPortStatusAdminEdge OBJECT-TYPE
   SYNTAX      DisplayString
   MAX-ACCESS  read-only
   STATUS      current
   DESCRIPTION
       " port(s) as edge or non-edge. "
   ::= { xgs360028fMRSTPPortStatusEntry 8 }
   
xgs360028fMRSTPPortStatusAdminP2P OBJECT-TYPE
   SYNTAX      DisplayString
   MAX-ACCESS  read-only
   STATUS      current
   DESCRIPTION
       " administrative point-to-point (p2p) port. "
   ::= { xgs360028fMRSTPPortStatusEntry 9 }

----------------------------------------------------------------------------------------------------------------------------
xgs360028fSecurity                                              OBJECT IDENTIFIER ::= { xgs360028fProductId 3 }

xgs360028fIPSourceGuard                                         OBJECT IDENTIFIER ::= { xgs360028fSecurity 1 }

xgs360028fIPSourceGuardConf                                     OBJECT IDENTIFIER ::= { xgs360028fIPSourceGuard 1 }

xgs360028fIPSourceGuardMode OBJECT-TYPE
   SYNTAX      INTEGER (0|1)
   MAX-ACCESS  read-write
   STATUS      current
   DESCRIPTION
       " default:  0
        0: disable
        1: enable"
   ::= { xgs360028fIPSourceGuardConf 1 }

xgs360028fIPSourceGuardPortConfigTable OBJECT-TYPE
   SYNTAX      SEQUENCE OF XGS360028FIPSourceGuardPortConfigEntry
   MAX-ACCESS  not-accessible
   STATUS      current
   DESCRIPTION
       " "
   ::= { xgs360028fIPSourceGuardConf 2 }

xgs360028fIPSourceGuardPortConfigEntry OBJECT-TYPE
   SYNTAX      XGS360028FIPSourceGuardPortConfigEntry
   MAX-ACCESS  not-accessible
   STATUS      current
   DESCRIPTION
       ""
   INDEX    { xgs360028fIPSourceGuardPortConfigPort  }
   ::= { xgs360028fIPSourceGuardPortConfigTable 1 }

XGS360028FIPSourceGuardPortConfigEntry ::= SEQUENCE {
   xgs360028fIPSourceGuardPortConfigPort               INTEGER,
   xgs360028fIPSourceGuardPortConfigMode               INTEGER,
   xgs360028fIPSourceGuardPortMaxDynamicClients        INTEGER
}

xgs360028fIPSourceGuardPortConfigPort OBJECT-TYPE
   SYNTAX      INTEGER (1..4095)
   MAX-ACCESS  not-accessible
   STATUS      current
   DESCRIPTION
       " "
   ::= { xgs360028fIPSourceGuardPortConfigEntry 1 }

xgs360028fIPSourceGuardPortConfigMode OBJECT-TYPE
   SYNTAX      INTEGER (0|1)
   MAX-ACCESS  read-write
   STATUS      current
   DESCRIPTION
       "default: 0
       0:disable
       1:enable "
   ::= { xgs360028fIPSourceGuardPortConfigEntry 2 }

xgs360028fIPSourceGuardPortMaxDynamicClients OBJECT-TYPE
   SYNTAX      INTEGER (0..2|99)
   MAX-ACCESS  read-write
   STATUS      current
   DESCRIPTION
       "default: 99
       0~2: Max Dynamic clients
       99:Unlimited "
   ::= { xgs360028fIPSourceGuardPortConfigEntry 3 }


xgs360028fIPSourceGuardStatic                                OBJECT IDENTIFIER ::= { xgs360028fIPSourceGuard 2 }

xgs360028fIPSourceGuardStaticCreate OBJECT-TYPE
   SYNTAX       INTEGER(0|1)
   MAX-ACCESS   read-write
   STATUS       current
   DESCRIPTION
       "default: 0
        0 : None  (read only)
        1 : Create a IP Source Guard"
   ::= { xgs360028fIPSourceGuardStatic 1 }

xgs360028fIPSourceGuardStaticTable OBJECT-TYPE
   SYNTAX      SEQUENCE OF XGS360028FIPSourceGuardStaticEntry
   MAX-ACCESS  not-accessible
   STATUS      current
   DESCRIPTION
       " "
   ::= { xgs360028fIPSourceGuardStatic 2 }

xgs360028fIPSourceGuardStaticEntry OBJECT-TYPE
   SYNTAX      XGS360028FIPSourceGuardStaticEntry
   MAX-ACCESS  not-accessible
   STATUS      current
   DESCRIPTION
       ""
   INDEX    { xgs360028fIPSourceGuardStaticIndex  }
   ::= { xgs360028fIPSourceGuardStaticTable 1 }

XGS360028FIPSourceGuardStaticEntry ::= SEQUENCE {
   xgs360028fIPSourceGuardStaticIndex         INTEGER,
   xgs360028fIPSourceGuardStaticPort          INTEGER,
   xgs360028fIPSourceGuardStaticVLANId        INTEGER,
   xgs360028fIPSourceGuardStaticIPAddress     IpAddress,
   xgs360028fIPSourceGuardStaticMACAddress    MacAddress,
   xgs360028fIPSourceGuardStaticRowStatus     INTEGER
}

xgs360028fIPSourceGuardStaticIndex OBJECT-TYPE
   SYNTAX      INTEGER (1..28)
   MAX-ACCESS  not-accessible
   STATUS      current
   DESCRIPTION
       " "
   ::= { xgs360028fIPSourceGuardStaticEntry 1 }

xgs360028fIPSourceGuardStaticPort OBJECT-TYPE
   SYNTAX      INTEGER (1..4095)
   MAX-ACCESS  read-write
   STATUS      current
   DESCRIPTION
       " Port, range: 1 - port number. "
   ::= { xgs360028fIPSourceGuardStaticEntry 2 }

xgs360028fIPSourceGuardStaticVLANId OBJECT-TYPE
   SYNTAX      INTEGER (1..4094)
   MAX-ACCESS  read-write
   STATUS      current
   DESCRIPTION
       " VLAN ID, range: 1 - 4094. "
   ::= { xgs360028fIPSourceGuardStaticEntry 3 }

xgs360028fIPSourceGuardStaticIPAddress OBJECT-TYPE
   SYNTAX      IpAddress
   MAX-ACCESS  read-write
   STATUS      current
   DESCRIPTION
       " IP address allowed for doing IP source guard. "
   ::= { xgs360028fIPSourceGuardStaticEntry 4 }

xgs360028fIPSourceGuardStaticMACAddress OBJECT-TYPE
   SYNTAX      MacAddress
   MAX-ACCESS  read-write
   STATUS      current
   DESCRIPTION
       " Allowed Source MAC address, format 0a 1b 2c 3d 4e 5f "
   ::= { xgs360028fIPSourceGuardStaticEntry 5 }

xgs360028fIPSourceGuardStaticRowStatus OBJECT-TYPE
   SYNTAX      INTEGER (1..5)
   MAX-ACCESS  read-write
   STATUS      current
   DESCRIPTION
       "1: active
        2: notInservice
        3: edit
        4: destroy
        5: undo"
   ::= { xgs360028fIPSourceGuardStaticEntry 6 }

xgs360028fIPSourceGuardDynamicTable OBJECT-TYPE
   SYNTAX      SEQUENCE OF XGS360028FIPSourceGuardDynamicEntry
   MAX-ACCESS  not-accessible
   STATUS      current
   DESCRIPTION
       " "
   ::= { xgs360028fIPSourceGuard 3 }

xgs360028fIPSourceGuardDynamicEntry OBJECT-TYPE
   SYNTAX      XGS360028FIPSourceGuardDynamicEntry
   MAX-ACCESS  not-accessible
   STATUS      current
   DESCRIPTION
       ""
   INDEX    { xgs360028fIPSourceGuardDynamicIndex  }
   ::= { xgs360028fIPSourceGuardDynamicTable 1 }

XGS360028FIPSourceGuardDynamicEntry ::= SEQUENCE {
   xgs360028fIPSourceGuardDynamicIndex		    INTEGER,
   xgs360028fIPSourceGuardDynamicPort		    INTEGER,
   xgs360028fIPSourceGuardDynamicVLANId		    INTEGER,
   xgs360028fIPSourceGuardDynamicIPAddress		IpAddress,
   xgs360028fIPSourceGuardDynamicMACAddress		MacAddress
}

xgs360028fIPSourceGuardDynamicIndex OBJECT-TYPE
   SYNTAX      INTEGER(1..4095)
   MAX-ACCESS  not-accessible
   STATUS      current
   DESCRIPTION
       " "
   ::= { xgs360028fIPSourceGuardDynamicEntry 1 }

xgs360028fIPSourceGuardDynamicPort OBJECT-TYPE
   SYNTAX      INTEGER (1..10)
   MAX-ACCESS  read-only
   STATUS      current
   DESCRIPTION
       " "
   ::= { xgs360028fIPSourceGuardDynamicEntry 2 }

xgs360028fIPSourceGuardDynamicVLANId OBJECT-TYPE
   SYNTAX      INTEGER (1..4094)
   MAX-ACCESS  read-only
   STATUS      current
   DESCRIPTION
       " "
   ::= { xgs360028fIPSourceGuardDynamicEntry 3 }

xgs360028fIPSourceGuardDynamicIPAddress OBJECT-TYPE
   SYNTAX      IpAddress
   MAX-ACCESS  read-only
   STATUS      current
   DESCRIPTION
       " "
   ::= { xgs360028fIPSourceGuardDynamicEntry 4 }

xgs360028fIPSourceGuardDynamicMACAddress OBJECT-TYPE
   SYNTAX      MacAddress
   MAX-ACCESS  read-only
   STATUS      current
   DESCRIPTION
       " "
   ::= { xgs360028fIPSourceGuardDynamicEntry 5 }

xgs360028fARPInspection                                         OBJECT IDENTIFIER ::= { xgs360028fSecurity 2 }

xgs360028fARPInspectionConf                                     OBJECT IDENTIFIER ::= { xgs360028fARPInspection 1 }

xgs360028fARPInspectionConfMode OBJECT-TYPE
   SYNTAX      INTEGER(0|1)
   MAX-ACCESS  read-write
   STATUS      current
   DESCRIPTION
       "default: 0
        0: disable
        1: enable"
   ::= { xgs360028fARPInspectionConf 1 }

xgs360028fARPInspectionConfTable OBJECT-TYPE
   SYNTAX      SEQUENCE OF XGS360028FARPInspectionConfEntry
   MAX-ACCESS  not-accessible
   STATUS      current
   DESCRIPTION
       " "
   ::= { xgs360028fARPInspectionConf 2 }

xgs360028fARPInspectionConfEntry OBJECT-TYPE
   SYNTAX      XGS360028FARPInspectionConfEntry
   MAX-ACCESS  not-accessible
   STATUS      current
   DESCRIPTION
       ""
   INDEX    { xgs360028fARPInspectionConfPortIndex  }
   ::= { xgs360028fARPInspectionConfTable 1 }

XGS360028FARPInspectionConfEntry ::= SEQUENCE {
   xgs360028fARPInspectionConfPortIndex	INTEGER,
   xgs360028fARPInspectionConfPortMode	INTEGER
}

xgs360028fARPInspectionConfPortIndex OBJECT-TYPE
   SYNTAX      INTEGER(1..4095)
   MAX-ACCESS  not-accessible
   STATUS      current
   DESCRIPTION
       " "
   ::= { xgs360028fARPInspectionConfEntry 1 }

xgs360028fARPInspectionConfPortMode OBJECT-TYPE
   SYNTAX      INTEGER (0|1)
   MAX-ACCESS  read-write
   STATUS      current
   DESCRIPTION
       "default: 0
        0: disable
        1: enable"
   ::= { xgs360028fARPInspectionConfEntry 2 }


xgs360028fARPInspectionStatic                                OBJECT IDENTIFIER ::= { xgs360028fARPInspection 2 }

xgs360028fARPInspectionStaticCreate OBJECT-TYPE
   SYNTAX      INTEGER (0|1)
   MAX-ACCESS  read-write
   STATUS      current
   DESCRIPTION
       "default: 0
        0: none
        1: create"
   ::= { xgs360028fARPInspectionStatic 1 }

xgs360028fARPInspectionStaticTable OBJECT-TYPE
   SYNTAX      SEQUENCE OF XGS360028FARPInspectionStaticEntry
   MAX-ACCESS  not-accessible
   STATUS      current
   DESCRIPTION
       " "
   ::= { xgs360028fARPInspectionStatic 2 }

xgs360028fARPInspectionStaticEntry OBJECT-TYPE
   SYNTAX      XGS360028FARPInspectionStaticEntry
   MAX-ACCESS  not-accessible
   STATUS      current
   DESCRIPTION
       ""
   INDEX    { xgs360028fARPInspectionStaticIndex  }
   ::= { xgs360028fARPInspectionStaticTable 1 }

XGS360028FARPInspectionStaticEntry ::= SEQUENCE {
   xgs360028fARPInspectionStaticIndex        INTEGER,
   xgs360028fARPInspectionStaticPort         INTEGER,
   xgs360028fARPInspectionStaticVLANId       INTEGER,
   xgs360028fARPInspectionStaticIPAddress	IpAddress,
   xgs360028fARPInspectionStaticMACAddress	MacAddress,
   xgs360028fARPInspectionStaticRowStatus	INTEGER
}

xgs360028fARPInspectionStaticIndex OBJECT-TYPE
   SYNTAX      INTEGER(1..4095)
   MAX-ACCESS  not-accessible
   STATUS      current
   DESCRIPTION
       ""
   ::= { xgs360028fARPInspectionStaticEntry 1 }

xgs360028fARPInspectionStaticPort OBJECT-TYPE
   SYNTAX      INTEGER(1..4095)
   MAX-ACCESS  read-write
   STATUS      current
   DESCRIPTION
       " Port, range: 1 - port number. "
   ::= { xgs360028fARPInspectionStaticEntry 2 }

xgs360028fARPInspectionStaticVLANId OBJECT-TYPE
   SYNTAX      INTEGER (1..4094)
   MAX-ACCESS  read-write
   STATUS      current
   DESCRIPTION
       " VLAN ID, range: 1 - 4094. "
   ::= { xgs360028fARPInspectionStaticEntry 3 }

xgs360028fARPInspectionStaticIPAddress OBJECT-TYPE
   SYNTAX      IpAddress
   MAX-ACCESS  read-write
   STATUS      current
   DESCRIPTION
       " IP address allowed for doing ARP request. "
   ::= { xgs360028fARPInspectionStaticEntry 4 }

xgs360028fARPInspectionStaticMACAddress OBJECT-TYPE
   SYNTAX      MacAddress
   MAX-ACCESS  read-write
   STATUS      current
   DESCRIPTION
       " Allowed Source MAC address in ARP request packets, format 0a 1b 2c 3d 4e 5f "
   ::= { xgs360028fARPInspectionStaticEntry 5 }

xgs360028fARPInspectionStaticRowStatus OBJECT-TYPE
   SYNTAX      INTEGER(1..5)
   MAX-ACCESS  read-write
   STATUS      current
   DESCRIPTION
       "1: active
        2: notInservice
        3: edit
        4: destroy
        5: undo"
   ::= { xgs360028fARPInspectionStaticEntry 6 }

xgs360028fARPInspectionDynamicTable OBJECT-TYPE
   SYNTAX      SEQUENCE OF XGS360028FARPInspectionDynamicEntry
   MAX-ACCESS  not-accessible
   STATUS      current
   DESCRIPTION
       " "
   ::= { xgs360028fARPInspection 3 }

xgs360028fARPInspectionDynamicEntry OBJECT-TYPE
   SYNTAX      XGS360028FARPInspectionDynamicEntry
   MAX-ACCESS  not-accessible
   STATUS      current
   DESCRIPTION
       ""
   INDEX    { xgs360028fARPInspectionDynamicIndex  }
   ::= { xgs360028fARPInspectionDynamicTable 1 }

XGS360028FARPInspectionDynamicEntry ::= SEQUENCE {
   xgs360028fARPInspectionDynamicIndex		    INTEGER,
   xgs360028fARPInspectionDynamicPort		    INTEGER,
   xgs360028fARPInspectionDynamicVLANId		    INTEGER,
   xgs360028fARPInspectionDynamicIPAddress		IpAddress,
   xgs360028fARPInspectionDynamicMACAddress		MacAddress
}

xgs360028fARPInspectionDynamicIndex OBJECT-TYPE
   SYNTAX      INTEGER(1..4095)
   MAX-ACCESS  not-accessible
   STATUS      current
   DESCRIPTION
       " "
   ::= { xgs360028fARPInspectionDynamicEntry 1 }

xgs360028fARPInspectionDynamicPort OBJECT-TYPE
   SYNTAX      INTEGER(1..4095)
   MAX-ACCESS  read-only
   STATUS      current
   DESCRIPTION
       ""
   ::= { xgs360028fARPInspectionDynamicEntry 2 }

xgs360028fARPInspectionDynamicVLANId OBJECT-TYPE
   SYNTAX      INTEGER (1..4094)
   MAX-ACCESS  read-only
   STATUS      current
   DESCRIPTION
       ""
   ::= { xgs360028fARPInspectionDynamicEntry 3 }

xgs360028fARPInspectionDynamicIPAddress OBJECT-TYPE
   SYNTAX      IpAddress
   MAX-ACCESS  read-only
   STATUS      current
   DESCRIPTION
       ""
   ::= { xgs360028fARPInspectionDynamicEntry 4 }

xgs360028fARPInspectionDynamicMACAddress OBJECT-TYPE
   SYNTAX      MacAddress
   MAX-ACCESS  read-only
   STATUS      current
   DESCRIPTION
       ""
   ::= { xgs360028fARPInspectionDynamicEntry 5 }

xgs360028fDHCPSnooping                                          OBJECT IDENTIFIER ::= { xgs360028fSecurity 3 }

xgs360028fDHCPSnoopingConf                                          OBJECT IDENTIFIER ::= { xgs360028fDHCPSnooping 1 }

xgs360028fDHCPSnoopingMode OBJECT-TYPE
   SYNTAX      INTEGER(0|1)
   MAX-ACCESS  read-write
   STATUS      current
   DESCRIPTION
       "default: 0
       0: disable
       1: enable"
   ::= { xgs360028fDHCPSnoopingConf 1 }

xgs360028fDHCPSnoopingPortModeConfigurationTable OBJECT-TYPE
   SYNTAX      SEQUENCE OF XGS360028FDHCPSnoopingPortModeConfigurationEntry
   MAX-ACCESS  not-accessible
   STATUS      current
   DESCRIPTION
       " "
   ::= { xgs360028fDHCPSnoopingConf 2 }

xgs360028fDHCPSnoopingPortModeConfigurationEntry OBJECT-TYPE
   SYNTAX      XGS360028FDHCPSnoopingPortModeConfigurationEntry
   MAX-ACCESS  not-accessible
   STATUS      current
   DESCRIPTION
       ""
   INDEX    { xgs360028fDHCPSnoopingPortModeConfigurationPort  }
   ::= { xgs360028fDHCPSnoopingPortModeConfigurationTable 1 }
   
XGS360028FDHCPSnoopingPortModeConfigurationEntry ::= SEQUENCE {
   xgs360028fDHCPSnoopingPortModeConfigurationPort	INTEGER,
   xgs360028fDHCPSnoopingPortModeConfigurationMode	INTEGER
}

xgs360028fDHCPSnoopingPortModeConfigurationPort OBJECT-TYPE
   SYNTAX      INTEGER(1..4095)
   MAX-ACCESS  not-accessible
   STATUS      current
   DESCRIPTION
       " "
   ::= { xgs360028fDHCPSnoopingPortModeConfigurationEntry 1 }

xgs360028fDHCPSnoopingPortModeConfigurationMode OBJECT-TYPE
   SYNTAX      INTEGER (0|1)
   MAX-ACCESS  read-write
   STATUS      current
   DESCRIPTION
       "default: 1
       0: trust port mode
       1: untrust port mode"
   ::= { xgs360028fDHCPSnoopingPortModeConfigurationEntry 2 }

xgs360028fDHCPSnoopingStatisticsTable OBJECT-TYPE
   SYNTAX      SEQUENCE OF XGS360028FDHCPSnoopingStatisticsEntry
   MAX-ACCESS  not-accessible
   STATUS      current
   DESCRIPTION
       " "
   ::= { xgs360028fDHCPSnooping 2 }

xgs360028fDHCPSnoopingStatisticsEntry OBJECT-TYPE
   SYNTAX      XGS360028FDHCPSnoopingStatisticsEntry
   MAX-ACCESS  not-accessible
   STATUS      current
   DESCRIPTION
       ""
   INDEX    { xgs360028fDHCPSnoopingStatisticsPort  }
   ::= { xgs360028fDHCPSnoopingStatisticsTable 1 }

XGS360028FDHCPSnoopingStatisticsEntry ::= SEQUENCE {
   xgs360028fDHCPSnoopingStatisticsPort         INTEGER,
   xgs360028fDHCPSnoopingStatisticsClear        INTEGER,
   xgs360028fDHCPSnoopingRxDiscover             Counter32,
   xgs360028fDHCPSnoopingRxOffer                Counter32,
   xgs360028fDHCPSnoopingRxRequest              Counter32,
   xgs360028fDHCPSnoopingRxDecline              Counter32,
   xgs360028fDHCPSnoopingRxACK                  Counter32,
   xgs360028fDHCPSnoopingRxNAK                  Counter32,
   xgs360028fDHCPSnoopingRxRelease              Counter32,
   xgs360028fDHCPSnoopingRxInform               Counter32,
   xgs360028fDHCPSnoopingRxLeaseQuery           Counter32,
   xgs360028fDHCPSnoopingRxLeaseUnassigned      Counter32,
   xgs360028fDHCPSnoopingRxLeaseUnknown         Counter32,
   xgs360028fDHCPSnoopingRxLeaseActive          Counter32,
   xgs360028fDHCPSnoopingTxDiscover             Counter32,
   xgs360028fDHCPSnoopingTxOffer                Counter32,
   xgs360028fDHCPSnoopingTxRequest              Counter32,
   xgs360028fDHCPSnoopingTxDecline              Counter32,
   xgs360028fDHCPSnoopingTxACK                  Counter32,
   xgs360028fDHCPSnoopingTxNAK                  Counter32,
   xgs360028fDHCPSnoopingTxRelease              Counter32,
   xgs360028fDHCPSnoopingTxInform               Counter32,
   xgs360028fDHCPSnoopingTxLeaseQuery           Counter32,
   xgs360028fDHCPSnoopingTxLeaseUnassigned      Counter32,
   xgs360028fDHCPSnoopingTxLeaseUnknown         Counter32,
   xgs360028fDHCPSnoopingTxLeaseActive          Counter32
}

xgs360028fDHCPSnoopingStatisticsPort OBJECT-TYPE
   SYNTAX      INTEGER(1..4095)
   MAX-ACCESS  not-accessible
   STATUS      current
   DESCRIPTION
       " "
   ::= { xgs360028fDHCPSnoopingStatisticsEntry 1 }

xgs360028fDHCPSnoopingStatisticsClear OBJECT-TYPE
   SYNTAX      INTEGER (0|1)
   MAX-ACCESS  read-write
   STATUS      current
   DESCRIPTION
       "default: 0
       0: none
       1: clear"
   ::= { xgs360028fDHCPSnoopingStatisticsEntry 2 }
   
xgs360028fDHCPSnoopingRxDiscover OBJECT-TYPE
   SYNTAX      Counter32
   MAX-ACCESS  read-only
   STATUS      current
   DESCRIPTION
       " "
   ::= { xgs360028fDHCPSnoopingStatisticsEntry 3 }

xgs360028fDHCPSnoopingRxOffer OBJECT-TYPE
   SYNTAX      Counter32
   MAX-ACCESS  read-only
   STATUS      current
   DESCRIPTION
       " "
   ::= { xgs360028fDHCPSnoopingStatisticsEntry 4 }

xgs360028fDHCPSnoopingRxRequest OBJECT-TYPE
   SYNTAX      Counter32
   MAX-ACCESS  read-only
   STATUS      current
   DESCRIPTION
       " "
   ::= { xgs360028fDHCPSnoopingStatisticsEntry 5 }

xgs360028fDHCPSnoopingRxDecline OBJECT-TYPE
   SYNTAX      Counter32
   MAX-ACCESS  read-only
   STATUS      current
   DESCRIPTION
       " "
   ::= { xgs360028fDHCPSnoopingStatisticsEntry 6 }

xgs360028fDHCPSnoopingRxACK OBJECT-TYPE
   SYNTAX      Counter32
   MAX-ACCESS  read-only
   STATUS      current
   DESCRIPTION
       " "
   ::= { xgs360028fDHCPSnoopingStatisticsEntry 7 }

xgs360028fDHCPSnoopingRxNAK OBJECT-TYPE
   SYNTAX      Counter32
   MAX-ACCESS  read-only
   STATUS      current
   DESCRIPTION
       " "
   ::= { xgs360028fDHCPSnoopingStatisticsEntry 8 }   

xgs360028fDHCPSnoopingRxRelease OBJECT-TYPE
   SYNTAX      Counter32
   MAX-ACCESS  read-only
   STATUS      current
   DESCRIPTION
       " "
   ::= { xgs360028fDHCPSnoopingStatisticsEntry 9 }

xgs360028fDHCPSnoopingRxInform OBJECT-TYPE
   SYNTAX      Counter32
   MAX-ACCESS  read-only
   STATUS      current
   DESCRIPTION
       " "
   ::= { xgs360028fDHCPSnoopingStatisticsEntry 10 }

xgs360028fDHCPSnoopingRxLeaseQuery OBJECT-TYPE
   SYNTAX      Counter32
   MAX-ACCESS  read-only
   STATUS      current
   DESCRIPTION
       " "
   ::= { xgs360028fDHCPSnoopingStatisticsEntry 11 }

xgs360028fDHCPSnoopingRxLeaseUnassigned OBJECT-TYPE
   SYNTAX      Counter32
   MAX-ACCESS  read-only
   STATUS      current
   DESCRIPTION
       " "
   ::= { xgs360028fDHCPSnoopingStatisticsEntry 12 }

xgs360028fDHCPSnoopingRxLeaseUnknown OBJECT-TYPE
   SYNTAX      Counter32
   MAX-ACCESS  read-only
   STATUS      current
   DESCRIPTION
       " "
   ::= { xgs360028fDHCPSnoopingStatisticsEntry 13 }

xgs360028fDHCPSnoopingRxLeaseActive OBJECT-TYPE
   SYNTAX      Counter32
   MAX-ACCESS  read-only
   STATUS      current
   DESCRIPTION
       " "
   ::= { xgs360028fDHCPSnoopingStatisticsEntry 14 }

xgs360028fDHCPSnoopingTxDiscover OBJECT-TYPE
   SYNTAX      Counter32
   MAX-ACCESS  read-only
   STATUS      current
   DESCRIPTION
       " "
   ::= { xgs360028fDHCPSnoopingStatisticsEntry 15 }

xgs360028fDHCPSnoopingTxOffer OBJECT-TYPE
   SYNTAX      Counter32
   MAX-ACCESS  read-only
   STATUS      current
   DESCRIPTION
       " "
   ::= { xgs360028fDHCPSnoopingStatisticsEntry 16 }

xgs360028fDHCPSnoopingTxRequest OBJECT-TYPE
   SYNTAX      Counter32
   MAX-ACCESS  read-only
   STATUS      current
   DESCRIPTION
       " "
   ::= { xgs360028fDHCPSnoopingStatisticsEntry 17 }

xgs360028fDHCPSnoopingTxDecline OBJECT-TYPE
   SYNTAX      Counter32
   MAX-ACCESS  read-only
   STATUS      current
   DESCRIPTION
       " "
   ::= { xgs360028fDHCPSnoopingStatisticsEntry 18 }

xgs360028fDHCPSnoopingTxACK OBJECT-TYPE
   SYNTAX      Counter32
   MAX-ACCESS  read-only
   STATUS      current
   DESCRIPTION
       " "
   ::= { xgs360028fDHCPSnoopingStatisticsEntry 19 }

xgs360028fDHCPSnoopingTxNAK OBJECT-TYPE
   SYNTAX      Counter32
   MAX-ACCESS  read-only
   STATUS      current
   DESCRIPTION
       " "
   ::= { xgs360028fDHCPSnoopingStatisticsEntry 20 }   

xgs360028fDHCPSnoopingTxRelease OBJECT-TYPE
   SYNTAX      Counter32
   MAX-ACCESS  read-only
   STATUS      current
   DESCRIPTION
       " "
   ::= { xgs360028fDHCPSnoopingStatisticsEntry 21 }

xgs360028fDHCPSnoopingTxInform OBJECT-TYPE
   SYNTAX      Counter32
   MAX-ACCESS  read-only
   STATUS      current
   DESCRIPTION
       " "
   ::= { xgs360028fDHCPSnoopingStatisticsEntry 22 }

xgs360028fDHCPSnoopingTxLeaseQuery OBJECT-TYPE
   SYNTAX      Counter32
   MAX-ACCESS  read-only
   STATUS      current
   DESCRIPTION
       " "
   ::= { xgs360028fDHCPSnoopingStatisticsEntry 23 }

xgs360028fDHCPSnoopingTxLeaseUnassigned OBJECT-TYPE
   SYNTAX      Counter32
   MAX-ACCESS  read-only
   STATUS      current
   DESCRIPTION
       " "
   ::= { xgs360028fDHCPSnoopingStatisticsEntry 24 }

xgs360028fDHCPSnoopingTxLeaseUnknown OBJECT-TYPE
   SYNTAX      Counter32
   MAX-ACCESS  read-only
   STATUS      current
   DESCRIPTION
       " "
   ::= { xgs360028fDHCPSnoopingStatisticsEntry 25 }

xgs360028fDHCPSnoopingTxLeaseActive OBJECT-TYPE
   SYNTAX      Counter32
   MAX-ACCESS  read-only
   STATUS      current
   DESCRIPTION
       " "
   ::= { xgs360028fDHCPSnoopingStatisticsEntry 26 }


xgs360028fDHCPRelay                                             OBJECT IDENTIFIER ::= { xgs360028fSecurity 4 }

xgs360028fDHCPRelayConfiguration                                         OBJECT IDENTIFIER ::= { xgs360028fDHCPRelay 1 }

xgs360028fDHCPRelayMode OBJECT-TYPE
   SYNTAX      INTEGER(0|1)
   MAX-ACCESS  read-write
   STATUS      current
   DESCRIPTION
       "default: 0
       0: disable
       1: enable 
       We need at least one server"
   ::= { xgs360028fDHCPRelayConfiguration 1 }

xgs360028fDHCPRelayServer OBJECT-TYPE
   SYNTAX      IpAddress
   MAX-ACCESS  read-write
   STATUS      current
   DESCRIPTION
       " "
   ::= { xgs360028fDHCPRelayConfiguration 2 }

xgs360028fDHCPRelayInformationMode OBJECT-TYPE
   SYNTAX      INTEGER(0|1)
   MAX-ACCESS  read-write
   STATUS      current
   DESCRIPTION
       "default: 0
       0: disable
       1: enable "
   ::= { xgs360028fDHCPRelayConfiguration 3 }

xgs360028fDHCPRelayInformationPolicy OBJECT-TYPE
   SYNTAX      INTEGER(0..2)
   MAX-ACCESS  read-write
   STATUS      current
   DESCRIPTION
       "default: 0
       0: replace
       1: keep
       2: drop "
   ::= { xgs360028fDHCPRelayConfiguration 4 }

xgs360028fDHCPRelayStatistics                                   OBJECT IDENTIFIER ::= { xgs360028fDHCPRelay 2 }

xgs360028fDHCPRelayServerStatistics                                   OBJECT IDENTIFIER ::= { xgs360028fDHCPRelayStatistics 1 }

xgs360028fServerStatTransmitToServer OBJECT-TYPE
   SYNTAX      Counter32
   MAX-ACCESS  read-only
   STATUS      current
   DESCRIPTION
       " "
   ::= { xgs360028fDHCPRelayServerStatistics 1 }

xgs360028fServerStatTransmitError OBJECT-TYPE
   SYNTAX      Counter32
   MAX-ACCESS  read-only
   STATUS      current
   DESCRIPTION
       " "
   ::= { xgs360028fDHCPRelayServerStatistics 2 }

xgs360028fServerStatReceiveFromServer OBJECT-TYPE
   SYNTAX      Counter32
   MAX-ACCESS  read-only
   STATUS      current
   DESCRIPTION
       " "
   ::= { xgs360028fDHCPRelayServerStatistics 3 }

xgs360028fServerStatReceiveMissingAgentOption OBJECT-TYPE
   SYNTAX      Counter32
   MAX-ACCESS  read-only
   STATUS      current
   DESCRIPTION
       " "
   ::= { xgs360028fDHCPRelayServerStatistics 4 }

xgs360028fServerStatReceiveMissingCircuitID OBJECT-TYPE
   SYNTAX      Counter32
   MAX-ACCESS  read-only
   STATUS      current
   DESCRIPTION
       " "
   ::= { xgs360028fDHCPRelayServerStatistics 5 }

xgs360028fServerStatReceiveMissingRemoteID OBJECT-TYPE
   SYNTAX      Counter32
   MAX-ACCESS  read-only
   STATUS      current
   DESCRIPTION
       " "
   ::= { xgs360028fDHCPRelayServerStatistics 6 }

xgs360028fServerStatReceiveBadCircuitID OBJECT-TYPE
   SYNTAX      Counter32
   MAX-ACCESS  read-only
   STATUS      current
   DESCRIPTION
       " "
   ::= { xgs360028fDHCPRelayServerStatistics 7 }

xgs360028fServerStatReceiveBadRemoteID OBJECT-TYPE
   SYNTAX      Counter32
   MAX-ACCESS  read-only
   STATUS      current
   DESCRIPTION
       " "
   ::= { xgs360028fDHCPRelayServerStatistics 8 }

xgs360028fDHCPRelayClientStatistics                                   OBJECT IDENTIFIER ::= { xgs360028fDHCPRelayStatistics 2 }

xgs360028fClientStatTransmitToClient OBJECT-TYPE
   SYNTAX      Counter32
   MAX-ACCESS  read-only
   STATUS      current
   DESCRIPTION
       " "
   ::= { xgs360028fDHCPRelayClientStatistics 1 }

xgs360028fClientStatTransmitError OBJECT-TYPE
   SYNTAX      Counter32
   MAX-ACCESS  read-only
   STATUS      current
   DESCRIPTION
       " "
   ::= { xgs360028fDHCPRelayClientStatistics 2 }

xgs360028fClientStatReceivefromClient OBJECT-TYPE
   SYNTAX      Counter32
   MAX-ACCESS  read-only
   STATUS      current
   DESCRIPTION
       " "
   ::= { xgs360028fDHCPRelayClientStatistics 3 }

xgs360028fClientStatReceiveAgentOption OBJECT-TYPE
   SYNTAX      Counter32
   MAX-ACCESS  read-only
   STATUS      current
   DESCRIPTION
       " "
   ::= { xgs360028fDHCPRelayClientStatistics 4 }

xgs360028fClientStatReplaceAgentOption OBJECT-TYPE
   SYNTAX      Counter32
   MAX-ACCESS  read-only
   STATUS      current
   DESCRIPTION
       " "
   ::= { xgs360028fDHCPRelayClientStatistics 5 }

xgs360028fClientStatKeepAgentOption OBJECT-TYPE
   SYNTAX      Counter32
   MAX-ACCESS  read-only
   STATUS      current
   DESCRIPTION
       " "
   ::= { xgs360028fDHCPRelayClientStatistics 6 }

xgs360028fClientStatDropAgentOption OBJECT-TYPE
   SYNTAX      Counter32
   MAX-ACCESS  read-only
   STATUS      current
   DESCRIPTION
       " "
   ::= { xgs360028fDHCPRelayClientStatistics 7 }

xgs360028fPortSecurity                                          OBJECT IDENTIFIER ::= { xgs360028fSecurity 5 }

xgs360028fPortSecLimitCtrl                                      OBJECT IDENTIFIER ::= { xgs360028fPortSecurity 1 }

xgs360028fPortSecLimitCtrlSystemConf                                      OBJECT IDENTIFIER ::= { xgs360028fPortSecLimitCtrl 1 }

xgs360028fPortSecurityMode OBJECT-TYPE
   SYNTAX      INTEGER(0|1)
   MAX-ACCESS  read-write
   STATUS      current
   DESCRIPTION
       "default: 0
       0: disable
       1: enable "
   ::= { xgs360028fPortSecLimitCtrlSystemConf 1 }

xgs360028fPortSecurityAging OBJECT-TYPE
   SYNTAX      INTEGER(0|1)
   MAX-ACCESS  read-write
   STATUS      current
   DESCRIPTION
       "default: 0
       0: disable
       1: enable "
   ::= { xgs360028fPortSecLimitCtrlSystemConf 2 }

xgs360028fPortSecurityAgingPeriod OBJECT-TYPE
   SYNTAX      INTEGER(10..10000000)
   MAX-ACCESS  read-write
   STATUS      current
   DESCRIPTION
       "default: 3600, range: 10-10000000 "
   ::= { xgs360028fPortSecLimitCtrlSystemConf 3 }

xgs360028fPortSecLimitCtrlTable OBJECT-TYPE
   SYNTAX      SEQUENCE OF XGS360028FPortSecLimitCtrlEntry
   MAX-ACCESS  not-accessible
   STATUS      current
   DESCRIPTION
       " "
   ::= { xgs360028fPortSecLimitCtrl 2 }

xgs360028fPortSecLimitCtrlEntry OBJECT-TYPE
   SYNTAX      XGS360028FPortSecLimitCtrlEntry
   MAX-ACCESS  not-accessible
   STATUS      current
   DESCRIPTION
       ""
   INDEX    { xgs360028fPortSecLimitCtrlPort  }
   ::= { xgs360028fPortSecLimitCtrlTable 1 }

XGS360028FPortSecLimitCtrlEntry ::= SEQUENCE {
   xgs360028fPortSecLimitCtrlPort        INTEGER,
   xgs360028fPortSecLimitCtrlPortMode	INTEGER,
   xgs360028fPortSecLimitCtrlPortLimit	INTEGER,
   xgs360028fPortSecLimitCtrlPortAction	INTEGER,
   xgs360028fPortSecLimitCtrlPortState	DisplayString,
   xgs360028fPortSecLimitCtrlPortReOpen	INTEGER
}

xgs360028fPortSecLimitCtrlPort OBJECT-TYPE
   SYNTAX      INTEGER (1..4095)
   MAX-ACCESS  not-accessible
   STATUS      current
   DESCRIPTION
       " "
   ::= { xgs360028fPortSecLimitCtrlEntry 1 }

xgs360028fPortSecLimitCtrlPortMode OBJECT-TYPE
   SYNTAX      INTEGER (0|1)
   MAX-ACCESS  read-write
   STATUS      current
   DESCRIPTION
       "default: 0
       0: disable
       1: enable"
   ::= { xgs360028fPortSecLimitCtrlEntry 2 }

xgs360028fPortSecLimitCtrlPortLimit OBJECT-TYPE
   SYNTAX      INTEGER(1..1024)
   MAX-ACCESS  read-write
   STATUS      current
   DESCRIPTION
       "default: 4, range: 1-1024"
   ::= { xgs360028fPortSecLimitCtrlEntry 3 }

xgs360028fPortSecLimitCtrlPortAction OBJECT-TYPE
   SYNTAX      INTEGER(0..3)
   MAX-ACCESS  read-write
   STATUS      current
   DESCRIPTION
       "default: 0
       0: none
       1: trap
       2: shutdown
       3: trap&shutdown"
   ::= { xgs360028fPortSecLimitCtrlEntry 4 }

xgs360028fPortSecLimitCtrlPortState OBJECT-TYPE
   SYNTAX      DisplayString
   MAX-ACCESS  read-only
   STATUS      current
   DESCRIPTION
       ""
   ::= { xgs360028fPortSecLimitCtrlEntry 5 }

xgs360028fPortSecLimitCtrlPortReOpen OBJECT-TYPE
   SYNTAX      INTEGER (0|1)
   MAX-ACCESS  read-write
   STATUS      current
   DESCRIPTION
       "default: 0
       0: none
       1: reopen"
   ::= { xgs360028fPortSecLimitCtrlEntry 6 }

xgs360028fPortSecSwitchStatusTable OBJECT-TYPE
   SYNTAX      SEQUENCE OF XGS360028FPortSecSwitchStatusEntry
   MAX-ACCESS  not-accessible
   STATUS      current
   DESCRIPTION
       " "
   ::= { xgs360028fPortSecurity 2 }

xgs360028fPortSecSwitchStatusEntry OBJECT-TYPE
   SYNTAX      XGS360028FPortSecSwitchStatusEntry
   MAX-ACCESS  not-accessible
   STATUS      current
   DESCRIPTION
       ""
   INDEX    { xgs360028fPortSecSwitchStatusPort  }
   ::= { xgs360028fPortSecSwitchStatusTable 1 }

XGS360028FPortSecSwitchStatusEntry ::= SEQUENCE {
   xgs360028fPortSecSwitchStatusPort		            INTEGER,
   xgs360028fPortSecSwitchStatusUsers        		DisplayString,
   xgs360028fPortSecSwitchStatusState		        DisplayString,
   xgs360028fPortSecSwitchStatusMACCountCurrent		INTEGER,
   xgs360028fPortSecSwitchStatusMACCountLimit		INTEGER
}

xgs360028fPortSecSwitchStatusPort OBJECT-TYPE
   SYNTAX      INTEGER (1..4095)
   MAX-ACCESS  not-accessible
   STATUS      current
   DESCRIPTION
       " "
   ::= { xgs360028fPortSecSwitchStatusEntry 1 }

xgs360028fPortSecSwitchStatusUsers OBJECT-TYPE
   SYNTAX      DisplayString
   MAX-ACCESS  read-only
   STATUS      current
   DESCRIPTION
       " Users Abbr: L = Limit Control, 8 = 802.1X, D = DHCP Snooping, V = Voice VLAN, 
         '-' means that the corresponding user module is not enabled. "
   ::= { xgs360028fPortSecSwitchStatusEntry 2 }

xgs360028fPortSecSwitchStatusState OBJECT-TYPE
   SYNTAX      DisplayString
   MAX-ACCESS  read-only
   STATUS      current
   DESCRIPTION
       " Shows the current state of the port : Disabled, Ready, Limit Reached, Shutdown. "
   ::= { xgs360028fPortSecSwitchStatusEntry 3 }

xgs360028fPortSecSwitchStatusMACCountCurrent OBJECT-TYPE
   SYNTAX      INTEGER (1..4095)
   MAX-ACCESS  read-only
   STATUS      current
   DESCRIPTION
       ""
   ::= { xgs360028fPortSecSwitchStatusEntry 4 }

xgs360028fPortSecSwitchStatusMACCountLimit OBJECT-TYPE
   SYNTAX      INTEGER(1..4095)
   MAX-ACCESS  read-only
   STATUS      current
   DESCRIPTION
       ""
   ::= { xgs360028fPortSecSwitchStatusEntry 5 }

xgs360028fPortSecPortStatus                                      OBJECT IDENTIFIER ::= { xgs360028fPortSecurity 3 }

xgs360028fPortSecPortStatusPort OBJECT-TYPE
   SYNTAX       INTEGER (1..4095)
   MAX-ACCESS   read-write
   STATUS       current
   DESCRIPTION
       "default: 0
        0 : None"
   ::= { xgs360028fPortSecPortStatus 1 }

xgs360028fPortSecPortStatusTable OBJECT-TYPE
   SYNTAX      SEQUENCE OF XGS360028FPortSecPortStatusEntry
   MAX-ACCESS  not-accessible
   STATUS      current
   DESCRIPTION
      " "
   ::= { xgs360028fPortSecPortStatus 2 }
       
xgs360028fPortSecPortStatusEntry OBJECT-TYPE
   SYNTAX      XGS360028FPortSecPortStatusEntry
   MAX-ACCESS  not-accessible
   STATUS      current
   DESCRIPTION
       ""
   INDEX    { xgs360028fPortSecPortStatusIndex  }
   ::= { xgs360028fPortSecPortStatusTable 1 }       

XGS360028FPortSecPortStatusEntry ::= SEQUENCE {
   xgs360028fPortSecPortStatusIndex              INTEGER,
   xgs360028fPortSecPortStatusMACAddress         MacAddress,
   xgs360028fPortSecPortStatusVLANId             INTEGER,
   xgs360028fPortSecPortStatusState              DisplayString,
   xgs360028fPortSecPortStatusTimeOfAddition     DisplayString,
   xgs360028fPortSecPortStatusAgeAndHold         DisplayString
}

xgs360028fPortSecPortStatusIndex OBJECT-TYPE
   SYNTAX      INTEGER(1..4095)
   MAX-ACCESS  not-accessible
   STATUS      current
   DESCRIPTION
       " "
   ::= { xgs360028fPortSecPortStatusEntry 1 }

xgs360028fPortSecPortStatusMACAddress OBJECT-TYPE
   SYNTAX      MacAddress
   MAX-ACCESS  read-only
   STATUS      current
   DESCRIPTION
       " "
   ::= { xgs360028fPortSecPortStatusEntry 2 }

xgs360028fPortSecPortStatusVLANId OBJECT-TYPE
   SYNTAX      INTEGER(1..4094)
   MAX-ACCESS  read-only
   STATUS      current
   DESCRIPTION
       " "
   ::= { xgs360028fPortSecPortStatusEntry 3 }

xgs360028fPortSecPortStatusState OBJECT-TYPE
   SYNTAX      DisplayString
   MAX-ACCESS  read-only
   STATUS      current
   DESCRIPTION
       "Blocked / Forwarding "
   ::= { xgs360028fPortSecPortStatusEntry 4 }

xgs360028fPortSecPortStatusTimeOfAddition OBJECT-TYPE
   SYNTAX      DisplayString
   MAX-ACCESS  read-only
   STATUS      current
   DESCRIPTION
       " "
   ::= { xgs360028fPortSecPortStatusEntry 5 }

xgs360028fPortSecPortStatusAgeAndHold OBJECT-TYPE
   SYNTAX      DisplayString
   MAX-ACCESS  read-only
   STATUS      current
   DESCRIPTION
       " "
   ::= { xgs360028fPortSecPortStatusEntry 6 }       


xgs360028fAccessManagement                                      OBJECT IDENTIFIER ::= { xgs360028fSecurity 6 }

xgs360028fAccessMgtConf                                         OBJECT IDENTIFIER ::= { xgs360028fAccessManagement 1 }

xgs360028fAccessMgtConfMode OBJECT-TYPE
   SYNTAX      INTEGER(0|1)
   MAX-ACCESS  read-write
   STATUS      current
   DESCRIPTION
       "default: 0
       0: disable
       1: enable "
   ::= { xgs360028fAccessMgtConf 1 }

xgs360028fAccessMgtConfCreate OBJECT-TYPE
   SYNTAX      INTEGER(0|1)
   MAX-ACCESS  read-write
   STATUS      current
   DESCRIPTION
       "default: 0
       0: none
       1: create "
   ::= { xgs360028fAccessMgtConf 2 }

xgs360028fAccessMgtConfTable OBJECT-TYPE
   SYNTAX      SEQUENCE OF XGS360028FAccessMgtConfEntry
   MAX-ACCESS  not-accessible
   STATUS      current
   DESCRIPTION
       " "
   ::= { xgs360028fAccessMgtConf 3 }

xgs360028fAccessMgtConfEntry OBJECT-TYPE
   SYNTAX      XGS360028FAccessMgtConfEntry
   MAX-ACCESS  not-accessible
   STATUS      current
   DESCRIPTION
       ""
   INDEX    { xgs360028fAccessMgtIndex  }
   ::= { xgs360028fAccessMgtConfTable 1 }
   
XGS360028FAccessMgtConfEntry ::= SEQUENCE {
   xgs360028fAccessMgtIndex             INTEGER,
   xgs360028fAccessMgtAddresstype       INTEGER,
   xgs360028fAccessMgtStartIpAddress    DisplayString,
   xgs360028fAccessMgtEndIpAddress      DisplayString,
   xgs360028fAccessMgtHttpHttps         INTEGER,
   xgs360028fAccessMgtSNMP              INTEGER,
   xgs360028fAccessMgtTelnetSSH         INTEGER,
   xgs360028fAccessMgtRowStatus         INTEGER
}

xgs360028fAccessMgtIndex OBJECT-TYPE
   SYNTAX      INTEGER(1..16)
   MAX-ACCESS  read-write
   STATUS      current
   DESCRIPTION
       "Set Access Management config index
        range : 1-16."
   ::= { xgs360028fAccessMgtConfEntry 1 }

xgs360028fAccessMgtAddresstype OBJECT-TYPE
   SYNTAX      INTEGER(0|1)
   MAX-ACCESS  read-write
   STATUS      current
   DESCRIPTION
       "0: ipv4
       1: ipv6 "
   ::= { xgs360028fAccessMgtConfEntry 2 }
   
xgs360028fAccessMgtStartIpAddress OBJECT-TYPE
   SYNTAX      DisplayString
   MAX-ACCESS  read-write
   STATUS      current
   DESCRIPTION
       " Start IP address. 
         IP address doesn't allowed all zero or all 'ff'H."
   ::= { xgs360028fAccessMgtConfEntry 3 }
   
xgs360028fAccessMgtEndIpAddress OBJECT-TYPE
   SYNTAX      DisplayString
   MAX-ACCESS  read-write
   STATUS      current
   DESCRIPTION
       " End IP address. 
         IP address doesn't allowed all zero or all 'ff'H.
         End ip address is not less than start ip address."
   ::= { xgs360028fAccessMgtConfEntry 4 }

xgs360028fAccessMgtHttpHttps OBJECT-TYPE
   SYNTAX      INTEGER(0|1)
   MAX-ACCESS  read-write
   STATUS      current
   DESCRIPTION
       "default: 0
       0: disable
       1: enable "
   ::= { xgs360028fAccessMgtConfEntry 5 }

xgs360028fAccessMgtSNMP OBJECT-TYPE
   SYNTAX      INTEGER(0|1)
   MAX-ACCESS  read-write
   STATUS      current
   DESCRIPTION
       "default: 0
       0: disable
       1: enable "
   ::= { xgs360028fAccessMgtConfEntry 6 }

xgs360028fAccessMgtTelnetSSH OBJECT-TYPE
   SYNTAX      INTEGER(0|1)
   MAX-ACCESS  read-write
   STATUS      current
   DESCRIPTION
       "default: 0
       0: disable
       1: enable "
   ::= { xgs360028fAccessMgtConfEntry 7 }

xgs360028fAccessMgtRowStatus OBJECT-TYPE
   SYNTAX      INTEGER(1..5)
   MAX-ACCESS  read-write
   STATUS      current
   DESCRIPTION
       "1: active
        2: notInservice
        3: edit
        4: destroy
        5: undo"
   ::= { xgs360028fAccessMgtConfEntry 8 }

xgs360028fAccessMgtStatistics                                   OBJECT IDENTIFIER ::= { xgs360028fAccessManagement 2 }

xgs360028fHttpReceivedPkts OBJECT-TYPE
   SYNTAX      Counter32
   MAX-ACCESS  read-only
   STATUS      current
   DESCRIPTION
       " "
   ::= { xgs360028fAccessMgtStatistics 1 }

xgs360028fHttpAllowedPkts OBJECT-TYPE
   SYNTAX      Counter32
   MAX-ACCESS  read-only
   STATUS      current
   DESCRIPTION
       " "
   ::= { xgs360028fAccessMgtStatistics 2 }

xgs360028fHttpDiscardedPkts OBJECT-TYPE
   SYNTAX      Counter32
   MAX-ACCESS  read-only
   STATUS      current
   DESCRIPTION
       " "
   ::= { xgs360028fAccessMgtStatistics 3 }

xgs360028fHttpsReceivedPkts OBJECT-TYPE
   SYNTAX      Counter32
   MAX-ACCESS  read-only
   STATUS      current
   DESCRIPTION
       " "
   ::= { xgs360028fAccessMgtStatistics 4 }

xgs360028fHttpsAllowedPkts OBJECT-TYPE
   SYNTAX      Counter32
   MAX-ACCESS  read-only
   STATUS      current
   DESCRIPTION
       " "
   ::= { xgs360028fAccessMgtStatistics 5 }

xgs360028fHttpsDiscardedPkts OBJECT-TYPE
   SYNTAX      Counter32
   MAX-ACCESS  read-only
   STATUS      current
   DESCRIPTION
       " "
   ::= { xgs360028fAccessMgtStatistics 6 }

xgs360028fSnmpReceivedPkts OBJECT-TYPE
   SYNTAX      Counter32
   MAX-ACCESS  read-only
   STATUS      current
   DESCRIPTION
       " "
   ::= { xgs360028fAccessMgtStatistics 7 }

xgs360028fSnmpAllowedPkts OBJECT-TYPE
   SYNTAX      Counter32
   MAX-ACCESS  read-only
   STATUS      current
   DESCRIPTION
       " "
   ::= { xgs360028fAccessMgtStatistics 8 }

xgs360028fSnmpDiscardedPkts OBJECT-TYPE
   SYNTAX      Counter32
   MAX-ACCESS  read-only
   STATUS      current
   DESCRIPTION
       " "
   ::= { xgs360028fAccessMgtStatistics 9 }

xgs360028fTelnetReceivedPkts OBJECT-TYPE
   SYNTAX      Counter32
   MAX-ACCESS  read-only
   STATUS      current
   DESCRIPTION
       " "
   ::= { xgs360028fAccessMgtStatistics 10 }

xgs360028fTelnetAllowedPkts OBJECT-TYPE
   SYNTAX      Counter32
   MAX-ACCESS  read-only
   STATUS      current
   DESCRIPTION
       " "
   ::= { xgs360028fAccessMgtStatistics 11 }

xgs360028fTelnetDiscardedPkts OBJECT-TYPE
   SYNTAX      Counter32
   MAX-ACCESS  read-only
   STATUS      current
   DESCRIPTION
       " "
   ::= { xgs360028fAccessMgtStatistics 12 }

xgs360028fSSHReceivedPkts OBJECT-TYPE
   SYNTAX      Counter32
   MAX-ACCESS  read-only
   STATUS      current
   DESCRIPTION
       " "
   ::= { xgs360028fAccessMgtStatistics 13 }

xgs360028fSSHAllowedPkts OBJECT-TYPE
   SYNTAX      Counter32
   MAX-ACCESS  read-only
   STATUS      current
   DESCRIPTION
       " "
   ::= { xgs360028fAccessMgtStatistics 14 }

xgs360028fSSHDiscardedPkts OBJECT-TYPE
   SYNTAX      Counter32
   MAX-ACCESS  read-only
   STATUS      current
   DESCRIPTION
       " "
   ::= { xgs360028fAccessMgtStatistics 15 }

xgs360028fAccessMgtStatisticsClearAll OBJECT-TYPE
   SYNTAX      INTEGER(0|1)
   MAX-ACCESS  read-write
   STATUS      current
   DESCRIPTION
       "0: none
        1: clear"
   ::= { xgs360028fAccessMgtStatistics 16 }

xgs360028fSSH                                                   OBJECT IDENTIFIER ::= { xgs360028fSecurity 7 }

xgs360028fSSHMode OBJECT-TYPE
   SYNTAX      INTEGER(0|1)
   MAX-ACCESS  read-write
   STATUS      current
   DESCRIPTION
       "default: 1
        0: disable
        1: enable"
   ::= { xgs360028fSSH 1 }

xgs360028fHTTPS                                                 OBJECT IDENTIFIER ::= { xgs360028fSecurity 8 }

xgs360028fHTTPSMode OBJECT-TYPE
   SYNTAX      INTEGER(0|1)
   MAX-ACCESS  read-write
   STATUS      current
   DESCRIPTION
       "default: 1
        0: disable
        1: enable"
   ::= { xgs360028fHTTPS 1 }

xgs360028fHTTPSAutoRedirect OBJECT-TYPE
   SYNTAX      INTEGER(0|1)
   MAX-ACCESS  read-write
   STATUS      current
   DESCRIPTION
       "default: 0
        0: disable
        1: enable"
   ::= { xgs360028fHTTPS 2 }

xgs360028fAuthMethod                                            OBJECT IDENTIFIER ::= { xgs360028fSecurity 9 }

xgs360028fConsoleAuthMethod OBJECT-TYPE
   SYNTAX      INTEGER(0..3)
   MAX-ACCESS  read-write
   STATUS      current
   DESCRIPTION
       "default: 1
        0: none
        1: local
        2: RADIUS
        3: TACACS+"
   ::= { xgs360028fAuthMethod 1 }

xgs360028fConsoleFallback OBJECT-TYPE
   SYNTAX      INTEGER(0|1)
   MAX-ACCESS  read-write
   STATUS      current
   DESCRIPTION
       "default: 0
        0:disable
        1:enable"
   ::= { xgs360028fAuthMethod 2 }

xgs360028fTelnetAuthMethod OBJECT-TYPE
   SYNTAX      INTEGER(0..3)
   MAX-ACCESS  read-write
   STATUS      current
   DESCRIPTION
       "default: 1
        0: none
        1: local
        2: RADIUS
        3: TACACS+"
   ::= { xgs360028fAuthMethod 3 }

xgs360028fTelnetFallback OBJECT-TYPE
   SYNTAX      INTEGER(0|1)
   MAX-ACCESS  read-write
   STATUS      current
   DESCRIPTION
       "default: 0
        0:disable
        1:enable"
   ::= { xgs360028fAuthMethod 4 }

xgs360028fSshAuthMethod OBJECT-TYPE
   SYNTAX      INTEGER(0..3)
   MAX-ACCESS  read-write
   STATUS      current
   DESCRIPTION
       "default: 1
        0: none
        1: local
        2: RADIUS
        3: TACACS+"
   ::= { xgs360028fAuthMethod 5 }

xgs360028fSshFallback OBJECT-TYPE
   SYNTAX      INTEGER(0|1)
   MAX-ACCESS  read-write
   STATUS      current
   DESCRIPTION
       "default: 0
        0:disable
        1:enable"
   ::= { xgs360028fAuthMethod 6 }

xgs360028fWebAuthMethod OBJECT-TYPE
   SYNTAX      INTEGER(0..3)
   MAX-ACCESS  read-write
   STATUS      current
   DESCRIPTION
       "default: 1
        0: none
        1: local
        2: RADIUS
        3: TACACS+"
   ::= { xgs360028fAuthMethod 7 }

xgs360028fWebFallback OBJECT-TYPE
   SYNTAX      INTEGER(0|1)
   MAX-ACCESS  read-write
   STATUS      current
   DESCRIPTION
       "default: 0
        0:disable
        1:enable"
   ::= { xgs360028fAuthMethod 8 }

xgs360028fMaintenance                                           OBJECT IDENTIFIER ::= { xgs360028fProductId 4 }

xgs360028fRestartDevice OBJECT-TYPE
   SYNTAX      INTEGER(0|1)
   MAX-ACCESS  read-write
   STATUS      current
   DESCRIPTION
       "default: 0
        0:none
        1:yes"
   ::= { xgs360028fMaintenance 1 }

xgs360028fFirmware                                         OBJECT IDENTIFIER ::= { xgs360028fMaintenance 2 }

xgs360028fFirmwareIpAddress OBJECT-TYPE
   SYNTAX       IpAddress
   MAX-ACCESS   read-write
   STATUS       current
   DESCRIPTION
        "Get/Set the firmware tftp server."
   ::= { xgs360028fFirmware 1 }

xgs360028fFirmwareFileName OBJECT-TYPE
   SYNTAX       DisplayString
   MAX-ACCESS   read-write
   STATUS       current
   DESCRIPTION
        "Get/Set the path and filename for firmware upgrading."
   ::= { xgs360028fFirmware 2 }

xgs360028fDoFirmwareUpgrade OBJECT-TYPE
   SYNTAX       INTEGER(0|1)
   MAX-ACCESS   read-write
   STATUS       current
   DESCRIPTION
        "Do firmware upgrade. Get this OID always return zero.
              1 - do firmware upgrade.
              0 - do nothing."
   ::= { xgs360028fFirmware 3 }

xgs360028fSaveOrRestore                                         OBJECT IDENTIFIER ::= { xgs360028fMaintenance 3 }

xgs360028fFactoryDefaults OBJECT-TYPE
   SYNTAX      INTEGER(0|1)
   MAX-ACCESS  read-write
   STATUS      current
   DESCRIPTION
       "default: 0
        0:none
        1:yes"
   ::= { xgs360028fSaveOrRestore 1 }

xgs360028fSaveStart OBJECT-TYPE
   SYNTAX      INTEGER(0|1)
   MAX-ACCESS  read-write
   STATUS      current
   DESCRIPTION
       "default: 0
        0:none
        1:yes"
   ::= { xgs360028fSaveOrRestore 2 }

xgs360028fSaveUser OBJECT-TYPE
   SYNTAX      INTEGER(0|1)
   MAX-ACCESS  read-write
   STATUS      current
   DESCRIPTION
       "default: 0
        0:none
        1:yes"
   ::= { xgs360028fSaveOrRestore 3 }

xgs360028fRestoreUser OBJECT-TYPE
   SYNTAX      INTEGER(0|1)
   MAX-ACCESS  read-write
   STATUS      current
   DESCRIPTION
       "default: 0
        0:none
        1:yes"
   ::= { xgs360028fSaveOrRestore 4 }


xgs360028fExportOrImport                                        OBJECT IDENTIFIER ::= { xgs360028fMaintenance 4 }

xgs360028fExportIpAddress OBJECT-TYPE
   SYNTAX       IpAddress
   MAX-ACCESS   read-write
   STATUS       current
   DESCRIPTION
        "Get/Set the export tftp server."
   ::= { xgs360028fExportOrImport 1 }

xgs360028fExportConfigName OBJECT-TYPE
   SYNTAX       DisplayString
   MAX-ACCESS   read-write
   STATUS       current
   DESCRIPTION
       "Get/Set the export file path and name."
   ::= { xgs360028fExportOrImport 2 }

xgs360028fDoExportConfig OBJECT-TYPE
   SYNTAX       INTEGER(1)
   MAX-ACCESS   read-write
   STATUS       current
   DESCRIPTION
        "Do export-config.
         Get this OID always return zero.
         1 - export."
   ::= { xgs360028fExportOrImport 3 }

xgs360028fImportIpAddress OBJECT-TYPE
   SYNTAX       IpAddress
   MAX-ACCESS   read-write
   STATUS       current
   DESCRIPTION
        "Get/Set the import tftp server."
   ::= { xgs360028fExportOrImport 4 }

xgs360028fImportConfigName OBJECT-TYPE
   SYNTAX      DisplayString
   MAX-ACCESS  read-write
   STATUS      current
   DESCRIPTION
       "Get/Set the import file path and name."
   ::= { xgs360028fExportOrImport 5 }

xgs360028fDoImportConfig OBJECT-TYPE
   SYNTAX       INTEGER(1)
   MAX-ACCESS   read-write
   STATUS       current
   DESCRIPTION
        "Do export-config.
         Get this OID always return zero.
         1 - import."
   ::= { xgs360028fExportOrImport 6 }

xgs360028fDiagnostics                                           OBJECT IDENTIFIER ::= { xgs360028fMaintenance 5 }

xgs360028fPingIpAddress OBJECT-TYPE
   SYNTAX      IpAddress
   MAX-ACCESS  read-write
   STATUS      current
   DESCRIPTION
       " The destination IP Address. "
   ::= { xgs360028fDiagnostics 1 }
   
xgs360028fPingSize OBJECT-TYPE
   SYNTAX      INTEGER(60..1400)
   MAX-ACCESS  read-write
   STATUS      current
   DESCRIPTION
       " Size of ICMP echo packet.
         range : 60-1400, default : 64. "
   ::= { xgs360028fDiagnostics 2 }   

xgs360028fDoPingConfig OBJECT-TYPE
   SYNTAX      INTEGER(1)
   MAX-ACCESS  read-write
   STATUS      current
   DESCRIPTION
       "Do ping-config.
         Get this OID always return zero.
         1 - ping. Uses the ICMP protocol's mandatory ECHO_REQUEST datagram
         to elicit an ICMP ECHO_RESPONSE from a host or gateway. "
   ::= { xgs360028fDiagnostics 3 }

xgs360028fPingResult OBJECT-TYPE
   SYNTAX      DisplayString
   MAX-ACCESS  read-only
   STATUS      current
   DESCRIPTION
       " Show ping result. "
   ::= { xgs360028fDiagnostics 4 }

xgs360028fPing6IpAddress OBJECT-TYPE
   SYNTAX      DisplayString
   MAX-ACCESS  read-write
   STATUS      current
   DESCRIPTION
       " The destination IPv6 Address. "
   ::= { xgs360028fDiagnostics 5 }
   
xgs360028fPing6Size OBJECT-TYPE
   SYNTAX      INTEGER(60..1400)
   MAX-ACCESS  read-write
   STATUS      current
   DESCRIPTION
       " Size of ICMP echo packet.
         range : 60-1400. "
   ::= { xgs360028fDiagnostics 6 }   

xgs360028fDoPing6Config OBJECT-TYPE
   SYNTAX      INTEGER(1)
   MAX-ACCESS  read-write
   STATUS      current
   DESCRIPTION
       "Do ping-config.
         Get this OID always return zero.
         1 - ping. Uses the ICMP protocol's mandatory ECHO_REQUEST datagram
         to elicit an ICMP ECHO_RESPONSE from a host or gateway. "
   ::= { xgs360028fDiagnostics 7 }

xgs360028fPing6Result OBJECT-TYPE
   SYNTAX      DisplayString
   MAX-ACCESS  read-only
   STATUS      current
   DESCRIPTION
       " Show ping result. "
   ::= { xgs360028fDiagnostics 8 }


xgs360028fVeriPHY                                           OBJECT IDENTIFIER ::= { xgs360028fDiagnostics 9 }

xgs360028fVeriPHYTest OBJECT-TYPE
   SYNTAX      INTEGER (1..4095)
   MAX-ACCESS  read-write
   STATUS      current
   DESCRIPTION
       "Run VeriPHY Cable Diagnostics.
        port, range : 0 - port number.
        0 : ALL "
   ::= { xgs360028fVeriPHY 1 }

xgs360028fVeriPHYTable OBJECT-TYPE
   SYNTAX      SEQUENCE OF XGS360028FVeriPHYEntry
   MAX-ACCESS  not-accessible
   STATUS      current
   DESCRIPTION
       " "
   ::= { xgs360028fVeriPHY 2 }

xgs360028fVeriPHYEntry OBJECT-TYPE
   SYNTAX      XGS360028FVeriPHYEntry
   MAX-ACCESS  not-accessible
   STATUS      current
   DESCRIPTION
       ""
   INDEX    { xgs360028fVeriPHYPort  }
   ::= { xgs360028fVeriPHYTable 1 }

XGS360028FVeriPHYEntry ::= SEQUENCE {
   xgs360028fVeriPHYPort		    INTEGER,
   xgs360028fVeriPHYPairA		DisplayString,
   xgs360028fVeriPHYLengthA		DisplayString,
   xgs360028fVeriPHYPairB		DisplayString,
   xgs360028fVeriPHYLengthB		DisplayString,
   xgs360028fVeriPHYPairC		DisplayString,
   xgs360028fVeriPHYLengthC		DisplayString,
   xgs360028fVeriPHYPairD		DisplayString,
   xgs360028fVeriPHYLengthD		DisplayString
}

xgs360028fVeriPHYPort OBJECT-TYPE
   SYNTAX      INTEGER (1..4095)
   MAX-ACCESS  not-accessible
   STATUS      current
   DESCRIPTION
       " The length (in meters) of the cable pair. "
   ::= { xgs360028fVeriPHYEntry 1 }

xgs360028fVeriPHYPairA OBJECT-TYPE
   SYNTAX      DisplayString
   MAX-ACCESS  read-only
   STATUS      current
   DESCRIPTION
       " The status of the cable pair. "
   ::= { xgs360028fVeriPHYEntry 2 }

xgs360028fVeriPHYLengthA OBJECT-TYPE
   SYNTAX      DisplayString
   MAX-ACCESS  read-only
   STATUS      current
   DESCRIPTION
       " The length (in meters) of the cable pair. "
   ::= { xgs360028fVeriPHYEntry 3 }

xgs360028fVeriPHYPairB OBJECT-TYPE
   SYNTAX      DisplayString
   MAX-ACCESS  read-only
   STATUS      current
   DESCRIPTION
       " The status of the cable pair. "
   ::= { xgs360028fVeriPHYEntry 4 }

xgs360028fVeriPHYLengthB OBJECT-TYPE
   SYNTAX      DisplayString
   MAX-ACCESS  read-only
   STATUS      current
   DESCRIPTION
       " The length (in meters) of the cable pair. "
   ::= { xgs360028fVeriPHYEntry 5 }

xgs360028fVeriPHYPairC OBJECT-TYPE
   SYNTAX      DisplayString
   MAX-ACCESS  read-only
   STATUS      current
   DESCRIPTION
       " The status of the cable pair. "
   ::= { xgs360028fVeriPHYEntry 6 }

xgs360028fVeriPHYLengthC OBJECT-TYPE
   SYNTAX      DisplayString
   MAX-ACCESS  read-only
   STATUS      current
   DESCRIPTION
       " The length (in meters) of the cable pair. "
   ::= { xgs360028fVeriPHYEntry 7 }

xgs360028fVeriPHYPairD OBJECT-TYPE
   SYNTAX      DisplayString
   MAX-ACCESS  read-only
   STATUS      current
   DESCRIPTION
       " The status of the cable pair. "
   ::= { xgs360028fVeriPHYEntry 8 }

xgs360028fVeriPHYLengthD OBJECT-TYPE
   SYNTAX      DisplayString
   MAX-ACCESS  read-only
   STATUS      current
   DESCRIPTION
       " The length (in meters) of the cable pair. "
   ::= { xgs360028fVeriPHYEntry 9 }


------------------------------------------------------------------------------------------------------------------
xgs360028fTrap                                                  OBJECT IDENTIFIER ::= { xgs360028fProductId 5 }

xgs360028fTrapEvent                                             OBJECT IDENTIFIER ::= { xgs360028fTrap 1 }

xgs360028fEmergency NOTIFICATION-TYPE
  OBJECTS   { xgs360028fInformation }
  STATUS        current
    DESCRIPTION
        "The severity level is Emergency. The system is unusable."
    ::= { xgs360028fTrapEvent 1 }

xgs360028fAlert NOTIFICATION-TYPE
  OBJECTS   { xgs360028fInformation }
  STATUS        current
    DESCRIPTION
        "The severity level is Alert. The action must be taken immediately."
    ::= { xgs360028fTrapEvent 2 }

xgs360028fCritical NOTIFICATION-TYPE
  OBJECTS   { xgs360028fInformation }
  STATUS        current
    DESCRIPTION
        "The severity level is Critical. Critical conditions."
    ::= { xgs360028fTrapEvent 3 }

xgs360028fError NOTIFICATION-TYPE
  OBJECTS   { xgs360028fInformation }
  STATUS        current
    DESCRIPTION
        "The severity level is Error. Error conditions."
    ::= { xgs360028fTrapEvent 4 }

xgs360028fWarning NOTIFICATION-TYPE
  OBJECTS   { xgs360028fInformation }
  STATUS        current
    DESCRIPTION
        "The severity level is Warning. Warning conditions."
    ::= { xgs360028fTrapEvent 5 }

xgs360028fNotice NOTIFICATION-TYPE
  OBJECTS   { xgs360028fInformation }
  STATUS        current
    DESCRIPTION
        "The severity level is Notice. Normal but significant condition."
    ::= { xgs360028fTrapEvent 6 }

xgs360028fInformational NOTIFICATION-TYPE
  OBJECTS   { xgs360028fInformation }
  STATUS        current
    DESCRIPTION
        "The severity level is Informational. Informational messages."
    ::= { xgs360028fTrapEvent 7 }

xgs360028fDebug NOTIFICATION-TYPE
  OBJECTS   { xgs360028fInformation }
  STATUS        current
    DESCRIPTION
        "The severity level is Debug. debug-level messages."
    ::= { xgs360028fTrapEvent 8 }

xgs360028fTrapVariable                                          OBJECT IDENTIFIER ::= { xgs360028fTrap 2 }

xgs360028fInformation OBJECT-TYPE
    SYNTAX      DisplayString
    MAX-ACCESS  read-only
    STATUS      current
    DESCRIPTION
        "Trap information."
    ::= { xgs360028fTrapVariable 1 }


END
