Wellfleet-IF-MIB DEFINITIONS ::= BEGIN

-- Created by mdl2asn version 3.1
-- Creation date: Wed Aug 30 16:42:42 EDT 1995


    IMPORTS

      Counter, Gauge, TimeTicks
        FROM RFC1155-SMI
      OBJECT-TYPE
        FROM RFC-1212
      DisplayString
        FROM RFC1213-MIB
      wfIfGroup
        FROM Wellfleet-COMMON-MIB;


    wfIf		OBJECT IDENTIFIER ::= { wfIfGroup 1 }

    wfIfNumber OBJECT-TYPE
        SYNTAX	INTEGER
        ACCESS	read-only
        STATUS	mandatory
        DESCRIPTION
                "Total number of possible active interfaces"
        ::= { wfIf 1 }

    wfIfRegistrationMode OBJECT-TYPE
        SYNTAX	INTEGER {
                    wellfleetstandard(1),
                    dialcircuitunique(2)
                }
        ACCESS	read-write
        STATUS	mandatory
        DESCRIPTION
                "Method of instance specification

                 Wellfleet Standard defines ifEntry instances by their
                 router internal circuit number. Dial Circuit Unique is
                 similar, but adds a bias to dial circuit instances so that
                 a dial backup interface will have an ifEntry instance
                 distinct from the primary interface. Neither selection is
                 RFC 1213 compliant."

        DEFVAL  { wellfleetstandard }
        ::= { wfIf 2 }

    wfIfTable OBJECT-TYPE
        SYNTAX	SEQUENCE OF WfIfEntry
        ACCESS	not-accessible
        STATUS	mandatory
        DESCRIPTION
                "A table containing active interfaces"
        ::= { wfIfGroup 2 }

    wfIfEntry OBJECT-TYPE
        SYNTAX	WfIfEntry
        ACCESS	not-accessible
        STATUS	mandatory
        DESCRIPTION
                "A particular interface"
        INDEX	{ wfIfIndex }
        ::= { wfIfTable 1 }

    WfIfEntry ::= SEQUENCE {
    	    wfIfIndex
    		INTEGER,
    	    wfIfDescr
    		DisplayString,
    	    wfIfType
    		INTEGER,
    	    wfIfMtu
    		INTEGER,
    	    wfIfSpeed
    		Gauge,
    	    wfIfPhysAddress
    		OCTET STRING,
    	    wfIfAdminStatus
    		INTEGER,
    	    wfIfOperStatus
    		INTEGER,
    	    wfIfLastChange
    		TimeTicks,
    	    wfIfInOctets
    		Counter,
    	    wfIfInUcastPkts
    		Counter,
    	    wfIfInNUCastPkts
    		Counter,
    	    wfIfInDiscards
    		Counter,
    	    wfIfInErrors
    		Counter,
    	    wfIfInUnknownProtos
    		Counter,
    	    wfIfOutOctets
    		Counter,
    	    wfIfOutUcastPkts
    		Counter,
    	    wfIfOutNUcastPkts
    		Counter,
    	    wfIfOutDiscards
    		Counter,
    	    wfIfOutErrors
    		Counter,
    	    wfIfOutQLen
    		Gauge,
    	    wfIfSpecific
    		OBJECT IDENTIFIER
        }

    wfIfIndex OBJECT-TYPE
        SYNTAX	INTEGER
        ACCESS	read-only
        STATUS	mandatory
        DESCRIPTION
                "Corresponds to same attribute of MIB-II's ifTable"
        ::= { wfIfEntry 1 }

    wfIfDescr OBJECT-TYPE
        SYNTAX	DisplayString
        ACCESS	read-only
        STATUS	mandatory
        DESCRIPTION
                "Corresponds to same attribute of MIB-II's ifTable"
        ::= { wfIfEntry 2 }

    wfIfType OBJECT-TYPE
        SYNTAX	INTEGER
        ACCESS	read-only
        STATUS	mandatory
        DESCRIPTION
                "Corresponds to same attribute of MIB-II's ifTable"
        ::= { wfIfEntry 3 }

    wfIfMtu OBJECT-TYPE
        SYNTAX	INTEGER
        ACCESS	read-only
        STATUS	mandatory
        DESCRIPTION
                "Corresponds to same attribute of MIB-II's ifTable"
        ::= { wfIfEntry 4 }

    wfIfSpeed OBJECT-TYPE
        SYNTAX	Gauge
        ACCESS	read-only
        STATUS	mandatory
        DESCRIPTION
                "Corresponds to same attribute of MIB-II's ifTable"
        ::= { wfIfEntry 5 }

    wfIfPhysAddress OBJECT-TYPE
        SYNTAX	OCTET STRING
        ACCESS	read-only
        STATUS	mandatory
        DESCRIPTION
                "Corresponds to same attribute of MIB-II's ifTable"
        ::= { wfIfEntry 6 }

    wfIfAdminStatus OBJECT-TYPE
        SYNTAX	INTEGER
        ACCESS	read-only
        STATUS	mandatory
        DESCRIPTION
                "Corresponds to same attribute of MIB-II's ifTable"
        ::= { wfIfEntry 7 }

    wfIfOperStatus OBJECT-TYPE
        SYNTAX	INTEGER
        ACCESS	read-only
        STATUS	mandatory
        DESCRIPTION
                "Corresponds to same attribute of MIB-II's ifTable"
        ::= { wfIfEntry 8 }

    wfIfLastChange OBJECT-TYPE
        SYNTAX	TimeTicks
        ACCESS	read-only
        STATUS	mandatory
        DESCRIPTION
                "Corresponds to same attribute of MIB-II's ifTable"
        ::= { wfIfEntry 9 }

    wfIfInOctets OBJECT-TYPE
        SYNTAX	Counter
        ACCESS	read-only
        STATUS	mandatory
        DESCRIPTION
                "Corresponds to same attribute of MIB-II's ifTable"
        ::= { wfIfEntry 10 }

    wfIfInUcastPkts OBJECT-TYPE
        SYNTAX	Counter
        ACCESS	read-only
        STATUS	mandatory
        DESCRIPTION
                "Corresponds to same attribute of MIB-II's ifTable"
        ::= { wfIfEntry 11 }

    wfIfInNUCastPkts OBJECT-TYPE
        SYNTAX	Counter
        ACCESS	read-only
        STATUS	mandatory
        DESCRIPTION
                "Corresponds to same attribute of MIB-II's ifTable"
        ::= { wfIfEntry 12 }

    wfIfInDiscards OBJECT-TYPE
        SYNTAX	Counter
        ACCESS	read-only
        STATUS	mandatory
        DESCRIPTION
                "Corresponds to same attribute of MIB-II's ifTable"
        ::= { wfIfEntry 13 }

    wfIfInErrors OBJECT-TYPE
        SYNTAX	Counter
        ACCESS	read-only
        STATUS	mandatory
        DESCRIPTION
                "Corresponds to same attribute of MIB-II's ifTable"
        ::= { wfIfEntry 14 }

    wfIfInUnknownProtos OBJECT-TYPE
        SYNTAX	Counter
        ACCESS	read-only
        STATUS	mandatory
        DESCRIPTION
                "Corresponds to same attribute of MIB-II's ifTable"
        ::= { wfIfEntry 15 }

    wfIfOutOctets OBJECT-TYPE
        SYNTAX	Counter
        ACCESS	read-only
        STATUS	mandatory
        DESCRIPTION
                "Corresponds to same attribute of MIB-II's ifTable"
        ::= { wfIfEntry 16 }

    wfIfOutUcastPkts OBJECT-TYPE
        SYNTAX	Counter
        ACCESS	read-only
        STATUS	mandatory
        DESCRIPTION
                "Corresponds to same attribute of MIB-II's ifTable"
        ::= { wfIfEntry 17 }

    wfIfOutNUcastPkts OBJECT-TYPE
        SYNTAX	Counter
        ACCESS	read-only
        STATUS	mandatory
        DESCRIPTION
                "Corresponds to same attribute of MIB-II's ifTable"
        ::= { wfIfEntry 18 }

    wfIfOutDiscards OBJECT-TYPE
        SYNTAX	Counter
        ACCESS	read-only
        STATUS	mandatory
        DESCRIPTION
                "Corresponds to same attribute of MIB-II's ifTable"
        ::= { wfIfEntry 19 }

    wfIfOutErrors OBJECT-TYPE
        SYNTAX	Counter
        ACCESS	read-only
        STATUS	mandatory
        DESCRIPTION
                "Corresponds to same attribute of MIB-II's ifTable"
        ::= { wfIfEntry 20 }

    wfIfOutQLen OBJECT-TYPE
        SYNTAX	Gauge
        ACCESS	read-only
        STATUS	mandatory
        DESCRIPTION
                "Corresponds to same attribute of MIB-II's ifTable"
        ::= { wfIfEntry 21 }

    wfIfSpecific OBJECT-TYPE
        SYNTAX	OBJECT IDENTIFIER
        ACCESS	read-only
        STATUS	mandatory
        DESCRIPTION
                "Corresponds to same attribute of MIB-II's ifTable"
        ::= { wfIfEntry 22 }

    wfIfCfgTable OBJECT-TYPE
        SYNTAX  SEQUENCE OF WfIfCfgEntry
        ACCESS  not-accessible
        STATUS  mandatory
        DESCRIPTION
                "A table used to configure the rfc-1573 subagent"
        ::= { wfIfGroup 3 }

    wfIfCfgEntry OBJECT-TYPE
        SYNTAX	WfIfCfgEntry
        ACCESS	not-accessible
        STATUS	mandatory
        DESCRIPTION
                "Single row used to configure rfc-1573 subagent for entire box"
        INDEX	{ wfIfCfgIndex }
        ::= { wfIfCfgTable 1 }

    WfIfCfgEntry ::= SEQUENCE {
	    wfIfCfgIndex
		INTEGER,
    	    wfIfCfgConformanceTesting
		INTEGER,
	    wfIfCfgSparseTableAdminStatus
		INTEGER
        }

    wfIfCfgIndex OBJECT-TYPE
        SYNTAX	INTEGER(1)
        ACCESS	read-only
        STATUS	mandatory
        DESCRIPTION
                "Unique index for configuration table"
        ::= { wfIfCfgEntry 1 }

    wfIfCfgConformanceTesting OBJECT-TYPE
        SYNTAX	INTEGER {
		     enabled(1),
		     disabled(2)
		   }
        ACCESS	read-write
        STATUS	mandatory
        DESCRIPTION
                "When enabled, this informs the system to ensure that
		 all objects supported for rfc1573 in the box follow
		 rfc1573's conformance guidelines.  Objects that do
		 not follow the guidelines will not be accessible." 
        DEFVAL  { enabled }
        ::= { wfIfCfgEntry 2 }

     wfIfCfgSparseTableAdminStatus OBJECT-TYPE
	 SYNTAX  INTEGER {
		      allowed(1),
		      zerofill(2)
	            }
        ACCESS	read-write
        STATUS	mandatory
        DESCRIPTION
                "When enabled, this informs the system of the method
		 to use when dealing with sparse tables (i.e rows that
	         contain columns that are not all supported ).

		 allowed - the agent must do nothing when sparse tables 
			   are encountered.

		 zerofill - the agent must return a zero value for 
			    unsupported columns"
	
	DEFVAL { allowed }
        ::= { wfIfCfgEntry 3 }

    END  -- Wellfleet-IF-MIB
