AVICI-FABRIC-MIB DEFINITIONS ::= BEGIN

IMPORTS
   MODULE-IDENTITY, OBJECT-TYPE, Integer32, Unsigned32, Counter32,
   Counter64, TimeTicks
      FROM SNMPv2-SMI
   DisplayString, TruthValue, TEXTUAL-CONVENTION
      FROM SNMPv2-TC
   MODULE-COMPLIANCE, OBJECT-GROUP
      FROM SNMPv2-CONF
   aviciMibs
      FROM AVICI-SMI
   AviciRevisionType, AviciBayType, AviciSlotType, AviciModuleName,
   AviciFabricLinkType
      FROM AVICI-TC
   aviciBayIndex, aviciSlotIndex
      FROM AVICI-BAY-MIB;

aviciFabricMIB MODULE-IDENTITY
        LAST-UPDATED "000905130000Z"
        ORGANIZATION "Avici Systems Inc."
        CONTACT-INFO "
                  Avici Systems, Inc.
                  101 Billerica Avenue
                  North Billerica, MA 01862
 
                  (978) 964-2000
                  (978) 964-2100 (fax)
 
                  snmp@avici.com"
        DESCRIPTION
            "Added compliance information."
        REVISION      "000905130000Z"
        DESCRIPTION  "The MIB module for the Avici Proprietary fabric MIB."
        ::= { aviciMibs 8 }

aviciFabricObjects    OBJECT IDENTIFIER ::= { aviciFabricMIB 1 }
aviciFabricGroup      OBJECT IDENTIFIER ::= { aviciFabricMIB 2 }
aviciFabricCounters   OBJECT IDENTIFIER ::= { aviciFabricObjects 1 }
aviciFabricConfig     OBJECT IDENTIFIER ::= { aviciFabricObjects 2 }
aviciFabricRouting    OBJECT IDENTIFIER ::= { aviciFabricObjects 3 }


--
-- aviciFabricGroup
--

aviciFabricHardwareVersion OBJECT-TYPE
   SYNTAX      AviciRevisionType
   MAX-ACCESS  read-only
   STATUS      current
   DESCRIPTION
       "The current hardware version of the fabric."
   ::= { aviciFabricGroup 1 }

aviciFabricRoutingProtocolVersion OBJECT-TYPE
   SYNTAX      AviciRevisionType
   MAX-ACCESS  read-only
   STATUS      current
   DESCRIPTION
       "The current fabric routing protocol version used on the fabric."
   ::= { aviciFabricGroup 2 }

--
-- Fabric counters for inserted and forwarded packets/flits
--

aviciFabricCountersTable    OBJECT-TYPE
   SYNTAX      SEQUENCE OF AviciFabricCountersEntry
   MAX-ACCESS  not-accessible
   STATUS      current
   DESCRIPTION
       "This table contains fabric counters for inserted and
        forwarded packets/flits."
   ::= { aviciFabricCounters 1 }

aviciFabricCountersEntry    OBJECT-TYPE
   SYNTAX      AviciFabricCountersEntry
   MAX-ACCESS  not-accessible
   STATUS      current
   DESCRIPTION
       "."
   INDEX       { aviciBayIndex, aviciSlotIndex, aviciFabricLinkIndex }
   ::= { aviciFabricCountersTable 1 }
    
AviciFabricCountersEntry ::= SEQUENCE {
   aviciFabricHiPriPktsInserted    Counter64,
   aviciFabricLoPriPktsInserted    Counter64,
   aviciFabricHiPriPktsForwarded   Counter64,
   aviciFabricLoPriPktsForwarded   Counter64,
   aviciFabricHiPriFlitsForwarded  Counter64,
   aviciFabricLoPriFlitsForwarded  Counter64
}

aviciFabricHiPriPktsInserted OBJECT-TYPE
   SYNTAX       Counter64
   MAX-ACCESS   read-only
   STATUS       current
   DESCRIPTION
       "High priority packets inserted into the fabric from an input
        framer and destined for some other module in the system."
   ::= { aviciFabricCountersEntry 1 }
                
aviciFabricLoPriPktsInserted OBJECT-TYPE
   SYNTAX       Counter64
   MAX-ACCESS   read-only
   STATUS       current
   DESCRIPTION
       "Low priority packets inserted into the fabric from an input
        framer and destined for some other module in the system."
   ::= { aviciFabricCountersEntry 2 }

aviciFabricHiPriPktsForwarded OBJECT-TYPE
   SYNTAX       Counter64
   MAX-ACCESS   read-only
   STATUS       current
   DESCRIPTION
       "High priority packets forwarded through this module."
   ::= { aviciFabricCountersEntry 3 }

aviciFabricLoPriPktsForwarded OBJECT-TYPE
   SYNTAX       Counter64
   MAX-ACCESS   read-only
   STATUS       current
   DESCRIPTION
       "Low priority packets forwarded through this module."
   ::= { aviciFabricCountersEntry 4 }

aviciFabricHiPriFlitsForwarded OBJECT-TYPE
   SYNTAX       Counter64
   MAX-ACCESS   read-only
   STATUS       current
   DESCRIPTION
       "High priority flits (parts of packets) forwarded through this module."
   ::= { aviciFabricCountersEntry 5 }

aviciFabricLoPriFlitsForwarded OBJECT-TYPE
   SYNTAX       Counter64
   MAX-ACCESS   read-only
   STATUS       current
   DESCRIPTION
       "Low priority flits (parts of packets) forwarded through this module."
   ::= { aviciFabricCountersEntry 6 }


--
-- Fabric counters for extracted packets/flits
--

aviciFabricExtractedCountersTable    OBJECT-TYPE
   SYNTAX      SEQUENCE OF AviciFabricExtractedCountersEntry
   MAX-ACCESS  not-accessible
   STATUS      current
   DESCRIPTION
       "This table contains fabric extracted counters."
   ::= { aviciFabricCounters 2 }

aviciFabricExtractedCountersEntry    OBJECT-TYPE
   SYNTAX      AviciFabricExtractedCountersEntry
   MAX-ACCESS  not-accessible
   STATUS      current
   DESCRIPTION
       "An entry in the Avici Fabric Extracted Counters table."
   INDEX       { aviciBayIndex, aviciSlotIndex, aviciFabricLinkIndex }
   ::= { aviciFabricExtractedCountersTable 1 }

AviciFabricExtractedCountersEntry ::= SEQUENCE {
   aviciFabricExtractedHiPriPktsSelf  Counter64,
   aviciFabricExtractedLoPriPktsSelf  Counter64,
   aviciFabricExtractedHiPriPkts      Counter64,
   aviciFabricExtractedLoPriPkts      Counter64,
   aviciFabricExtractedHiPriFlits     Counter64,
   aviciFabricExtractedLoPriFlits     Counter64
}

aviciFabricExtractedHiPriPktsSelf  OBJECT-TYPE
   SYNTAX       Counter64
   MAX-ACCESS   read-only
   STATUS       current
   DESCRIPTION
       "High priority packets extracted from the fabric whose destination
        is this module."
   ::= { aviciFabricExtractedCountersEntry 1 }

aviciFabricExtractedLoPriPktsSelf  OBJECT-TYPE
   SYNTAX       Counter64
   MAX-ACCESS   read-only
   STATUS       current
   DESCRIPTION
       "Low priority packets extracted from the fabric whose destination
        is this module."
   ::= { aviciFabricExtractedCountersEntry 2 }

aviciFabricExtractedHiPriPkts  OBJECT-TYPE
   SYNTAX       Counter64
   MAX-ACCESS   read-only
   STATUS       current
   DESCRIPTION
       "High priority packets extracted from the fabric whose destination
        is this module."
   ::= { aviciFabricExtractedCountersEntry 3 }

aviciFabricExtractedLoPriPkts  OBJECT-TYPE
   SYNTAX       Counter64
   MAX-ACCESS   read-only
   STATUS       current
   DESCRIPTION
       "Low priority packets extracted from the fabric whose destination
        is this module."
   ::= { aviciFabricExtractedCountersEntry 4 }

aviciFabricExtractedHiPriFlits  OBJECT-TYPE
   SYNTAX       Counter64
   MAX-ACCESS   read-only
   STATUS       current
   DESCRIPTION
       "High priority flits (parts of packets) extracted from the fabric
        whose destination is this module."
   ::= { aviciFabricExtractedCountersEntry 5 }

aviciFabricExtractedLoPriFlits  OBJECT-TYPE
   SYNTAX       Counter64
   MAX-ACCESS   read-only
   STATUS       current
   DESCRIPTION
       "Low priority flits (parts of packets) extracted from the fabric
        whose destination is this module."
   ::= { aviciFabricExtractedCountersEntry 6 }

--
-- The Fabric Link Table
--

aviciFabricLinkTable    OBJECT-TYPE
   SYNTAX      SEQUENCE OF AviciFabricLinkEntry
   MAX-ACCESS  not-accessible
   STATUS      current
   DESCRIPTION
       "This table contains information for a fabric link."
   ::= { aviciFabricConfig 1 }

aviciFabricLinkEntry OBJECT-TYPE
   SYNTAX	AviciFabricLinkEntry
   MAX-ACCESS   not-accessible
   STATUS	current
   DESCRIPTION
       "An entry in the Avici Fabric Link table."
   INDEX   { aviciBayIndex, aviciSlotIndex, aviciFabricLinkIndex }
   ::= { aviciFabricLinkTable 1 }

AviciFabricLinkEntry ::= SEQUENCE { 
   aviciFabricLinkIndex           AviciFabricLinkType,
   aviciFabricLinkDescr           DisplayString,
   aviciFabricLinkAdminStatus     INTEGER,
   aviciFabricLinkOperStatus      INTEGER,
   aviciFabricLinkSpeed           Unsigned32,
   aviciFabricLinkCRCErrors       Counter32,
   aviciFabricLinkDownTransitions Counter32,
   aviciFabricLinkLastChange      TimeTicks
}

aviciFabricLinkIndex  OBJECT-TYPE
   SYNTAX       AviciFabricLinkType
   MAX-ACCESS   read-only
   STATUS	current
   DESCRIPTION
       "The index of the fabric link."
   ::= { aviciFabricLinkEntry 1 }

aviciFabricLinkDescr  OBJECT-TYPE
   SYNTAX       DisplayString (SIZE(0..48))
   MAX-ACCESS   read-only
   STATUS	current
   DESCRIPTION
       "A string containing a description of the link.  This string
        could contain name of the module at the other end of this link.

        Example:

        Plus X link to module 1/22"
   ::= { aviciFabricLinkEntry 2 }

aviciFabricLinkAdminStatus  OBJECT-TYPE
   SYNTAX       INTEGER {
                up          (1),
                down        (2)
   }
   MAX-ACCESS   read-write
   STATUS       current
   DESCRIPTION
     "The current administrative state of the link."
   ::= { aviciFabricLinkEntry 3 }

aviciFabricLinkOperStatus  OBJECT-TYPE
   SYNTAX       INTEGER {
                up             (1),
                down           (2),
                admin-down     (3),
                failed         (4)
   }
   MAX-ACCESS   read-only
   STATUS       current
   DESCRIPTION
       "The current operational state of the link."
   ::= { aviciFabricLinkEntry 4 }

aviciFabricLinkSpeed  OBJECT-TYPE
   SYNTAX       Unsigned32
   MAX-ACCESS   read-only
   STATUS	current
   DESCRIPTION
       "The speed of the fabric link in units of 1 Mb/s."
   ::= { aviciFabricLinkEntry 5 }

aviciFabricLinkCRCErrors  OBJECT-TYPE
   SYNTAX       Counter32
   MAX-ACCESS   read-only
   STATUS	current
   DESCRIPTION
       "The number of CRC errors on the link."
   ::= { aviciFabricLinkEntry 6 }

aviciFabricLinkDownTransitions  OBJECT-TYPE
   SYNTAX       Counter32
   MAX-ACCESS   read-only
   STATUS	current
   DESCRIPTION
       "The number of times this link has transitioned to the down state."
   ::= { aviciFabricLinkEntry 7 }

aviciFabricLinkLastChange OBJECT-TYPE
   SYNTAX       TimeTicks
   MAX-ACCESS   read-only
   STATUS	current
   DESCRIPTION
       "The time, in 1/00ths of a second, since this link last changed
        state."
   ::= { aviciFabricLinkEntry 8 }

--
-- The Fabric Channel table
--

aviciFabricChannelTable  OBJECT-TYPE
   SYNTAX	SEQUENCE OF AviciFabricChannelEntry
   MAX-ACCESS	not-accessible
   STATUS	current
   DESCRIPTION
      "This table contains information about fabric channels."
   ::= { aviciFabricConfig 2 }

aviciFabricChannelEntry OBJECT-TYPE
   SYNTAX	AviciFabricChannelEntry
   MAX-ACCESS   not-accessible
   STATUS	current
   DESCRIPTION
       "An entry in the Avici Fabric Channel table."
   INDEX   { aviciBayIndex, aviciSlotIndex, aviciFabricChannelIndex }
   ::= { aviciFabricChannelTable 1 }

AviciFabricChannelEntry ::= SEQUENCE {
   aviciFabricChannelIndex	          Integer32,
   aviciFabricChannelHiPriScrubEvents     Counter32,
   aviciFabricChannelLoPriScrubEvents     Counter32,
   aviciFabricChannelHiPriLastScrubTime   TimeTicks,
   aviciFabricChannelLoPriLastScrubTime   TimeTicks
}


aviciFabricChannelIndex OBJECT-TYPE
   SYNTAX       Integer32 (0..255)
   MAX-ACCESS   read-only
   STATUS       current
   DESCRIPTION
       "The index of the Fabric Channel pair.  Each of the Fabric Channels
        consists of a high and a low priority channel."
   ::= { aviciFabricChannelEntry 1 }

aviciFabricChannelHiPriScrubEvents OBJECT-TYPE
   SYNTAX       Counter32
   MAX-ACCESS   read-only
   STATUS       current
   DESCRIPTION
       "The number of times the high priority Fabric Channel has scrubbed."
   ::= { aviciFabricChannelEntry 2 }

aviciFabricChannelLoPriScrubEvents OBJECT-TYPE
   SYNTAX       Counter32
   MAX-ACCESS   read-only
   STATUS       current
   DESCRIPTION
       "The number of times the low priority Fabric Channel has scrubbed."
   ::= { aviciFabricChannelEntry 3 }

aviciFabricChannelHiPriLastScrubTime OBJECT-TYPE
   SYNTAX       TimeTicks
   MAX-ACCESS   read-only
   STATUS       current
   DESCRIPTION
       "The time in 1/100ths of a second since the high priority Fabric
        Channel last scrubbed."
   ::= { aviciFabricChannelEntry 4 }

aviciFabricChannelLoPriLastScrubTime OBJECT-TYPE
   SYNTAX       TimeTicks
   MAX-ACCESS   read-only
   STATUS       current
   DESCRIPTION
       "The time in 1/100ths of a second since the low priority Fabric
        Channel last scrubbed."
   ::= { aviciFabricChannelEntry 5 }


--
-- The Fabric Link State Advertisement table
--
-- This table contains the Link State Advertisment database for every
-- module in the system.  Every module has the complete LSA database
-- for all modules in the system (i.e. every module knows what every
-- other module in the system is advertising for connectivity).

aviciFabricLsaTable    OBJECT-TYPE
   SYNTAX      SEQUENCE OF AviciFabricLsaEntry
   MAX-ACCESS  not-accessible
   STATUS      current
   DESCRIPTION
       "This table contains Fabric Link State Advertisement database."
   ::= { aviciFabricRouting 1 }

aviciFabricLsaEntry OBJECT-TYPE
   SYNTAX	AviciFabricLsaEntry
   MAX-ACCESS   not-accessible
   STATUS	current
   DESCRIPTION
       "An entry in the Avici Fabric Link State Advertisement table."
   INDEX   { aviciBayIndex, aviciSlotIndex, aviciFabricLsaOriginBay,
             aviciFabricLsaOriginSlot}
   ::= { aviciFabricLsaTable 1 }


AviciFabricLsaEntry ::= SEQUENCE {
   aviciFabricLsaOriginBay         AviciBayType,
   aviciFabricLsaOriginSlot        AviciSlotType,
   aviciFabricLsaSequenceNum       Unsigned32,
   aviciFabricLsaCreationTime      DisplayString,
   aviciFabricLsaModuleReachable   TruthValue,
   aviciFabricLsaChannels          DisplayString,
   aviciFabricLsaModulePlusX       AviciModuleName,
   aviciFabricLsaModuleMinusX      AviciModuleName,
   aviciFabricLsaModulePlusY       AviciModuleName,
   aviciFabricLsaModuleMinusY      AviciModuleName,
   aviciFabricLsaModulePlusZ       AviciModuleName,
   aviciFabricLsaModuleMinusZ      AviciModuleName
}

aviciFabricLsaOriginBay OBJECT-TYPE
   SYNTAX       AviciBayType
   MAX-ACCESS   not-accessible
   STATUS       current
   DESCRIPTION
       "The bay number for the module that originated this entry."
   ::= { aviciFabricLsaEntry 1 }
  
aviciFabricLsaOriginSlot OBJECT-TYPE
   SYNTAX       AviciSlotType
   MAX-ACCESS   not-accessible
   STATUS       current
   DESCRIPTION
       "The slot number for the module that originated this entry."
   ::= { aviciFabricLsaEntry 2 }

aviciFabricLsaSequenceNum OBJECT-TYPE
   SYNTAX       Unsigned32
   MAX-ACCESS   read-only
   STATUS       current
   DESCRIPTION
       "The sequence number for this LSA.  Sequence numbers start at
        1 and are incremented by the originator every time the LSA is
        re-originated."
   ::= { aviciFabricLsaEntry 3 }

aviciFabricLsaCreationTime OBJECT-TYPE
   SYNTAX       DisplayString
   MAX-ACCESS   read-only
   STATUS       current
   DESCRIPTION
       "A string containing the creation time for this 
        LSA (wall clock time to 1/1000 sec)."
-- alternative would be timeTicks
   ::= { aviciFabricLsaEntry 4 }

aviciFabricLsaModuleReachable OBJECT-TYPE
   SYNTAX       TruthValue 
   MAX-ACCESS   read-only
   STATUS       current
   DESCRIPTION
       "True if the originator module is reachable from this module."
   ::= { aviciFabricLsaEntry 5 }

aviciFabricLsaChannels OBJECT-TYPE
   SYNTAX       DisplayString (SIZE(0..64)) 
   MAX-ACCESS   read-only
   STATUS       current
   DESCRIPTION
       "The list of fabric channels currently assigned for this module.

        Example:  1 3 5 11
       "
   ::= { aviciFabricLsaEntry 6 }


aviciFabricLsaModulePlusX OBJECT-TYPE
   SYNTAX       AviciModuleName 
   MAX-ACCESS   read-only
   STATUS       current
   DESCRIPTION
       "The immediate neighbor module on the plusX link."
   ::= { aviciFabricLsaEntry 7 }

aviciFabricLsaModuleMinusX OBJECT-TYPE
   SYNTAX       AviciModuleName 
   MAX-ACCESS   read-only
   STATUS       current
   DESCRIPTION
       "The immediate neighbor module on the minusX link."
   ::= { aviciFabricLsaEntry 8 }

aviciFabricLsaModulePlusY OBJECT-TYPE
   SYNTAX       AviciModuleName 
   MAX-ACCESS   read-only
   STATUS       current
   DESCRIPTION
       "The immediate neighbor module on the plusY link."
   ::= { aviciFabricLsaEntry 9 }

aviciFabricLsaModuleMinusY OBJECT-TYPE
   SYNTAX       AviciModuleName 
   MAX-ACCESS   read-only
   STATUS       current
   DESCRIPTION
       "The immediate neighbor module on the minusY link."
   ::= { aviciFabricLsaEntry 10 }

aviciFabricLsaModulePlusZ OBJECT-TYPE
   SYNTAX       AviciModuleName 
   MAX-ACCESS   read-only
   STATUS       current
   DESCRIPTION
       "The immediate neighbor module on the plusZ link."
   ::= { aviciFabricLsaEntry 11 }

aviciFabricLsaModuleMinusZ OBJECT-TYPE
   SYNTAX       AviciModuleName 
   MAX-ACCESS   read-only
   STATUS       current
   DESCRIPTION
       "The immediate neighbor module on the minusZ link."
   ::= { aviciFabricLsaEntry 12 }

--
-- The Link State Advertisement Database Summary table
--

aviciFabricLsaSummaryTable    OBJECT-TYPE
   SYNTAX      SEQUENCE OF AviciFabricLsaSummaryEntry
   MAX-ACCESS  not-accessible
   STATUS      current
   DESCRIPTION
       "This table contains summary information for the Fabric
        Link State Advertisement database."
   ::= { aviciFabricRouting 2 }

aviciFabricLsaSummaryEntry OBJECT-TYPE
   SYNTAX	AviciFabricLsaSummaryEntry
   MAX-ACCESS   not-accessible
   STATUS	current
   DESCRIPTION
       "An entry in the LSA summary table."
   INDEX   { aviciBayIndex, aviciSlotIndex }
   ::= { aviciFabricLsaSummaryTable 1 }


AviciFabricLsaSummaryEntry ::= SEQUENCE {
   aviciFabricLsaSummaryChecksum           Unsigned32
}

aviciFabricLsaSummaryChecksum OBJECT-TYPE
   SYNTAX       Unsigned32 
   MAX-ACCESS   read-only
   STATUS       current
   DESCRIPTION
       "The sum of all of the checksums of all LSA's in the 
        LSA database on this module."
   ::= { aviciFabricLsaSummaryEntry 1 }


--
-- Fabric Paths Table
--

aviciFabricPathTable    OBJECT-TYPE
   SYNTAX      SEQUENCE OF AviciFabricPathEntry
   MAX-ACCESS  not-accessible
   STATUS      current
   DESCRIPTION
       "This table contains information for a Fabric Routing Protocol link."
   ::= { aviciFabricRouting 3 }

aviciFabricPathEntry OBJECT-TYPE
   SYNTAX	AviciFabricPathEntry
   MAX-ACCESS   not-accessible
   STATUS	current
   DESCRIPTION
       "An entry in the Avici Fabric Routing Link State table."
   INDEX   { aviciBayIndex, aviciSlotIndex, aviciFabricPathDestinationBay,
             aviciFabricPathDestinationSlot, aviciFabricPathIndex }
   ::= { aviciFabricPathTable 1 }

AviciFabricPathEntry ::= SEQUENCE { 
   aviciFabricPathIndex           INTEGER,
   aviciFabricPathDestinationBay  AviciBayType,
   aviciFabricPathDestinationSlot AviciSlotType,
   aviciFabricPathVector          DisplayString
}

aviciFabricPathIndex  OBJECT-TYPE
   SYNTAX       INTEGER (1..24)
   MAX-ACCESS   read-only
   STATUS       current
   DESCRIPTION
       "The index for this fabric path."
   ::= { aviciFabricPathEntry 1 }

aviciFabricPathDestinationBay  OBJECT-TYPE
   SYNTAX       AviciBayType
   MAX-ACCESS   not-accessible
   STATUS       current
   DESCRIPTION
       "The destination bay for this fabric path."
   ::= { aviciFabricPathEntry 2 }

aviciFabricPathDestinationSlot  OBJECT-TYPE
   SYNTAX       AviciSlotType
   MAX-ACCESS   not-accessible
   STATUS       current
   DESCRIPTION
       "The destination slot for this fabric path."
   ::= { aviciFabricPathEntry 3 }

aviciFabricPathVector  OBJECT-TYPE
   SYNTAX       DisplayString (SIZE(0..185))
   MAX-ACCESS   read-only
   STATUS       current
   DESCRIPTION
       "The textual representation of the vector describing this fabric path.
        This vector is described using a shorthand notation for each fabric
        link from source to destination.  Each component of the vector
        consists of: destination bay/slot fabricLink.

        Example:  1/1 +X 1/10 +Y 1/30 +Z 1/28

        This example shows the path from module 1/1 to module 1/28.

        The first vector is the bay/slot of this module and the origin link
        onto the fabric.  There are a maximum of 16 fabric hops in a path."
   ::= { aviciFabricPathEntry 4 }


--
-- Conformance Information
--    

aviciFabricMIBConformance OBJECT IDENTIFIER ::= { aviciFabricMIB 3 }
aviciFabricMIBCompliances OBJECT IDENTIFIER ::= { aviciFabricMIBConformance 1 }
aviciFabricMIBGroups OBJECT IDENTIFIER ::= { aviciFabricMIBConformance 2 }

aviciFabricMIBCompliance MODULE-COMPLIANCE
        STATUS current
        DESCRIPTION
            "The compliance statement for aviciFabric."
        MODULE
        MANDATORY-GROUPS {
            aviciFabricGroup,
            aviciFabricCountersGroup,
            aviciFabricGeneralGroup,
            aviciFabricRoutingGroup
        }
        ::= { aviciFabricMIBCompliances 1 }

aviciFabricCountersGroup OBJECT-GROUP
        OBJECTS {
            aviciFabricHiPriPktsInserted,
            aviciFabricLoPriPktsInserted,
            aviciFabricHiPriPktsForwarded,
            aviciFabricLoPriPktsForwarded,
            aviciFabricHiPriFlitsForwarded,
            aviciFabricLoPriFlitsForwarded,
            aviciFabricExtractedHiPriPktsSelf,
            aviciFabricExtractedLoPriPktsSelf,
            aviciFabricExtractedHiPriPkts,
            aviciFabricExtractedLoPriPkts,
            aviciFabricExtractedHiPriFlits,
            aviciFabricExtractedLoPriFlits
        }
        STATUS     current
        DESCRIPTION
            "Objects for the fabric counters."
        ::= { aviciFabricMIBGroups 1 }

aviciFabricGeneralGroup OBJECT-GROUP
        OBJECTS {
            aviciFabricLinkIndex,
            aviciFabricLinkDescr,
            aviciFabricLinkAdminStatus,
            aviciFabricLinkOperStatus,
            aviciFabricLinkSpeed,
            aviciFabricLinkCRCErrors,
            aviciFabricLinkDownTransitions,
            aviciFabricLinkLastChange,
            aviciFabricChannelIndex,
            aviciFabricChannelHiPriScrubEvents,
            aviciFabricChannelLoPriScrubEvents,
            aviciFabricChannelHiPriLastScrubTime,
            aviciFabricChannelLoPriLastScrubTime
        }
        STATUS     current
        DESCRIPTION
            "Objects for the fabric."
        ::= { aviciFabricMIBGroups 2 }

aviciFabricRoutingGroup OBJECT-GROUP
        OBJECTS {
            aviciFabricLsaSequenceNum,
            aviciFabricLsaCreationTime,
            aviciFabricLsaModuleReachable,
            aviciFabricLsaChannels,
            aviciFabricLsaModulePlusX,
            aviciFabricLsaModuleMinusX,
            aviciFabricLsaModulePlusY,
            aviciFabricLsaModuleMinusY,
            aviciFabricLsaModulePlusZ,
            aviciFabricLsaModuleMinusZ,
            aviciFabricLsaSummaryChecksum,
            aviciFabricPathIndex,
            aviciFabricPathVector
        }
        STATUS     current
        DESCRIPTION
            "Objects for fabric routing."
        ::= { aviciFabricMIBGroups 3 }
END
