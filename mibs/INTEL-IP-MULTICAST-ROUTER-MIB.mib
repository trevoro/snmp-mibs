INTEL-IP-MULTICAST-ROUTER-MIB DEFINITIONS ::= BEGIN

-- Copyright (C) 1998 Intel Corporation. All rights reserved.
--
-- IP Multicast router MIB, 98-05-14
--
-- This MIB defines the management information for a system functioning
-- as an DVMRP IP Multicast router.
--
-- Change History:
-- 98-05-14 Initial version

    IMPORTS
--      Counter, IpAddress FROM RFC1155-SMI
      mib2ext            FROM INTEL-GEN-MIB
      OBJECT-TYPE        FROM RFC-1212;


    ipmrouter            OBJECT IDENTIFIER ::= { mib2ext 32 }

--********************** IP MC configuration *********************************

    conf                 OBJECT IDENTIFIER ::= { ipmrouter 1 }

    confMaxDvmrpRoutes OBJECT-TYPE
    SYNTAX INTEGER (1..100000)
    ACCESS read-write
    STATUS mandatory
    DESCRIPTION "Limits the number of DVMRP routes handled by the router"
    ::= { conf 1 }

--********************** IP MC Interface configuration ***********************

    confIfTable OBJECT-TYPE
    SYNTAX SEQUENCE OF ConfIfEntry
    ACCESS not-accessible
    STATUS mandatory
    DESCRIPTION "This table contains configuration information for each
                 IP Multicast link."
    ::= { conf 2 }

    confIfEntry OBJECT-TYPE
    SYNTAX ConfIfEntry
    ACCESS not-accessible
    STATUS mandatory
    DESCRIPTION "Configuration information for the IP Multicast link."
    INDEX { confIfIndex }
    ::= { confIfTable 1 }

    ConfIfEntry ::=
    SEQUENCE {
      confIfIndex
        INTEGER,
      confIfMCRouteProto
        INTEGER,
      confIfIgmpQueryInterval
        INTEGER,
      confIfIgmpRobustness
        INTEGER,
      confIfDvmrpMetric
        INTEGER,
      confIfDvmrpUnreachableMetric
        INTEGER,
      confIfCreateObj
        OCTET STRING (SIZE (11)),
      confIfDeleteObj
        INTEGER
    }

    confIfIndex OBJECT-TYPE
    SYNTAX INTEGER
    ACCESS read-only
    STATUS mandatory
    DESCRIPTION "The ifIndex of the IP link."
    ::= { confIfEntry 1 }

    confIfMCRouteProto OBJECT-TYPE
    SYNTAX INTEGER {
      disabled (1),
      enabled (2)
    }
    ACCESS read-write
    STATUS mandatory
    DESCRIPTION "The multicast Routing Protocol used on the link."
    ::= { confIfEntry 2 }

    confIfIgmpQueryInterval OBJECT-TYPE
    SYNTAX INTEGER
    ACCESS read-write
    STATUS mandatory
    DESCRIPTION "The IGMP query interval used on the link."
    ::= { confIfEntry 3 }

    confIfIgmpRobustness OBJECT-TYPE
    SYNTAX INTEGER
    ACCESS read-write
    STATUS mandatory
    DESCRIPTION "The IGMP robustness variable used on the link."
    ::= { confIfEntry 4 }

    confIfDvmrpMetric OBJECT-TYPE
    SYNTAX INTEGER (1..31)
    ACCESS read-write
    STATUS mandatory
    DESCRIPTION "The DVMRP metric (cost) used on the link."
    ::= { confIfEntry 5 }

    confIfDvmrpUnreachableMetric OBJECT-TYPE
    SYNTAX INTEGER (1..31)
    ACCESS read-write
    STATUS mandatory
    DESCRIPTION "When a route report is received this parameter is used
    to determine if a route should be considered unreachable and thus ignored "
    ::= { confIfEntry 6 }

    confIfCreateObj OBJECT-TYPE
    SYNTAX OCTET STRING (SIZE (11))
    ACCESS read-write
    STATUS mandatory
    DESCRIPTION "Create a non existing table entry. If the entry already exist,
                 genError is returned.
                 Binary format:
                 1 bytes   confIfMCRouteProto
                 4 bytes   confIfIgmpQueryInterval
                 4 bytes   confIfIgmpRobustness
                 1 byte    confIfDvmrpMetric
                 1 bytes   confIfDvmrpUnreachableMetric
                 "
    ::= { confIfEntry 7 }

    confIfDeleteObj OBJECT-TYPE
    SYNTAX INTEGER {
      delete (1)
    }
    ACCESS read-write
    STATUS mandatory
    DESCRIPTION "Delete an existing table entry"
    ::= { confIfEntry 8 }


    END
