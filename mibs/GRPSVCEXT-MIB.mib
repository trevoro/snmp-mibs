GRPSVCEXT-MIB 

   --FORCE-INCLUDE <mib.h>
   --FORCE-INCLUDE <snmpdefs.h>
   --FORCE-INCLUDE <snmpstat.h>
   --FORCE-INCLUDE "mibproto.h"
 
	DEFINITIONS ::= BEGIN

	IMPORTS
		MODULE-IDENTITY, OBJECT-TYPE
			FROM SNMPv2-SMI
		DisplayString, RowStatus
			FROM SNMPv2-TC
		grpsvcExt
			FROM APENT-MIB;

--GRPSVCEXT MIB

    apGrpsvcExtMib MODULE-IDENTITY
	   LAST-UPDATED "9710092000Z" -- Thu October 9 20:00:00 EST 1997
	   ORGANIZATION "ArrowPoint Communications Inc."
	   CONTACT-INFO
	   "                      
	   Postal:               ArrowPoint Communications Inc.
				                 50 Nagog Park
				                 Acton, Massachusetts 01720
	   Tel:                   +1 978-206-3000  option 1
	   E-Mail:                support@arrowpoint.com"
       DESCRIPTION
	  "The MIB module used to describe the ArrowPoint Communications
	  content rule table"
      ::= { grpsvcExt 1}


apGrpsvcTable OBJECT-TYPE
	SYNTAX          SEQUENCE OF APGrpsvcEntry
	MAX-ACCESS      not-accessible
	STATUS          current
	DESCRIPTION
		"A list of group rule entries."
	::= { grpsvcExt 2 }

apGrpsvcEntry OBJECT-TYPE
	SYNTAX          APGrpsvcEntry
	MAX-ACCESS      not-accessible
	STATUS          current
	DESCRIPTION
		"A group of information to uniquely identify a source grouping."
	INDEX   { apGrpsvcGrpName, apGrpsvcSvcName }
	--DEFAULT apjam-group apGroupSvcInst, apGrpsvcSvcName
	--DEFAULT apjam-popup-def apGroupSvcInst, Properties, local
	--DEFAULT apjam-popup-def apGroupSvcInst, Delete, special, apGrpsvcStatus
	--DEFAULT apjam-wizard apGroupSvcInst, 1, images/arrowlogo.gif, "This wizard will let you add a service to a given Source Group rule."
	::= { apGrpsvcTable 1 }

APGrpsvcEntry ::= SEQUENCE {
		apGrpsvcGrpName              DisplayString,
		apGrpsvcSvcName              DisplayString,
		apGrpsvcStatus               RowStatus
}

apGrpsvcGrpName OBJECT-TYPE
	SYNTAX          DisplayString (SIZE(1..31))
	MAX-ACCESS      read-create
	STATUS          current
	DESCRIPTION     
			"The name of the content rule."
	--DEFAULT ap-display-name	Group Name
	--DEFAULT apjam-popup-ref apGroupSvcInst, Properties
	--DEFAULT ap-create-requires Yes
	--DEFAULT apjam-noedit-dlg	True
	--DEFAULT apjam-wizard-field 1, choice, apGrpName( ), nodepend
	::= {apGrpsvcEntry 1}

apGrpsvcSvcName OBJECT-TYPE
	SYNTAX          DisplayString (SIZE(1..31))
	MAX-ACCESS      read-create
	STATUS          current
	DESCRIPTION     
			"The name of the service."
	--DEFAULT ap-display-name	Service Name
	--DEFAULT apjam-popup-ref apGroupSvcInst, Properties
	--DEFAULT ap-create-requires Yes
	--DEFAULT apjam-noedit-dlg	True
	--DEFAULT apjam-wizard-field 1, choice, apSvcName( ), nodepend
	::= {apGrpsvcEntry 2}

apGrpsvcStatus OBJECT-TYPE
	SYNTAX          RowStatus
	MAX-ACCESS      read-create
	STATUS          current
	DESCRIPTION      
		"Status entry for this row "
	::= {apGrpsvcEntry 3}

apGrpDestSvcTable OBJECT-TYPE
	SYNTAX          SEQUENCE OF APGrpDestSvcEntry
	MAX-ACCESS      not-accessible
	STATUS          current
	DESCRIPTION
		"A list of group destination service entries."
	::= { grpsvcExt 3 }

apGrpDestSvcEntry OBJECT-TYPE
	SYNTAX          APGrpDestSvcEntry
	MAX-ACCESS      not-accessible
	STATUS          current
	DESCRIPTION
		"A group of information to uniquely identify a source grouping
         by a destination service."
	INDEX   { apGrpDestSvcGrpName, apGrpDestSvcSvcName }
	--DEFAULT apjam-group apGroupDestSvcInst, apGrpDestSvcSvcName
	--DEFAULT apjam-popup-def apGroupDestSvcInst, Properties, local
	--DEFAULT apjam-popup-def apGroupDestSvcInst, Delete, special, apGrpDestSvcStatus
	--DEFAULT apjam-wizard apGroupDestSvcInst, 1, images/arrowlogo.gif, "This wizard will let you add a destination service to a given Source Group rule."
	::= { apGrpDestSvcTable 1 }

APGrpDestSvcEntry ::= SEQUENCE {
		apGrpDestSvcGrpName              DisplayString,
		apGrpDestSvcSvcName              DisplayString,
		apGrpDestSvcStatus               RowStatus
}

apGrpDestSvcGrpName OBJECT-TYPE
	SYNTAX          DisplayString (SIZE(1..31))
	MAX-ACCESS      read-create
	STATUS          current
	DESCRIPTION     
			"The name of the source group destination service."
	--DEFAULT ap-display-name	Group Name
	--DEFAULT apjam-popup-ref apGroupDestSvcInst, Properties
	--DEFAULT ap-create-requires Yes
	--DEFAULT apjam-noedit-dlg	True
	--DEFAULT apjam-wizard-field 1, choice, apGrpName( ), nodepend
	::= {apGrpDestSvcEntry 1}

apGrpDestSvcSvcName OBJECT-TYPE
	SYNTAX          DisplayString (SIZE(1..31))
	MAX-ACCESS      read-create
	STATUS          current
	DESCRIPTION     
			"The name of the destination service."
	--DEFAULT ap-display-name	Service Name
	--DEFAULT apjam-popup-ref apGroupDestSvcInst, Properties
	--DEFAULT ap-create-requires Yes
	--DEFAULT apjam-noedit-dlg	True
	--DEFAULT apjam-wizard-field 1, choice, apSvcName( ), nodepend
	::= {apGrpDestSvcEntry 2}

apGrpDestSvcStatus OBJECT-TYPE
	SYNTAX          RowStatus
	MAX-ACCESS      read-create
	STATUS          current
	DESCRIPTION      
		"Status entry for this row "
	::= {apGrpDestSvcEntry 3}

END
