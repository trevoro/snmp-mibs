-- ****************************************************************************
--
--                         Manegeable IDE Drive
--         Management Information Base for SNMP Network Management
--
--
--      Copyright 1992,2003 Hewlett-Packard Development Company, L.P.
--      Hewlett-Packard Company shall not be liable for technical or
--      editorial errors or omissions contained herein. The information in
--      this document is provided "as is" without warranty of any kind and
--      is subject to change without notice. The warranties for HP products
--      are set forth in the express limited warranty statements
--      accompanying such products. Nothing herein should be construed as
--      constituting an additional warranty.
--
--      Confidential computer software. Valid license from HP required for
--      possession, use or copying. Consistent with FAR 12.211 and 12.212,
--      Commercial Computer Software, Computer Software Documentation, and
--      Technical Data for Commercial Items are licensed to the U.S.
--      Government under vendor's standard commercial license.
--
--      Refer to the READMIB.RDM file for more information about the
--      organization of the information in the Compaq Enterprise.
--
--      The Compaq Enterprise number is 232.
--      The ASN.1 prefix to, and including the Compaq Enterprise is:
--           1.3.6.1.4.1.232
--
-- ****************************************************************************

CPQIDE-MIB DEFINITIONS ::= BEGIN

    IMPORTS
        compaq                  FROM CPQHOST-MIB
        enterprises             FROM RFC1155-SMI
        Counter                 FROM RFC1155-SMI
        Gauge                   FROM RFC1155-SMI
        DisplayString           FROM RFC1213-MIB
        OBJECT-TYPE             FROM RFC-1212
        TRAP-TYPE               FROM RFC-1215
        sysName                 FROM RFC1213-MIB
        cpqHoTrapFlags          FROM CPQHOST-MIB;

--  compaq              OBJECT IDENTIFIER ::= { enterprises 232 }
    cpqIde              OBJECT IDENTIFIER ::= { compaq 14 }
    cpqIdeMibRev        OBJECT IDENTIFIER ::= { cpqIde 1 }
    cpqIdeComponent     OBJECT IDENTIFIER ::= { cpqIde 2 }

    cpqIdeInterface     OBJECT IDENTIFIER ::= { cpqIdeComponent 1 }
    cpqIdeIdent         OBJECT IDENTIFIER ::= { cpqIdeComponent 2 }
    cpqIdeController    OBJECT IDENTIFIER ::= { cpqIdeComponent 3 }
    cpqIdeAtaDisk       OBJECT IDENTIFIER ::= { cpqIdeComponent 4 }
    cpqIdeAtapiDevice   OBJECT IDENTIFIER ::= { cpqIdeComponent 5 }
    cpqIdeLogicalDrive  OBJECT IDENTIFIER ::= { cpqIdeComponent 6 }

    cpqIdeOsCommon      OBJECT IDENTIFIER ::= { cpqIdeInterface 4 }

-- ****************************************************************************
-- Ide MIB Revision
-- ================
--
-- The compaq enterprise               (1.3.6.1.4.1.232)
--      cpqIde Group                   (1.3.6.1.4.1.232.14)
--       cpqIdeMibRev Group            (1.3.6.1.4.1.232.14.1)
--
--
--     An Insight Agent conforming to this document will return a mibRevMajor
--     of one (1) and a mibRevMinor of six (6).
--
--
--    Implementation of the MibRev group is mandatory for all agents
--    supporting the Ide MIB.
--
-- ****************************************************************************

    cpqIdeMibRevMajor OBJECT-TYPE
       SYNTAX  INTEGER (1..65535)
       ACCESS  read-only
       STATUS  mandatory
       DESCRIPTION
           "The Major Revision level.

            A change in the major revision level represents a major change
            in the architecture of the MIB.  A change in the major revision
            level may indicate a significant change in the information
            supported and/or the meaning of the supported information,
            correct interpretation of data may require a MIB document with
            the same major revision level."
       ::= { cpqIdeMibRev 1 }

       cpqIdeMibRevMinor OBJECT-TYPE
       SYNTAX  INTEGER (0..65535)
       ACCESS  read-only
       STATUS  mandatory
       DESCRIPTION
           "The Minor Revision level.

            A change in the minor revision level may represent some minor
            additional support; no changes to any pre-existing information
            has occurred."
       ::= { cpqIdeMibRev 2 }

       cpqIdeMibCondition OBJECT-TYPE
           SYNTAX  INTEGER {
               other(1),
               ok(2),           -- default
               degraded(3),
               failed(4)
               }
           ACCESS  read-only
           STATUS  mandatory
           DESCRIPTION
               "The overall condition.

                This object represents the overall status of the Ide system
                represented by this MIB."
           ::= { cpqIdeMibRev 3 }

-- ****************************************************************************
--    Ide OS Common
--    ==============
--
-- The compaq enterprise               (1.3.6.1.4.1.232)
--      cpqIde Group                   (1.3.6.1.4.1.232.14)
--       cpqIdeComponent Group         (1.3.6.1.4.1.232.14.2)
--        cpqIdeInterface Group        (1.3.6.1.4.1.232.14.2.1)
--         cpqIdeOsCommon Group        (1.3.6.1.4.1.232.14.2.1.4)
--
--
--  The cpqIdeOsCommon group describes the Ide common OS interface.
--  This information describes the interface modules general OS interface
--  architectural information.
--
--  Implementation of the cpqIdeOsCommon group is mandatory for all
--  agents that support the Ide MIB.
--
-- ****************************************************************************

    cpqIdeOsCommonPollFreq OBJECT-TYPE
        SYNTAX  INTEGER (0..65535)
        ACCESS  read-write
        STATUS  mandatory
        DESCRIPTION
            "The Insight Agent's polling frequency.

             The frequency, in seconds, at which the Insight Agent requests
             information from the device driver.  A frequency of zero
             indicates that the Insight Agent retrieves the information upon
             request of a management station, it does not poll the device
             driver at a specific interval.

             If the poll frequency is zero (0) all attempts to write to this
             object will fail.  If the poll frequency is non-zero,
             setting this value will change the polling frequency of the
             Insight Agent.  Setting the poll frequency to zero will always
             fail, an agent may also choose to fail any request to change
             the poll frequency to a value that would severely impact system
             performance."
           ::= { cpqIdeOsCommon 1 }

-- ****************************************************************************
--    Ide OS Common Module
--    =====================
--
-- The compaq enterprise               (1.3.6.1.4.1.232)
--      cpqIde Group                   (1.3.6.1.4.1.232.14)
--       cpqIdeComponent Group         (1.3.6.1.4.1.232.14.2)
--        cpqIdeInterface Group        (1.3.6.1.4.1.232.14.2.1)
--         cpqIdeOsCommon Group        (1.3.6.1.4.1.232.14.2.1.4)
--          cpqIdeOsCommonModuleTable  (1.3.6.1.4.1.232.14.2.1.4.2) deprecated
--
-- ****************************************************************************

    cpqIdeOsCommonModuleTable OBJECT-TYPE
        SYNTAX  SEQUENCE OF CpqIdeOsCommonModuleEntry
        ACCESS  not-accessible
        STATUS  deprecated
        DESCRIPTION
            "A table of software modules that provide an interface to the
             device this MIB describes."
        ::= { cpqIdeOsCommon 2 }

    cpqIdeOsCommonModuleEntry OBJECT-TYPE
        SYNTAX  CpqIdeOsCommonModuleEntry
        ACCESS  not-accessible
        STATUS  deprecated
        DESCRIPTION
            "A description of a software modules that provide an interface
             to the device this MIB describes."
        INDEX   { cpqIdeOsCommonModuleIndex }
        ::= { cpqIdeOsCommonModuleTable 1 }

        CpqIdeOsCommonModuleEntry ::= SEQUENCE {
            cpqIdeOsCommonModuleIndex       INTEGER,
            cpqIdeOsCommonModuleName        DisplayString,
            cpqIdeOsCommonModuleVersion     DisplayString,
            cpqIdeOsCommonModuleDate        OCTET STRING,
            cpqIdeOsCommonModulePurpose     DisplayString
        }

    cpqIdeOsCommonModuleIndex OBJECT-TYPE
        SYNTAX  INTEGER (0..255)
        ACCESS  read-only
        STATUS  deprecated
        DESCRIPTION
            "A unique index for this module description."
        ::= { cpqIdeOsCommonModuleEntry 1 }

    cpqIdeOsCommonModuleName OBJECT-TYPE
        SYNTAX  DisplayString (SIZE (0..255))
        ACCESS  read-only
        STATUS  deprecated
        DESCRIPTION
            "The module name."
        ::= { cpqIdeOsCommonModuleEntry 2 }

    cpqIdeOsCommonModuleVersion OBJECT-TYPE
        SYNTAX  DisplayString (SIZE (0..5))
        ACCESS  read-only
        STATUS  deprecated
        DESCRIPTION
            "The module version in XX.YY format.

            Where XX is the major version number and YY is the minor version
            number.  This field will be a null (size 0) string if the agent
            cannot provide the module version."
        ::= { cpqIdeOsCommonModuleEntry 3 }

    cpqIdeOsCommonModuleDate OBJECT-TYPE
        SYNTAX  OCTET STRING (SIZE (7))
        ACCESS  read-only
        STATUS  deprecated
        DESCRIPTION
            "The module date.

             field  octets  contents                  range
             =====  ======  =======                  =====
               1      1-2   year                      0..65536
               2       3    month                     1..12
               3       4    day                       1..31
               4       5    hour                      0..23
               5       6    minute                    0..59
               6       7    second                    0..60
                            (use 60 for leap-second)


            This field will be set to year = 0 if the agent cannot provide
            the module date.  The hour, minute, and second field will be set
            to zero (0) if they are not relevant."
        ::= { cpqIdeOsCommonModuleEntry 4 }

    cpqIdeOsCommonModulePurpose OBJECT-TYPE
        SYNTAX  DisplayString (SIZE (0..255))
        ACCESS  read-only
        STATUS  deprecated
        DESCRIPTION
            "The purpose of the module described in this entry."
        ::= { cpqIdeOsCommonModuleEntry 5 }

-- ****************************************************************************
--    IDE Ident Group
--    ===============
--
-- The compaq enterprise               (1.3.6.1.4.1.232)
--      cpqIde Group                   (1.3.6.1.4.1.232.14)
--       cpqIdeComponent Group         (1.3.6.1.4.1.232.14.2)
--        cpqIdeIdent Group            (1.3.6.1.4.1.232.14.2.2)
--         cpqIdeIdentTable            (1.3.6.1.4.1.232.14.2.2.1)
--
--
--  The Ident group contains basic indentification information about the
--  IDE drives in the system.
--
--  Implementation of the Ident group is mandatory for all agents that
--  support the IDE MIB.
--
-- ****************************************************************************

    cpqIdeIdentTable OBJECT-TYPE
        SYNTAX  SEQUENCE OF CpqIdeIdentEntry
        ACCESS  not-accessible
        STATUS  mandatory
        DESCRIPTION
           "IDE Drive Identification Table."
        ::= { cpqIdeIdent 1 }

    cpqIdeIdentEntry OBJECT-TYPE
        SYNTAX  CpqIdeIdentEntry
        ACCESS  not-accessible
        STATUS  mandatory
        DESCRIPTION
           "IDE Identification Table Entry."
        INDEX   { cpqIdeIdentIndex }
        ::= { cpqIdeIdentTable 1 }

        CpqIdeIdentEntry ::= SEQUENCE
        {
              cpqIdeIdentIndex                INTEGER,
              cpqIdeIdentModel                DisplayString,
              cpqIdeIdentSerNum               DisplayString,
              cpqIdeIdentFWVers               DisplayString,
              cpqIdeIdentCondition            INTEGER,
              cpqIdeIdentErrorNumber          DisplayString,
              cpqIdeIdentType                 INTEGER,
              cpqIdeIdentTypeExtended         INTEGER,
              cpqIdeIdentCondition2           INTEGER,
              cpqIdeIdentStatus               INTEGER,
              cpqIdeIdentUltraAtaAvailability INTEGER
        }

    cpqIdeIdentIndex OBJECT-TYPE
        SYNTAX  INTEGER (0..65535)
        ACCESS  read-only
        STATUS  mandatory
        DESCRIPTION
            "An index that uniquely specifies each device.  For disks,
             this index value will match the value of the cpqSeFixedDiskIndex
             in the Standard Equipment MIB (CPQSTDEQ.MIB) when the same
             disk is being described.

             Each possible index value indicates a specific drive as shown in
             the table below:

                Drive Index   IDE Controller   Drive Unit
                ===========   ==============   ==========
                     0            Primary           1
                     1            Primary           2
                     2            Secondary         1
                     3            Secondary         2

             Any other index value would be implementation specific."
        ::= { cpqIdeIdentEntry 1 }

    cpqIdeIdentModel OBJECT-TYPE
        SYNTAX  DisplayString (SIZE (0..41))
        ACCESS  read-only
        STATUS  mandatory
        DESCRIPTION
           "IDE Drive Model.

            The is the drive model name and can be used for identification
            purposes."
        ::= { cpqIdeIdentEntry 2 }

    cpqIdeIdentSerNum OBJECT-TYPE
        SYNTAX  DisplayString (SIZE (0..21))
        ACCESS  read-only
        STATUS  mandatory
        DESCRIPTION
           "IDE Drive Serial Number.

            The is the drive serial number and can be used for identification
            purposes."
        ::= { cpqIdeIdentEntry 3 }

    cpqIdeIdentFWVers OBJECT-TYPE
        SYNTAX  DisplayString (SIZE (0..9))
        ACCESS  read-only
        STATUS  mandatory
        DESCRIPTION
           "IDE Firmware Version.

            This is the version of the firmware on the IDE drive.
            If the IDE drive firmware version is unavailable, then this
            string will be of length zero (0)."
        ::= { cpqIdeIdentEntry 4 }

    cpqIdeIdentCondition OBJECT-TYPE
        SYNTAX  INTEGER {
            other(1),
            ok(2),
            degraded(3),
            failed(4)
            }
        ACCESS  read-only
        STATUS  deprecated
        DESCRIPTION
           "IDE Drive Condition.

            This is the overall condition of the IDE drive.
            The following values are defined:

            other(1)
              The drive does not support drive condition monitoring.

            ok(2)
              The drive is operating normally.  No user action is required.

            degraded(3)
              The drive is degraded.  The drive may need to be replaced.

            failed(4)
              The drive has failed.  The drive should be replaced."
        ::= { cpqIdeIdentEntry 5 }

    cpqIdeIdentErrorNumber OBJECT-TYPE
        SYNTAX  DisplayString (SIZE (0..32))
        ACCESS  read-only
        STATUS  mandatory
        DESCRIPTION
           "IDE Error Number.

            This value represents the error code associated with a failing
            IDE drive."

        ::= { cpqIdeIdentEntry 6 }

    cpqIdeIdentType OBJECT-TYPE
        SYNTAX  INTEGER
        {
           other(1),
           disk(2),
           tape(3),
           printer(4),
           processor(5),
           wormDrive(6),
           cd-rom(7),
           scanner(8),
           optical(9),
           jukeBox(10),
           commDev(11)
        }
        ACCESS  read-only
        STATUS  mandatory
        DESCRIPTION
           "IDE Device Type.

            This is the type of ATAPI device.  The following types are defined:

            other(1)
              The Insight agent does not recognize this type.
              You may need to upgrade your software.

            disk(2)
              This is a direct-access device like a disk drive.

            tape(3)
              This is a sequential-access device like a tape drive.

            printer(4)
              This is a printer device.

            processor(5)
              This is a processor device.

            worm(6)
              This is a write-once, read-many times device.

            cd-rom(7)
              This is a CD or DVD device.

            scanner(8)
              This is a scanner device.

            optical(9)
              This is an optical memory device.

            jukeBox(10)
              This is a media changer device like a jukebox.

            commDev(11)
              This is a communications device like a LAN bridge."
        ::= { cpqIdeIdentEntry 7 }

    cpqIdeIdentTypeExtended OBJECT-TYPE
        SYNTAX  INTEGER
        {
           other(1),
           pdcd(2),
           removableDisk(3)
        }
        ACCESS  read-only
        STATUS  mandatory
        DESCRIPTION
           "IDE Extended Device Type.

            This is additional information about the type of IDE device.
            The following types are defined:

            other(1)
              This target does not have any extended type information.

            pdcd(2)
              This is a power-drive CD-ROM.

            removableDisk(3)
              This is a removable media disk device like a floppy drive."
        ::= { cpqIdeIdentEntry 8 }

     cpqIdeIdentCondition2 OBJECT-TYPE
        SYNTAX  INTEGER {
            other(1),
            ok(2),
            degraded(3),
            failed(4)
            }
        ACCESS  read-only
        STATUS  mandatory
        DESCRIPTION
           "IDE Drive Condition.

            This is the overall condition of the IDE drive.
            The following values are defined:

            other(1)
              The drive does not support drive condition monitoring.

            ok(2)
              The drive is operating normally.
              No user action is required.

            degraded(3)
              The drive is degraded.
              See cpqIdeIdentStatus for the appropriate action.

            failed(4)
              The drive has failed.
              See cpqIdeIdentStatus for the appropriate action."
        ::= { cpqIdeIdentEntry 9 }

     cpqIdeIdentStatus OBJECT-TYPE
        SYNTAX  INTEGER {
            other(1),
            ok(2),
            preFailureDegraded(3),
            ultraAtaDegraded(4)
            }
        ACCESS  read-only
        STATUS  mandatory
        DESCRIPTION
           "IDE Drive Satus.

            This indicates the status of the IDE drive.

            The following values are defined:

            other(1)
              The drive does not support drive status monitoring.

            ok(2)
              The drive is operating normally.  No user action is required.

            preFailureDegraded(3)
              The drive has detected that at least one pre-failure SMART
              attribute has gone out of range.  The drive may need to be
              replaced.

            ultraAtaDegraded(4)
              The Ultra ATA Integrity Monitor has detected data transmission
              errors between the hard drive and processor.  For best
              performance, move Ultra ATA devices to the primary
              controller and non Ultra ATA devices to the secondary
              controller.  If errors still persist, consider replacing the
              standard 40-conductor cable with and 80-conductor cable."
        ::= { cpqIdeIdentEntry 10 }

     cpqIdeIdentUltraAtaAvailability OBJECT-TYPE
        SYNTAX  INTEGER {
            other(1),
            noNotSupportedByDeviceAndController(2),
            noNotSupportedByDevice(3),
            noNotSupportedByController(4),
            noDisabledInSetup(5),
            yesEnabledInSetup(6)
            }
        ACCESS  read-only
        STATUS  mandatory
        DESCRIPTION
           "This describes the availability of Ultra ATA
            transfers between this device and the controller.

            The following values are defined:

            other(1)
               The agents do not support reporting this variable or the
               agent need to be upgraded.

            noNotSupportedByDeviceAndController(2),
               The device and the controller do not support Ultra ATA.

            noNotSupportedByDevice(3),
               The device does not support Ultra ATA but the controller
               does support Ultra ATA.

            noNotSupportedByController(4),
               The controller does not support Ultra ATA but the device
               does support Ultra ATA.

            NoDisabledInSetup(5),
               The device and the controller do support Ultra ATA but it
               has been disabled in F10 Setup.

            yesEnabledInSetup(6),
               The device and the controller do support Ultra ATA and it
               is enabled in F10 Setup."
        ::= { cpqIdeIdentEntry 11 }


-- ****************************************************************************
--    IDE Controller Group
--    ====================
--
-- The compaq enterprise               (1.3.6.1.4.1.232)
--      cpqIde Group                   (1.3.6.1.4.1.232.14)
--       cpqIdeComponent Group         (1.3.6.1.4.1.232.14.2)
--        cpqIdeController Group       (1.3.6.1.4.1.232.14.2.3)
--         cpqIdeControllerTable       (1.3.6.1.4.1.232.14.2.3.1)
--
--
--  The controller group contains information about the IDE controllers
--  in a system.
--
--  Implementation of the controller group is mandatory for all agents that
--  support the IDE MIB.
--
-- ****************************************************************************

    cpqIdeControllerTable OBJECT-TYPE
        SYNTAX  SEQUENCE OF CpqIdeControllerEntry
        ACCESS  not-accessible
        STATUS  mandatory
        DESCRIPTION
           "IDE Controller Table."
        ::= { cpqIdeController 1 }

    cpqIdeControllerEntry OBJECT-TYPE
        SYNTAX  CpqIdeControllerEntry
        ACCESS  not-accessible
        STATUS  mandatory
        DESCRIPTION
           "IDE Controller Table Entry."
        INDEX   { cpqIdeControllerIndex }
        ::= { cpqIdeControllerTable 1 }

        CpqIdeControllerEntry ::= SEQUENCE
        {
              cpqIdeControllerIndex             INTEGER,
              cpqIdeControllerOverallCondition  INTEGER,
              cpqIdeControllerModel             DisplayString,
              cpqIdeControllerFwRev             DisplayString,
              cpqIdeControllerSlot              INTEGER
        }

    cpqIdeControllerIndex OBJECT-TYPE
        SYNTAX  INTEGER
        ACCESS  read-only
        STATUS  mandatory
        DESCRIPTION
            "An index that uniquely identifies each controller."
        ::= { cpqIdeControllerEntry 1 }

    cpqIdeControllerOverallCondition OBJECT-TYPE
        SYNTAX  INTEGER {
            other(1),
            ok(2),
            degraded(3),
            failed(4)
            }
        ACCESS  read-only
        STATUS  mandatory
        DESCRIPTION
           "IDE Controller Overall Condition.

            This is the overall condition of the IDE controller and any
            associated devices."
        ::= { cpqIdeControllerEntry 2 }

    cpqIdeControllerModel OBJECT-TYPE
        SYNTAX  DisplayString
        ACCESS  read-only
        STATUS  mandatory
        DESCRIPTION
           "IDE Controller Model.

            The is the IDE controller model name."
        ::= { cpqIdeControllerEntry 3 }

    cpqIdeControllerFwRev OBJECT-TYPE
        SYNTAX  DisplayString
        ACCESS  read-only
        STATUS  mandatory
        DESCRIPTION
           "IDE Controller Firmware Revision.

            The is the IDE controller firmware revision."
        ::= { cpqIdeControllerEntry 4 }

    cpqIdeControllerSlot OBJECT-TYPE
        SYNTAX  INTEGER
        ACCESS  read-only
        STATUS  mandatory
        DESCRIPTION
            "IDE Controller Slot.

            This identifies the physical slot where the IDE controller
            resides in the system.  For example, if this value is three,
            the controller is located in slot three of your computer.
            If the value cannot be determined or is not applicable, the
            value is set to -1."
        ::= { cpqIdeControllerEntry 5 }


-- ****************************************************************************
--    IDE ATA Disk Group
--    ==================
--
-- The compaq enterprise               (1.3.6.1.4.1.232)
--      cpqIde Group                   (1.3.6.1.4.1.232.14)
--       cpqIdeComponent Group         (1.3.6.1.4.1.232.14.2)
--        cpqIdeAtaDisk Group          (1.3.6.1.4.1.232.14.2.4)
--         cpqIdeAtaDiskTable          (1.3.6.1.4.1.232.14.2.4.1)
--
--
--  The ATA disk group contains information about the disks attached to a
--  controller.
--
--  Implementation of the ATA disk group is mandatory for all agents that
--  support the IDE MIB.
--
-- ****************************************************************************

    cpqIdeAtaDiskTable OBJECT-TYPE
        SYNTAX  SEQUENCE OF CpqIdeAtaDiskEntry
        ACCESS  not-accessible
        STATUS  mandatory
        DESCRIPTION
           "IDE ATA Disk Table."
        ::= { cpqIdeAtaDisk 1 }

    cpqIdeAtaDiskEntry OBJECT-TYPE
        SYNTAX  CpqIdeAtaDiskEntry
        ACCESS  not-accessible
        STATUS  mandatory
        DESCRIPTION
           "IDE ATA Disk Table Entry."
        INDEX   { cpqIdeAtaDiskControllerIndex, cpqIdeAtaDiskIndex }
        ::= { cpqIdeAtaDiskTable 1 }

        CpqIdeAtaDiskEntry ::= SEQUENCE
        {
              cpqIdeAtaDiskControllerIndex      INTEGER,
              cpqIdeAtaDiskIndex                INTEGER,
              cpqIdeAtaDiskModel                DisplayString,
              cpqIdeAtaDiskFwRev                DisplayString,
              cpqIdeAtaDiskSerialNumber         DisplayString,
              cpqIdeAtaDiskStatus               INTEGER,
              cpqIdeAtaDiskCondition            INTEGER,
              cpqIdeAtaDiskCapacity             INTEGER,
              cpqIdeAtaDiskSmartEnabled         INTEGER,
              cpqIdeAtaDiskTransferMode         INTEGER,
              cpqIdeAtaDiskChannel              INTEGER,
              cpqIdeAtaDiskNumber               INTEGER,
              cpqIdeAtaDiskLogicalDriveMember   INTEGER,
              cpqIdeAtaDiskIsSpare              INTEGER,
              cpqIdeAtaDiskOsName               DisplayString
        }

    cpqIdeAtaDiskControllerIndex OBJECT-TYPE
        SYNTAX  INTEGER
        ACCESS  read-only
        STATUS  mandatory
        DESCRIPTION
            "An index that uniquely identifies each controller."
        ::= { cpqIdeAtaDiskEntry 1 }

    cpqIdeAtaDiskIndex OBJECT-TYPE
        SYNTAX  INTEGER
        ACCESS  read-only
        STATUS  mandatory
        DESCRIPTION
            "An index that uniquely identifies each disk."
        ::= { cpqIdeAtaDiskEntry 2 }

    cpqIdeAtaDiskModel OBJECT-TYPE
        SYNTAX  DisplayString
        ACCESS  read-only
        STATUS  mandatory
        DESCRIPTION
           "ATA Disk Model.

            The is the model name of the ATA disk."
        ::= { cpqIdeAtaDiskEntry 3 }

    cpqIdeAtaDiskFwRev OBJECT-TYPE
        SYNTAX  DisplayString
        ACCESS  read-only
        STATUS  mandatory
        DESCRIPTION
           "ATA Disk Firmware Revision.

            The is the firmware revision of the ATA disk."
        ::= { cpqIdeAtaDiskEntry 4 }

    cpqIdeAtaDiskSerialNumber OBJECT-TYPE
        SYNTAX  DisplayString
        ACCESS  read-only
        STATUS  mandatory
        DESCRIPTION
           "ATA Disk Serial Number.

            The is the serial number of the ATA disk."
        ::= { cpqIdeAtaDiskEntry 5 }

    cpqIdeAtaDiskStatus OBJECT-TYPE
        SYNTAX  INTEGER {
            other(1),
            ok(2),
            smartError(3),
            failed(4)
            }
        ACCESS  read-only
        STATUS  mandatory
        DESCRIPTION
           "ATA Disk Status.

            This is the status of the ATA disk."
        ::= { cpqIdeAtaDiskEntry 6 }

    cpqIdeAtaDiskCondition OBJECT-TYPE
        SYNTAX  INTEGER {
            other(1),
            ok(2),
            degraded(3),
            failed(4)
            }
        ACCESS  read-only
        STATUS  mandatory
        DESCRIPTION
           "ATA Disk Condition.

            This is the condition of the ATA disk."
        ::= { cpqIdeAtaDiskEntry 7 }

    cpqIdeAtaDiskCapacity OBJECT-TYPE
        SYNTAX  INTEGER
        ACCESS  read-only
        STATUS  mandatory
        DESCRIPTION
           "ATA Disk Capacity.

            This is the capacity of the ATA disk in megabytes."
        ::= { cpqIdeAtaDiskEntry 8 }

    cpqIdeAtaDiskSmartEnabled OBJECT-TYPE
        SYNTAX  INTEGER {
            other(1),
            true(2),
            false(3)
            }
        ACCESS  read-only
        STATUS  mandatory
        DESCRIPTION
           "ATA Disk S.M.A.R.T Enabled?

             other(1)
              The agent cannot determine the state of S.M.A.R.T. monitoring
              on this ATA disk.

             true(2)
              The ATA disk has S.M.A.R.T motitoring enabled.

             false(3)
              The ATA disk does not have S.M.A.R.T motitoring enabled."
        ::= { cpqIdeAtaDiskEntry 9 }

    cpqIdeAtaDiskTransferMode OBJECT-TYPE
        SYNTAX  INTEGER {
            other(1),
            pioMode0(2),
            pioMode1(3),
            pioMode2(4),
            pioMode3(5),
            pioMode4(6),
            dmaMode0(7),
            dmaMode1(8),
            dmaMode2(9),
            ultraDmaMode0(10),
            ultraDmaMode1(11),
            ultraDmaMode2(12),
            ultraDmaMode3(13),
            ultraDmaMode4(14),
            ultraDmaMode5(15)
            }
        ACCESS  read-only
        STATUS  mandatory
        DESCRIPTION
           "ATA Disk Transfer Mode.

             other(1)
              The agent cannot determine the transfer mode on this ATA disk.

             pioMode0(2)
              The ATA disk is using PIO mode 0.

             pioMode1(3)
              The ATA disk is using PIO mode 1.

             pioMode2(4)
              The ATA disk is using PIO mode 2.

             pioMode3(5)
              The ATA disk is using PIO mode 3.

             pioMode4(6)
              The ATA disk is using PIO mode 4.

             dmaMode0(7)
              The ATA disk is using DMA mode 0.

             dmaMode1(8)
              The ATA disk is using DMA mode 1.

             dmaMode2(9)
              The ATA disk is using DMA mode 2.

             ultraDmaMode0(10)
              The ATA disk is using Ultra DMA mode 0.

             ultraDmaMode1(11)
              The ATA disk is using Ultra DMA mode 1.

             ultraDmaMode2(12)
              The ATA disk is using Ultra DMA mode 2.

             ultraDmaMode3(13)
              The ATA disk is using Ultra DMA mode 3.

             ultraDmaMode4(14)
              The ATA disk is using Ultra DMA mode 4.

             ultraDmaMode5(15)
              The ATA disk is using Ultra DMA mode 5."
        ::= { cpqIdeAtaDiskEntry 10 }

    cpqIdeAtaDiskChannel OBJECT-TYPE
        SYNTAX  INTEGER {
            other(1),
            channel0(2),
            channel1(3)
            }
        ACCESS  read-only
        STATUS  mandatory
        DESCRIPTION
           "ATA Disk Channel.

             other(1)
              The agent cannot determine the channel to which the ATA disk
              is attached.

             channel0(2)
              The ATA disk is attached to the primary channel.

             channel1(3)
              The ATA disk is attached to the secondary channel."
        ::= { cpqIdeAtaDiskEntry 11 }

    cpqIdeAtaDiskNumber OBJECT-TYPE
        SYNTAX  INTEGER {
            other(1),
            device0(2),
            device1(3)
            }
        ACCESS  read-only
        STATUS  mandatory
        DESCRIPTION
           "ATA Disk Number.

             other(1)
              The agent cannot determine the number of the ATA disk.

             device0(2)
              The ATA disk is device 0 (master).

             device1(3)
              The ATA disk is device 1 (slave)."
        ::= { cpqIdeAtaDiskEntry 12 }

    cpqIdeAtaDiskLogicalDriveMember OBJECT-TYPE
        SYNTAX  INTEGER {
            other(1),
            true(2),
            false(3)
            }
        ACCESS  read-only
        STATUS  mandatory
        DESCRIPTION
           "Logical Drive Membership?

             other(1)
              The agent cannot determine if the ATA disk is part of a
              logical drive.

             true(2)
              The ATA disk is part of a logical drive.

             false(3)
              The ATA disk is not part of a logical drive."
        ::= { cpqIdeAtaDiskEntry 13 }

    cpqIdeAtaDiskIsSpare OBJECT-TYPE
        SYNTAX  INTEGER {
            other(1),
            true(2),
            false(3)
            }
        ACCESS  read-only
        STATUS  mandatory
        DESCRIPTION
           "ATA Disk Spare?

             other(1)
              The agent cannot if the ATA disk is a spare.

             true(2)
              The ATA disk is a spare disk.

             false(3)
              The ATA disk is not a spare disk."
        ::= { cpqIdeAtaDiskEntry 14 }

    cpqIdeAtaDiskOsName OBJECT-TYPE
        SYNTAX  DisplayString (SIZE (0..255))
        ACCESS  read-only
        STATUS  mandatory
        DESCRIPTION
            "ATA Disk OS Name.

            The OS name for this ATA disk.  This field will be a null
            (size 0) string if the agent does not support OS name or if the
            ATA disk is part of a logical drive."
        ::= { cpqIdeAtaDiskEntry 15 }


-- ****************************************************************************
--    IDE ATA Device Group
--    ====================
--
-- The compaq enterprise               (1.3.6.1.4.1.232)
--      cpqIde Group                   (1.3.6.1.4.1.232.14)
--       cpqIdeComponent Group         (1.3.6.1.4.1.232.14.2)
--        cpqIdeAtapiDevice Group      (1.3.6.1.4.1.232.14.2.5)
--         cpqIdeAtapiDeviceTable      (1.3.6.1.4.1.232.14.2.5.1)
--
--
--  The ATAPI device group contains information about ATAPI devices
--  attached to a controller.
--
--  Implementation of the ATAPI device group is mandatory for all agents
--  that support the IDE MIB.
--
-- ****************************************************************************

    cpqIdeAtapiDeviceTable OBJECT-TYPE
        SYNTAX  SEQUENCE OF CpqIdeAtapiDeviceEntry
        ACCESS  not-accessible
        STATUS  mandatory
        DESCRIPTION
           "IDE ATAPI Device Table."
        ::= { cpqIdeAtapiDevice 1 }

    cpqIdeAtapiDeviceEntry OBJECT-TYPE
        SYNTAX  CpqIdeAtapiDeviceEntry
        ACCESS  not-accessible
        STATUS  mandatory
        DESCRIPTION
           "IDE ATAPI Device Table Entry."
        INDEX   { cpqIdeAtapiDeviceControllerIndex, cpqIdeAtapiDeviceIndex }
        ::= { cpqIdeAtapiDeviceTable 1 }

        CpqIdeAtapiDeviceEntry ::= SEQUENCE
        {
              cpqIdeAtapiDeviceControllerIndex  INTEGER,
              cpqIdeAtapiDeviceIndex            INTEGER,
              cpqIdeAtapiDeviceModel            DisplayString,
              cpqIdeAtapiDeviceFwRev            DisplayString,
              cpqIdeAtapiDeviceType             INTEGER,
              cpqIdeAtapiDeviceTypeExtended     INTEGER,
              cpqIdeAtapiDeviceChannel          INTEGER,
              cpqIdeAtapiDeviceNumber           INTEGER
        }

    cpqIdeAtapiDeviceControllerIndex OBJECT-TYPE
        SYNTAX  INTEGER
        ACCESS  read-only
        STATUS  mandatory
        DESCRIPTION
            "An index that uniquely identifies each controller."
        ::= { cpqIdeAtapiDeviceEntry 1 }

    cpqIdeAtapiDeviceIndex OBJECT-TYPE
        SYNTAX  INTEGER
        ACCESS  read-only
        STATUS  mandatory
        DESCRIPTION
            "An index that uniquely identifies each ATAPI device."
        ::= { cpqIdeAtapiDeviceEntry 2 }

    cpqIdeAtapiDeviceModel OBJECT-TYPE
        SYNTAX  DisplayString
        ACCESS  read-only
        STATUS  mandatory
        DESCRIPTION
           "ATAPI Device Model.

            The is the model name of the ATAPI device."
        ::= { cpqIdeAtapiDeviceEntry 3 }

    cpqIdeAtapiDeviceFwRev OBJECT-TYPE
        SYNTAX  DisplayString
        ACCESS  read-only
        STATUS  mandatory
        DESCRIPTION
           "ATAPI Device Firmware Revision.

            The is the firmware revision of the ATAPI device."
        ::= { cpqIdeAtapiDeviceEntry 4 }

    cpqIdeAtapiDeviceType OBJECT-TYPE
        SYNTAX  INTEGER
        {
           other(1),
           disk(2),
           tape(3),
           printer(4),
           processor(5),
           wormDrive(6),
           cd-rom(7),
           scanner(8),
           optical(9),
           jukeBox(10),
           commDev(11)
        }
        ACCESS  read-only
        STATUS  mandatory
        DESCRIPTION
           "ATAPI Device Type.

            This is the type of ATAPI device.  The following types are defined:

            other(1)
              The agent does not recognize this type.
              You may need to upgrade your software.

            disk(2)
              This is a direct-access device like a disk drive.

            tape(3)
              This is a sequential-access device like a tape drive.

            printer(4)
              This is a printer device.

            processor(5)
              This is a processor device.

            worm(6)
              This is a write-once, read-many times device.

            cd-rom(7)
              This is a CD or DVD device.

            scanner(8)
              This is a scanner device.

            optical(9)
              This is an optical memory device.

            jukeBox(10)
              This is a media changer device like a jukebox.

            commDev(11)
              This is a communications device like a LAN bridge."
        ::= { cpqIdeAtapiDeviceEntry 5 }

    cpqIdeAtapiDeviceTypeExtended OBJECT-TYPE
        SYNTAX  INTEGER
        {
           other(1),
           pdcd(2),
           removableDisk(3)
        }
        ACCESS  read-only
        STATUS  mandatory
        DESCRIPTION
           "ATAPI Extended Device Type.

            This is additional information about the type of ATAPI device.
            The following types are defined:

            other(1)
              This target does not have any extended type information.

            pdcd(2)
              This is a power-drive CD-ROM.

            removableDisk(3)
              This is a removable media disk device like a floppy drive."
        ::= { cpqIdeAtapiDeviceEntry 6 }

    cpqIdeAtapiDeviceChannel OBJECT-TYPE
        SYNTAX  INTEGER {
            other(1),
            channel0(2),
            channel1(3)
            }
        ACCESS  read-only
        STATUS  mandatory
        DESCRIPTION
           "ATAPI Device Channel.

             other(1)
              The agent cannot determine the channel to which the ATAPI
              device is attached.

             channel0(2)
              The ATAPI device is attached to the primary channel.

             channel1(3)
              The ATAPI device is attached to the secondary channel."
        ::= { cpqIdeAtapiDeviceEntry 7 }

    cpqIdeAtapiDeviceNumber OBJECT-TYPE
        SYNTAX  INTEGER {
            other(1),
            device0(2),
            device1(3)
            }
        ACCESS  read-only
        STATUS  mandatory
        DESCRIPTION
           "ATAPI Device Number.

             other(1)
              The agent cannot determine the number of the ATAPI device.

             device0(2)
              The ATAPI device is device 0 (master).

             device1(3)
              The ATAPI device is device 1 (slave)."
        ::= { cpqIdeAtapiDeviceEntry 8 }


-- ****************************************************************************
--    IDE Logical Drive Group
--    =======================
--
-- The compaq enterprise               (1.3.6.1.4.1.232)
--      cpqIde Group                   (1.3.6.1.4.1.232.14)
--       cpqIdeComponent Group         (1.3.6.1.4.1.232.14.2)
--        cpqIdeLogicalDrive Group     (1.3.6.1.4.1.232.14.2.6)
--         cpqIdeLogicalDriveTable     (1.3.6.1.4.1.232.14.2.6.1)
--
--
--  The logical drive device group contains information about logical drives
--  configured on a controller.
--
--  Implementation of the logical drive group is mandatory for all agents
--  that support the IDE MIB.
--
-- ****************************************************************************

    cpqIdeLogicalDriveTable OBJECT-TYPE
        SYNTAX  SEQUENCE OF CpqIdeLogicalDriveEntry
        ACCESS  not-accessible
        STATUS  mandatory
        DESCRIPTION
           "IDE Logical Drive Table."
        ::= { cpqIdeLogicalDrive 1 }

    cpqIdeLogicalDriveEntry OBJECT-TYPE
        SYNTAX  CpqIdeLogicalDriveEntry
        ACCESS  not-accessible
        STATUS  mandatory
        DESCRIPTION
           "IDE Logical Drive Table Entry."
        INDEX   { cpqIdeLogicalDriveControllerIndex, cpqIdeLogicalDriveIndex }
        ::= { cpqIdeLogicalDriveTable 1 }

        CpqIdeLogicalDriveEntry ::= SEQUENCE
        {
              cpqIdeLogicalDriveControllerIndex INTEGER,
              cpqIdeLogicalDriveIndex           INTEGER,
              cpqIdeLogicalDriveRaidLevel       INTEGER,
              cpqIdeLogicalDriveCapacity        INTEGER,
              cpqIdeLogicalDriveStatus          INTEGER,
              cpqIdeLogicalDriveCondition       INTEGER,
              cpqIdeLogicalDriveDiskIds         OCTET STRING,
              cpqIdeLogicalDriveStripeSize      INTEGER,
              cpqIdeLogicalDriveSpareIds        OCTET STRING,
              cpqIdeLogicalDriveRebuildingDisk  INTEGER,
              cpqIdeLogicalDriveOsName          DisplayString
        }

    cpqIdeLogicalDriveControllerIndex OBJECT-TYPE
        SYNTAX  INTEGER
        ACCESS  read-only
        STATUS  mandatory
        DESCRIPTION
            "An index that uniquely identifies each controller."
        ::= { cpqIdeLogicalDriveEntry 1 }

    cpqIdeLogicalDriveIndex OBJECT-TYPE
        SYNTAX  INTEGER
        ACCESS  read-only
        STATUS  mandatory
        DESCRIPTION
            "An index that uniquely identifies each logical drive."
        ::= { cpqIdeLogicalDriveEntry 2 }

    cpqIdeLogicalDriveRaidLevel OBJECT-TYPE
        SYNTAX  INTEGER
        {
           other(1),
           raid0(2),
           raid1(3),
           raid0plus1(4)
        }
        ACCESS  read-only
        STATUS  mandatory
        DESCRIPTION
           "IDE Logical Drive RAID Level.

            The following RAID levels are defined:

            other(1)
             The agent cannot determine the RAID level of this logical drive.

            raid0(2)
             The logical drive is configured with RAID level 0.

            raid1(3)
             The logical drive is configured with RAID level 1.

            raid0plus1(4)
             The logical drive is configured with RAID level 0 plus 1."
        ::= { cpqIdeLogicalDriveEntry 3 }

    cpqIdeLogicalDriveCapacity OBJECT-TYPE
        SYNTAX  INTEGER
        ACCESS  read-only
        STATUS  mandatory
        DESCRIPTION
            "IDE Logical Drive Capacity.

            This is the capacity of the logical drive in megabytes."
        ::= { cpqIdeLogicalDriveEntry 4 }

    cpqIdeLogicalDriveStatus OBJECT-TYPE
        SYNTAX  INTEGER {
            other(1),
            ok(2),
            degraded(3),
            rebuilding(4),
            failed(5)
            }
        ACCESS  read-only
        STATUS  mandatory
        DESCRIPTION
           "IDE Logical Drive Status.

            This is the status of the logical drive.

            other(1)
             The agent cannot determine the logical drive status.

            ok(2)
             Indicates that the logical drive is in normal operation mode.

            degraded(3)
             Indicates that at least one physical drive has failed, but the
             logical drive's RAID level lets the drive continue to operate
             with no data loss.

            rebuilding(4)
             Indicates that the logical drive is rebuilding a physical drive.
             When complete, the logical drive will return to normal
             operation.

            failed(5)
             Indicates that more physical drives have failed than the RAID
             level of the logical drive can handle without data loss."
        ::= { cpqIdeLogicalDriveEntry 5 }


    cpqIdeLogicalDriveCondition OBJECT-TYPE
        SYNTAX  INTEGER {
            other(1),
            ok(2),
            degraded(3),
            failed(4)
            }
        ACCESS  read-only
        STATUS  mandatory
        DESCRIPTION
           "IDE Logical Drive Condition.

            This is the condition of the logical drive."
        ::= { cpqIdeLogicalDriveEntry 6 }

     cpqIdeLogicalDriveDiskIds OBJECT-TYPE
        SYNTAX  OCTET STRING (SIZE (0..255))
        ACCESS  read-only
        STATUS  mandatory
        DESCRIPTION
            "IDE Logical Drive Disk ID list.

            This lists the ATA disks drive IDs which are associated with this
            logical drive. These are the same IDs which can be used as
            indices into the ATA disk table (cpqIdeAtaDiskIndex). Each byte
            of the string is an index."
        ::= { cpqIdeLogicalDriveEntry 7 }

    cpqIdeLogicalDriveStripeSize OBJECT-TYPE
        SYNTAX  INTEGER
        ACCESS  read-only
        STATUS  mandatory
        DESCRIPTION
            "IDE Logical Drive Stripe Size.

            This is the stripe size in kilobytes."
        ::= { cpqIdeLogicalDriveEntry 8 }

     cpqIdeLogicalDriveSpareIds OBJECT-TYPE
        SYNTAX  OCTET STRING (SIZE (0..255))
        ACCESS  read-only
        STATUS  mandatory
        DESCRIPTION
            "IDE Logical Drive Spare ID list.

            This lists the ATA disks drive IDs which are possible spares for
            this logical drive. These are the same IDs which can be used as
            indices into the ATA disk table (cpqIdeAtaDiskIndex). Each byte
            of the string is an index."
        ::= { cpqIdeLogicalDriveEntry 9 }

    cpqIdeLogicalDriveRebuildingDisk OBJECT-TYPE
        SYNTAX  INTEGER
        ACCESS  read-only
        STATUS  mandatory
        DESCRIPTION
            "IDE Logical Drive Rebuilding Disk.

            This is the ATA disk that is in the process of rebuilding.  If no
            drive is currently rebuilding, a value of -1 will be returned."
        ::= { cpqIdeLogicalDriveEntry 10 }

    cpqIdeLogicalDriveOsName OBJECT-TYPE
        SYNTAX  DisplayString (SIZE (0..255))
        ACCESS  read-only
        STATUS  mandatory
        DESCRIPTION
            "IDE Logical Drive OS Name.

            The OS name for this logical drive.  This field will be a null
            (size 0) string if the agent does not support OS name."
        ::= { cpqIdeLogicalDriveEntry 11 }


-- ****************************************************************************
--  IDE Trap Definitions
--  ======================
--
--  The SNMP trap messages must not be bigger than 484 octets (bytes).
--
--  Trap support in an SNMP agent implementation is optional.  An SNMP
--  agent implementation may support all, some, or none of the traps.
--  If traps are supported, The user should be provided with the option of
--  disabling traps.
--
-- **************************************************************************

    cpqIdeDriveDegraded TRAP-TYPE
        ENTERPRISE compaq
        VARIABLES  { sysName, cpqHoTrapFlags, cpqIdeIdentIndex }
        DESCRIPTION
            "An IDE drive status has been set to degraded.

             User Action: The drive should be scheduled for replacement.

             Refer to the appropriate Maintenance and Service Guide for
             detailed information on a component replacement."

        --#TYPE "IDE Drive Degraded"
        --#SUMMARY "IDE drive %d has become degraded."
        --#ARGUMENTS {2}
        --#SEVERITY CRITICAL
        --#TIMEINDEX 99
        --#STATE   DEGRADED
        ::= 14001

    cpqIdeDriveOk TRAP-TYPE
        ENTERPRISE compaq
        VARIABLES  { sysName, cpqHoTrapFlags, cpqIdeIdentIndex }
        DESCRIPTION
            "An IDE drive status has been set to ok.

            User Action: None."

        --#TYPE "IDE Drive OK"
        --#SUMMARY "IDE drive %d has returned to normal operating condition."
        --#ARGUMENTS {2}
        --#SEVERITY INFORMATIONAL
        --#TIMEINDEX 99
        --#STATE OPERATIONAL
        ::= 14002

     cpqIdeDriveUltraAtaDegraded TRAP-TYPE
        ENTERPRISE compaq
        VARIABLES  { sysName, cpqHoTrapFlags, cpqIdeIdentIndex }
        DESCRIPTION
            "An IDE drive detects an excessive number of Ultra ATA
             data transmission errors between the hard drive and the
             processor.

             User Action: For best performance move Ultra ATA devices to the
             primary controller and non Ultra ATA devices to the secondary
             controller.  If errors still persist, consider replacing the
             standard 40-conductor IDE cable with an 80-conductor Ultra ATA
             cable."

        --#TYPE "IDE Drive Ultra ATA Degraded"
        --#SUMMARY "IDE drive %d has detected Ultra ATA errors."
        --#ARGUMENTS {2}
        --#SEVERITY INFORMATIONAL
        --#TIMEINDEX 99
        --#STATE   DEGRADED
        ::= 14003

    cpqIdeAtaDiskStatusChange TRAP-TYPE
        ENTERPRISE compaq
        VARIABLES  { sysName, cpqHoTrapFlags, cpqIdeAtaDiskControllerIndex,
                     cpqIdeAtaDiskIndex, cpqIdeAtaDiskModel,
                     cpqIdeAtaDiskFwRev, cpqIdeAtaDiskSerialNumber,
                     cpqIdeAtaDiskStatus, cpqIdeAtaDiskChannel,
                     cpqIdeAtaDiskNumber }
        DESCRIPTION
            "ATA Disk Status Change.

             This trap signifies that the agent has detected a change in the
             status of an ATA disk drive.  The variable cpqIdeAtaDiskStatus
             indicates the current disk drive status.

             User Action: If the physical drive status is smartError(3) or
             failed(4), replace the drive."

        --#TYPE "ATA Disk Drive Status Change"
        --#SUMMARY "Status is now %d for the ATA disk."
        --#ARGUMENTS {7}
        --#SEVERITY CRITICAL
        --#TIMEINDEX 99
        ::= 14004

    cpqIdeLogicalDriveStatusChange TRAP-TYPE
        ENTERPRISE compaq
        VARIABLES  { sysName, cpqHoTrapFlags, cpqIdeControllerModel,
                     cpqIdeControllerSlot, cpqIdeLogicalDriveControllerIndex,
                     cpqIdeLogicalDriveIndex, cpqIdeLogicalDriveStatus }
        DESCRIPTION
            "IDE Logical Drive Status Change.

             This trap signifies that the agent has detected a change in the
             status of an IDE logical drive.  The variable
             cpqIdeLogicalDriveStatus indicates the current logical drive
             status.

             User Action: If the logical drive status is failed(5), examine
             the array for failed drives that need replacement."

        --#TYPE "IDE Logical Drive Status Change"
        --#SUMMARY "Status is now %d for the IDE logical drive."
        --#ARGUMENTS {6}
        --#SEVERITY CRITICAL
        --#TIMEINDEX 99
        ::= 14005

END
