-------------------------------------------------------------------------------
-- file: CallRoutingStats.mib 
--
-- description:
--  This file contains the MIB definitions for the Call Routing Statistics area.
--
-- history:
-- $Log: 1.CallRoutingStats.mib,v $
-- Revision 1.1.1.4  2000/10/02 20:41:40  sbasinsk
-- 31A1564: Merge from ctl_kan_pm_43 to ctl
--
-- Revision 1.1.1.3  2000/10/02 20:37:45  sbasinsk
-- 31A1564: Merge from ctl_kan_pm_43 to ctl
--
-- Revision 1.1.1.2.1.2  2000/09/26 20:19:13  yfang
-- 31A1382: Changed Interger32 to Counter32 for a few mib variable tobe consistent with their definitions in the table entrie.
--
-- Revision 1.1.1.2  2000/08/14 19:45:49  ambrosep
-- 31A1425: merge from ctl_ss_pm_43 into ctl
--
-- Revision 1.1.1.1.1.2  2000/06/28 20:25:56  yfang
-- 31A1382: new file
--
--  31A1382 / 2000.03.07 / Y. Fang / Creation from V1.0 of MIBTemplate.mib.
--  31A1382 / 2000.03.29 / Y. Fang / Updated after internal review.
--  31A1382 / 2000.04.24 / Y. Fang / Updated after formal review.                                  
--  
--
--%%history-start%%
-- 
-- 
--%%history-end%%
--
-- Copyright 2000 Newbridge Networks Corporation.  All Rights Reserved
-------------------------------------------------------------------------------
NNCEXTCALLROUTINGSTATS-MIB DEFINITIONS ::= BEGIN

  IMPORTS
    MODULE-IDENTITY, OBJECT-TYPE, Integer32, Counter32 
            FROM SNMPv2-SMI
    TEXTUAL-CONVENTION 
            FROM SNMPv2-TC
    MODULE-COMPLIANCE, OBJECT-GROUP 
            FROM SNMPv2-CONF
    nncExtensions
            FROM NNCGNI0001-SMI
    NncExtIntvlStateType
            FROM NNC-INTERVAL-STATISTICS-TC-MIB;


  nncExtRoutingStats MODULE-IDENTITY
    LAST-UPDATED   "20000307000z"
    ORGANIZATION   "Newbridge Networks Corporation"
    CONTACT-INFO
                  "Newbridge Networks Corporation
                   Postal: 600 March Road
                         Kanata, Ontario
                         Canada K2K 2E6

                   Phone:  +1 613 591 3600
                   Fax:    +1 613 591 3680"
    
    DESCRIPTION
      "This MIB module contains management information for
       performance monitoring of call routing statistics.

       Seven types of statistics are provided through 30 tables.
 	Type 1: common stats for static and PNNI routing
	Type 2: static routing specific stats
	Type 3: non-border node PNNI routing per routing table stats
	Type 4:     border node PNNI routing per routing table stats
	Type 5: total stats for non-border node PNNI routing table stats
	Type 6: total stats for     border node PNNI routing table stats
	Type 7: raw stats for all stats in types 1-6.

       The statistics that are maintained are described below together with 
       their definition. For each statistic, a call identifies a setup or 
       an add party to a point to multipoint connection, as signaled by an
       entity originating the connection. A call does not include setup or 
       add party events that are generated as a result of receiving a 
       crankback during processing of the original setup or add party. For a 
       call based statistic ( e.g. PNNI Stat 2- Calls Generating an Initial 
       DTL), a call that is cranked back twice is considered as a single call, 
       and not as three calls, as opposed to an event based statistic (e.g. 
       Crankbacks Received as DTL Originator) where such a call is considered 
       as one setup and two crankbacks. Note that these routing statistics are 
       not maintained across a CallP card activity switch.

       i) Static & PNNI Routing Common Statistics: 

       1.  Number of Successfully Routed Calls Originated from Local Subscribers: 
       This statistic measures all the calls which are originated from subscribers
       at this node and are successfully routed to the called party regardless of
       whether a re-route attempt is involved. This statistic does not include 
       those calls which are originated from a local subscriber and terminated to 
       a local subscriber. It is incremented only when a call is accepted or 
       alerted by the called party.

       2. Successfully Routed Calls Transited via This Node:
       This statistic measures all the calls which are successfully routed via 
       this node. The calls are neither originated from nor terminated to a
       subscriber at this node and are successfully routed to the called party.
       This includes cases where a crankback occurred and the call was successfully 
       re-routed by this node. It is incremented only when a call is accepted 
       or alerted by the called party. 

       3.  Number of Successfully Routed Calls Terminated to Local Subscribers
       This statistic measures all the calls which are successfully terminated 
       to a subscriber at this node. This does not include a call which is 
       originated from a subscriber at this node. A terminating call is treated 
       as successful if it is accepted by the called subscriber. It is 
       incremented when the call is accepted or alerted by the local subscriber.

       4. Successfully Routed Local Calls
       This statistic measures all the calls which are originated from 
       subscribers at this node and are successfully terminated to subscribers 
       at this node. A terminating call is treated as successful if it is 
       accepted or alerted by the called subscriber.

       5. Calls Originated from Local Subscribers
       This statistic measures all the calls which are originated from 
       local subscribers or local subscriber equivalents, e.g., calls 
       originated from SPVC connections, regardless of whether the calls 
       are  successfully routed or not. This statistic includes those calls which
       are terminated to local subscribers. If a call is re-routed by 
       this node, the re-route attempts are not counted.

       6. Calls Terminated to Local  Subscribers
       This statistic measures all the calls which are terminated to a 
       local subscriber or to an SPVC endpoint on this node regardless 
       of whether the calls are successfully routed or not. This statistic 
       includes those calls which are originated from local subscribers.

       7. Local Call Attempts
       This statistic measures all the calls which are originated from 
       subscribers at this node and are terminated to subscribers at 
       this node regardless of whether the calls are successfully 
       terminated or not.

       8. Calls Cleared due to No Routing Table Entry
       This statistic measures all the calls which are cleared by this 
       node due to lack of a routing table entry that matches the called 
       party number. For static routing, this node could serve as an 
       originating node, a transiting node or a terminating node. 
       For PNNI routing, this node could serve as a DTL originator, or a 
       DTL terminator. The called party numbers and calling party numbers
       of the last N cleared calls are made available for a user to display 
       on NMTI screens.
     
       9. Crankbacks Generated by This Node
       This statistic measures all the crankbacks which are generated 
       by this node while routing calls either as a transiting node or 
       a terminating node. The crankbacks which are generated due to 
       signaling failures are not included in this statistic. The called 
       party numbers and calling party numbers plus their failure causes 
       and diagnostics of the last N cranked back calls are made available 
       for a user to display on NMTI screens.
     
       10. Failed Calls at Local Subscribers
       This statistic measures all the calls which are terminating to a 
       local subscriber and fails at this node either because, e.g., the 
       required bearer capability can not be allocated or the local 
       subscriber rejects the call. This includes a call which is 
       originated from a subscriber at this node. The called party 
       numbers and calling party numbers plus their failure causes 
       and diagnostics of the last N failed calls are made available 
       for a user to display on NMTI screens.
     
       11. Successfully Re-routed Calls
       This statistic counts all calls which were successfully setup 
       after having been re-routed at least once by this node (as a 
       result of receiving a crankback). This count is also incremented 
       for entry border nodes that successfully reroute calls. The called 
       party numbers and calling party numbers plus their failure causes 
       and diagnostics of the last N failed calls are made available for 
       a user to display on NMTI screens.
    
       12. Calls Failed in Re-routing  
       This statistic counts all calls which failed to be setup after 
       having attempted re-routing at least once by this node (as a 
       result of receiving a crankback).  This count is also incremented  
       for entry border nodes that failed to reroute calls. The called 
       party numbers and calling party numbers plus their failure causes 
       and diagnostics of the last N failed calls are made available for 
       a user to display on NMTI screens. 

      ii) Static Routing Specific Statistics:

      1. Calls Statically Routed by This Node
      This statistic measures all the calls which are statically routed 
      over an NNI by this node regardless of whether the calls are 
      successfully routed or not. If a call is cranked back and re-routed 
      by this node again, the re-route attempts are not counted.

      2. Crankbacks Received by This Node
      This statistic measures all the static routing crankbacks which are 
      received by this node either as an originating node, or as a 
      transiting node. The called party numbers and calling party numbers 
      plus their failure causes and diagnostics of the last N cranked back 
      calls are made available for a user to display on NMTI screens.

      3. Re-route Attempts
      This statistic measures the number of times static routing is used 
      to re-route calls as a result of crankbacks. This node could be 
      serving as a transiting node or an originating node. The called 
      party numbers and calling party numbers plus their failure causes 
      and diagnostics of the last N re-routed calls are made available 
      for a user to display on NMTI screens.

      4. Routing Loops Detected by This Node
      This statistic counts the number of routing loops which are detected 
      by this node. The called party numbers and calling party numbers of 
      the last N routing loops are made available for a user to display on 
      NMTI screens.

      iii) PNNI Per Routing Table Statistics:
      The following statistics are gathered for each PNNI QoS routing 
      table generated as a result of a configured PNNI Routing Table
      Descriptor. The PNNI Per Routing Table Statistics are divided 
      into two subsets: 
      a)  Non Border Node Statistics
      These statistics are relevant for calls for which this node does 
      not serve as a peer group border node. This node can serve as 
      originator, transit, or terminator for such calls.
      b)  Border Node Statistics
      These statistics are relevant for calls for which this node is a border 
      node. The node can serve as an entry border, or an exit border for 
      such calls.
      Note that a given node can increment both types of statistics, 
      depending on the role it plays for a specific call. 
     
      iiia)Non Border PNNI Per Routing Table Statistics:

      1. Failed Calls Due to Initial DTL Not Generated 
      This statistic measures the number of calls for which an initial 
      DTL could not be generated by the originating node.  
      This is the case where a routing table entry is found for the called 
      party in the routing table but a path could not be built due to 
      routing constraints (e.g. insufficient path bandwidth to the called 
      party, path cost exceeding the configured Routing Table Descriptor 
      maximum). Note that this is different from having no routing table
      entry for the called party. This statistic is not incremented in 
      crank back cases. The called party numbers and calling party 
      numbers plus their failure causes and diagnostics of the last N 
      cranked back calls are made available for the user to display on NMTI.

      2. Calls Generating an Initial DTL 
      This statistic measures the number of DTLs which are generated
      initially by this node for calls which are originated from 
      local subscribers, or from an SPVC source, or for calls which are 
      received over an NNI from outside the PNNI domain. 
      This statistic is incremented regardless of whether the calls are 
      successfully routed or not. This count does not include the DTLs 
      which are generated in order to re-route calls as a result of crankbacks.

      3. DTL Originated Calls Successfully Established Without Re-routing 
      This statistic measures the number of calls for which this node 
      is the DTL Originator which were successfully established without 
      being cranked back to this node. 
      Note that this includes the case where a call has been rerouted 
      in some other peer groups by the entry border nodes.

      4. DTL Originated Calls Successfully Re-routed 
      This statistic measures the number of calls for which this node 
      is the DTL Originator which were successfully setup after having 
      been re-routed at least once by this node (as a result of receiving 
      a crankback).  The called party numbers and calling party numbers 
      plus their failure causes and diagnostics of the last N reroute 
      attempts are made available for the user to display on NMTI.

      5. DTL Originated Calls Failed in Re-routing  
      This statistic measures the number of calls which failed to be 
      setup after having attempted re-routing at least once by this 
      node (as a result of receiving a crankback).  The called party 
      numbers and calling party numbers plus their failure causes and 
      diagnostics of the last N failed calls are made available for 
      the user to display on NMTI. 

      6. Successful Calls with Bandwidth Greater than Routing Table 
      Descriptor Minimum Bandwidth 
      This statistic measures the number of successfully established 
      calls for which this node is the DTL originator, and which were 
      routed using this routing table even though the call's requested 
      bandwidth was greater than the Routing Table Descriptor's 
      Minimum Trunk Available Bandwidth. This statistic indicates 
      that no configured Routing Table Descriptor was configured to 
      match the traffic descriptor of the call, and 
      that this routing table was the best one to attempt to route 
      the call. 

      7. Failed Calls with Bandwidth Greater than Routing Table 
      Descriptor Minimum Bandwidth
      This statistic measures the number of failed calls for which this
      node is the DTL originator, and which were routed using this 
      routing table even though the call's requested bandwidth is greater 
      than the Routing Table Descriptor's Minimum Trunk Available Bandwidth. 
      This statistic indicates that no configured Routing Table Descriptor 
      was configured to match the traffic descriptor of the call, and that 
      this routing table was the best one to attempt to route the call. 
      The called party numbers and calling party numbers plus their failure 
      causes and diagnostics of the last N failed calls are made available 
      for the user to display on NMTI. 

      8. Crankbacks Received as DTL Originator 
      This statistic measures the number of crankbacks which are received 
      by this node for calls which are originated from local subscribers 
      or from a local SPVC source or for calls which are from an NNI from 
      outside the PNNI domain. It includes the crankbacks which are received 
      on a re-route attempt. Note that a single call can receive many 
      crankbacks and hence increment this statistic multiple times. The 
      called party numbers and calling party numbers plus their failure 
      causes and diagnostics of the last N cranked back 
      calls are made available for the user to display on NMTI.

      9. DTLs Generated as DTL Originator due to Crankback 
      This statistic measures the number of DTLs which are generated by 
      this node in order to re-route a call for which this is the originating 
      node, as a result of receiving a crankback from a previous attempt to 
      route the call. This count does not include the DTL which is generated
      initially to route a call. This count specifies the number of times 
      the originating node generated DTLs for alternate paths. The called 
      party numbers and calling party numbers plus their failure causes and 
      diagnostics of the last N cranked back 
      calls are made available for the user to display on NMTI.


      iiib) Border Node PNNI Per Routing Table Statistics:
      These statistics are only relevant for border nodes, that is nodes 
      with at least one outside link crossing the peer group boundary. 
      These statistics are incremented for calls for which this node serves 
      as an entry border node or/and an exit border node.

      1. Failed calls due to initial lower level DTLs not generated
      This statistic measures the number of calls from another peer group 
      for which this node is an entry border node and for which a lower 
      level DTL could not be initially generated. This can be due to 
      different reasons, ( e.g., the destination address is not found, 
      a path to the next peer group specified in the DTL is not found, 
      insufficient path bandwidth to the called party number, ..). 
      This count is not incremented in crankback cases. The called party 
      numbers and calling party numbers plus their failure causes and 
      diagnostics of the last N calls are made available for the user to 
      display on NMTI. This statistic is equivalent to non-border node 
      statistic 1.

      2. Calls generating initial lower level DTLs 
      This statistic measures the number of calls from another peer group 
      for which this node is an entry border node,  and for which lower 
      level DTLs are generated and pushed by this node onto the received 
      DTL stack.  This statistic is incremented regardless of whether the 
      call is successful or not. This count does not include the lower 
      level DTLs that are generated as a result of crankbacks. 
      This statistic is equivalent to non-border node statistic 2.

      3. DTL generated calls successfully established, no reroute
      This statistic measures the number of calls for which this node 
      is an entry border node, which were successfully established 
      without being cranked back to this node.  This statistic is 
      equivalent to non-border node statistic 3.

      4. DTL generated calls successfully established, with reroute
      This statistic measures the number of calls for which this node 
      is an entry border node, which were successfully established after 
      being rerouted at least once by this node. The called party numbers 
      and calling party numbers plus their failure causes and diagnostics 
      of the last N calls are made available for the user to display on NMTI.
      This statistic is equivalent to non-border node statistic 4.

      5. DTL generated calls failed in rerouting
      This statistic measures the number of calls for which this node is 
      an entry border node, which failed to be established after having 
      attempted rerouting at least once by this node. In this case, a 
      crankback is generated and forwarded by this node to the previous 
      peer group. The called party numbers and calling party numbers plus 
      their failure causes and diagnostics of the last N calls are made 
      available for the user to display on NMTI. This statistic is 
      equivalent to non-border node statistic 5.

      6. Successful Calls with Bandwidth Greater than Routing Table Descriptor 
      Minimum Bandwidth 
      This statistic measures the number of successfully established 
      calls for which this node is an entry border node, and which were 
      routed using this routing table even though the call's requested 
      bandwidth was greater than the Routing Table Descriptor's Minimum 
      Trunk  Available Bandwidth. This statistic indicates that no Routing 
      Table Descriptor was configured to match the traffic descriptor of the 
      call,   and that this routing table was the best one to attempt to 
      route the call.  This statistic is equivalent to non-border node 
      statistic 6.

      7. Failed Calls with Bandwidth Greater than Routing Table Descriptor 
      Minimum Bandwidth
      This statistic measures the number of failed calls for which this node 
      is an entry border node, and which were routed using this routing table
      even though the call's requested bandwidth is greater than the Routing 
      Table Descriptor's Minimum Trunk Available Bandwidth. This statistic 
      indicates that no Routing Table Descriptor was configured to match 
      the traffic descriptor of the call, and that this routing table was 
      the best one to attempt to route the call. The called party numbers and
      calling party numbers plus their failure causes and diagnostics of the 
      last N failed calls are made available for the user to display on NMTI. 
      This statistic is equivalent to non-border node statistic 7.

      8. Crankback received as an entry border node
      This statistic measures the number of crankbacks received for calls 
      for which this node serves as an entry border node. This count is 
      incremented only for crankbacks for which this entry border node is 
      allowed to perform rerouting. This count includes the crankbacks 
      which are received on a re-route attempt. The called party numbers 
      and calling party numbers plus their failure causes and diagnostics of 
      the last N calls are made available for the user to display on NMTI. 
      This statistic is equivalent to non-border node statistic 8.

      9. Lower level DTLs generated due to received crankback
      This statistic measures the number of lower level DTLs that are 
      generated and pushed by this entry border node in order to re-route 
      a call as a result of receiving a crankback from a previous attempt 
      to route the call. This count does not include the lower level DTLs 
      that are generated initially to route the call. The called party 
      numbers and calling party numbers plus their failure causes and 
      diagnostics of the last N cranked back calls are made available 
      for the user to display on NMTI. This statistic is equivalent to 
      non-border node statistic 9. 

      iv) PNNI Routing Total Statistics:
      These statistics are totals for all QoS routing tables used to route 
      calls.One routing table is generated for each QoS Routing Table 
      Descriptor. These statistics are divided into two   subsets:
      a)  Non Border Node Statistics
      These statistics are relevant for calls for which this node does 
      not serve as a border node. This node can 
      serve as originator, transit, or terminator for such calls.
      b)  Border Node Statistics
      These statistics are relevant for calls for which this node is a 
      border node. The node can serve as an entry 
      border, or an exit border for such calls.
 
     iv a) Non Border Node PNNI Routing Total Statistics
     These statistics include an aggregate for each statistic maintained 
     per QoS  routing table,  in addition to some other PNNI statistics. 
     The statistics 1 to 9 are the total values for all QoS routing tables. 
     The statistics 10 to 12 are not maintained per routing table because 
     they do not involve a DTL Originator node where a routing table 
     lookup is required.

     1. Failed Calls due to initial DTL Not Generated
     This statistic is the total value, for all routing tables, 
     of the per routing table statistic 1 described in section 
     iii a). No diagnostic info is available for this aggregate statistic.

     2. Calls Generating an initial DTL 
     This statistic is the total value, for all routing tables, of the per 
     routing table statistic 2 described in section iii a).

     3. DTL Originated Calls successfully established without Re-routing
     This statistic is the total value, for all routing tables, of the 
     per routing table statistic 3 described in section iii a).

     4. DTL Originated Calls successfully Re-routed
     This statistic is the total value, for all routing tables, of the 
     per routing table statistic 4 described in section iii a). 
     No diagnostic info is available for this aggregate statistic.

     5. DTL Originated Calls Failed in Re-routing
     This statistic is the total value, for all routing tables, of the 
     per routing table statistic 5 described in section iii a). 
     No diagnostic info is available for this aggregate statistic.
  
    6.Successful calls with bandwidth greater than routing table 
    descriptor minimum  bandwidth
    This statistic is the total value, for all routing tables, of the per 
    routing table statistic 6 described in section iii a). 

    7.Failed calls with bandwidth greater than routing table descriptor 
    minimum bandwidth
    This statistic is the total value, for all routing tables, of 
    the per routing table statistic 7 described in section iii a).
    No diagnostic info is available for this aggregate statistic.

    8. Crankbacks Received as DTL Originator
    This statistic is the total value, for all routing tables, of the 
    per routing table statistic 8 described in section iii a).
    No diagnostic info is available for this aggregate statistic.
    Note that this statistic does not include statistic 12.

    9. DTLs Generated as DTL Originator due to Crankbacks
    This statistic is the total value, for all routing tables, of the 
    per routing table statistic 9 described in section iii a). 
    No diagnostic info is available for this aggregate statistic.
 
    10. Calls Received as Transit Node over Inside Links
    This statistic measures the number of calls received over a PNNI 
    signaling link when this node is not the DTL terminator. This node 
    serves as a PNNI transit node for such calls. Incrementing this 
    statistic does not imply that the call was forwarded to the next 
    node. Calls that fail CAC or that encounter other call 
    processing failures are counted by this statistic.

    11. Crankbacks Received as Transit Node over Inside Links
    This statistic measures the number of crankbacks which are received 
    by this node over inside links, when this node serves as a PNNI 
    transit node. This statistic does not include statistic 12, since in 
    this case the 36170 passes on the crankback without making any 
    alternate routing decisions while in the case of statistic 12,  the 
    36170 may choose a parallel trunk group to route the call on. The 
    called party numbers and calling party numbers plus their failure 
    causes and diagnostics of the last N cranked back calls are 
    made available for a user to display on NMTI screens.

    12. Succeeding End Blocked Crankbacks Received over Inside Links
    This statistic measures the number of Succeeding End Blocked PNNI 
    crankbacks received by this node over inside links, when this node 
    serves as a DTL Originator or a PNNI transit node. This count specifies 
    the number of times this node chose a trunk group to use to forward 
    a call and the succeeding node could not admit the call on this trunk group
    (e.g., due to CAC failure, no VCIs available, etc.). In this case, if 
    a parallel trunk group exists to this same succeeding node, the call 
    may be retried by this node to the succeeding node using this parallel 
    trunk group. The called party numbers and calling party numbers plus 
    their failure causes and diagnostics of the last N cranked back calls 
    are made available for a user to display on NMTI screens.

    iv b) Border Node PNNI Routing Total Statistics
    These statistics are only relevant for border nodes, that is nodes 
    with at least one outside link crossing the peer group boundary. 
    These counts are incremented for calls for which this node serves as 
    an entry border node or/and an exit border node. These statistics 
    include an aggregate for each border node statistic 
    maintained per QoS routing table, in addition to some other border 
    node statistics that are not maintained 
    per QoS routing table since no routing table lookup is required. 
    The statistics 1 to 9 are the total values for all QoS routing tables. 
    The statistics 10 to 14 are not maintained per QoS routing table.
 
    1. Failed calls due to initial lower level DTLs not generated
    This statistic is the total value, for all routing tables, of the 
    per routing table border node statistic 1 
    described in section iii b). No diagnostic info is available for this 
    aggregate statistic.

    2. Calls generating initial lower level DTLs 
    This statistic is the total value, for all routing tables, of the 
    per routing table border node statistic 2 described in section iii b).

    3. DTL generated calls successfully established, no reroute
    This statistic is the total value, for all routing tables, of the 
    per routing table border node statistic 3 described in section iii b).

    4. DTL generated calls successfully established, with reroute
    This statistic is the total value, for all routing tables, of the 
    per routing table border node statistic 4 described in section iii b). 
    No diagnostic info is available for this aggregate statistic.

    5. DTL generated calls failed in rerouting
    This statistic is the total value, for all routing tables, of the 
    per routing table border node statistic 5 described in section iii b). 
    No diagnostic info is available for this aggregate statistic.

    6. Successful Calls with Bandwidth Greater than Routing Table 
    Descriptor Minimum Bandwidth 
    This statistic is the total value, for all routing tables, of the 
    per routing table border node statistic 6 described in section iii b). 

    7. Failed Calls with Bandwidth Greater than Routing Table Descriptor 
    Minimum Bandwidth
    This statistic is the total value, for all routing tables, of the 
    per routing table border node statistic 7 described in section iii b). 
    No diagnostic info is available for this aggregate statistic.

    8. Crankback received as an entry border node
    This statistic is the total value, for all routing tables, of the 
    per routing table border node statistic 8 described in section iii b). 
    No diagnostic info is available for this aggregate statistic.

    9. Lower level DTLs generated due to received crankback
    This statistic is the total value, for all routing tables, of the 
    per routing table border node statistic 9 
    described in section iii b). No diagnostic info is available for 
    this aggregate statistic. 
 
    10. Calls received over an outside link
    This statistic measures the total number of calls received at this 
    entry border node from a node in a different peer group over an 
    outside link. This count is incremented regardless of whether the 
    call is successful or not.  

    11. Calls transmitted over an outside link
    This statistic measures the total number of calls transmitted by 
    this exit border node over an outside link 
    to a node in a different peer group. This count is incremented 
    regardless of whether the call is successful or not. 

    12. Crankback received over an outside link
    This statistic measures the number of crankbacks that are received
    at this exit border node from a node in a different peer group over 
    an outside link. This statistic does not include statistic 13 below. 
    The called party numbers and calling party numbers plus their failure 
    causes and diagnostics of the last N cranked 
    back calls are made available for the user to display on NMTI.

    13. Succeeding End Blocked crankback received over an outside link
    This statistic measures the number of succeeding end blocked crankbacks 
    received at this exit border node from a node in a different peer 
    group over an outside link. In this case, the exit border node tries to 
    reroute the call to the same neighbor peer group using a parallel trunk 
    group if one exists. The called party numbers and calling party numbers 
    plus their failure causes and diagnostics of the last N cranked back 
    calls are made available for the user to display on NMTI.

    14. Crankback forwarded to previous PG, crankback level too high
    This statistic measures the crankbacks that are passed on to the 
    previous node in a different peer group, when this entry border node 
    receives crankbacks for calls for which it did not generate any DTLs 
    of equal or higher level than the crankback level. In this case, 
    this node is not allowed to re-route the call, and the crankback 
    is forwarded unchanged to the previous peer group. The called party 
    numbers and calling party numbers plus their failure causes and 
    diagnostics of the last N cranked back calls are made available for 
    the user to display on NMTI.
   



	The call routing stats are intervalized with 15-minutes and 24-hour
   intervals. In addition to the intervals, the raw cpunter of the stats are 
   also provided. The 15-minute intervals include the current interval and 
   the last 4 intervals.The 24-hour intervals include the current interval and 
   the last 1 interval.

	All tables use one or all of the three indices, namely, 
   nncExtCallControlGroupNumber,  nncExtNBPerTbl15MinIntervalNumber,
   nncExtTableDescriptor.
   (1) nncExtCallControlGroupNumber contains information about Shelf, Slot No. etc. It uniquely identifies 
       the slot number associated with call routing stats.
   (2) nncExtNBPerTbl15MinIntervalNumber or nncExtNBPerTbl24HourIntervalNumber identifies
	at which interval the stats should be retrieved.
   (3) nncExtTableDescriptor determines a routing table number whose stats are to be displayed.
	


     "
  
  ::= { nncExtensions 78 }


    nncRoutingStatsObjects     OBJECT IDENTIFIER   ::=  { nncExtRoutingStats 1 }
--  nncRoutingStatsTraps       OBJECT IDENTIFIER   ::=  { nncExtRoutingStats 2 }
    nncRoutingStatsGroups      OBJECT IDENTIFIER   ::=  { nncExtRoutingStats 3 }
    nncRoutingStatsCompliances OBJECT IDENTIFIER   ::=  { nncExtRoutingStats 4 }


--------------------------------------------------------------------------------
-- Type Definitions
--------------------------------------------------------------------------------
-- Nil


--------------------------------------------------------------------------------
-- Object Definitions
--
-- This MIB module contains the following tables 1-30. 
-- Tables 1-24 are for stats; Table 25-30 are for raw counters

--
--  Table No. | Table name

--   1- Static and PNNI Routing Common Statistic 15 Minutes Current  Table
--   2- Static and PNNI Routing Common Statistic 15 Minutes Interval Table
--   3- Static and PNNI Routing Common Statistic 24 Hour    Current  Table
--   4- Static and PNNI Routing Common Statistic 24 Hour    Interval Table

--   5- Static Routing Specific Statistic 15 Minutes Current Table
--   6- Static Routing Specific Statistic 15 Minutes Interval Table
--   7- Static Routing Specific Statistic 24 Hour    Current Table
--   8- Static Routing Specific Statistic 24 Hour    Interval Table

--   9- Non Border Node PNNI Per Routing Table Statistics 15 Minutes Current  Table
--  10- Non Border Node PNNI Per Routing Table Statistics 15 Minutes Interval Table
--  11- Non Border Node PNNI Per Routing Table Statistics 24 Hour    Current  Table
--  12- Non Border Node PNNI Per Routing Table Statistics 24 Hour    Interval Table

--  13- Border Node PNNI Per Routing Table Statistics 15 Minutes Current  Table
--  14- Border Node PNNI Per Routing Table Statistics 15 Minutes Interval Table
--  15- Border Node PNNI Per Routing Table Statistics 24 Hour    Current  Table
--  16- Border Node PNNI Per Routing Table Statistics 24 Hour    Interval Table


--  17- Non-Border Node PNNI Total Statistics 15 Minutes Current  Table
--  18- Non-Border Node PNNI Total Statistics 15 Minutes Interval Table
--  19- Non-Border Node PNNI Total Statistics 24 Hour    Current  Table
--  20- Non-Border Node PNNI Total Statistics 24 Hour    Interval Table


--  21- Border Node PNNI Total Statistics 15 Minutes Current  Table
--  22- Border Node PNNI Total Statistics 15 Minutes Interval Table
--  23- Border Node PNNI Total Statistics 24 Hour    Current  Table
--  24- Border Node PNNI Total Statistics 24 Hour    Interval Table


--  25- Raw Counters for Static and PNNI Routing Common Statistic Table
--  26- Raw Counters for Static Routing Specific Statistic Table
--  27- Raw Counters for Non Border Node PNNI Per Routing Table Statistics Table
--  28- Raw Counters for Border Node PNNI Per Routing Table Statistics Table
--  29- Raw Counters for Non-Border Node PNNI Total Statistics Table
--  30- Raw Counters for Border Node PNNI Total Statistics Table

--
--------------------------------------------------------------------------------


--------------------------------------------------------------------------------
--  Table 1: Static and PNNI Routing Common Statistic 15 Minutes Current  Table  
--------------------------------------------------------------------------------
  nncRoutingStatsCommon15MinCurrentTable OBJECT-TYPE
    SYNTAX       SEQUENCE OF NncRoutingStatsCommon15MinCurrentEntry
    MAX-ACCESS   not-accessible
    STATUS       current
    DESCRIPTION  
    "The nncRoutingStatsCommon15MinCurrentTable contains objects for monitoring the 
     static and PNNI routing common stats during the current 15 minute interval."
  ::= { nncRoutingStatsObjects 1 }


  nncRoutingStatsCommon15MinCurrentEntry OBJECT-TYPE
    SYNTAX      NncRoutingStatsCommon15MinCurrentEntry
    MAX-ACCESS  not-accessible
    STATUS      current
    DESCRIPTION  
    "An entry in the 15 minute current statistics table. Each conceptual row
    contains current common statistics for static and PNNI routing."
    INDEX       { nncCallControlGroupNumber }
  ::= { nncRoutingStatsCommon15MinCurrentTable 1 }


  NncRoutingStatsCommon15MinCurrentEntry ::=
    SEQUENCE {
      nncCallControlGroupNumber                                         INTEGER,
      nncCommon15MinCurrentState                                     NncExtIntvlStateType,
      nncCommon15MinCurrentAbsoluteIntervalNumber                    	Integer32,
      nncCommon15MinCurrentSuccessRoutedCallsOrigFromLocalSubs       	Counter32,
      nncCommon15MinCurrentSuccessRoutedCallsTransitedViaThisNode    	Counter32,
      nncCommon15MinCurrentSuccessRoutedCallsTermToLocalSubs	        Counter32,
      nncCommon15MinCurrentSuccessRoutedLocalCalls                   	Counter32,
      nncCommon15MinCurrentCallsOrigFromLocalCalls		 	Counter32,
      nncCommon15MinCurrentCallsTermToLocalCalls			Counter32,
      nncCommon15MinCurrentLocalCallAttempts			 	Counter32,
      nncCommon15MinCurrentCallsClearedDueToNoRoutingTabEntry      	Counter32,
      nncCommon15MinCurrentCrankbacksGeneratedByThisNode		Counter32,
      nncCommon15MinCurrentFailedCallsAtLocalSubs			Counter32,
      nncCommon15MinCurrentCallsSuccessRerouted		 		Counter32,
      nncCommon15MinCurrentCallsFailedInRerouting			Counter32
    }

 nncCallControlGroupNumber         		                        OBJECT-TYPE
    SYNTAX                                          			INTEGER(1..5)
    MAX-ACCESS                                      			not-accessible
    STATUS                                          			current
    DESCRIPTION                    
    "The call control group number. The object represents one active call processing
     service card. There is a one-to-one mapping between a call control group number 
     and the set of stats associated with the call control group number."
  ::= { nncRoutingStatsCommon15MinCurrentEntry 1 }

 nncCommon15MinCurrentState         					OBJECT-TYPE
    SYNTAX                                          			NncExtIntvlStateType
    MAX-ACCESS                                      			read-only
    STATUS                                          			current
    DESCRIPTION                    
    "The state of the current interval. The object provides a status for those entries
     which have been reset by the user, or have been subject to a wall clock time change"
  ::= { nncRoutingStatsCommon15MinCurrentEntry 2 }

 nncCommon15MinCurrentAbsoluteIntervalNumber     		    	OBJECT-TYPE
    SYNTAX                                          			Counter32
    MAX-ACCESS                                      			read-only
    STATUS                                          			current
    DESCRIPTION                    
    "The absolute interval number of this interval."
  ::= { nncRoutingStatsCommon15MinCurrentEntry 3 }


  nncCommon15MinCurrentSuccessRoutedCallsOrigFromLocalSubs         	OBJECT-TYPE
    SYNTAX                                          			Counter32
    MAX-ACCESS                                      			read-only
    STATUS                                          			current
    DESCRIPTION                    
    "Number of successfully routed calls originated from local subscribers."
  ::= { nncRoutingStatsCommon15MinCurrentEntry 4 }

  nncCommon15MinCurrentSuccessRoutedCallsTransitedViaThisNode       	OBJECT-TYPE
    SYNTAX                                          			Counter32
    MAX-ACCESS                                      			read-only
    STATUS                                          			current
    DESCRIPTION                    
    "Number of successfully routed calls transited via this node."
  ::= { nncRoutingStatsCommon15MinCurrentEntry 5 }

  nncCommon15MinCurrentSuccessRoutedCallsTermToLocalSubs           	OBJECT-TYPE
    SYNTAX                                          			Counter32
    MAX-ACCESS                                      			read-only
    STATUS                                          		 	current
    DESCRIPTION                    
    "Number of successfully routed calls terminated to local subscribers."
  ::= { nncRoutingStatsCommon15MinCurrentEntry 6 }

  nncCommon15MinCurrentSuccessRoutedLocalCalls                     	OBJECT-TYPE
    SYNTAX                                          			Counter32
    MAX-ACCESS                                      			read-only
    STATUS                                          			current
    DESCRIPTION                    
    "Number of successfully routed local calls."
  ::= { nncRoutingStatsCommon15MinCurrentEntry 7 }

  nncCommon15MinCurrentCallsOrigFromLocalCalls  		        OBJECT-TYPE
    SYNTAX                                          			Counter32
    MAX-ACCESS                                      			read-only
    STATUS                                          			current
    DESCRIPTION                    
    "Number of calls originated from local calls."
  ::= { nncRoutingStatsCommon15MinCurrentEntry 8 }

  nncCommon15MinCurrentCallsTermToLocalCalls		         	OBJECT-TYPE
    SYNTAX                                          			Counter32
    MAX-ACCESS                                      			read-only
    STATUS                                          			current
    DESCRIPTION                    
    "Number of calls terminated to local subscribers."
  ::= { nncRoutingStatsCommon15MinCurrentEntry 9 }

  nncCommon15MinCurrentLocalCallAttempts 			        OBJECT-TYPE
    SYNTAX                                          			Counter32
    MAX-ACCESS                                      			read-only
    STATUS                                          			current
    DESCRIPTION                    
    "Number of local call attempts."
  ::= { nncRoutingStatsCommon15MinCurrentEntry 10 }

  nncCommon15MinCurrentCallsClearedDueToNoRoutingTabEntry          	OBJECT-TYPE
    SYNTAX                                          			Counter32
    MAX-ACCESS                                      			read-only
    STATUS                                          			current
    DESCRIPTION                    
    "Number of calls cleared due to no routing table entry."
  ::= { nncRoutingStatsCommon15MinCurrentEntry 11 }

  nncCommon15MinCurrentCrankbacksGeneratedByThisNode	         	OBJECT-TYPE
    SYNTAX                                          			Counter32
    MAX-ACCESS                                      			read-only
    STATUS                                          			current
    DESCRIPTION                    
    "Number of crankbacks generated by this node."
  ::= { nncRoutingStatsCommon15MinCurrentEntry 12 }

  nncCommon15MinCurrentFailedCallsAtLocalSubs		        	OBJECT-TYPE
    SYNTAX                                          			Counter32
    MAX-ACCESS                                      			read-only
    STATUS                                          			current
    DESCRIPTION                    
    "Number of failed calls at local subscribers."
  ::= { nncRoutingStatsCommon15MinCurrentEntry 13 }

  nncCommon15MinCurrentCallsSuccessRerouted		         	OBJECT-TYPE
    SYNTAX                                          			Counter32
    MAX-ACCESS                                      			read-only
    STATUS                                          			current
    DESCRIPTION                    
    "Number of calls successfully rerouted."
  ::= { nncRoutingStatsCommon15MinCurrentEntry 14 }

  nncCommon15MinCurrentCallsFailedInRerouting		        	OBJECT-TYPE
    SYNTAX                                          			Counter32
    MAX-ACCESS                                      			read-only
    STATUS                                          			current
    DESCRIPTION                    
    "Number of calls failed in rerouting."
  ::= { nncRoutingStatsCommon15MinCurrentEntry 15 }


--------------------------------------------------------------------------------
--  Table 2: Static and PNNI Routing Common Statistic 15 Minutes Interval Table
--------------------------------------------------------------------------------
  nncRoutingStatsCommon15MinIntervalTable OBJECT-TYPE
    SYNTAX       SEQUENCE OF NncRoutingStatsCommon15MinIntervalEntry
    MAX-ACCESS   not-accessible
    STATUS       current
    DESCRIPTION  
    "The nncRoutingStatsCommon15MinIntervalTable contains objects for monitoring the 
     static and PNNI routing common stats over a historical stratum of 15 minute intervals."
  ::= { nncRoutingStatsObjects 2 }


  nncRoutingStatsCommon15MinIntervalEntry OBJECT-TYPE
    SYNTAX      NncRoutingStatsCommon15MinIntervalEntry
    MAX-ACCESS  not-accessible
    STATUS      current
    DESCRIPTION  
    "An entry in the 15 minute interval statistics table. Each conceptual row
    contains interval common statistics for static and PNNI routing."
    INDEX       { nncCallControlGroupNumber, 
                  nncCommon15MinIntervalNumber }
  ::= { nncRoutingStatsCommon15MinIntervalTable 1 }


  NncRoutingStatsCommon15MinIntervalEntry ::=
    SEQUENCE {
      nncCommon15MinIntervalNumber					Integer32,
      nncCommon15MinIntervalState					NncExtIntvlStateType,
      nncCommon15MinIntervalAbsoluteIntervalNumber  			Integer32,
      nncCommon15MinIntervalSuccessRoutedCallsOrigFromLocalSubs     	Counter32,
      nncCommon15MinIntervalSuccessRoutedCallsTransitedViaThisNode	Counter32,
      nncCommon15MinIntervalSuccessRoutedCallsTermToLocalSubs	        Counter32,
      nncCommon15MinIntervalSuccessRoutedLocalCalls		 	Counter32,
      nncCommon15MinIntervalCallsOrigFromLocalCalls		 	Counter32,
      nncCommon15MinIntervalCallsTermToLocalCalls			Counter32,
      nncCommon15MinIntervalLocalCallAttempts		 	        Counter32,
      nncCommon15MinIntervalCallsClearedDueToNoRoutingTabEntry      	Counter32,
      nncCommon15MinIntervalCrankbacksGeneratedByThisNode		Counter32,
      nncCommon15MinIntervalFailedCallsAtLocalSubs			Counter32,
      nncCommon15MinIntervalCallsSuccessRerouted		 	Counter32,
      nncCommon15MinIntervalCallsFailedInRerouting			Counter32
    }


nncCommon15MinIntervalNumber        					OBJECT-TYPE
    SYNTAX                                          			Integer32(1..96)
    MAX-ACCESS                                      			not-accessible
    STATUS                                          			current
    DESCRIPTION                    
    "The interval number of the statistics in this row."
  ::= { nncRoutingStatsCommon15MinIntervalEntry 2 }

 nncCommon15MinIntervalState         				        OBJECT-TYPE
    SYNTAX                                          			NncExtIntvlStateType
    MAX-ACCESS                                      			read-only
    STATUS                                          			current
    DESCRIPTION                    
    "The state of the interval represented by this row. The object provides a status for those
     entries which have been reset by the user, or have been subject to a wall clock time change."
  ::= { nncRoutingStatsCommon15MinIntervalEntry 3 }

 nncCommon15MinIntervalAbsoluteIntervalNumber     		    	OBJECT-TYPE
    SYNTAX                                          			Integer32
    MAX-ACCESS                                      			read-only
    STATUS                                          			current
    DESCRIPTION                    
    "The absolute interval number of this interval."
  ::= { nncRoutingStatsCommon15MinIntervalEntry 4 }


  nncCommon15MinIntervalSuccessRoutedCallsOrigFromLocalSubs         	OBJECT-TYPE
    SYNTAX                                          			Counter32
    MAX-ACCESS                                      			read-only
    STATUS                                          			current
    DESCRIPTION                    
    "Number of successfully routed calls originated from local subscribers."
  ::= { nncRoutingStatsCommon15MinIntervalEntry 5 }

  nncCommon15MinIntervalSuccessRoutedCallsTransitedViaThisNode          OBJECT-TYPE
    SYNTAX                                          			Counter32
    MAX-ACCESS                                      			read-only
    STATUS                                          			current
    DESCRIPTION                    
    "Number of successfully routed calls transited via this node."
  ::= { nncRoutingStatsCommon15MinIntervalEntry 6 }

  nncCommon15MinIntervalSuccessRoutedCallsTermToLocalSubs           	OBJECT-TYPE
    SYNTAX                                          			Counter32
    MAX-ACCESS                                      			read-only
    STATUS                                          		 	current
    DESCRIPTION                    
    "Number of successfully routed calls terminated to local subscribers."
  ::= { nncRoutingStatsCommon15MinIntervalEntry 7 }

  nncCommon15MinIntervalSuccessRoutedLocalCalls                     	OBJECT-TYPE
    SYNTAX                                          			Counter32
    MAX-ACCESS                                      			read-only
    STATUS                                          			current
    DESCRIPTION                    
    "Number of successfully routed local calls."
  ::= { nncRoutingStatsCommon15MinIntervalEntry 8 }

  nncCommon15MinIntervalCallsOrigFromLocalCalls  		        OBJECT-TYPE
    SYNTAX                                          			Counter32
    MAX-ACCESS                                      			read-only
    STATUS                                          			current
    DESCRIPTION                    
    "Number of calls originated from local calls."
  ::= { nncRoutingStatsCommon15MinIntervalEntry 9 }

  nncCommon15MinIntervalCallsTermToLocalCalls		        	OBJECT-TYPE
    SYNTAX                                          			Counter32
    MAX-ACCESS                                      			read-only
    STATUS                                          			current
    DESCRIPTION                    
    "Number of calls terminated to local subscribers."
  ::= { nncRoutingStatsCommon15MinIntervalEntry 10 }

  nncCommon15MinIntervalLocalCallAttempts 			        OBJECT-TYPE
    SYNTAX                                          			Counter32
    MAX-ACCESS                                      			read-only
    STATUS                                          			current
    DESCRIPTION                    
    "Number of local call attempts."
  ::= { nncRoutingStatsCommon15MinIntervalEntry 11 }

  nncCommon15MinIntervalCallsClearedDueToNoRoutingTabEntry          	OBJECT-TYPE
    SYNTAX                                          			Counter32
    MAX-ACCESS                                      			read-only
    STATUS                                          			current
    DESCRIPTION                    
    "Number of calls cleared due to no routing table entry."
  ::= { nncRoutingStatsCommon15MinIntervalEntry 12 }

  nncCommon15MinIntervalCrankbacksGeneratedByThisNode	        	OBJECT-TYPE
    SYNTAX                                          			Counter32
    MAX-ACCESS                                      			read-only
    STATUS                                          			current
    DESCRIPTION                    
    "Number of crankbacks generated by this node."
  ::= { nncRoutingStatsCommon15MinIntervalEntry 13 }

  nncCommon15MinIntervalFailedCallsAtLocalSubs		        	OBJECT-TYPE
    SYNTAX                                          			Counter32
    MAX-ACCESS                                      			read-only
    STATUS                                          			current
    DESCRIPTION                    
    "Number of failed calls at local subscribers."
  ::= { nncRoutingStatsCommon15MinIntervalEntry 14 }

  nncCommon15MinIntervalCallsSuccessRerouted		         	OBJECT-TYPE
    SYNTAX                                          			Counter32
    MAX-ACCESS                                      			read-only
    STATUS                                          			current
    DESCRIPTION                    
    "Number of calls successfully rerouted."
  ::= { nncRoutingStatsCommon15MinIntervalEntry 15 }

  nncCommon15MinIntervalCallsFailedInRerouting		        	OBJECT-TYPE
    SYNTAX                                          			Counter32
    MAX-ACCESS                                      			read-only
    STATUS                                          			current
    DESCRIPTION                    
    "Number of calls failed in rerouting."
  ::= { nncRoutingStatsCommon15MinIntervalEntry 16 }


--------------------------------------------------------------------------------
--  Table 3: Static and PNNI Routing Common Statistic 24 Hour Current Table
--------------------------------------------------------------------------------
  nncRoutingStatsCommon24HourCurrentTable OBJECT-TYPE
    SYNTAX       SEQUENCE OF NncRoutingStatsCommon24HourCurrentEntry
    MAX-ACCESS   not-accessible
    STATUS       current
    DESCRIPTION  
    "The nncRoutingStatsCommon15MinCurrentTable contains objects for monitoring the 
     static and PNNI routing common stats during the current 24 hour interval."
  ::= { nncRoutingStatsObjects 3 }


  nncRoutingStatsCommon24HourCurrentEntry OBJECT-TYPE
    SYNTAX      NncRoutingStatsCommon24HourCurrentEntry
    MAX-ACCESS  not-accessible
    STATUS      current
    DESCRIPTION  
    "An entry in the 24 current statistics table. Each conceptual row
    contains current common statistics for static and PNNI routing."
    INDEX       { nncCallControlGroupNumber }
  ::= { nncRoutingStatsCommon24HourCurrentTable 1 }


  NncRoutingStatsCommon24HourCurrentEntry ::=
    SEQUENCE {
      nncCommon24HourCurrentState					NncExtIntvlStateType,
      nncCommon24HourCurrentAbsoluteIntervalNumber  			Integer32,
      nncCommon24HourCurrentSuccessRoutedCallsOrigFromLocalSubs     	Counter32,
      nncCommon24HourCurrentSuccessRoutedCallsTransitedViaThisNode	Counter32,
      nncCommon24HourCurrentSuccessRoutedCallsTermToLocalSubs		Counter32,
      nncCommon24HourCurrentSuccessRoutedLocalCalls		 	Counter32,
      nncCommon24HourCurrentCallsOrigFromLocalCalls		 	Counter32,
      nncCommon24HourCurrentCallsTermToLocalCalls			Counter32,
      nncCommon24HourCurrentLocalCallAttempts				Counter32,
      nncCommon24HourCurrentCallsClearedDueToNoRoutingTabEntry      	Counter32,
      nncCommon24HourCurrentCrankbacksGeneratedByThisNode		Counter32,
      nncCommon24HourCurrentFailedCallsAtLocalSubs			Counter32,
      nncCommon24HourCurrentCallsSuccessRerouted		 	Counter32,
      nncCommon24HourCurrentCallsFailedInRerouting			Counter32
    }

 nncCommon24HourCurrentState         					OBJECT-TYPE
    SYNTAX                                          			NncExtIntvlStateType
    MAX-ACCESS                                      			read-only
    STATUS                                          			current
    DESCRIPTION                    
    "The state of the current interval. The object provides a status for those entries
     which have been reset by the user, or have been subject to a wall clock time change"
  ::= { nncRoutingStatsCommon24HourCurrentEntry 2 }

 nncCommon24HourCurrentAbsoluteIntervalNumber     		    	OBJECT-TYPE
    SYNTAX                                          			Integer32
    MAX-ACCESS                                      			read-only
    STATUS                                          			current
    DESCRIPTION                    
    "The absolute interval number of this interval."
  ::= { nncRoutingStatsCommon24HourCurrentEntry 3 }


  nncCommon24HourCurrentSuccessRoutedCallsOrigFromLocalSubs         	OBJECT-TYPE
    SYNTAX                                          			Counter32
    MAX-ACCESS                                      			read-only
    STATUS                                          			current
    DESCRIPTION                    
    "Number of successfully routed calls originated from local subscribers."
  ::= { nncRoutingStatsCommon24HourCurrentEntry 4 }

  nncCommon24HourCurrentSuccessRoutedCallsTransitedViaThisNode          OBJECT-TYPE
    SYNTAX                                          			Counter32
    MAX-ACCESS                                      			read-only
    STATUS                                          			current
    DESCRIPTION                    
    "Number of successfully routed calls transited via this node."
  ::= { nncRoutingStatsCommon24HourCurrentEntry 5 }

  nncCommon24HourCurrentSuccessRoutedCallsTermToLocalSubs           	OBJECT-TYPE
    SYNTAX                                          			Counter32
    MAX-ACCESS                                      			read-only
    STATUS                                          		 	current
    DESCRIPTION                    
    "Number of successfully routed calls terminated to local subscribers."
  ::= { nncRoutingStatsCommon24HourCurrentEntry 6 }

  nncCommon24HourCurrentSuccessRoutedLocalCalls                     	OBJECT-TYPE
    SYNTAX                                          			Counter32
    MAX-ACCESS                                      			read-only
    STATUS                                          			current
    DESCRIPTION                    
    "Number of successfully routed local calls."
  ::= { nncRoutingStatsCommon24HourCurrentEntry 7 }

  nncCommon24HourCurrentCallsOrigFromLocalCalls  		        OBJECT-TYPE
    SYNTAX                                          			Counter32
    MAX-ACCESS                                      			read-only
    STATUS                                          			current
    DESCRIPTION                    
    "Number of calls originated from local calls."
  ::= { nncRoutingStatsCommon24HourCurrentEntry 8 }

  nncCommon24HourCurrentCallsTermToLocalCalls		        	OBJECT-TYPE
    SYNTAX                                          			Counter32
    MAX-ACCESS                                      			read-only
    STATUS                                          			current
    DESCRIPTION                    
    "Number of calls terminated to local subscribers."
  ::= { nncRoutingStatsCommon24HourCurrentEntry 9 }

  nncCommon24HourCurrentLocalCallAttempts 			        OBJECT-TYPE
    SYNTAX                                          			Counter32
    MAX-ACCESS                                      			read-only
    STATUS                                          			current
    DESCRIPTION                    
    "Number of local call attempts."
  ::= { nncRoutingStatsCommon24HourCurrentEntry 10 }

  nncCommon24HourCurrentCallsClearedDueToNoRoutingTabEntry          	OBJECT-TYPE
    SYNTAX                                          			Counter32
    MAX-ACCESS                                      			read-only
    STATUS                                          			current
    DESCRIPTION                    
    "Number of calls cleared due to no routing table entry."
  ::= { nncRoutingStatsCommon24HourCurrentEntry 11 }

  nncCommon24HourCurrentCrankbacksGeneratedByThisNode	        	OBJECT-TYPE
    SYNTAX                                          			Counter32
    MAX-ACCESS                                      			read-only
    STATUS                                          			current
    DESCRIPTION                    
    "Number of crankbacks generated by this node."
  ::= { nncRoutingStatsCommon24HourCurrentEntry 12 }

  nncCommon24HourCurrentFailedCallsAtLocalSubs		        	OBJECT-TYPE
    SYNTAX                                          			Counter32
    MAX-ACCESS                                      			read-only
    STATUS                                          			current
    DESCRIPTION                    
    "Number of failed calls at local subscribers."
  ::= { nncRoutingStatsCommon24HourCurrentEntry 13 }

  nncCommon24HourCurrentCallsSuccessRerouted		         	OBJECT-TYPE
    SYNTAX                                          			Counter32
    MAX-ACCESS                                      			read-only
    STATUS                                          			current
    DESCRIPTION                    
    "Number of calls successfully rerouted."
  ::= { nncRoutingStatsCommon24HourCurrentEntry 14 }

  nncCommon24HourCurrentCallsFailedInRerouting		        	OBJECT-TYPE
    SYNTAX                                          			Counter32
    MAX-ACCESS                                      			read-only
    STATUS                                          			current
    DESCRIPTION                    
    "Number of calls failed in rerouting."
  ::= { nncRoutingStatsCommon24HourCurrentEntry 15 }


--------------------------------------------------------------------------------
--  Table 4: Static and PNNI Routing Common Statistic 24 Hour    Interval Table
--------------------------------------------------------------------------------
  nncRoutingStatsCommon24HourIntervalTable OBJECT-TYPE
    SYNTAX       SEQUENCE OF NncRoutingStatsCommon24HourIntervalEntry
    MAX-ACCESS   not-accessible
    STATUS       current
    DESCRIPTION  
    "The nncRoutingStatsCommon24HourIntervalTable contains objects for monitoring the 
     static and PNNI routing common stats over a historical stratum of 24 hour intervals."
  ::= { nncRoutingStatsObjects 4 }


  nncRoutingStatsCommon24HourIntervalEntry OBJECT-TYPE
    SYNTAX      NncRoutingStatsCommon24HourIntervalEntry
    MAX-ACCESS  not-accessible
    STATUS      current
    DESCRIPTION  
    "An entry in the 24 hour interval statistics table. Each conceptual row
    contains interval common statistics for static and PNNI routing."
    INDEX       { nncCallControlGroupNumber,
                  nncCommon24HourIntervalNumber }
  ::= { nncRoutingStatsCommon24HourIntervalTable 1 }


  NncRoutingStatsCommon24HourIntervalEntry ::=
    SEQUENCE {
      
      nncCommon24HourIntervalNumber					Integer32,
      nncCommon24HourIntervalState					NncExtIntvlStateType,
      nncCommon24HourIntervalAbsoluteIntervalNumber  			Integer32,
      nncCommon24HourIntervalSuccessRoutedCallsOrigFromLocalSubs    	Counter32,
      nncCommon24HourIntervalSuccessRoutedCallsTransitedViaThisNode	Counter32,
      nncCommon24HourIntervalSuccessRoutedCallsTermToLocalSubs		Counter32,
      nncCommon24HourIntervalSuccessRoutedLocalCalls		 	Counter32,
      nncCommon24HourIntervalCallsOrigFromLocalCalls		 	Counter32,
      nncCommon24HourIntervalCallsTermToLocalCalls			Counter32,
      nncCommon24HourIntervalLocalCallAttempts		 		Counter32,
      nncCommon24HourIntervalCallsClearedDueToNoRoutingTabEntry      	Counter32,
      nncCommon24HourIntervalCrankbacksGeneratedByThisNode		Counter32,
      nncCommon24HourIntervalFailedCallsAtLocalSubs			Counter32,
      nncCommon24HourIntervalCallsSuccessRerouted		 	Counter32,
      nncCommon24HourIntervalCallsFailedInRerouting			Counter32
    }


 
nncCommon24HourIntervalNumber        					OBJECT-TYPE
    SYNTAX                                          			Integer32
    MAX-ACCESS                                      			not-accessible
    STATUS                                          			current
    DESCRIPTION                    
    "The interval number of the statistics in this row."
  ::= { nncRoutingStatsCommon24HourIntervalEntry 2 }

 nncCommon24HourIntervalState         					OBJECT-TYPE
    SYNTAX                                          			NncExtIntvlStateType
    MAX-ACCESS                                      			read-only
    STATUS                                          			current
    DESCRIPTION                    
    "The state of the interval represented by this row. The object provides a status for those
     entries which have been reset by the user, or have been subject to a wall clock time change."
  ::= { nncRoutingStatsCommon24HourIntervalEntry 3 }

 nncCommon24HourIntervalAbsoluteIntervalNumber     		    	OBJECT-TYPE
    SYNTAX                                          			Integer32
    MAX-ACCESS                                      			read-only
    STATUS                                          			current
    DESCRIPTION                    
    "The absolute interval number of this interval."
  ::= { nncRoutingStatsCommon24HourIntervalEntry 4 }


  nncCommon24HourIntervalSuccessRoutedCallsOrigFromLocalSubs         	OBJECT-TYPE
    SYNTAX                                          			Counter32
    MAX-ACCESS                                      			read-only
    STATUS                                          			current
    DESCRIPTION                    
    "Number of successfully routed calls originated from local subscribers."
  ::= { nncRoutingStatsCommon24HourIntervalEntry 5 }

  nncCommon24HourIntervalSuccessRoutedCallsTransitedViaThisNode      	OBJECT-TYPE
    SYNTAX                                          			Counter32
    MAX-ACCESS                                      			read-only
    STATUS                                          			current
    DESCRIPTION                    
    "Number of successfully routed calls transited via this node."
  ::= { nncRoutingStatsCommon24HourIntervalEntry 6 }

  nncCommon24HourIntervalSuccessRoutedCallsTermToLocalSubs           	OBJECT-TYPE
    SYNTAX                                          			Counter32
    MAX-ACCESS                                      			read-only
    STATUS                                          		 	current
    DESCRIPTION                    
    "Number of successfully routed calls terminated to local subscribers."
  ::= { nncRoutingStatsCommon24HourIntervalEntry 7 }

  nncCommon24HourIntervalSuccessRoutedLocalCalls                     	OBJECT-TYPE
    SYNTAX                                          			Counter32
    MAX-ACCESS                                      			read-only
    STATUS                                          			current
    DESCRIPTION                    
    "Number of successfully routed local calls."
  ::= { nncRoutingStatsCommon24HourIntervalEntry 8 }

  nncCommon24HourIntervalCallsOrigFromLocalCalls  		        OBJECT-TYPE
    SYNTAX                                          			Counter32
    MAX-ACCESS                                      			read-only
    STATUS                                          			current
    DESCRIPTION                    
    "Number of calls originated from local calls."
  ::= { nncRoutingStatsCommon24HourIntervalEntry 9 }

  nncCommon24HourIntervalCallsTermToLocalCalls		        	OBJECT-TYPE
    SYNTAX                                          			Counter32
    MAX-ACCESS                                      			read-only
    STATUS                                          			current
    DESCRIPTION                    
    "Number of calls terminated to local subscribers."
  ::= { nncRoutingStatsCommon24HourIntervalEntry 10 }

  nncCommon24HourIntervalLocalCallAttempts 			        OBJECT-TYPE
    SYNTAX                                          			Counter32
    MAX-ACCESS                                      			read-only
    STATUS                                          			current
    DESCRIPTION                    
    "Number of local call attempts."
  ::= { nncRoutingStatsCommon24HourIntervalEntry 11 }

  nncCommon24HourIntervalCallsClearedDueToNoRoutingTabEntry          	OBJECT-TYPE
    SYNTAX                                          			Counter32
    MAX-ACCESS                                      			read-only
    STATUS                                          			current
    DESCRIPTION                    
    "Number of calls cleared due to no routing table entry."
  ::= { nncRoutingStatsCommon24HourIntervalEntry 12 }

  nncCommon24HourIntervalCrankbacksGeneratedByThisNode	        	OBJECT-TYPE
    SYNTAX                                          			Counter32
    MAX-ACCESS                                      			read-only
    STATUS                                          			current
    DESCRIPTION                    
    "Number of crankbacks generated by this node."
  ::= { nncRoutingStatsCommon24HourIntervalEntry 13 }

  nncCommon24HourIntervalFailedCallsAtLocalSubs		        	OBJECT-TYPE
    SYNTAX                                          			Counter32
    MAX-ACCESS                                      			read-only
    STATUS                                          			current
    DESCRIPTION                    
    "Number of failed calls at local subscribers."
  ::= { nncRoutingStatsCommon24HourIntervalEntry 14 }

  nncCommon24HourIntervalCallsSuccessRerouted		        	OBJECT-TYPE
    SYNTAX                                          			Counter32
    MAX-ACCESS                                      			read-only
    STATUS                                          			current
    DESCRIPTION                    
    "Number of calls successfully rerouted."
  ::= { nncRoutingStatsCommon24HourIntervalEntry 15 }

  nncCommon24HourIntervalCallsFailedInRerouting		        	OBJECT-TYPE
    SYNTAX                                          			Counter32
    MAX-ACCESS                                      			read-only
    STATUS                                          			current
    DESCRIPTION                    
    "Number of calls failed in rerouting."
  ::= { nncRoutingStatsCommon24HourIntervalEntry 16 }


---------------------------------------------------------------------------------------
--  Table 5: Static Routing Specific Statistic 15 Minutes Current Table
---------------------------------------------------------------------------------------
  nncRoutingStatsSpecific15MinCurrentTable OBJECT-TYPE
    SYNTAX       SEQUENCE OF NncRoutingStatsSpecific15MinCurrentEntry
    MAX-ACCESS   not-accessible
    STATUS       current
    DESCRIPTION  
    "The nncRoutingStatsSpecific15MinCurrentTable contains objects for monitoring the 
     static routing specific stats during the current 15 minute interval."
  ::= { nncRoutingStatsObjects 5 }


  nncRoutingStatsSpecific15MinCurrentEntry OBJECT-TYPE
    SYNTAX      NncRoutingStatsSpecific15MinCurrentEntry
    MAX-ACCESS  not-accessible
    STATUS      current
    DESCRIPTION  
    "An entry in the 15 minute current statistics table. Each conceptual row
    contains current static routing specific statistics."
    INDEX       { nncCallControlGroupNumber }
  ::= { nncRoutingStatsSpecific15MinCurrentTable 1 }


  NncRoutingStatsSpecific15MinCurrentEntry ::=
    SEQUENCE {
      
      nncSpecific15MinCurrentState					NncExtIntvlStateType,
      nncSpecific15MinCurrentAbsoluteIntervalNumber  			Integer32,
      nncSpecific15MinCurrentCallsStaticallyRoutedByThisNode     	Counter32,
      nncSpecific15MinCurrentCrankbacksReceivedByThisNode		Counter32,
      nncSpecific15MinCurrentRerouteAttempts			 	Counter32,
      nncSpecific15MinCurrentRoutingLoopsDetectedByThisNode		Counter32
  }

 
 nncSpecific15MinCurrentState         					OBJECT-TYPE
    SYNTAX                                          			NncExtIntvlStateType
    MAX-ACCESS                                      			read-only
    STATUS                                          			current
    DESCRIPTION                    
    "The state of the interval represented by this row. The object provides a status for those
     entries which have been reset by the user, or have been subject to a wall clock time change."
  ::= { nncRoutingStatsSpecific15MinCurrentEntry 2 }

 nncSpecific15MinCurrentAbsoluteIntervalNumber     		    	OBJECT-TYPE
    SYNTAX                                          			Integer32
    MAX-ACCESS                                      			read-only
    STATUS                                          			current
    DESCRIPTION                    
    "The absolute interval number of this interval."
  ::= { nncRoutingStatsSpecific15MinCurrentEntry 3 }


  nncSpecific15MinCurrentCallsStaticallyRoutedByThisNode         	OBJECT-TYPE
    SYNTAX                                          			Counter32
    MAX-ACCESS                                      			read-only
    STATUS                                          			current
    DESCRIPTION                    
    "The number of calls statically routed by this node."
  ::= { nncRoutingStatsSpecific15MinCurrentEntry 4 }

  nncSpecific15MinCurrentCrankbacksReceivedByThisNode	       		OBJECT-TYPE
    SYNTAX                                          			Counter32
    MAX-ACCESS                                      			read-only
    STATUS                                          			current
    DESCRIPTION                    
    "The number ofcrankbacks received by this node."
  ::= { nncRoutingStatsSpecific15MinCurrentEntry 5 }

nncSpecific15MinCurrentRerouteAttempts		         		OBJECT-TYPE
    SYNTAX                                          			Counter32
    MAX-ACCESS                                      			read-only
    STATUS                                          			current
    DESCRIPTION                    
    "The number of rerouted attempts."
  ::= { nncRoutingStatsSpecific15MinCurrentEntry 6 }

  nncSpecific15MinCurrentRoutingLoopsDetectedByThisNode       		OBJECT-TYPE
    SYNTAX                                          			Counter32
    MAX-ACCESS                                      			read-only
    STATUS                                          			current
    DESCRIPTION                    
    "The number of routing loops detected by this node."
  ::= { nncRoutingStatsSpecific15MinCurrentEntry 7 }


---------------------------------------------------------------------------------------
--  Table 6: Static Routing Specific Statistic 15 Minutes Interval Table
---------------------------------------------------------------------------------------
  nncRoutingStatsSpecific15MinIntervalTable OBJECT-TYPE
    SYNTAX       SEQUENCE OF NncRoutingStatsSpecific15MinIntervalEntry
    MAX-ACCESS   not-accessible
    STATUS       current
    DESCRIPTION  
    "The nncRoutingStatsSpecific15MinCurrentTable contains objects for monitoring the 
     static routing specific stats over a 15 minute interval."
  ::= { nncRoutingStatsObjects 6 }


  nncRoutingStatsSpecific15MinIntervalEntry OBJECT-TYPE
    SYNTAX      NncRoutingStatsSpecific15MinIntervalEntry
    MAX-ACCESS  not-accessible
    STATUS      current
    DESCRIPTION  
    "An entry in the 15 minute inteval statistics table. Each conceptual row
    contains interval statisticst for static routing specific statistics."
    INDEX       { nncCallControlGroupNumber,
                  nncSpecific15MinIntervalNumber }
  ::= { nncRoutingStatsSpecific15MinIntervalTable 1 }


  NncRoutingStatsSpecific15MinIntervalEntry ::=
    SEQUENCE {
     
      nncSpecific15MinIntervalNumber					Integer32,
      nncSpecific15MinIntervalState					NncExtIntvlStateType,
      nncSpecific15MinIntervalAbsoluteIntervalNumber  			Integer32,
      nncSpecific15MinIntervalCallsStaticallyRoutedByThisNode     	Counter32,
      nncSpecific15MinIntervalCrankbacksReceivedByThisNode		Counter32,
      nncSpecific15MinIntervalRerouteAttempts				Counter32,
      nncSpecific15MinIntervalRoutingLoopsDetectedByThisNode		Counter32
  }


 nncSpecific15MinIntervalNumber						OBJECT-TYPE
    SYNTAX                                         			Integer32(1..96)
    MAX-ACCESS                                      			not-accessible
    STATUS                                          			current
    DESCRIPTION                    
    "The interval number of the statistics in this row."
  ::= { nncRoutingStatsSpecific15MinIntervalEntry 2 }

 nncSpecific15MinIntervalState         					OBJECT-TYPE
    SYNTAX                                          			NncExtIntvlStateType
    MAX-ACCESS                                      			read-only
    STATUS                                          			current
    DESCRIPTION                    
    "The state of the interval represented by this row. The object provides a status for those
     entries which have been reset by the user, or have been subject to a wall clock time change."
  ::= { nncRoutingStatsSpecific15MinIntervalEntry 3 }

 nncSpecific15MinIntervalAbsoluteIntervalNumber     		    	OBJECT-TYPE
    SYNTAX                                          			Integer32
    MAX-ACCESS                                      			read-only
    STATUS                                          			current
    DESCRIPTION                    
    "The absolute interval number of this interval."
  ::= { nncRoutingStatsSpecific15MinIntervalEntry 4 }


  nncSpecific15MinIntervalCallsStaticallyRoutedByThisNode         	OBJECT-TYPE
    SYNTAX                                          			Counter32
    MAX-ACCESS                                      			read-only
    STATUS                                          			current
    DESCRIPTION                    
    "The number of calls statically routed by this node."
  ::= { nncRoutingStatsSpecific15MinIntervalEntry 5 }

  nncSpecific15MinIntervalCrankbacksReceivedByThisNode	       		OBJECT-TYPE
    SYNTAX                                          			Counter32
    MAX-ACCESS                                      			read-only
    STATUS                                          			current
    DESCRIPTION                    
    "The number ofcrankbacks received by this node."
  ::= { nncRoutingStatsSpecific15MinIntervalEntry 6 }

nncSpecific15MinIntervalRerouteAttempts		         		OBJECT-TYPE
    SYNTAX                                          			Counter32
    MAX-ACCESS                                      			read-only
    STATUS                                          			current
    DESCRIPTION                    
    "The number of rerouted attempts."
  ::= { nncRoutingStatsSpecific15MinIntervalEntry 7 }

  nncSpecific15MinIntervalRoutingLoopsDetectedByThisNode       		OBJECT-TYPE
    SYNTAX                                          			Counter32
    MAX-ACCESS                                      			read-only
    STATUS                                          			current
    DESCRIPTION                    
    "The number of routing loops detected by this node."
  ::= { nncRoutingStatsSpecific15MinIntervalEntry 8 }


---------------------------------------------------------------------------------------
--  Table 7: Static Routing Specific Statistic 24 Hour Current Table
---------------------------------------------------------------------------------------
  nncRoutingStatsSpecific24HourCurrentTable OBJECT-TYPE
    SYNTAX       SEQUENCE OF NncRoutingStatsSpecific24HourCurrentEntry
    MAX-ACCESS   not-accessible
    STATUS       current
    DESCRIPTION  
    "The nncRoutingStatsSpecific15MinCurrentTable contains objects for monitoring the 
     static routing specific stats during the current 24 hour interval."
  ::= { nncRoutingStatsObjects 7 }


  nncRoutingStatsSpecific24HourCurrentEntry OBJECT-TYPE
    SYNTAX      NncRoutingStatsSpecific24HourCurrentEntry
    MAX-ACCESS  not-accessible
    STATUS      current
    DESCRIPTION  
    "An entry in the 24 hour current statistics table. Each conceptual row
    contains current static routing specific statistics."
    INDEX       { nncCallControlGroupNumber }
  ::= { nncRoutingStatsSpecific24HourCurrentTable 1 }


  NncRoutingStatsSpecific24HourCurrentEntry ::=
    SEQUENCE {
      
      nncSpecific24HourCurrentState					NncExtIntvlStateType,
      nncSpecific24HourCurrentAbsoluteIntervalNumber  			Integer32,
      nncSpecific24HourCurrentCallsStaticallyRoutedByThisNode     	Counter32,
      nncSpecific24HourCurrentCrankbacksReceivedByThisNode		Counter32,
      nncSpecific24HourCurrentRerouteAttempts				Counter32,
      nncSpecific24HourCurrentRoutingLoopsDetectedByThisNode		Counter32
  }

 

 nncSpecific24HourCurrentState         					OBJECT-TYPE
    SYNTAX                                          			NncExtIntvlStateType
    MAX-ACCESS                                      			read-only
    STATUS                                          			current
    DESCRIPTION                    
    "The state of the interval represented by this row. The object provides a status for those
     entries which have been reset by the user, or have been subject to a wall clock time change."
  ::= { nncRoutingStatsSpecific24HourCurrentEntry 2 }

 nncSpecific24HourCurrentAbsoluteIntervalNumber     		    	OBJECT-TYPE
    SYNTAX                                          			Integer32
    MAX-ACCESS                                      			read-only
    STATUS                                          			current
    DESCRIPTION                    
    "The absolute interval number of this interval."
  ::= { nncRoutingStatsSpecific24HourCurrentEntry 3 }


  nncSpecific24HourCurrentCallsStaticallyRoutedByThisNode         	OBJECT-TYPE
    SYNTAX                                          			Counter32
    MAX-ACCESS                                      			read-only
    STATUS                                          			current
    DESCRIPTION                    
    "The number of calls statically routed by this node."
  ::= { nncRoutingStatsSpecific24HourCurrentEntry 4 }

  nncSpecific24HourCurrentCrankbacksReceivedByThisNode	       		OBJECT-TYPE
    SYNTAX                                          			Counter32
    MAX-ACCESS                                      			read-only
    STATUS                                          			current
    DESCRIPTION                    
    "The number ofcrankbacks received by this node."
  ::= { nncRoutingStatsSpecific24HourCurrentEntry 5 }

nncSpecific24HourCurrentRerouteAttempts		         		OBJECT-TYPE
    SYNTAX                                          			Counter32
    MAX-ACCESS                                      			read-only
    STATUS                                          			current
    DESCRIPTION                    
    "The number of rerouted attempts."
  ::= { nncRoutingStatsSpecific24HourCurrentEntry 6 }

  nncSpecific24HourCurrentRoutingLoopsDetectedByThisNode       		OBJECT-TYPE
    SYNTAX                                          			Counter32
    MAX-ACCESS                                      			read-only
    STATUS                                          			current
    DESCRIPTION                    
    "The number of routing loops detected by this node."
  ::= { nncRoutingStatsSpecific24HourCurrentEntry 7 }


---------------------------------------------------------------------------------------
--  Table 8: Static Routing Specific Statistic 24 hour Interval Table
---------------------------------------------------------------------------------------
  nncRoutingStatsSpecific24HourIntervalTable OBJECT-TYPE
    SYNTAX       SEQUENCE OF NncRoutingStatsSpecific24HourIntervalEntry
    MAX-ACCESS   not-accessible
    STATUS       current
    DESCRIPTION  
    "The nncRoutingStatsSpecific24HourCurrentTable contains objects for monitoring the 
     static routing specific stats during the current 24 hour interval."
  ::= { nncRoutingStatsObjects 8 }


  nncRoutingStatsSpecific24HourIntervalEntry OBJECT-TYPE
    SYNTAX      NncRoutingStatsSpecific24HourIntervalEntry
    MAX-ACCESS  not-accessible
    STATUS      current
    DESCRIPTION  
    "An entry in the 24 hour interval statistics table. Each conceptual row
    contains current static routing specific statistics."
    INDEX       { nncCallControlGroupNumber,
                  nncSpecific24HourIntervalNumber }
  ::= { nncRoutingStatsSpecific24HourIntervalTable 1 }


  NncRoutingStatsSpecific24HourIntervalEntry ::=
    SEQUENCE {
      
      nncSpecific24HourIntervalNumber					Integer32,
      nncSpecific24HourIntervalState					NncExtIntvlStateType,
      nncSpecific24HourIntervalAbsoluteIntervalNumber  			Integer32,
      nncSpecific24HourIntervalCallsStaticallyRoutedByThisNode     	Counter32,
      nncSpecific24HourIntervalCrankbacksReceivedByThisNode		Counter32,
      nncSpecific24HourIntervalRerouteAttempts		 		Counter32,
      nncSpecific24HourIntervalRoutingLoopsDetectedByThisNode		Counter32
  }

 


  nncSpecific24HourIntervalNumber					OBJECT-TYPE
    SYNTAX                                         			Integer32
    MAX-ACCESS                                      			not-accessible
    STATUS                                          			current
    DESCRIPTION                    
    "The interval number of the statistics in this row."
  ::= { nncRoutingStatsSpecific24HourIntervalEntry 2 }

 nncSpecific24HourIntervalState         				OBJECT-TYPE
    SYNTAX                                          			NncExtIntvlStateType
    MAX-ACCESS                                      			read-only
    STATUS                                          			current
    DESCRIPTION                    
    "The state of the interval represented by this row. The object provides a status for those
     entries which have been reset by the user, or have been subject to a wall clock time change."
  ::= { nncRoutingStatsSpecific24HourIntervalEntry 3 }

 nncSpecific24HourIntervalAbsoluteIntervalNumber     			OBJECT-TYPE
    SYNTAX                                          			Integer32
    MAX-ACCESS                                      			read-only
    STATUS                                          			current
    DESCRIPTION                    
    "The absolute interval number of this interval."
  ::= { nncRoutingStatsSpecific24HourIntervalEntry 4 }


  nncSpecific24HourIntervalCallsStaticallyRoutedByThisNode         	OBJECT-TYPE
    SYNTAX                                          			Counter32
    MAX-ACCESS                                      			read-only
    STATUS                                          			current
    DESCRIPTION                    
    "The number of calls statically routed by this node."
  ::= { nncRoutingStatsSpecific24HourIntervalEntry 5 }

  nncSpecific24HourIntervalCrankbacksReceivedByThisNode	       		OBJECT-TYPE
    SYNTAX                                          			Counter32
    MAX-ACCESS                                      			read-only
    STATUS                                          			current
    DESCRIPTION                    
    "The number ofcrankbacks received by this node."
  ::= { nncRoutingStatsSpecific24HourIntervalEntry 6 }

nncSpecific24HourIntervalRerouteAttempts		         	OBJECT-TYPE
    SYNTAX                                          			Counter32
    MAX-ACCESS                                      			read-only
    STATUS                                          			current
    DESCRIPTION                    
    "The number of rerouted attempts."
  ::= { nncRoutingStatsSpecific24HourIntervalEntry 7 }

  nncSpecific24HourIntervalRoutingLoopsDetectedByThisNode       	OBJECT-TYPE
    SYNTAX                                          			Counter32
    MAX-ACCESS                                      			read-only
    STATUS                                          			current
    DESCRIPTION                    
    "The number of routing loops detected by this node."
  ::= { nncRoutingStatsSpecific24HourIntervalEntry 8 }


---------------------------------------------------------------------------------------
--  Table 9: Non Border Node PNNI Per Routing Table Statistics 15 Minutes Current Table
---------------------------------------------------------------------------------------
  nncRoutingStatsNonBorderPerTbl15MinCurrentTable OBJECT-TYPE
    SYNTAX       SEQUENCE OF NncRoutingStatsNonBorderPerTbl15MinCurrentEntry
    MAX-ACCESS   not-accessible
    STATUS       current
    DESCRIPTION  
    "The nncRoutingStatsNonBorderPerTbl15MinCurrentTable contains objects for monitoring the 
     non-border node PNNI routing per routing table stats during the current 15 minute interval."
  ::= { nncRoutingStatsObjects 9 }


  nncRoutingStatsNonBorderPerTbl15MinCurrentEntry OBJECT-TYPE
    SYNTAX      NncRoutingStatsNonBorderPerTbl15MinCurrentEntry
    MAX-ACCESS  not-accessible
    STATUS      current
    DESCRIPTION  
    "An entry in the 15 minute current statistics table. Each conceptual row
    contains current statistics for the non-border node PNNI routing per routing table."
    INDEX       { nncCallControlGroupNumber,
                  nncNBPerTbl15MinCurrentTableDescriptor }
  ::= { nncRoutingStatsNonBorderPerTbl15MinCurrentTable 1 }


  NncRoutingStatsNonBorderPerTbl15MinCurrentEntry ::=
    SEQUENCE {
      
      nncNBPerTbl15MinCurrentTableDescriptor				INTEGER,
      nncNBPerTbl15MinCurrentState					NncExtIntvlStateType,
      nncNBPerTbl15MinCurrentAbsoluteIntervalNumber  			Integer32,
      nncNBPerTbl15MinCurrentFailedCallsDueToInitDTLNotGenerated	Counter32,
      nncNBPerTbl15MinCurrentCallsGeneratingAnInitDTL		        Counter32,
      nncNBPerTble15MinCurrentDTLOrigCallsSuccessEstWithoutReroute	Counter32,
      nncNBPerTbl15MinCurrentDTLOrigCallsSuccessEstWithReroute	        Counter32,
      nncNBPerTbl15MinCurrentDTLOrigCallsFailedInReRouting		Counter32,
      nncNBPerTbl15MinCurrentSuccessCallsBdwGreaterThanRTDMinBdw	Counter32,
      nncNBPerTbl15MinCurrentFailedCallsBdwGreaterThanRTDMinBdw	        Counter32,
      nncNBPerTbl15MinCurrentCrankbackReceivedAsDTLOriginator	        Counter32,
      nncNBPerTbl15MinCurrentDTLsGeneratedDueToCrankback		Counter32
    }

 

 nncNBPerTbl15MinCurrentTableDescriptor	         		        OBJECT-TYPE
    SYNTAX                                          			INTEGER(0..6)
    MAX-ACCESS                                      			not-accessible
    STATUS                                          			current
    DESCRIPTION                    
    "nncTableDescriptor determines a routing table number whose stats are to be displayed."
  ::= { nncRoutingStatsNonBorderPerTbl15MinCurrentEntry 2 }

 nncNBPerTbl15MinCurrentState		     		    	        OBJECT-TYPE
    SYNTAX                                          			NncExtIntvlStateType
    MAX-ACCESS                                      			read-only
    STATUS                                          			current
    DESCRIPTION                    
    "The state of the current interval. The object provides a status for those entries
     which have been reset by the user, or have been subject to a wall clock time change."
  ::= { nncRoutingStatsNonBorderPerTbl15MinCurrentEntry 3 }

  nncNBPerTbl15MinCurrentAbsoluteIntervalNumber				OBJECT-TYPE
    SYNTAX                                         			Integer32
    MAX-ACCESS                                      			read-only
    STATUS                                          			current
    DESCRIPTION                    
    "The interval number of the statistics in this row."
  ::= { nncRoutingStatsNonBorderPerTbl15MinCurrentEntry 4 }

 nncNBPerTbl15MinCurrentFailedCallsDueToInitDTLNotGenerated		OBJECT-TYPE
    SYNTAX                                          			Counter32
    MAX-ACCESS                                      			read-only
    STATUS                                          			current
    DESCRIPTION                    
    "The number of failed calls due to initial DTL not generated."
  ::= { nncRoutingStatsNonBorderPerTbl15MinCurrentEntry 5 }

 nncNBPerTbl15MinCurrentCallsGeneratingAnInitDTL		        OBJECT-TYPE
    SYNTAX                                          			Counter32
    MAX-ACCESS                                      			read-only
    STATUS                                          			current
    DESCRIPTION                    
    "The number of calls generating an initial DTL."
  ::= { nncRoutingStatsNonBorderPerTbl15MinCurrentEntry 6 }

  nncNBPerTble15MinCurrentDTLOrigCallsSuccessEstWithoutReroute     	OBJECT-TYPE
    SYNTAX                                         			Counter32
    MAX-ACCESS                                      			read-only
    STATUS                                          			current
    DESCRIPTION                    
    "The number of DTL originated calls successfully established without reroute."
  ::= { nncRoutingStatsNonBorderPerTbl15MinCurrentEntry 7 }

 nncNBPerTbl15MinCurrentDTLOrigCallsSuccessEstWithReroute		OBJECT-TYPE
    SYNTAX                                          			Counter32
    MAX-ACCESS                                      			read-only
    STATUS                                          			current
    DESCRIPTION                    
    "The number of DTL originated calls successfully established with reroute."
  ::= { nncRoutingStatsNonBorderPerTbl15MinCurrentEntry 8 }

 nncNBPerTbl15MinCurrentDTLOrigCallsFailedInReRouting     		OBJECT-TYPE
    SYNTAX                                          			Counter32
    MAX-ACCESS                                      			read-only
    STATUS                                          			current
    DESCRIPTION                    
    "The number of DTL originated calls failed in reRouting."
  ::= { nncRoutingStatsNonBorderPerTbl15MinCurrentEntry 9 }

 nncNBPerTbl15MinCurrentSuccessCallsBdwGreaterThanRTDMinBdw	        OBJECT-TYPE
    SYNTAX                                         			Counter32
    MAX-ACCESS                                      			read-only
    STATUS                                          			current
    DESCRIPTION                    
    "The number of successful calls with bandwidth greater than RTD min bandwidth."
  ::= { nncRoutingStatsNonBorderPerTbl15MinCurrentEntry 10 }

 nncNBPerTbl15MinCurrentFailedCallsBdwGreaterThanRTDMinBdw         	OBJECT-TYPE
    SYNTAX                                          			Counter32
    MAX-ACCESS                                      			read-only
    STATUS                                          			current
    DESCRIPTION                    
    "The number of failed calls with bandwidth greater than RTD min bandwidth."
  ::= { nncRoutingStatsNonBorderPerTbl15MinCurrentEntry 11 }

 nncNBPerTbl15MinCurrentCrankbackReceivedAsDTLOriginator     		OBJECT-TYPE
    SYNTAX                                          			Counter32
    MAX-ACCESS                                      			read-only
    STATUS                                          			current
    DESCRIPTION                    
    "The number of crankback received as DTL originator."
  ::= { nncRoutingStatsNonBorderPerTbl15MinCurrentEntry 12 }

  nncNBPerTbl15MinCurrentDTLsGeneratedDueToCrankback			OBJECT-TYPE
    SYNTAX                                         			Counter32
    MAX-ACCESS                                      			read-only
    STATUS                                          			current
    DESCRIPTION                    
    "The number of DTLs generated due to crankback."
  ::= { nncRoutingStatsNonBorderPerTbl15MinCurrentEntry 13 }

------------------------------------------------------------------------------------------
--  Table 10: Non Border Node PNNI Per Routing Table Statistics 15 Minutes Interval Table ------------------------------------------------------------------------------------------

  nncRoutingStatsNonBorderPerTbl15MinIntervalTable OBJECT-TYPE
    SYNTAX       SEQUENCE OF NncRoutingStatsNonBorderPerTbl15MinIntervalEntry
    MAX-ACCESS   not-accessible
    STATUS       current
    DESCRIPTION  
    "The nncRoutingStatsNonBorderPerTbl15MinIntervalTable contains objects for monitoring the 
     non-border node PNNI routing per routing table stats over a 15 minute interval."
  ::= { nncRoutingStatsObjects 10}


  nncRoutingStatsNonBorderPerTbl15MinIntervalEntry OBJECT-TYPE
    SYNTAX      NncRoutingStatsNonBorderPerTbl15MinIntervalEntry
    MAX-ACCESS  not-accessible
    STATUS      current
    DESCRIPTION  
    "An entry in the 15 minute inteval statistics table. Each conceptual row
    contains interval statistics for the non-border node PNNI routing per routing table."
    INDEX       { nncCallControlGroupNumber,
                  nncNBPerTbl15MinIntervalNumber, 
                  nncNBPerTbl15MinIntervalTableDescriptor}
  ::= { nncRoutingStatsNonBorderPerTbl15MinIntervalTable 1 }


  NncRoutingStatsNonBorderPerTbl15MinIntervalEntry ::=
    SEQUENCE {
      
      nncNBPerTbl15MinIntervalNumber					Integer32,
      nncNBPerTbl15MinIntervalTableDescriptor				INTEGER,
      nncNBPerTbl15MinIntervalState					NncExtIntvlStateType,
      nncNBPerTbl15MinIntervalAbsoluteIntervalNumber  			Integer32,
      nncNBPerTbl15MinIntervalFailedCallsDueToInitDTLNotGenerated	Counter32,
      nncNBPerTbl15MinIntervalCallsGeneratingAnInitDTL			Counter32,
      nncNBPerTbl15MinIntervalDTLOrigCallsSuccessEstWithoutReroute	Counter32,
      nncNBPerTbl15MinIntervalDTLOrigCallsSuccessEstWithReroute		Counter32,
      nncNBPerTbl15MinIntervalDTLOrigCallsFailedInReRouting		Counter32,
      nncNBPerTbl15MinIntervalSuccessCallsBdwGreaterThanRTDMinBdw	Counter32,
      nncNBPerTbl15MinIntervalFailedCallsBdwGreaterThanRTDMinBdw	Counter32,
      nncNBPerTbl15MinIntervalCrankbackReceivedAsDTLOriginator		Counter32,
      nncNBPerTbl15MinIntervalDTLsGeneratedDueToCrankback		Counter32
    }

 

 nncNBPerTbl15MinIntervalNumber				        	OBJECT-TYPE
    SYNTAX                                         			Integer32(1..96)
    MAX-ACCESS                                      			not-accessible
    STATUS                                          			current
    DESCRIPTION                    
    "The interval number of the statistics in this row."
  ::= { nncRoutingStatsNonBorderPerTbl15MinIntervalEntry 2 }

 nncNBPerTbl15MinIntervalTableDescriptor	         		OBJECT-TYPE
    SYNTAX                                          			INTEGER(0..6)
    MAX-ACCESS                                      			not-accessible
    STATUS                                          			current
    DESCRIPTION                    
    "nncTableDescriptor determines a routing table number whose stats are to be displayed."
  ::= { nncRoutingStatsNonBorderPerTbl15MinIntervalEntry 3 }

 nncNBPerTbl15MinIntervalState		     		    		OBJECT-TYPE
    SYNTAX                                          			NncExtIntvlStateType
    MAX-ACCESS                                      			read-only
    STATUS                                          			current
    DESCRIPTION                    
    "The state of the interval represented by this row. The object provides a status for those
     entries which have been reset by the user, or have been subject to a wall clock time change."
  ::= { nncRoutingStatsNonBorderPerTbl15MinIntervalEntry 4 }

  nncNBPerTbl15MinIntervalAbsoluteIntervalNumber			OBJECT-TYPE
    SYNTAX                                         			Integer32
    MAX-ACCESS                                      			read-only
    STATUS                                          			current
    DESCRIPTION                    
    "The absolute interval number of this interval."
  ::= { nncRoutingStatsNonBorderPerTbl15MinIntervalEntry 5 }

 nncNBPerTbl15MinIntervalFailedCallsDueToInitDTLNotGenerated		OBJECT-TYPE
    SYNTAX                                          			Counter32
    MAX-ACCESS                                      			read-only
    STATUS                                          			current
    DESCRIPTION                    
    "The number of failed calls due to initial DTL not generated."
  ::= { nncRoutingStatsNonBorderPerTbl15MinIntervalEntry 6 }

 nncNBPerTbl15MinIntervalCallsGeneratingAnInitDTL		        OBJECT-TYPE
    SYNTAX                                          			Counter32
    MAX-ACCESS                                      			read-only
    STATUS                                          			current
    DESCRIPTION                    
    "The number of calls generating an initial DTL."
  ::= { nncRoutingStatsNonBorderPerTbl15MinIntervalEntry 7 }

  nncNBPerTbl15MinIntervalDTLOrigCallsSuccessEstWithoutReroute    	OBJECT-TYPE
    SYNTAX                                         			Counter32
    MAX-ACCESS                                      			read-only
    STATUS                                          			current
    DESCRIPTION                    
    "The number of DTL originated calls successfully established without reroute."
  ::= { nncRoutingStatsNonBorderPerTbl15MinIntervalEntry 8 }

 nncNBPerTbl15MinIntervalDTLOrigCallsSuccessEstWithReroute		OBJECT-TYPE
    SYNTAX                                          			Counter32
    MAX-ACCESS                                      			read-only
    STATUS                                          			current
    DESCRIPTION                    
    "The number of DTL originated calls successfully established with reroute."
  ::= { nncRoutingStatsNonBorderPerTbl15MinIntervalEntry 9 }

 nncNBPerTbl15MinIntervalDTLOrigCallsFailedInReRouting     		OBJECT-TYPE
    SYNTAX                                          			Counter32
    MAX-ACCESS                                      			read-only
    STATUS                                          			current
    DESCRIPTION                    
    "The number of DTL originated calls failed in reRouting."
  ::= { nncRoutingStatsNonBorderPerTbl15MinIntervalEntry 10 }

 nncNBPerTbl15MinIntervalSuccessCallsBdwGreaterThanRTDMinBdw	        OBJECT-TYPE
    SYNTAX                                         			Counter32
    MAX-ACCESS                                      			read-only
    STATUS                                          			current
    DESCRIPTION                    
    "The number of successful calls with bandwidth greater than RTD min bandwidth."
  ::= { nncRoutingStatsNonBorderPerTbl15MinIntervalEntry 11 }

 nncNBPerTbl15MinIntervalFailedCallsBdwGreaterThanRTDMinBdw         	OBJECT-TYPE
    SYNTAX                                          			Counter32
    MAX-ACCESS                                      			read-only
    STATUS                                          			current
    DESCRIPTION                    
    "The number of failed calls with bandwidth greater than RTD min bandwidth."
  ::= { nncRoutingStatsNonBorderPerTbl15MinIntervalEntry 12 }

 nncNBPerTbl15MinIntervalCrankbackReceivedAsDTLOriginator     		OBJECT-TYPE
    SYNTAX                                          			Counter32
    MAX-ACCESS                                      			read-only
    STATUS                                          			current
    DESCRIPTION                    
    "The number of crankback received as DTL originator."
  ::= { nncRoutingStatsNonBorderPerTbl15MinIntervalEntry 13 }

  nncNBPerTbl15MinIntervalDTLsGeneratedDueToCrankback			OBJECT-TYPE
    SYNTAX                                         			Counter32
    MAX-ACCESS                                      			read-only
    STATUS                                          			current
    DESCRIPTION                    
    "The number of DTLs generated due to crankback."
  ::= { nncRoutingStatsNonBorderPerTbl15MinIntervalEntry 14 }


---------------------------------------------------------------------------------------
--  Table 11: Non Border Node PNNI Per Routing Table Statistics 24 Hour Current Table
---------------------------------------------------------------------------------------
  nncRoutingStatsNonBorderPerTbl24HourCurrentTable OBJECT-TYPE
    SYNTAX       SEQUENCE OF NncRoutingStatsNonBorderPerTbl24HourCurrentEntry
    MAX-ACCESS   not-accessible
    STATUS       current
    DESCRIPTION  
    "The nncRoutingStatsNonBorderPerTbl15MinCurrentTable contains objects for monitoring the 
     non-border node PNNI routing per routing table stats during the current 24 hour interval."
  ::= { nncRoutingStatsObjects 11 }


  nncRoutingStatsNonBorderPerTbl24HourCurrentEntry OBJECT-TYPE
    SYNTAX      NncRoutingStatsNonBorderPerTbl24HourCurrentEntry
    MAX-ACCESS  not-accessible
    STATUS      current
    DESCRIPTION  
    "An entry in the 24 hour current statistics table. Each conceptual row
    contains current statistics for the non-border node PNNI routing per routing table."
    INDEX       { nncCallControlGroupNumber,
                  nncNBPerTbl24HourCurrentTableDescriptor }
  ::= { nncRoutingStatsNonBorderPerTbl24HourCurrentTable 1 }


  NncRoutingStatsNonBorderPerTbl24HourCurrentEntry ::=
    SEQUENCE {
      
      nncNBPerTbl24HourCurrentTableDescriptor				INTEGER,
      nncNBPerTbl24HourCurrentState					NncExtIntvlStateType,
      nncNBPerTbl24HourCurrentAbsoluteIntervalNumber  			Integer32,
      nncNBPerTbl24HourCurrentFailedCallsDueToInitDTLNotGenerated	Counter32,
      nncNBPerTbl24HourCurrentCallsGeneratingAnInitDTL			Counter32,
      nncNBPerTbl24HourCurrentDTLOrigCallsSuccessEstWithoutReroute  	Counter32,
      nncNBPerTbl24HourCurrentDTLOrigCallsSuccessEstWithReroute		Counter32,
      nncNBPerTbl24HourCurrentDTLOrigCallsFailedInReRouting		Counter32,
      nncNBPerTbl24HourCurrentSuccessCallsBdwGreaterThanRTDMinBdw	Counter32,
      nncNBPerTbl24HourCurrentFailedCallsBdwGreaterThanRTDMinBdw	Counter32,
      nncNBPerTbl24HourCurrentCrankbackReceivedAsDTLOriginator		Counter32,
      nncNBPerTbl24HourCurrentDTLsGeneratedDueToCrankback		Counter32
    }



 nncNBPerTbl24HourCurrentTableDescriptor	         		OBJECT-TYPE
    SYNTAX                                          			INTEGER(0..6)
    MAX-ACCESS                                      			not-accessible
    STATUS                                          			current
    DESCRIPTION                    
    "nncTableDescriptor determines a routing table number whose stats are to be displayed."
  ::= { nncRoutingStatsNonBorderPerTbl24HourCurrentEntry 2 }

 nncNBPerTbl24HourCurrentState		     		    		OBJECT-TYPE
    SYNTAX                                          			NncExtIntvlStateType
    MAX-ACCESS                                      			read-only
    STATUS                                          			current
    DESCRIPTION                    
    "The state of the current interval. The object provides a status for those entries
     which have been reset by the user, or have been subject to a wall clock time change"
  ::= { nncRoutingStatsNonBorderPerTbl24HourCurrentEntry 3 }

  nncNBPerTbl24HourCurrentAbsoluteIntervalNumber				OBJECT-TYPE
    SYNTAX                                         			Integer32
    MAX-ACCESS                                      			read-only
    STATUS                                          			current
    DESCRIPTION                    
    "The interval number of the statistics in this row."
  ::= { nncRoutingStatsNonBorderPerTbl24HourCurrentEntry 4 }

 nncNBPerTbl24HourCurrentFailedCallsDueToInitDTLNotGenerated		OBJECT-TYPE
    SYNTAX                                          			Counter32
    MAX-ACCESS                                      			read-only
    STATUS                                          			current
    DESCRIPTION                    
    "The number of failed calls due to initial DTL not generated."
  ::= { nncRoutingStatsNonBorderPerTbl24HourCurrentEntry 5 }

 nncNBPerTbl24HourCurrentCallsGeneratingAnInitDTL		        OBJECT-TYPE
    SYNTAX                                          			Counter32
    MAX-ACCESS                                      			read-only
    STATUS                                          			current
    DESCRIPTION                    
    "The number of calls generating an initial DTL."
  ::= { nncRoutingStatsNonBorderPerTbl24HourCurrentEntry 6 }

  nncNBPerTbl24HourCurrentDTLOrigCallsSuccessEstWithoutReroute     	OBJECT-TYPE
    SYNTAX                                         			Counter32
    MAX-ACCESS                                      			read-only
    STATUS                                          			current
    DESCRIPTION                    
    "The number of DTL originated calls successfully established without reroute."
  ::= { nncRoutingStatsNonBorderPerTbl24HourCurrentEntry 7 }

 nncNBPerTbl24HourCurrentDTLOrigCallsSuccessEstWithReroute		OBJECT-TYPE
    SYNTAX                                          			Counter32
    MAX-ACCESS                                      			read-only
    STATUS                                          			current
    DESCRIPTION                    
    "The number of DTL originated calls successfully established with reroute."
  ::= { nncRoutingStatsNonBorderPerTbl24HourCurrentEntry 8 }

 nncNBPerTbl24HourCurrentDTLOrigCallsFailedInReRouting     		OBJECT-TYPE
    SYNTAX                                          			Counter32
    MAX-ACCESS                                      			read-only
    STATUS                                          			current
    DESCRIPTION                    
    "The number of DTL originated calls failed in reRouting."
  ::= { nncRoutingStatsNonBorderPerTbl24HourCurrentEntry 9 }

 nncNBPerTbl24HourCurrentSuccessCallsBdwGreaterThanRTDMinBdw	        OBJECT-TYPE
    SYNTAX                                         			Counter32
    MAX-ACCESS                                      			read-only
    STATUS                                          			current
    DESCRIPTION                    
    "The number of successful calls with bandwidth greater than RTD min bandwidth."
  ::= { nncRoutingStatsNonBorderPerTbl24HourCurrentEntry 10 }

 nncNBPerTbl24HourCurrentFailedCallsBdwGreaterThanRTDMinBdw         	OBJECT-TYPE
    SYNTAX                                          			Counter32
    MAX-ACCESS                                      			read-only
    STATUS                                          			current
    DESCRIPTION                    
    "The number of failed calls with bandwidth greater than RTD min bandwidth."
  ::= { nncRoutingStatsNonBorderPerTbl24HourCurrentEntry 11 }

 nncNBPerTbl24HourCurrentCrankbackReceivedAsDTLOriginator     		OBJECT-TYPE
    SYNTAX                                          			Counter32
    MAX-ACCESS                                      			read-only
    STATUS                                          			current
    DESCRIPTION                    
    "The number of crankback received as DTL originator."
  ::= { nncRoutingStatsNonBorderPerTbl24HourCurrentEntry 12 }

  nncNBPerTbl24HourCurrentDTLsGeneratedDueToCrankback			OBJECT-TYPE
    SYNTAX                                         			Counter32
    MAX-ACCESS                                      			read-only
    STATUS                                          			current
    DESCRIPTION                    
    "The number of DTLs generated due to crankback."
  ::= { nncRoutingStatsNonBorderPerTbl24HourCurrentEntry 13 }

 
------------------------------------------------------------------------------------------
--  Table 12: Non Border Node PNNI Per Routing Table Statistics 24 Hour Interval Table
------------------------------------------------------------------------------------------
  nncRoutingStatsNonBorderPerTbl24HourIntervalTable OBJECT-TYPE
    SYNTAX       SEQUENCE OF NncRoutingStatsNonBorderPerTbl24HourIntervalEntry
    MAX-ACCESS   not-accessible
    STATUS       current
    DESCRIPTION  
    "The nncRoutingStatsNonBorderPerTbl15MinIntervalTable contains objects for monitoring the 
     non-border node PNNI routing per routing table stats over a 24 hour interval."
  ::= { nncRoutingStatsObjects 12}


  nncRoutingStatsNonBorderPerTbl24HourIntervalEntry OBJECT-TYPE
    SYNTAX      NncRoutingStatsNonBorderPerTbl24HourIntervalEntry
    MAX-ACCESS  not-accessible
    STATUS      current
    DESCRIPTION  
    "An entry in the 24 hour inteval statistics table. Each conceptual row
    contains interval statistics for the non-border node PNNI routing per routing table."
    INDEX       { nncCallControlGroupNumber,  
                  nncNBPerTbl24HourIntervalNumber, 
                  nncNBPerTbl24HourIntervalTableDescriptor }
  ::= { nncRoutingStatsNonBorderPerTbl24HourIntervalTable 1 }


  NncRoutingStatsNonBorderPerTbl24HourIntervalEntry ::=
    SEQUENCE {
      
      nncNBPerTbl24HourIntervalNumber					Integer32,
      nncNBPerTbl24HourIntervalTableDescriptor				INTEGER,
      nncNBPerTbl24HourIntervalState					NncExtIntvlStateType,
      nncNBPerTbl24HourIntervalAbsoluteIntervalNumber  			Integer32,
      nncNBPerTbl24HourIntervalFailedCallsDueToInitDTLNotGenerated	Counter32,
      nncNBPerTbl24HourIntervalCallsGeneratingAnInitDTL			Counter32,
      nncNBPerTbl24HourIntervalDTLOrigCallsSuccessEstWithoutReroute   	Counter32,
      nncNBPerTbl24HourIntervalDTLOrigCallsSuccessEstWithReroute	Counter32,
      nncNBPerTbl24HourIntervalDTLOrigCallsFailedInReRouting		Counter32,
      nncNBPerTbl24HourIntervalSuccessCallsBdwGreaterThanRTDMinBdw	Counter32,
      nncNBPerTbl24HourIntervalFailedCallsBdwGreaterThanRTDMinBdw	Counter32,
      nncNBPerTbl24HourIntervalCrankbackReceivedAsDTLOriginator		Counter32,
      nncNBPerTbl24HourIntervalDTLsGeneratedDueToCrankback		Counter32
    }



 nncNBPerTbl24HourIntervalNumber				        OBJECT-TYPE
    SYNTAX                                         			Integer32
    MAX-ACCESS                                      			not-accessible
    STATUS                                          			current
    DESCRIPTION                    
    "The interval number of the statistics in this row."
  ::= { nncRoutingStatsNonBorderPerTbl24HourIntervalEntry 2}

 nncNBPerTbl24HourIntervalTableDescriptor	         		OBJECT-TYPE
    SYNTAX                                          			INTEGER(0..6)
    MAX-ACCESS                                      			not-accessible
    STATUS                                          			current
    DESCRIPTION                    
    "nncTableDescriptor determines a routing table number whose stats are to be displayed."
  ::= { nncRoutingStatsNonBorderPerTbl24HourIntervalEntry 3 }

 nncNBPerTbl24HourIntervalState		     		    		OBJECT-TYPE
    SYNTAX                                          			NncExtIntvlStateType
    MAX-ACCESS                                      			read-only
    STATUS                                          			current
    DESCRIPTION                    
    "The state of the interval represented by this row. The object provides a status for those
     entries which have been reset by the user, or have been subject to a wall clock time change."
  ::= { nncRoutingStatsNonBorderPerTbl24HourIntervalEntry 4 }

  nncNBPerTbl24HourIntervalAbsoluteIntervalNumber			OBJECT-TYPE
    SYNTAX                                         			Integer32
    MAX-ACCESS                                      			read-only
    STATUS                                          			current
    DESCRIPTION                    
    "The absolute interval number of this interval."
  ::= { nncRoutingStatsNonBorderPerTbl24HourIntervalEntry 5 }

 nncNBPerTbl24HourIntervalFailedCallsDueToInitDTLNotGenerated		OBJECT-TYPE
    SYNTAX                                          			Counter32
    MAX-ACCESS                                      			read-only
    STATUS                                          			current
    DESCRIPTION                    
    "The number of failed calls due to initial DTL not generated."
  ::= { nncRoutingStatsNonBorderPerTbl24HourIntervalEntry 6}

 nncNBPerTbl24HourIntervalCallsGeneratingAnInitDTL		        OBJECT-TYPE
    SYNTAX                                          			Counter32
    MAX-ACCESS                                      			read-only
    STATUS                                          			current
    DESCRIPTION                    
    "The number of calls generating an initial DTL."
  ::= { nncRoutingStatsNonBorderPerTbl24HourIntervalEntry 7 }

  nncNBPerTbl24HourIntervalDTLOrigCallsSuccessEstWithoutReroute    	OBJECT-TYPE
    SYNTAX                                         			Counter32
    MAX-ACCESS                                      			read-only
    STATUS                                          			current
    DESCRIPTION                    
    "The number of DTL originated calls successfully established without reroute."
  ::= { nncRoutingStatsNonBorderPerTbl24HourIntervalEntry 8 }

 nncNBPerTbl24HourIntervalDTLOrigCallsSuccessEstWithReroute		OBJECT-TYPE
    SYNTAX                                          			Counter32
    MAX-ACCESS                                      			read-only
    STATUS                                          			current
    DESCRIPTION                    
    "The number of DTL originated calls successfully established with reroute."
  ::= { nncRoutingStatsNonBorderPerTbl24HourIntervalEntry 9 }

 nncNBPerTbl24HourIntervalDTLOrigCallsFailedInReRouting     		OBJECT-TYPE
    SYNTAX                                          			Counter32
    MAX-ACCESS                                      			read-only
    STATUS                                          			current
    DESCRIPTION                    
    "The number of DTL originated calls failed in reRouting."
  ::= { nncRoutingStatsNonBorderPerTbl24HourIntervalEntry 10 }

 nncNBPerTbl24HourIntervalSuccessCallsBdwGreaterThanRTDMinBdw		OBJECT-TYPE
    SYNTAX                                         			Counter32
    MAX-ACCESS                                      			read-only
    STATUS                                          			current
    DESCRIPTION                    
    "The number of successful calls with bandwidth greater than RTD min bandwidth."
  ::= { nncRoutingStatsNonBorderPerTbl24HourIntervalEntry 11 }

 nncNBPerTbl24HourIntervalFailedCallsBdwGreaterThanRTDMinBdw         	OBJECT-TYPE
    SYNTAX                                          			Counter32
    MAX-ACCESS                                      			read-only
    STATUS                                          			current
    DESCRIPTION                    
    "The number of failed calls with bandwidth greater than RTD min bandwidth."
  ::= { nncRoutingStatsNonBorderPerTbl24HourIntervalEntry 12 }

 nncNBPerTbl24HourIntervalCrankbackReceivedAsDTLOriginator     		OBJECT-TYPE
    SYNTAX                                          			Counter32
    MAX-ACCESS                                      			read-only
    STATUS                                          			current
    DESCRIPTION                    
    "The number of crankback received as DTL originator."
  ::= { nncRoutingStatsNonBorderPerTbl24HourIntervalEntry 13 }

  nncNBPerTbl24HourIntervalDTLsGeneratedDueToCrankback			OBJECT-TYPE
    SYNTAX                                         			Counter32
    MAX-ACCESS                                      			read-only
    STATUS                                          			current
    DESCRIPTION                    
    "The number of DTLs generated due to crankback."
  ::= { nncRoutingStatsNonBorderPerTbl24HourIntervalEntry 14 }
 
 
---------------------------------------------------------------------------------------
--  Table 13: Border Node PNNI Per Routing Table Statistics 15 Minutes Current Table
---------------------------------------------------------------------------------------
  nncRoutingStatsBorderPerTbl15MinCurrentTable OBJECT-TYPE
    SYNTAX       SEQUENCE OF NncRoutingStatsBorderPerTbl15MinCurrentEntry
    MAX-ACCESS   not-accessible
    STATUS       current
    DESCRIPTION  
    "The nncRoutingStatsBorderPerTbl15MinCurrentTable contains objects for monitoring the 
     border node PNNI routing per routing table stats during the current 15 minute interval."
  ::= { nncRoutingStatsObjects 13 }


  nncRoutingStatsBorderPerTbl15MinCurrentEntry OBJECT-TYPE
    SYNTAX      NncRoutingStatsBorderPerTbl15MinCurrentEntry
    MAX-ACCESS  not-accessible
    STATUS      current
    DESCRIPTION  
    "An entry in the 15 minute current statistics table. Each conceptual row
    contains current statistics for the border node PNNI routing per routing table."
    INDEX       { nncCallControlGroupNumber, 
                  nncBPerTbl15MinCurrentTableDescriptor }
  ::= { nncRoutingStatsBorderPerTbl15MinCurrentTable 1 }


  NncRoutingStatsBorderPerTbl15MinCurrentEntry ::=
    SEQUENCE {
      
      nncBPerTbl15MinCurrentTableDescriptor				INTEGER,
      nncBPerTbl15MinCurrentState					NncExtIntvlStateType,
      nncBPerTbl15MinCurrentAbsoluteIntervalNumber  			Integer32,
      nncBPerTbl15MinCurrentFailedCallsDueInitLowerLvlDTLsNotGen	Counter32,
      nncBPerTbl15MinCurrentCallsGeneratingInitLowerLvlDTLs		Counter32,
      nncBPerTbl15MinCurrentDTLGenCallsSuccessEstWithoutReroute		Counter32,
      nncBPerTbl15MinCurrentDTLGenCallsSuccessEstWithReroute		Counter32,
      nncBPerTbl15MinCurrentDTLGenCallsFailedInReRouting		Counter32,
      nncBPerTbl15MinCurrentSuccessCallsBdwGreaterThanRTDMinBdw		Counter32,
      nncBPerTbl15MinCurrentFailedCallsBdwGreaterThanRTDMinBdw		Counter32,
      nncBPerTbl15MinCurrentCrankbackReceivedAsAnEntryBorderNode	Counter32,
      nncBPerTbl15MinCurrentLowerLvlDTLsGenDueToRecdCrankback		Counter32
    }

 

 nncBPerTbl15MinCurrentTableDescriptor	         			OBJECT-TYPE
    SYNTAX                                          			INTEGER(0..6)
    MAX-ACCESS                                      			not-accessible
    STATUS                                          			current
    DESCRIPTION                    
    "nncTableDescriptor determines a routing table number whose stats are to be displayed."
  ::= { nncRoutingStatsBorderPerTbl15MinCurrentEntry 2}

 nncBPerTbl15MinCurrentState		     		    		OBJECT-TYPE
    SYNTAX                                          			NncExtIntvlStateType
    MAX-ACCESS                                      			read-only
    STATUS                                          			current
    DESCRIPTION                    
    "The state of the current interval. The object provides a status for those entries
     which have been reset by the user, or have been subject to a wall clock time change"
  ::= { nncRoutingStatsBorderPerTbl15MinCurrentEntry 3 }

  nncBPerTbl15MinCurrentAbsoluteIntervalNumber				OBJECT-TYPE
    SYNTAX                                         			Integer32
    MAX-ACCESS                                      			read-only
    STATUS                                          			current
    DESCRIPTION                    
    "The interval number of the statistics in this row."
  ::= { nncRoutingStatsBorderPerTbl15MinCurrentEntry 4 }

 nncBPerTbl15MinCurrentFailedCallsDueInitLowerLvlDTLsNotGen		OBJECT-TYPE
    SYNTAX                                          			Counter32
    MAX-ACCESS                                      			read-only
    STATUS                                          			current
    DESCRIPTION                    
    "The number of failed calls generating initial lower level DTLs."
  ::= { nncRoutingStatsBorderPerTbl15MinCurrentEntry 5 }

 nncBPerTbl15MinCurrentCallsGeneratingInitLowerLvlDTLs			OBJECT-TYPE
    SYNTAX                                          			Counter32
    MAX-ACCESS                                      			read-only
    STATUS                                          			current
    DESCRIPTION                    
    "The number of calls generating initial lower level DTLs."
  ::= { nncRoutingStatsBorderPerTbl15MinCurrentEntry 6}

  nncBPerTbl15MinCurrentDTLGenCallsSuccessEstWithoutReroute      	OBJECT-TYPE
    SYNTAX                                         			Counter32
    MAX-ACCESS                                      			read-only
    STATUS                                          			current
    DESCRIPTION                    
    "The number of DTL generated calls successfully established without reroute."
  ::= { nncRoutingStatsBorderPerTbl15MinCurrentEntry 7 }

 nncBPerTbl15MinCurrentDTLGenCallsSuccessEstWithReroute			OBJECT-TYPE
    SYNTAX                                          			Counter32
    MAX-ACCESS                                      			read-only
    STATUS                                          			current
    DESCRIPTION                    
    "The number of DTL generated calls successfully established with reroute."
  ::= { nncRoutingStatsBorderPerTbl15MinCurrentEntry 8 }

 nncBPerTbl15MinCurrentDTLGenCallsFailedInReRouting     		OBJECT-TYPE
    SYNTAX                                          			Counter32
    MAX-ACCESS                                      			read-only
    STATUS                                          			current
    DESCRIPTION                    
    "The number of DTL generated calls failed in rerouting."
  ::= { nncRoutingStatsBorderPerTbl15MinCurrentEntry 9 }

 nncBPerTbl15MinCurrentSuccessCallsBdwGreaterThanRTDMinBdw	        OBJECT-TYPE
    SYNTAX                                         			Counter32
    MAX-ACCESS                                      			read-only
    STATUS                                          			current
    DESCRIPTION                    
    "The number of successful calls with bandwidth greater than RTD min bandwidth."
  ::= { nncRoutingStatsBorderPerTbl15MinCurrentEntry 10 }

 nncBPerTbl15MinCurrentFailedCallsBdwGreaterThanRTDMinBdw         	OBJECT-TYPE
    SYNTAX                                          			Counter32
    MAX-ACCESS                                      			read-only
    STATUS                                          			current
    DESCRIPTION                    
    "The number of failed calls with bandwidth greater than RTD min bandwidth."
  ::= { nncRoutingStatsBorderPerTbl15MinCurrentEntry 11 }

 nncBPerTbl15MinCurrentCrankbackReceivedAsAnEntryBorderNode     	OBJECT-TYPE
    SYNTAX                                          			Counter32
    MAX-ACCESS                                      			read-only
    STATUS                                          			current
    DESCRIPTION                    
    "The number of crankback received as an entry border node."
  ::= { nncRoutingStatsBorderPerTbl15MinCurrentEntry 12 }

  nncBPerTbl15MinCurrentLowerLvlDTLsGenDueToRecdCrankback		OBJECT-TYPE
    SYNTAX                                         			Counter32
    MAX-ACCESS                                      			read-only
    STATUS                                          			current
    DESCRIPTION                    
    "The number of lower Level DTLs generated due to received crankback."
  ::= { nncRoutingStatsBorderPerTbl15MinCurrentEntry 13 }

 
------------------------------------------------------------------------------------------
--  Table 14: Border Node PNNI Per Routing Table Statistics 15 Minutes Interval Table
------------------------------------------------------------------------------------------
  nncRoutingStatsBorderPerTbl15MinIntervalTable OBJECT-TYPE
    SYNTAX       SEQUENCE OF NncRoutingStatsBorderPerTbl15MinIntervalEntry
    MAX-ACCESS   not-accessible
    STATUS       current
    DESCRIPTION  
    "The nncRoutingStatsBorderPerTbl15MinIntervalTable contains objects for monitoring the 
     border node PNNI routing per routing table stats over a 15 minute interval."
  ::= { nncRoutingStatsObjects 14}


  nncRoutingStatsBorderPerTbl15MinIntervalEntry OBJECT-TYPE
    SYNTAX      NncRoutingStatsBorderPerTbl15MinIntervalEntry
    MAX-ACCESS  not-accessible
    STATUS      current
    DESCRIPTION  
    "An entry in the 15 minute interval statistics table. Each conceptual row
    contains interval statistics for the border node PNNI routing per routing table."
    INDEX       { nncCallControlGroupNumber, 
                  nncBPerTbl15MinIntervalNumber, 
                  nncBPerTbl15MinIntervalTableDescriptor }
  ::= { nncRoutingStatsBorderPerTbl15MinIntervalTable 1 }


  NncRoutingStatsBorderPerTbl15MinIntervalEntry ::=
    SEQUENCE {
     
      nncBPerTbl15MinIntervalNumber					Integer32,
      nncBPerTbl15MinIntervalTableDescriptor				INTEGER,
      nncBPerTbl15MinIntervalState					NncExtIntvlStateType,
      nncBPerTbl15MinIntervalAbsoluteIntervalNumber  			Integer32,
      nncBPerTbl15MinIntervalFailedCallsDueInitLowerLvlDTLsNotGen	Counter32,
      nncBPerTbl15MinIntervalCallsGeneratingInitLowerLvlDTLs		Counter32,
      nncBPerTbl15MinIntervalDTLGenCallsSuccessEstWithoutReroute	Counter32,
      nncBPerTbl15MinIntervalDTLGenCallsSuccessEstWithReroute		Counter32,
      nncBPerTbl15MinIntervalDTLGenCallsFailedInReRouting		Counter32,
      nncBPerTbl15MinIntervalSuccessCallsBdwGreaterThanRTDMinBdw	Counter32,
      nncBPerTbl15MinIntervalFailedCallsBdwGreaterThanRTDMinBdw		Counter32,
      nncBPerTbl15MinIntervalCrankbackReceivedAsAnEntryBorderNode	Counter32,
      nncBPerTbl15MinIntervalLowerLvlDTLsGenDueToRecdCrankback		Counter32
    }



 nncBPerTbl15MinIntervalNumber				        	OBJECT-TYPE
    SYNTAX                                         			Integer32(1..96)
    MAX-ACCESS                                      			not-accessible
    STATUS                                          			current
    DESCRIPTION                    
    "The interval number of the statistics in this row."
  ::= { nncRoutingStatsBorderPerTbl15MinIntervalEntry 2}

 nncBPerTbl15MinIntervalTableDescriptor	         			OBJECT-TYPE
    SYNTAX                                          			INTEGER(0..6)
    MAX-ACCESS                                      			not-accessible
    STATUS                                          			current
    DESCRIPTION                    
    "nncTableDescriptor determines a routing table number whose stats are to be displayed."
  ::= { nncRoutingStatsBorderPerTbl15MinIntervalEntry 3 }

 nncBPerTbl15MinIntervalState		     		    		OBJECT-TYPE
    SYNTAX                                          			NncExtIntvlStateType
    MAX-ACCESS                                      			read-only
    STATUS                                          			current
    DESCRIPTION                    
    "The state of the interval represented by this row. The object provides a status for those
     entries which have been reset by the user, or have been subject to a wall clock time change."
  ::= { nncRoutingStatsBorderPerTbl15MinIntervalEntry 4 }

  nncBPerTbl15MinIntervalAbsoluteIntervalNumber				OBJECT-TYPE
    SYNTAX                                         			Integer32
    MAX-ACCESS                                      			read-only
    STATUS                                          			current
    DESCRIPTION                    
    "The absolute interval number of this interval."
  ::= { nncRoutingStatsBorderPerTbl15MinIntervalEntry 5 }

 nncBPerTbl15MinIntervalFailedCallsDueInitLowerLvlDTLsNotGen		OBJECT-TYPE
    SYNTAX                                          			Counter32
    MAX-ACCESS                                      			read-only
    STATUS                                          			current
    DESCRIPTION                    
    "The number of failed calls generating initial lower level DTLs."
  ::= { nncRoutingStatsBorderPerTbl15MinIntervalEntry 6}

 nncBPerTbl15MinIntervalCallsGeneratingInitLowerLvlDTLs			OBJECT-TYPE
    SYNTAX                                          			Counter32
    MAX-ACCESS                                      			read-only
    STATUS                                          			current
    DESCRIPTION                    
    "The number of calls generating initial lower level DTLs."
  ::= { nncRoutingStatsBorderPerTbl15MinIntervalEntry 7 }

  nncBPerTbl15MinIntervalDTLGenCallsSuccessEstWithoutReroute         	OBJECT-TYPE
    SYNTAX                                         			Counter32
    MAX-ACCESS                                      			read-only
    STATUS                                          			current
    DESCRIPTION                    
    "The number of DTL generated calls successfully established without reroute."
  ::= { nncRoutingStatsBorderPerTbl15MinIntervalEntry 8 }

 nncBPerTbl15MinIntervalDTLGenCallsSuccessEstWithReroute		OBJECT-TYPE
    SYNTAX                                          			Counter32
    MAX-ACCESS                                      			read-only
    STATUS                                          			current
    DESCRIPTION                    
    "The number of DTL generated calls successfully established with reroute."
  ::= { nncRoutingStatsBorderPerTbl15MinIntervalEntry 9 }

 nncBPerTbl15MinIntervalDTLGenCallsFailedInReRouting     		OBJECT-TYPE
    SYNTAX                                          			Counter32
    MAX-ACCESS                                      			read-only
    STATUS                                          			current
    DESCRIPTION                    
    "The number of DTL generated calls failed in rerouting."
  ::= { nncRoutingStatsBorderPerTbl15MinIntervalEntry 10 }

 nncBPerTbl15MinIntervalSuccessCallsBdwGreaterThanRTDMinBdw	        OBJECT-TYPE
    SYNTAX                                         			Counter32
    MAX-ACCESS                                      			read-only
    STATUS                                          			current
    DESCRIPTION                    
    "The number of successful calls with bandwidth greater than RTD min bandwidth."
  ::= { nncRoutingStatsBorderPerTbl15MinIntervalEntry 11 }

 nncBPerTbl15MinIntervalFailedCallsBdwGreaterThanRTDMinBdw         	OBJECT-TYPE
    SYNTAX                                          			Counter32
    MAX-ACCESS                                      			read-only
    STATUS                                          			current
    DESCRIPTION                    
    "The number of failed calls with bandwidth greater than RTD min bandwidth."
  ::= { nncRoutingStatsBorderPerTbl15MinIntervalEntry 12 }

 nncBPerTbl15MinIntervalCrankbackReceivedAsAnEntryBorderNode     	OBJECT-TYPE
    SYNTAX                                          			Counter32
    MAX-ACCESS                                      			read-only
    STATUS                                          			current
    DESCRIPTION                    
    "The number of crankback received as an entry border node."
  ::= { nncRoutingStatsBorderPerTbl15MinIntervalEntry 13 }

  nncBPerTbl15MinIntervalLowerLvlDTLsGenDueToRecdCrankback		OBJECT-TYPE
    SYNTAX                                         			Counter32
    MAX-ACCESS                                      			read-only
    STATUS                                          			current
    DESCRIPTION                    
    "The number of lower Level DTLs generated due to received crankback."
  ::= { nncRoutingStatsBorderPerTbl15MinIntervalEntry 14 }


---------------------------------------------------------------------------------------
--  Table 15: Border Node PNNI Per Routing Table Statistics 24 Hour Current Table
---------------------------------------------------------------------------------------
  nncRoutingStatsBorderPerTbl24HourCurrentTable OBJECT-TYPE
    SYNTAX       SEQUENCE OF NncRoutingStatsBorderPerTbl24HourCurrentEntry
    MAX-ACCESS   not-accessible
    STATUS       current
    DESCRIPTION  
    "The nncRoutingStatsBorderPerTbl15MinCurrentTable contains objects for monitoring the 
     border node PNNI routing per routing table stats during the current 24 hour interval."
  ::= { nncRoutingStatsObjects 15 }


  nncRoutingStatsBorderPerTbl24HourCurrentEntry OBJECT-TYPE
    SYNTAX      NncRoutingStatsBorderPerTbl24HourCurrentEntry
    MAX-ACCESS  not-accessible
    STATUS      current
    DESCRIPTION  
    "An entry in the 24 hour current statistics table. Each conceptual row
    contains current statistics for the border node PNNI routing per routing table."
    INDEX       { nncCallControlGroupNumber, 
                  nncBPerTbl24HourCurrentTableDescriptor }
  ::= { nncRoutingStatsBorderPerTbl24HourCurrentTable 1 }


  NncRoutingStatsBorderPerTbl24HourCurrentEntry ::=
    SEQUENCE {
      nncBPerTbl24HourCurrentTableDescriptor				INTEGER,
      nncBPerTbl24HourCurrentState					NncExtIntvlStateType,
      nncBPerTbl24HourCurrentAbsoluteIntervalNumber  			Integer32,
      nncBPerTbl24HourCurrentFailedCallsDueInitLowerLvlDTLsNotGen	Counter32,
      nncBPerTbl24HourCurrentCallsGeneratingInitLowerLvlDTLs		Counter32,
      nncBPerTbl24HourCurrentDTLGenCallsSuccessEstWithoutReroute	Counter32,
      nncBPerTbl24HourCurrentDTLGenCallsSuccessEstWithReroute		Counter32,
      nncBPerTbl24HourCurrentDTLGenCallsFailedInReRouting		Counter32,
      nncBPerTbl24HourCurrentSuccessCallsBdwGreaterThanRTDMinBdw	Counter32,
      nncBPerTbl24HourCurrentFailedCallsBdwGreaterThanRTDMinBdw		Counter32,
      nncBPerTbl24HourCurrentCrankbackReceivedAsAnEntryBorderNode	Counter32,
      nncBPerTbl24HourCurrentLowerLvlDTLsGenDueToRecdCrankback		Counter32
    }



 nncBPerTbl24HourCurrentTableDescriptor	         			OBJECT-TYPE
    SYNTAX                                          			INTEGER(0..6)
    MAX-ACCESS                                      			not-accessible
    STATUS                                          			current
    DESCRIPTION                    
    "nncTableDescriptor determines a routing table number whose stats are to be displayed."
  ::= { nncRoutingStatsBorderPerTbl24HourCurrentEntry 2}

 nncBPerTbl24HourCurrentState		     		    		OBJECT-TYPE
    SYNTAX                                          			NncExtIntvlStateType
    MAX-ACCESS                                      			read-only
    STATUS                                          			current
    DESCRIPTION                    
    "The state of the current interval. The object provides a status for those entries
     which have been reset by the user, or have been subject to a wall clock time change"
  ::= { nncRoutingStatsBorderPerTbl24HourCurrentEntry 3 }

  nncBPerTbl24HourCurrentAbsoluteIntervalNumber				OBJECT-TYPE
    SYNTAX                                         			Integer32
    MAX-ACCESS                                      			read-only
    STATUS                                          			current
    DESCRIPTION                    
    "The interval number of the statistics in this row."
  ::= { nncRoutingStatsBorderPerTbl24HourCurrentEntry 4 }

 nncBPerTbl24HourCurrentFailedCallsDueInitLowerLvlDTLsNotGen		OBJECT-TYPE
    SYNTAX                                          			Counter32
    MAX-ACCESS                                      			read-only
    STATUS                                          			current
    DESCRIPTION                    
    "The number of failed calls generating initial lower level DTLs."
  ::= { nncRoutingStatsBorderPerTbl24HourCurrentEntry 5 }

 nncBPerTbl24HourCurrentCallsGeneratingInitLowerLvlDTLs			OBJECT-TYPE
    SYNTAX                                          			Counter32
    MAX-ACCESS                                      			read-only
    STATUS                                          			current
    DESCRIPTION                    
    "The number of calls generating initial lower level DTLs."
  ::= { nncRoutingStatsBorderPerTbl24HourCurrentEntry 6}

  nncBPerTbl24HourCurrentDTLGenCallsSuccessEstWithoutReroute      	OBJECT-TYPE
    SYNTAX                                         			Counter32
    MAX-ACCESS                                      			read-only
    STATUS                                          			current
    DESCRIPTION                    
    "The number of DTL generated calls successfully established without reroute."
  ::= { nncRoutingStatsBorderPerTbl24HourCurrentEntry 7 }

 nncBPerTbl24HourCurrentDTLGenCallsSuccessEstWithReroute		OBJECT-TYPE
    SYNTAX                                          			Counter32
    MAX-ACCESS                                      			read-only
    STATUS                                          			current
    DESCRIPTION                    
    "The number of DTL generated calls successfully established with reroute."
  ::= { nncRoutingStatsBorderPerTbl24HourCurrentEntry 8 }

 nncBPerTbl24HourCurrentDTLGenCallsFailedInReRouting     		OBJECT-TYPE
    SYNTAX                                          			Counter32
    MAX-ACCESS                                      			read-only
    STATUS                                          			current
    DESCRIPTION                    
    "The number of DTL generated calls failed in rerouting."
  ::= { nncRoutingStatsBorderPerTbl24HourCurrentEntry 9 }

 nncBPerTbl24HourCurrentSuccessCallsBdwGreaterThanRTDMinBdw	        OBJECT-TYPE
    SYNTAX                                         			Counter32
    MAX-ACCESS                                      			read-only
    STATUS                                          			current
    DESCRIPTION                    
    "The number of successful calls with bandwidth greater than RTD min bandwidth."
  ::= { nncRoutingStatsBorderPerTbl24HourCurrentEntry 10 }

 nncBPerTbl24HourCurrentFailedCallsBdwGreaterThanRTDMinBdw         	OBJECT-TYPE
    SYNTAX                                          			Counter32
    MAX-ACCESS                                      			read-only
    STATUS                                          			current
    DESCRIPTION                    
    "The number of failed calls with bandwidth greater than RTD min bandwidth."
  ::= { nncRoutingStatsBorderPerTbl24HourCurrentEntry 11 }

 nncBPerTbl24HourCurrentCrankbackReceivedAsAnEntryBorderNode     	OBJECT-TYPE
    SYNTAX                                          			Counter32
    MAX-ACCESS                                      			read-only
    STATUS                                          			current
    DESCRIPTION                    
    "The number of crankback received as an entry border node."
  ::= { nncRoutingStatsBorderPerTbl24HourCurrentEntry 12 }

  nncBPerTbl24HourCurrentLowerLvlDTLsGenDueToRecdCrankback		OBJECT-TYPE
    SYNTAX                                         			Counter32
    MAX-ACCESS                                      			read-only
    STATUS                                          			current
    DESCRIPTION                    
    "The number of lower Level DTLs generated due to received crankback."
  ::= { nncRoutingStatsBorderPerTbl24HourCurrentEntry 13 }

 
------------------------------------------------------------------------------------------
--  Table 16: Border Node PNNI Per Routing Table Statistics 24 Hour Interval Table
------------------------------------------------------------------------------------------
  nncRoutingStatsBorderPerTbl24HourIntervalTable OBJECT-TYPE
    SYNTAX       SEQUENCE OF NncRoutingStatsBorderPerTbl24HourIntervalEntry
    MAX-ACCESS   not-accessible
    STATUS       current
    DESCRIPTION  
    "The nncRoutingStatsBorderPerTbl24HourIntervalTable contains objects for monitoring the 
     border node PNNI routing per routing table stats over a 24 hour interval."
  ::= { nncRoutingStatsObjects 16}


  nncRoutingStatsBorderPerTbl24HourIntervalEntry OBJECT-TYPE
    SYNTAX      NncRoutingStatsBorderPerTbl24HourIntervalEntry
    MAX-ACCESS  not-accessible
    STATUS      current
    DESCRIPTION  
    "An entry in the 24 hour interval statistics table. Each conceptual row
    contains interval statistics for the border node PNNI routing per routing table."
    INDEX       { nncCallControlGroupNumber,
                  nncBPerTbl24HourIntervalNumber, 
                  nncBPerTbl24HourIntervalTableDescriptor }
  ::= { nncRoutingStatsBorderPerTbl24HourIntervalTable 1 }


  NncRoutingStatsBorderPerTbl24HourIntervalEntry ::=
    SEQUENCE {
     
      nncBPerTbl24HourIntervalNumber					Integer32,
      nncBPerTbl24HourIntervalTableDescriptor				INTEGER,
      nncBPerTbl24HourIntervalState					NncExtIntvlStateType,
      nncBPerTbl24HourIntervalAbsoluteIntervalNumber  			Integer32,
      nncBPerTbl24HourIntervalFailedCallsDueInitLowerLvlDTLsNotGen	Counter32,
      nncBPerTbl24HourIntervalCallsGeneratingInitLowerLvlDTLs		Counter32,
      nncBPerTbl24HourIntervalDTLGenCallsSuccessEstWithoutReroute	Counter32,
      nncBPerTbl24HourIntervalDTLGenCallsSuccessEstWithReroute		Counter32,
      nncBPerTbl24HourIntervalDTLGenCallsFailedInReRouting		Counter32,
      nncBPerTbl24HourIntervalSuccessCallsBdwGreaterThanRTDMinBdw	Counter32,
      nncBPerTbl24HourIntervalFailedCallsBdwGreaterThanRTDMinBdw	Counter32,
      nncBPerTbl24HourIntervalCrankbackReceivedAsAnEntryBorderNode	Counter32,
      nncBPerTbl24HourIntervalLowerLvlDTLsGenDueToRecdCrankback		Counter32
    }

 
 

 nncBPerTbl24HourIntervalNumber				        	OBJECT-TYPE
    SYNTAX                                         			Integer32
    MAX-ACCESS                                      			not-accessible
    STATUS                                          			current
    DESCRIPTION                    
    "The interval number of the statistics in this row."
  ::= { nncRoutingStatsBorderPerTbl24HourIntervalEntry 2}

 nncBPerTbl24HourIntervalTableDescriptor	         		OBJECT-TYPE
    SYNTAX                                          			INTEGER(0..6)
    MAX-ACCESS                                      			not-accessible
    STATUS                                          			current
    DESCRIPTION                    
    "nncTableDescriptor determines a routing table number whose stats are to be displayed."
  ::= { nncRoutingStatsBorderPerTbl24HourIntervalEntry 3 }

 nncBPerTbl24HourIntervalState		     		    		OBJECT-TYPE
    SYNTAX                                          			NncExtIntvlStateType
    MAX-ACCESS                                      			read-only
    STATUS                                          			current
    DESCRIPTION                    
    "The state of the interval represented by this row. The object provides a status for those
     entries which have been reset by the user, or have been subject to a wall clock time change."
  ::= { nncRoutingStatsBorderPerTbl24HourIntervalEntry 4 }

  nncBPerTbl24HourIntervalAbsoluteIntervalNumber			OBJECT-TYPE
    SYNTAX                                         			Integer32
    MAX-ACCESS                                      			read-only
    STATUS                                          			current
    DESCRIPTION                    
    "The absolute interval number of this interval."
  ::= { nncRoutingStatsBorderPerTbl24HourIntervalEntry 5 }

 nncBPerTbl24HourIntervalFailedCallsDueInitLowerLvlDTLsNotGen		OBJECT-TYPE
    SYNTAX                                          			Counter32
    MAX-ACCESS                                      			read-only
    STATUS                                          			current
    DESCRIPTION                    
    "The number of failed calls generating initial lower level DTLs."
  ::= { nncRoutingStatsBorderPerTbl24HourIntervalEntry 6}

 nncBPerTbl24HourIntervalCallsGeneratingInitLowerLvlDTLs		OBJECT-TYPE
    SYNTAX                                          			Counter32
    MAX-ACCESS                                      			read-only
    STATUS                                          			current
    DESCRIPTION                    
    "The number of calls generating initial lower level DTLs."
  ::= { nncRoutingStatsBorderPerTbl24HourIntervalEntry 7 }

  nncBPerTbl24HourIntervalDTLGenCallsSuccessEstWithoutReroute     	OBJECT-TYPE
    SYNTAX                                         			Counter32
    MAX-ACCESS                                      			read-only
    STATUS                                          			current
    DESCRIPTION                    
    "The number of DTL generated calls successfully established without reroute."
  ::= { nncRoutingStatsBorderPerTbl24HourIntervalEntry 8 }

 nncBPerTbl24HourIntervalDTLGenCallsSuccessEstWithReroute		OBJECT-TYPE
    SYNTAX                                          			Counter32
    MAX-ACCESS                                      			read-only
    STATUS                                          			current
    DESCRIPTION                    
    "The number of DTL generated calls successfully established with reroute."
  ::= { nncRoutingStatsBorderPerTbl24HourIntervalEntry 9 }

 nncBPerTbl24HourIntervalDTLGenCallsFailedInReRouting     		OBJECT-TYPE
    SYNTAX                                          			Counter32
    MAX-ACCESS                                      			read-only
    STATUS                                          			current
    DESCRIPTION                    
    "The number of DTL generated calls failed in rerouting."
  ::= { nncRoutingStatsBorderPerTbl24HourIntervalEntry 10 }

 nncBPerTbl24HourIntervalSuccessCallsBdwGreaterThanRTDMinBdw	        OBJECT-TYPE
    SYNTAX                                         			Counter32
    MAX-ACCESS                                      			read-only
    STATUS                                          			current
    DESCRIPTION                    
    "The number of successful calls with bandwidth greater than RTD min bandwidth."
  ::= { nncRoutingStatsBorderPerTbl24HourIntervalEntry 11 }

 nncBPerTbl24HourIntervalFailedCallsBdwGreaterThanRTDMinBdw         	OBJECT-TYPE
    SYNTAX                                          			Counter32
    MAX-ACCESS                                      			read-only
    STATUS                                          			current
    DESCRIPTION                    
    "The number of failed calls with bandwidth greater than RTD min bandwidth."
  ::= { nncRoutingStatsBorderPerTbl24HourIntervalEntry 12 }

 nncBPerTbl24HourIntervalCrankbackReceivedAsAnEntryBorderNode     	OBJECT-TYPE
    SYNTAX                                          			Counter32
    MAX-ACCESS                                      			read-only
    STATUS                                          			current
    DESCRIPTION                    
    "The number of crankback received as an entry border node."
  ::= { nncRoutingStatsBorderPerTbl24HourIntervalEntry 13 }

  nncBPerTbl24HourIntervalLowerLvlDTLsGenDueToRecdCrankback		OBJECT-TYPE
    SYNTAX                                         			Counter32
    MAX-ACCESS                                      			read-only
    STATUS                                          			current
    DESCRIPTION                    
    "The number of lower Level DTLs generated due to received crankback."
  ::= { nncRoutingStatsBorderPerTbl24HourIntervalEntry 14 }


---------------------------------------------------------------------------------------
--  Table 17: Non Border Node PNNI Routing Total Statistics 15 Minutes Current Table
---------------------------------------------------------------------------------------
  nncRoutingStatsNonBorderTotal15MinCurrentTable OBJECT-TYPE
    SYNTAX       SEQUENCE OF NncRoutingStatsNonBorderTotal15MinCurrentEntry
    MAX-ACCESS   not-accessible
    STATUS       current
    DESCRIPTION  
    "The nncRoutingStatsNonBorderTotal15MinCurrentTable contains objects for monitoring the 
     non-border node PNNI routing total stats during the current 15 minute interval."
  ::= { nncRoutingStatsObjects 17 }


  nncRoutingStatsNonBorderTotal15MinCurrentEntry OBJECT-TYPE
    SYNTAX      NncRoutingStatsNonBorderTotal15MinCurrentEntry
    MAX-ACCESS  not-accessible
    STATUS      current
    DESCRIPTION  
    "An entry in the 15 minute current statistics table. Each conceptual row
    contains current total for the non-border node PNNI routing stats."
    INDEX       { nncCallControlGroupNumber }
  ::= { nncRoutingStatsNonBorderTotal15MinCurrentTable 1 }


  NncRoutingStatsNonBorderTotal15MinCurrentEntry ::=
    SEQUENCE {
      
      nncNBTotal15MinCurrentState					NncExtIntvlStateType,  
      nncNBTotal15MinCurrentAbsoluteIntervalNumber  			Integer32,
      nncNBTotal15MinCurrentFailedCallsDueToInitDTLNotGenerated		Counter32,
      nncNBTotal15MinCurrentCallsGeneratingAnInitDTL			Counter32,
      nncNBTotal15MinCurrentDTLOrigCallsSuccessEstWithoutReroute	Counter32,
      nncNBTotal15MinCurrentDTLOrigCallsSuccessEstWithReroute		Counter32,
      nncNBTotal15MinCurrentDTLOrigCallsFailedInReRouting		Counter32,
      nncNBTotal15MinCurrentSuccessCallsBdwGreaterThanRTDMinBdw		Counter32,
      nncNBTotal15MinCurrentFailedCallsBdwGreaterThanRTDMinBdw		Counter32,
      nncNBTotal15MinCurrentCrankbackReceivedAsDTLOriginator		Counter32,
      nncNBTotal15MinCurrentDTLsGeneratedDueToCrankback			Counter32,
      nncNBTotal15MinCurrentCallsRecdAsTransitNodeOverInsideLinks	Counter32,
      nncNBTotal15MinCurrentCrnkbksRecdAsTransitNodeOvInsideLnks	Counter32,
      nncNBTotal15MinCurrentSucdEndBlocCrnkbksRecdOvInsideLnks		Counter32
    }

 


 nncNBTotal15MinCurrentState	         				OBJECT-TYPE
    SYNTAX                                          			NncExtIntvlStateType
    MAX-ACCESS                                      			read-only
    STATUS                                          			current
    DESCRIPTION                    
    "The state of the current interval. The object provides a status for those entries
     which have been reset by the user, or have been subject to a wall clock time change."
  ::= { nncRoutingStatsNonBorderTotal15MinCurrentEntry 2}

 nncNBTotal15MinCurrentAbsoluteIntervalNumber		     		OBJECT-TYPE
    SYNTAX                                          			Integer32
    MAX-ACCESS                                      			read-only
    STATUS                                          			current
    DESCRIPTION                    
    "The absolute interval number of this interval."
  ::= { nncRoutingStatsNonBorderTotal15MinCurrentEntry 3 }

  nncNBTotal15MinCurrentFailedCallsDueToInitDTLNotGenerated		OBJECT-TYPE
    SYNTAX                                         			Counter32
    MAX-ACCESS                                      			read-only
    STATUS                                          			current
    DESCRIPTION                    
    "The number of failed calls due to initial DTL not generated."
  ::= { nncRoutingStatsNonBorderTotal15MinCurrentEntry 4 }

 nncNBTotal15MinCurrentCallsGeneratingAnInitDTL				OBJECT-TYPE
    SYNTAX                                          			Counter32
    MAX-ACCESS                                      			read-only
    STATUS                                          			current
    DESCRIPTION                    
    "The number of calls generating an initial DTL."
  ::= { nncRoutingStatsNonBorderTotal15MinCurrentEntry 5 }

 nncNBTotal15MinCurrentDTLOrigCallsSuccessEstWithoutReroute		OBJECT-TYPE
    SYNTAX                                          			Counter32
    MAX-ACCESS                                      			read-only
    STATUS                                          			current
    DESCRIPTION                    
    "The number of DTL originated calls successfully established without reroute."
  ::= { nncRoutingStatsNonBorderTotal15MinCurrentEntry 6 }

  nncNBTotal15MinCurrentDTLOrigCallsSuccessEstWithReroute      		OBJECT-TYPE
    SYNTAX                                         			Counter32
    MAX-ACCESS                                      			read-only
    STATUS                                          			current
    DESCRIPTION                    
    "The number of DTL originated calls successfully established with reroute."
  ::= { nncRoutingStatsNonBorderTotal15MinCurrentEntry 7 }

 nncNBTotal15MinCurrentDTLOrigCallsFailedInReRouting			OBJECT-TYPE
    SYNTAX                                          			Counter32
    MAX-ACCESS                                      			read-only
    STATUS                                          			current
    DESCRIPTION                    
    "The number of DTL originated calls failed in rerouting."
  ::= { nncRoutingStatsNonBorderTotal15MinCurrentEntry 8 }

 nncNBTotal15MinCurrentSuccessCallsBdwGreaterThanRTDMinBdw     		OBJECT-TYPE
    SYNTAX                                          			Counter32
    MAX-ACCESS                                      			read-only
    STATUS                                          			current
    DESCRIPTION                    
    "The number of successful calls with bandwidth greater than RTD min bandwidth."
  ::= { nncRoutingStatsNonBorderTotal15MinCurrentEntry 9 }

 nncNBTotal15MinCurrentFailedCallsBdwGreaterThanRTDMinBdw	        OBJECT-TYPE
    SYNTAX                                         			Counter32
    MAX-ACCESS                                      			read-only
    STATUS                                          			current
    DESCRIPTION                    
    "The number of failed calls with bandwidth greater than RTD min bandwidth."
  ::= { nncRoutingStatsNonBorderTotal15MinCurrentEntry 10 }

 nncNBTotal15MinCurrentCrankbackReceivedAsDTLOriginator         	OBJECT-TYPE
    SYNTAX                                          			Counter32
    MAX-ACCESS                                      			read-only
    STATUS                                          			current
    DESCRIPTION                    
    "The number of crankback received as DTL originator."
  ::= { nncRoutingStatsNonBorderTotal15MinCurrentEntry 11 }

 nncNBTotal15MinCurrentDTLsGeneratedDueToCrankback     			OBJECT-TYPE
    SYNTAX                                          			Counter32
    MAX-ACCESS                                      			read-only
    STATUS                                          			current
    DESCRIPTION                    
    "The number of DTLs generated due to crankback."
  ::= { nncRoutingStatsNonBorderTotal15MinCurrentEntry 12 }

  nncNBTotal15MinCurrentCallsRecdAsTransitNodeOverInsideLinks		OBJECT-TYPE
    SYNTAX                                         			Counter32
    MAX-ACCESS                                      			read-only
    STATUS                                          			current
    DESCRIPTION                    
    "The number of calls received as transit node over inside links."
  ::= { nncRoutingStatsNonBorderTotal15MinCurrentEntry 13 }

 nncNBTotal15MinCurrentCrnkbksRecdAsTransitNodeOvInsideLnks     	OBJECT-TYPE
    SYNTAX                                          			Counter32
    MAX-ACCESS                                      			read-only
    STATUS                                          			current
    DESCRIPTION                    
    "The number of crankbacks received as transit node over inside links."
  ::= { nncRoutingStatsNonBorderTotal15MinCurrentEntry 14 }

  nncNBTotal15MinCurrentSucdEndBlocCrnkbksRecdOvInsideLnks		OBJECT-TYPE
    SYNTAX                                         			Counter32
    MAX-ACCESS                                      			read-only
    STATUS                                          			current
    DESCRIPTION                    
    "The number of succeeding end blocked crankbacks received over inside links."
  ::= { nncRoutingStatsNonBorderTotal15MinCurrentEntry 15 }
 
---------------------------------------------------------------------------------------
--  Table 18: Non Border Node PNNI Routing Total Statistics 15 Minutes Interval Table
---------------------------------------------------------------------------------------
  nncRoutingStatsNonBorderTotal15MinIntervalTable OBJECT-TYPE
    SYNTAX       SEQUENCE OF NncRoutingStatsNonBorderTotal15MinIntervalEntry
    MAX-ACCESS   not-accessible
    STATUS       current
    DESCRIPTION  
    "The nncRoutingStatsNonBorderTotal15MinIntervalTable contains objects for monitoring the 
     non-border node PNNI routing total stats during the current 15 minute interval."
  ::= { nncRoutingStatsObjects 18 }


  nncRoutingStatsNonBorderTotal15MinIntervalEntry OBJECT-TYPE
    SYNTAX      NncRoutingStatsNonBorderTotal15MinIntervalEntry
    MAX-ACCESS  not-accessible
    STATUS      current
    DESCRIPTION  
    "An entry in the 15 minute current statistics table. Each conceptual row
    contains current total for the non-border node PNNI routing stats."
    INDEX       { nncCallControlGroupNumber,
                  nncNBTotal15MinIntervalNumber }
  ::= { nncRoutingStatsNonBorderTotal15MinIntervalTable 1 }


  NncRoutingStatsNonBorderTotal15MinIntervalEntry ::=
    SEQUENCE {
      
      nncNBTotal15MinIntervalNumber					Integer32,
      nncNBTotal15MinIntervalState					NncExtIntvlStateType,  
      nncNBTotal15MinIntervalAbsoluteIntervalNumber  			Integer32,
      nncNBTotal15MinIntervalFailedCallsDueToInitDTLNotGenerated	Counter32,
      nncNBTotal15MinIntervalCallsGeneratingAnInitDTL			Counter32,
      nncNBTotal15MinIntervalDTLOrigCallsSuccessEstWithoutReroute	Counter32,
      nncNBTotal15MinIntervalDTLOrigCallsSuccessEstWithReroute		Counter32,
      nncNBTotal15MinIntervalDTLOrigCallsFailedInReRouting		Counter32,
      nncNBTotal15MinIntervalSuccessCallsBdwGreaterThanRTDMinBdw	Counter32,
      nncNBTotal15MinIntervalFailedCallsBdwGreaterThanRTDMinBdw		Counter32,
      nncNBTotal15MinIntervalCrankbackReceivedAsDTLOriginator		Counter32,
      nncNBTotal15MinIntervalDTLsGeneratedDueToCrankback		Counter32,
      nncNBTotal15MinIntervalCallsRecdAsTransitNodeOverInsideLinks	Counter32,
      nncNBTotal15MinIntervalCrnkbksRecdAsTransitNodeOvInsideLnks  	Counter32,
      nncNBTotal15MinIntervalSucdEndBlocCrnkbksRecdOvInsideLnks  	Counter32
    }

 

  nncNBTotal15MinIntervalNumber						OBJECT-TYPE
    SYNTAX                                         			Integer32(1..96)
    MAX-ACCESS                                      			not-accessible
    STATUS                                          			current
    DESCRIPTION                    
    "The interval number of the statistics in this row."
  ::= { nncRoutingStatsNonBorderTotal15MinIntervalEntry 2}

 nncNBTotal15MinIntervalState	         				OBJECT-TYPE
    SYNTAX                                          			NncExtIntvlStateType
    MAX-ACCESS                                      			read-only
    STATUS                                          			current
    DESCRIPTION                    
    "The state of the interval represented by this row. The object provides a status for those
     entries which have been reset by the user, or have been subject to a wall clock time change."
  ::= { nncRoutingStatsNonBorderTotal15MinIntervalEntry 3 }

 nncNBTotal15MinIntervalAbsoluteIntervalNumber		     		OBJECT-TYPE
    SYNTAX                                          			Integer32
    MAX-ACCESS                                      			read-only
    STATUS                                          			current
    DESCRIPTION                    
    "The absolute interval number of this interval."
  ::= { nncRoutingStatsNonBorderTotal15MinIntervalEntry 4 }

  nncNBTotal15MinIntervalFailedCallsDueToInitDTLNotGenerated		OBJECT-TYPE
    SYNTAX                                         			Counter32
    MAX-ACCESS                                      			read-only
    STATUS                                          			current
    DESCRIPTION                    
    "The number of failed calls due to initial DTL not generated."
  ::= { nncRoutingStatsNonBorderTotal15MinIntervalEntry 5 }

 nncNBTotal15MinIntervalCallsGeneratingAnInitDTL			OBJECT-TYPE
    SYNTAX                                          			Counter32
    MAX-ACCESS                                      			read-only
    STATUS                                          			current
    DESCRIPTION                    
    "The number of calls generating an initial DTL."
  ::= { nncRoutingStatsNonBorderTotal15MinIntervalEntry 6}

 nncNBTotal15MinIntervalDTLOrigCallsSuccessEstWithoutReroute		OBJECT-TYPE
    SYNTAX                                          			Counter32
    MAX-ACCESS                                      			read-only
    STATUS                                          			current
    DESCRIPTION                    
    "The number of DTL originated calls successfully established without reroute."
  ::= { nncRoutingStatsNonBorderTotal15MinIntervalEntry 7 }

  nncNBTotal15MinIntervalDTLOrigCallsSuccessEstWithReroute      	OBJECT-TYPE
    SYNTAX                                         			Counter32
    MAX-ACCESS                                      			read-only
    STATUS                                          			current
    DESCRIPTION                    
    "The number of DTL originated calls successfully established with reroute."
  ::= { nncRoutingStatsNonBorderTotal15MinIntervalEntry 8 }

 nncNBTotal15MinIntervalDTLOrigCallsFailedInReRouting			OBJECT-TYPE
    SYNTAX                                          			Counter32
    MAX-ACCESS                                      			read-only
    STATUS                                          			current
    DESCRIPTION                    
    "The number of DTL originated calls failed in rerouting."
  ::= { nncRoutingStatsNonBorderTotal15MinIntervalEntry 9 }

 nncNBTotal15MinIntervalSuccessCallsBdwGreaterThanRTDMinBdw     	OBJECT-TYPE
    SYNTAX                                          			Counter32
    MAX-ACCESS                                      			read-only
    STATUS                                          			current
    DESCRIPTION                    
    "The number of successful calls with bandwidth greater than RTD min bandwidth."
  ::= { nncRoutingStatsNonBorderTotal15MinIntervalEntry 10 }

 nncNBTotal15MinIntervalFailedCallsBdwGreaterThanRTDMinBdw	        OBJECT-TYPE
    SYNTAX                                         			Counter32
    MAX-ACCESS                                      			read-only
    STATUS                                          			current
    DESCRIPTION                    
    "The number of failed calls with bandwidth greater than RTD min bandwidth."
  ::= { nncRoutingStatsNonBorderTotal15MinIntervalEntry 11 }

 nncNBTotal15MinIntervalCrankbackReceivedAsDTLOriginator         	OBJECT-TYPE
    SYNTAX                                          			Counter32
    MAX-ACCESS                                      			read-only
    STATUS                                          			current
    DESCRIPTION                    
    "The number of crankback received as DTL originator."
  ::= { nncRoutingStatsNonBorderTotal15MinIntervalEntry 12 }

 nncNBTotal15MinIntervalDTLsGeneratedDueToCrankback     		OBJECT-TYPE
    SYNTAX                                          			Counter32
    MAX-ACCESS                                      			read-only
    STATUS                                          			current
    DESCRIPTION                    
    "The number of DTLs generated due to crankback."
  ::= { nncRoutingStatsNonBorderTotal15MinIntervalEntry 13 }

  nncNBTotal15MinIntervalCallsRecdAsTransitNodeOverInsideLinks		OBJECT-TYPE
    SYNTAX                                         			Counter32
    MAX-ACCESS                                      			read-only
    STATUS                                          			current
    DESCRIPTION                    
    "The number of calls received as transit node over inside links."
  ::= { nncRoutingStatsNonBorderTotal15MinIntervalEntry 14 }

 nncNBTotal15MinIntervalCrnkbksRecdAsTransitNodeOvInsideLnks     	OBJECT-TYPE
    SYNTAX                                          			Counter32
    MAX-ACCESS                                      			read-only
    STATUS                                          			current
    DESCRIPTION                    
    "The number of calls received as transit node over inside links."
  ::= { nncRoutingStatsNonBorderTotal15MinIntervalEntry 15 }

  nncNBTotal15MinIntervalSucdEndBlocCrnkbksRecdOvInsideLnks		OBJECT-TYPE
    SYNTAX                                         			Counter32
    MAX-ACCESS                                      			read-only
    STATUS                                          			current
    DESCRIPTION                    
    "The number of succeeding end blocked crankbacks received over inside links."
  ::= { nncRoutingStatsNonBorderTotal15MinIntervalEntry 16 }


---------------------------------------------------------------------------------------
--  Table 19: Non Border Node PNNI Routing Total Statistics 24 Hour Current Table
---------------------------------------------------------------------------------------
  nncRoutingStatsNonBorderTotal24HourCurrentTable OBJECT-TYPE
    SYNTAX       SEQUENCE OF NncRoutingStatsNonBorderTotal24HourCurrentEntry
    MAX-ACCESS   not-accessible
    STATUS       current
    DESCRIPTION  
    "The nncRoutingStatsNonBorderTotal24HourCurrentTable contains objects for monitoring the 
     non-border node PNNI routing total stats during the current 24 hour interval."
  ::= { nncRoutingStatsObjects 19 }


  nncRoutingStatsNonBorderTotal24HourCurrentEntry OBJECT-TYPE
    SYNTAX      NncRoutingStatsNonBorderTotal24HourCurrentEntry
    MAX-ACCESS  not-accessible
    STATUS      current
    DESCRIPTION  
    "An entry in the 24 hour current statistics table. Each conceptual row
    contains current total for the non-border node PNNI routing stats."
    INDEX       { nncCallControlGroupNumber }
  ::= { nncRoutingStatsNonBorderTotal24HourCurrentTable 1 }


  NncRoutingStatsNonBorderTotal24HourCurrentEntry ::=
    SEQUENCE {
      
      nncNBTotal24HourCurrentState					NncExtIntvlStateType,  
      nncNBTotal24HourCurrentAbsoluteIntervalNumber  			Integer32,
      nncNBTotal24HourCurrentFailedCallsDueToInitDTLNotGenerated	Counter32,
      nncNBTotal24HourCurrentCallsGeneratingAnInitDTL			Counter32,
      nncNBTotal24HourCurrentDTLOrigCallsSuccessEstWithoutReroute	Counter32,
      nncNBTotal24HourCurrentDTLOrigCallsSuccessEstWithReroute		Counter32,
      nncNBTotal24HourCurrentDTLOrigCallsFailedInReRouting		Counter32,
      nncNBTotal24HourCurrentSuccessCallsBdwGreaterThanRTDMinBdw	Counter32,
      nncNBTotal24HourCurrentFailedCallsBdwGreaterThanRTDMinBdw		Counter32,
      nncNBTotal24HourCurrentCrankbackReceivedAsDTLOriginator		Counter32,
      nncNBTotal24HourCurrentDTLsGeneratedDueToCrankback		Counter32,
      nncNBTotal24HourCurrentCallsRecdAsTransitNodeOverInsideLinks	Counter32,
      nncNBTotal24HourCurrentCrnkbksRecdAsTransNodeOvInsideLnks  	Counter32,
      nncNBTotal24HourCurrentSucdEndBlocCrnkbksRecdOverInsideLinks  	Counter32
    }



 nncNBTotal24HourCurrentState	         				OBJECT-TYPE
    SYNTAX                                          			NncExtIntvlStateType
    MAX-ACCESS                                      			read-only
    STATUS                                          			current
    DESCRIPTION                    
    "The state of the current interval. The object provides a status for those entries
     which have been reset by the user, or have been subject to a wall clock time change."
  ::= { nncRoutingStatsNonBorderTotal24HourCurrentEntry 2}

 nncNBTotal24HourCurrentAbsoluteIntervalNumber		     		OBJECT-TYPE
    SYNTAX                                          			Integer32
    MAX-ACCESS                                      			read-only
    STATUS                                          			current
    DESCRIPTION                    
    "The absolute interval number of this interval."
  ::= { nncRoutingStatsNonBorderTotal24HourCurrentEntry 3 }

  nncNBTotal24HourCurrentFailedCallsDueToInitDTLNotGenerated		OBJECT-TYPE
    SYNTAX                                         			Counter32
    MAX-ACCESS                                      			read-only
    STATUS                                          			current
    DESCRIPTION                    
    "The number of failed calls due to initial DTL not generated."
  ::= { nncRoutingStatsNonBorderTotal24HourCurrentEntry 4 }

 nncNBTotal24HourCurrentCallsGeneratingAnInitDTL			OBJECT-TYPE
    SYNTAX                                          			Counter32
    MAX-ACCESS                                      			read-only
    STATUS                                          			current
    DESCRIPTION                    
    "The number of calls generating an initial DTL."
  ::= { nncRoutingStatsNonBorderTotal24HourCurrentEntry 5 }

 nncNBTotal24HourCurrentDTLOrigCallsSuccessEstWithoutReroute		OBJECT-TYPE
    SYNTAX                                          			Counter32
    MAX-ACCESS                                      			read-only
    STATUS                                          			current
    DESCRIPTION                    
    "The number of DTL originated calls successfully established without reroute."
  ::= { nncRoutingStatsNonBorderTotal24HourCurrentEntry 6}

  nncNBTotal24HourCurrentDTLOrigCallsSuccessEstWithReroute      	OBJECT-TYPE
    SYNTAX                                         			Counter32
    MAX-ACCESS                                      			read-only
    STATUS                                          			current
    DESCRIPTION                    
    "The number of DTL originated calls successfully established with reroute."
  ::= { nncRoutingStatsNonBorderTotal24HourCurrentEntry 7 }

 nncNBTotal24HourCurrentDTLOrigCallsFailedInReRouting			OBJECT-TYPE
    SYNTAX                                          			Counter32
    MAX-ACCESS                                      			read-only
    STATUS                                          			current
    DESCRIPTION                    
    "The number of DTL originated calls failed in rerouting."
  ::= { nncRoutingStatsNonBorderTotal24HourCurrentEntry 8 }

 nncNBTotal24HourCurrentSuccessCallsBdwGreaterThanRTDMinBdw     	OBJECT-TYPE
    SYNTAX                                          			Counter32
    MAX-ACCESS                                      			read-only
    STATUS                                          			current
    DESCRIPTION                    
    "The number of successful calls with bandwidth greater than RTD min bandwidth."
  ::= { nncRoutingStatsNonBorderTotal24HourCurrentEntry 9 }

 nncNBTotal24HourCurrentFailedCallsBdwGreaterThanRTDMinBdw	        OBJECT-TYPE
    SYNTAX                                         			Counter32
    MAX-ACCESS                                      			read-only
    STATUS                                          			current
    DESCRIPTION                    
    "The number of failed calls with bandwidth greater than RTD min bandwidth."
  ::= { nncRoutingStatsNonBorderTotal24HourCurrentEntry 10 }

 nncNBTotal24HourCurrentCrankbackReceivedAsDTLOriginator         	OBJECT-TYPE
    SYNTAX                                          			Counter32
    MAX-ACCESS                                      			read-only
    STATUS                                          			current
    DESCRIPTION                    
    "The number of crankback received as DTL originator."
  ::= { nncRoutingStatsNonBorderTotal24HourCurrentEntry 11 }

 nncNBTotal24HourCurrentDTLsGeneratedDueToCrankback     		OBJECT-TYPE
    SYNTAX                                          			Counter32
    MAX-ACCESS                                      			read-only
    STATUS                                          			current
    DESCRIPTION                    
    "The number of DTLs generated due to crankback."
  ::= { nncRoutingStatsNonBorderTotal24HourCurrentEntry 12 }

  nncNBTotal24HourCurrentCallsRecdAsTransitNodeOverInsideLinks		OBJECT-TYPE
    SYNTAX                                         			Counter32
    MAX-ACCESS                                      			read-only
    STATUS                                          			current
    DESCRIPTION                    
    "The number of calls received as transit node over inside links."
  ::= { nncRoutingStatsNonBorderTotal24HourCurrentEntry 13 }

 nncNBTotal24HourCurrentCrnkbksRecdAsTransNodeOvInsideLnks     		OBJECT-TYPE
    SYNTAX                                          			Counter32
    MAX-ACCESS                                      			read-only
    STATUS                                          			current
    DESCRIPTION                    
    "The number of calls received as transit node over inside links."
  ::= { nncRoutingStatsNonBorderTotal24HourCurrentEntry 14 }

  nncNBTotal24HourCurrentSucdEndBlocCrnkbksRecdOverInsideLinks		OBJECT-TYPE
    SYNTAX                                         			Counter32
    MAX-ACCESS                                      			read-only
    STATUS                                          			current
    DESCRIPTION                    
    "The number of succeeding end blocked crankbacks received over inside links."
  ::= { nncRoutingStatsNonBorderTotal24HourCurrentEntry 15 }
 
---------------------------------------------------------------------------------------
--  Table 20: Non Border Node PNNI Routing Total Statistics 24 Hour Interval Table
---------------------------------------------------------------------------------------
  nncRoutingStatsNonBorderTotal24HourIntervalTable OBJECT-TYPE
    SYNTAX       SEQUENCE OF NncRoutingStatsNonBorderTotal24HourIntervalEntry
    MAX-ACCESS   not-accessible
    STATUS       current
    DESCRIPTION  
    "The nncRoutingStatsNonBorderTotal24HourIntervalTable contains objects for monitoring the 
     non-border node PNNI routing total stats during the 24 hour interval."
  ::= { nncRoutingStatsObjects 20 }


  nncRoutingStatsNonBorderTotal24HourIntervalEntry OBJECT-TYPE
    SYNTAX      NncRoutingStatsNonBorderTotal24HourIntervalEntry
    MAX-ACCESS  not-accessible
    STATUS      current
    DESCRIPTION  
    "An entry in the 24 hour interval statistics table. Each conceptual row
    contains current total for the non-border node PNNI routing stats."
    INDEX       { nncCallControlGroupNumber,
                  nncNBTotal24HourIntervalNumber }
  ::= { nncRoutingStatsNonBorderTotal24HourIntervalTable 1 }


  NncRoutingStatsNonBorderTotal24HourIntervalEntry ::=
    SEQUENCE {
      
      nncNBTotal24HourIntervalNumber					Integer32,
      nncNBTotal24HourIntervalState					NncExtIntvlStateType,  
      nncNBTotal24HourIntervalAbsoluteIntervalNumber  			Integer32,
      nncNBTotal24HourIntervalFailedCallsDueToInitDTLNotGenerated	Counter32,
      nncNBTotal24HourIntervalCallsGeneratingAnInitDTL			Counter32,
      nncNBTotal24HourIntervalDTLOrigCallsSuccessEstWithoutReroute 	Counter32,
      nncNBTotal24HourIntervalDTLOrigCallsSuccessEstWithReroute		Counter32,
      nncNBTotal24HourIntervalDTLOrigCallsFailedInReRouting		Counter32,
      nncNBTotal24HourIntervalSuccessCallsBdwGreaterThanRTDMinBdw	Counter32,
      nncNBTotal24HourIntervalFailedCallsBdwGreaterThanRTDMinBdw	Counter32,
      nncNBTotal24HourIntervalCrankbackReceivedAsDTLOriginator		Counter32,
      nncNBTotal24HourIntervalDTLsGeneratedDueToCrankback		Counter32,
      nncNBTotal24HourIntervalCallsRecdAsTransitNodeOverInsideLinks	Counter32,
      nncNBTotal24HourIntervalCrnkbksRecdAsTransNodeOverInsideLnks  	Counter32,
      nncNBTotal24HourIntervalSucdEndBlocCrnkbksRecdOverInsideLnks  	Counter32
    }

   
  nncNBTotal24HourIntervalNumber					OBJECT-TYPE
    SYNTAX                                         			Integer32
    MAX-ACCESS                                      			not-accessible
    STATUS                                          			current
    DESCRIPTION                    
    "The interval number of the statistics in this row."
  ::= { nncRoutingStatsNonBorderTotal24HourIntervalEntry 2}

 nncNBTotal24HourIntervalState	         				OBJECT-TYPE
    SYNTAX                                          			NncExtIntvlStateType
    MAX-ACCESS                                      			read-only
    STATUS                                          			current
    DESCRIPTION                    
    "The state of the interval represented by this row. The object provides a status for those
     entries which have been reset by the user, or have been subject to a wall clock time change."
  ::= { nncRoutingStatsNonBorderTotal24HourIntervalEntry 3 }

 nncNBTotal24HourIntervalAbsoluteIntervalNumber		     		OBJECT-TYPE
    SYNTAX                                          			Integer32
    MAX-ACCESS                                      			read-only
    STATUS                                          			current
    DESCRIPTION                    
    "The absolute interval number of this interval."
  ::= { nncRoutingStatsNonBorderTotal24HourIntervalEntry 4 }

  nncNBTotal24HourIntervalFailedCallsDueToInitDTLNotGenerated		OBJECT-TYPE
    SYNTAX                                         			Counter32
    MAX-ACCESS                                      			read-only
    STATUS                                          			current
    DESCRIPTION                    
    "The number of failed calls due to initial DTL not generated."
  ::= { nncRoutingStatsNonBorderTotal24HourIntervalEntry 5 }

 nncNBTotal24HourIntervalCallsGeneratingAnInitDTL			OBJECT-TYPE
    SYNTAX                                          			Counter32
    MAX-ACCESS                                      			read-only
    STATUS                                          			current
    DESCRIPTION                    
    "The number of calls generating an initial DTL."
  ::= { nncRoutingStatsNonBorderTotal24HourIntervalEntry 6 }

 nncNBTotal24HourIntervalDTLOrigCallsSuccessEstWithoutReroute		OBJECT-TYPE
    SYNTAX                                          			Counter32
    MAX-ACCESS                                      			read-only
    STATUS                                          			current
    DESCRIPTION                    
    "The number of DTL originated calls successfully established without reroute."
  ::= { nncRoutingStatsNonBorderTotal24HourIntervalEntry 7 }

  nncNBTotal24HourIntervalDTLOrigCallsSuccessEstWithReroute      	OBJECT-TYPE
    SYNTAX                                         			Counter32
    MAX-ACCESS                                      			read-only
    STATUS                                          			current
    DESCRIPTION                    
    "The number of DTL originated calls successfully established with reroute."
  ::= { nncRoutingStatsNonBorderTotal24HourIntervalEntry 8 }

 nncNBTotal24HourIntervalDTLOrigCallsFailedInReRouting			OBJECT-TYPE
    SYNTAX                                          			Counter32
    MAX-ACCESS                                      			read-only
    STATUS                                          			current
    DESCRIPTION                    
    "The number of DTL originated calls failed in rerouting."
  ::= { nncRoutingStatsNonBorderTotal24HourIntervalEntry 9 }

 nncNBTotal24HourIntervalSuccessCallsBdwGreaterThanRTDMinBdw     	OBJECT-TYPE
    SYNTAX                                          			Counter32
    MAX-ACCESS                                      			read-only
    STATUS                                          			current
    DESCRIPTION                    
    "The number of successful calls with bandwidth greater than RTD min bandwidth."
  ::= { nncRoutingStatsNonBorderTotal24HourIntervalEntry 10 }

 nncNBTotal24HourIntervalFailedCallsBdwGreaterThanRTDMinBdw	        OBJECT-TYPE
    SYNTAX                                         			Counter32
    MAX-ACCESS                                      			read-only
    STATUS                                          			current
    DESCRIPTION                    
    "The number of failed calls with bandwidth greater than RTD min bandwidth."
  ::= { nncRoutingStatsNonBorderTotal24HourIntervalEntry 11 }

 nncNBTotal24HourIntervalCrankbackReceivedAsDTLOriginator         	OBJECT-TYPE
    SYNTAX                                          			Counter32
    MAX-ACCESS                                      			read-only
    STATUS                                          			current
    DESCRIPTION                    
    "The number of crankback received as DTL originator."
  ::= { nncRoutingStatsNonBorderTotal24HourIntervalEntry 12 }

 nncNBTotal24HourIntervalDTLsGeneratedDueToCrankback     		OBJECT-TYPE
    SYNTAX                                          			Counter32
    MAX-ACCESS                                      			read-only
    STATUS                                          			current
    DESCRIPTION                    
    "The number of DTLs generated due to crankback."
  ::= { nncRoutingStatsNonBorderTotal24HourIntervalEntry 13 }

  nncNBTotal24HourIntervalCallsRecdAsTransitNodeOverInsideLinks		OBJECT-TYPE
    SYNTAX                                         			Counter32
    MAX-ACCESS                                      			read-only
    STATUS                                          			current
    DESCRIPTION                    
    "The number of calls received as transit node over inside links."
  ::= { nncRoutingStatsNonBorderTotal24HourIntervalEntry 14 }

 nncNBTotal24HourIntervalCrnkbksRecdAsTransNodeOverInsideLnks    	OBJECT-TYPE
    SYNTAX                                          			Counter32
    MAX-ACCESS                                      			read-only
    STATUS                                          			current
    DESCRIPTION                    
    "The number of calls received as transit node over inside links."
  ::= { nncRoutingStatsNonBorderTotal24HourIntervalEntry 15 }

  nncNBTotal24HourIntervalSucdEndBlocCrnkbksRecdOverInsideLnks		OBJECT-TYPE
    SYNTAX                                         			Counter32
    MAX-ACCESS                                      			read-only
    STATUS                                          			current
    DESCRIPTION                    
    "The number of succeeding end blocked crankbacks received over inside links."
  ::= { nncRoutingStatsNonBorderTotal24HourIntervalEntry 16 }

 
---------------------------------------------------------------------------------------
--  Table 21: Border Node PNNI Routing Total Statistics 15 Minutes Current Table
---------------------------------------------------------------------------------------
  nncRoutingStatsBorderTotal15MinCurrentTable OBJECT-TYPE
    SYNTAX       SEQUENCE OF NncRoutingStatsBorderTotal15MinCurrentEntry
    MAX-ACCESS   not-accessible
    STATUS       current
    DESCRIPTION  
    "The nncRoutingStatsBorderTotal15MinCurrentTable contains objects for monitoring the 
     border node PNNI routing total stats during the current 15 minute interval."
  ::= { nncRoutingStatsObjects 21 }


  nncRoutingStatsBorderTotal15MinCurrentEntry OBJECT-TYPE
    SYNTAX      NncRoutingStatsBorderTotal15MinCurrentEntry
    MAX-ACCESS  not-accessible
    STATUS      current
    DESCRIPTION  
    "An entry in the 15 minute current statistics table. Each conceptual row
    contains current total for the border node PNNI routing stats."
    INDEX       { nncCallControlGroupNumber }
  ::= { nncRoutingStatsBorderTotal15MinCurrentTable 1 }


  NncRoutingStatsBorderTotal15MinCurrentEntry ::=
    SEQUENCE {
      
      nncBTotal15MinCurrentState					NncExtIntvlStateType,  
      nncBTotal15MinCurrentAbsoluteIntervalNumber  			Integer32,
      nncBTotal15MinCurrentFailedCallsDueToInitLowerLvlDTLNotGen	Counter32,
      nncBTotal15MinCurrentCallsGeneratingInitLowerLvlDTLs		Counter32,
      nncBTotal15MinCurrentDTLGenCallsSuccessEstWithoutReroute		Counter32,
      nncBTotal15MinCurrentDTLGenCallsSuccessEstWithReroute		Counter32,
      nncBTotal15MinCurrentDTLGenCallsFailedInReRouting			Counter32,
      nncBTotal15MinCurrentSuccessCallsBdwGreaterThanRTDMinBdw		Counter32,
      nncBTotal15MinCurrentFailedCallsBdwGreaterThanRTDMinBdw		Counter32,
      nncBTotal15MinCurrentCrankbackReceivedAsAnEntryBorderNode		Counter32,
      nncBTotal15MinCurrentLowerLvlDTLsGenDueToRecdCrankback		Counter32,
      nncBTotal15MinCurrentCallsRecdOverAnOutsideLink			Counter32,   
      nncBTotal15MinCurrentCallsTransmittedOverAnOutsideLink		Counter32,
      nncBTotal15MinCurrentCrankbksRecdOverAnOutsideLink		Counter32,
      nncBTotal15MinCurreSucdEndBlocCrankbksRecdOverOutsideLink  	Counter32,
      nncBTotal15MinCurrentCrankbkForwdedToPrevPGCrankbkLvlTooHigh	Counter32
    }

 
 nncBTotal15MinCurrentState					        OBJECT-TYPE
    SYNTAX                                         			NncExtIntvlStateType
    MAX-ACCESS                                      			read-only
    STATUS                                          			current
    DESCRIPTION                    
    "The state of the current interval. The object provides a status for those entries
     which have been reset by the user, or have been subject to a wall clock time change."
  ::= { nncRoutingStatsBorderTotal15MinCurrentEntry 2}


 nncBTotal15MinCurrentAbsoluteIntervalNumber	         		OBJECT-TYPE
    SYNTAX                                          			Integer32
    MAX-ACCESS                                      			read-only
    STATUS                                          			current
    DESCRIPTION                    
    "The absolute interval number of this interval."
  ::= { nncRoutingStatsBorderTotal15MinCurrentEntry 3 }

 nncBTotal15MinCurrentFailedCallsDueToInitLowerLvlDTLNotGen		OBJECT-TYPE
    SYNTAX                                          			Counter32
    MAX-ACCESS                                      			read-only
    STATUS                                          			current
    DESCRIPTION                    
    "The number of failed calls due to initial lower level DTL not generated."
  ::= { nncRoutingStatsBorderTotal15MinCurrentEntry 4 }

  nncBTotal15MinCurrentCallsGeneratingInitLowerLvlDTLs			OBJECT-TYPE
    SYNTAX                                         			Counter32
    MAX-ACCESS                                      			read-only
    STATUS                                          			current
    DESCRIPTION                    
    "The number of calls generating initial lower level DTLs."
  ::= { nncRoutingStatsBorderTotal15MinCurrentEntry 5 }

 nncBTotal15MinCurrentDTLGenCallsSuccessEstWithoutReroute		OBJECT-TYPE
    SYNTAX                                          			Counter32
    MAX-ACCESS                                      			read-only
    STATUS                                          			current
    DESCRIPTION                    
    "The number of DTL generated calls successfully established without reroute."
  ::= { nncRoutingStatsBorderTotal15MinCurrentEntry 6}

 nncBTotal15MinCurrentDTLGenCallsSuccessEstWithReroute			OBJECT-TYPE
    SYNTAX                                          			Counter32
    MAX-ACCESS                                      			read-only
    STATUS                                          			current
    DESCRIPTION                    
    "The number of DTL generated calls successfully established with reroute."
  ::= { nncRoutingStatsBorderTotal15MinCurrentEntry 7 }

  nncBTotal15MinCurrentDTLGenCallsFailedInReRouting      		OBJECT-TYPE
    SYNTAX                                         			Counter32
    MAX-ACCESS                                      			read-only
    STATUS                                          			current
    DESCRIPTION                    
    "The number of DTL generated calls failed in rerouting."
  ::= { nncRoutingStatsBorderTotal15MinCurrentEntry 8 }

 nncBTotal15MinCurrentSuccessCallsBdwGreaterThanRTDMinBdw		OBJECT-TYPE
    SYNTAX                                          			Counter32
    MAX-ACCESS                                      			read-only
    STATUS                                          			current
    DESCRIPTION                    
    "The number of successful calls with bandwidth greater than RTD min bandwidth."
  ::= { nncRoutingStatsBorderTotal15MinCurrentEntry 9 }

 nncBTotal15MinCurrentFailedCallsBdwGreaterThanRTDMinBdw     		OBJECT-TYPE
    SYNTAX                                          			Counter32
    MAX-ACCESS                                      			read-only
    STATUS                                          			current
    DESCRIPTION                    
    "The number of failed calls with bandwidth greater than RTD min bandwidth."
  ::= { nncRoutingStatsBorderTotal15MinCurrentEntry 10 }

 nncBTotal15MinCurrentCrankbackReceivedAsAnEntryBorderNode	        OBJECT-TYPE
    SYNTAX                                         			Counter32
    MAX-ACCESS                                      			read-only
    STATUS                                          			current
    DESCRIPTION                    
    "The number of crankback received as an entry border node."
  ::= { nncRoutingStatsBorderTotal15MinCurrentEntry 11 }

 nncBTotal15MinCurrentLowerLvlDTLsGenDueToRecdCrankback         	OBJECT-TYPE
    SYNTAX                                          			Counter32
    MAX-ACCESS                                      			read-only
    STATUS                                          			current
    DESCRIPTION                    
    "The number of lower level DTLs generated due to received crankback."
  ::= { nncRoutingStatsBorderTotal15MinCurrentEntry 12 }

 nncBTotal15MinCurrentCallsRecdOverAnOutsideLink     			OBJECT-TYPE
    SYNTAX                                          			Counter32
    MAX-ACCESS                                      			read-only
    STATUS                                          			current
    DESCRIPTION                    
    "The number of calls received over an outside link."
  ::= { nncRoutingStatsBorderTotal15MinCurrentEntry 13 }

  nncBTotal15MinCurrentCallsTransmittedOverAnOutsideLink		OBJECT-TYPE
    SYNTAX                                         			Counter32
    MAX-ACCESS                                      			read-only
    STATUS                                          			current
    DESCRIPTION                    
    "The number of calls transmitted over an outside link."
  ::= { nncRoutingStatsBorderTotal15MinCurrentEntry 14 }

 nncBTotal15MinCurrentCrankbksRecdOverAnOutsideLink     		OBJECT-TYPE
    SYNTAX                                          			Counter32
    MAX-ACCESS                                      			read-only
    STATUS                                          			current
    DESCRIPTION                    
    "The number of crankbacks received over an outside link."
  ::= { nncRoutingStatsBorderTotal15MinCurrentEntry 15 }

   nncBTotal15MinCurreSucdEndBlocCrankbksRecdOverOutsideLink		OBJECT-TYPE
    SYNTAX                                         			Counter32
    MAX-ACCESS                                      			read-only
    STATUS                                          			current
    DESCRIPTION                    
    "The number of succeeding end blocked crankbacks received over an outside links."
  ::= { nncRoutingStatsBorderTotal15MinCurrentEntry 16 }

nncBTotal15MinCurrentCrankbkForwdedToPrevPGCrankbkLvlTooHigh		OBJECT-TYPE
    SYNTAX                                         			Counter32
    MAX-ACCESS                                      			read-only
    STATUS                                          			current
    DESCRIPTION                    
    "The number of crankback forwarded to previous PG, crankback level too high."
  ::= { nncRoutingStatsBorderTotal15MinCurrentEntry 17 }


---------------------------------------------------------------------------------------
--  Table 22: Border Node PNNI Routing Total Statistics 15 Minutes Interval Table
---------------------------------------------------------------------------------------
  nncRoutingStatsBorderTotal15MinIntervalTable OBJECT-TYPE
    SYNTAX       SEQUENCE OF NncRoutingStatsBorderTotal15MinIntervalEntry
    MAX-ACCESS   not-accessible
    STATUS       current
    DESCRIPTION  
    "The nncRoutingStatsBorderTotal15MinIntervalTable contains objects for monitoring the 
     border node PNNI routing total stats during the current 15 minute interval."
  ::= { nncRoutingStatsObjects 22 }


  nncRoutingStatsBorderTotal15MinIntervalEntry OBJECT-TYPE
    SYNTAX      NncRoutingStatsBorderTotal15MinIntervalEntry
    MAX-ACCESS  not-accessible
    STATUS      current
    DESCRIPTION  
    "An entry in the 15 minute current statistics table. Each conceptual row
    contains current total for the border node PNNI routing stats."
    INDEX       { nncCallControlGroupNumber,   
                  nncBTotal15MinIntervalNumber }
  ::= { nncRoutingStatsBorderTotal15MinIntervalTable 1 }


  NncRoutingStatsBorderTotal15MinIntervalEntry ::=
    SEQUENCE {
      
      nncBTotal15MinIntervalNumber					Integer32,
      nncBTotal15MinIntervalState					NncExtIntvlStateType,  
      nncBTotal15MinIntervalAbsoluteIntervalNumber  			Integer32,
      nncBTotal15MinIntervalFailedCallsDueToInitLowerLvlDTLNotGen	Counter32,
      nncBTotal15MinIntervalCallsGeneratingInitLowerLvlDTLs		Counter32,
      nncBTotal15MinIntervalDTLGenCallsSuccessEstWithoutReroute		Counter32,
      nncBTotal15MinIntervalDTLGenCallsSuccessEstWithReroute		Counter32,
      nncBTotal15MinIntervalDTLGenCallsFailedInReRouting		Counter32,
      nncBTotal15MinIntervalSuccessCallsBdwGreaterThanRTDMinBdw		Counter32,
      nncBTotal15MinIntervalFailedCallsBdwGreaterThanRTDMinBdw		Counter32,
      nncBTotal15MinIntervalCrankbackReceivedAsAnEntryBorderNode	Counter32,
      nncBTotal15MinIntervalLowerLvlDTLsGenDueToRecdCrankback		Counter32,
      nncBTotal15MinIntervalCallsRecdOverAnOutsideLink			Counter32,   
      nncBTotal15MinIntervalCallsTransmittedOverAnOutsideLink		Counter32,
      nncBTotal15MinIntervalCrankbksRecdOverAnOutsideLink		Counter32,
      nncBTotal15MinIntervalSucdEndBlocCrankbksRecdOverOutsideLink  	Counter32,
      nncBTotal15MinIntervalCrankbkForwdedToPrevPGCrankbkLvlTooHigh	Counter32
    }

 

 nncBTotal15MinIntervalNumber						OBJECT-TYPE
    SYNTAX                                         			Integer32(1..96)
    MAX-ACCESS                                      			not-accessible
    STATUS                                          			current
    DESCRIPTION                    
    "The interval number of the statistics in this row."
  ::= { nncRoutingStatsBorderTotal15MinIntervalEntry 2 }


 nncBTotal15MinIntervalState	         				OBJECT-TYPE
    SYNTAX                                          			NncExtIntvlStateType
    MAX-ACCESS                                      			read-only
    STATUS                                          			current
    DESCRIPTION                    
    "The state of the interval represented by this row. The object provides a status for those
     entries which have been reset by the user, or have been subject to a wall clock time change."
  ::= { nncRoutingStatsBorderTotal15MinIntervalEntry 3 }

 nncBTotal15MinIntervalAbsoluteIntervalNumber		     		OBJECT-TYPE
    SYNTAX                                          			Integer32
    MAX-ACCESS                                      			read-only
    STATUS                                          			current
    DESCRIPTION                    
    "The absolute interval number of this interval."
  ::= { nncRoutingStatsBorderTotal15MinIntervalEntry 4 }

  nncBTotal15MinIntervalFailedCallsDueToInitLowerLvlDTLNotGen		OBJECT-TYPE
    SYNTAX                                         			Counter32
    MAX-ACCESS                                      			read-only
    STATUS                                          			current
    DESCRIPTION                    
    "The number of failed calls due to initial lower level DTL not generated."
  ::= { nncRoutingStatsBorderTotal15MinIntervalEntry 5 }

 nncBTotal15MinIntervalCallsGeneratingInitLowerLvlDTLs			OBJECT-TYPE
    SYNTAX                                          			Counter32
    MAX-ACCESS                                      			read-only
    STATUS                                          			current
    DESCRIPTION                    
    "The number of calls generating initial lower level DTLs."
  ::= { nncRoutingStatsBorderTotal15MinIntervalEntry 6 }

 nncBTotal15MinIntervalDTLGenCallsSuccessEstWithoutReroute		OBJECT-TYPE
    SYNTAX                                          			Counter32
    MAX-ACCESS                                      			read-only
    STATUS                                          			current
    DESCRIPTION                    
    "The number of DTL generated calls successfully established without reroute."
  ::= { nncRoutingStatsBorderTotal15MinIntervalEntry 7 }

  nncBTotal15MinIntervalDTLGenCallsSuccessEstWithReroute       		OBJECT-TYPE
    SYNTAX                                         			Counter32
    MAX-ACCESS                                      			read-only
    STATUS                                          			current
    DESCRIPTION                    
    "The number of DTL generated calls successfully established with reroute."
  ::= { nncRoutingStatsBorderTotal15MinIntervalEntry 8 }

 nncBTotal15MinIntervalDTLGenCallsFailedInReRouting			OBJECT-TYPE
    SYNTAX                                          			Counter32
    MAX-ACCESS                                      			read-only
    STATUS                                          			current
    DESCRIPTION                    
    "The number of DTL generated calls failed in rerouting."
  ::= { nncRoutingStatsBorderTotal15MinIntervalEntry 9 }

 nncBTotal15MinIntervalSuccessCallsBdwGreaterThanRTDMinBdw     		OBJECT-TYPE
    SYNTAX                                          			Counter32
    MAX-ACCESS                                      			read-only
    STATUS                                          			current
    DESCRIPTION                    
    "The number of successful calls with bandwidth greater than RTD min bandwidth."
  ::= { nncRoutingStatsBorderTotal15MinIntervalEntry 10 }

 nncBTotal15MinIntervalFailedCallsBdwGreaterThanRTDMinBdw	        OBJECT-TYPE
    SYNTAX                                         			Counter32
    MAX-ACCESS                                      			read-only
    STATUS                                          			current
    DESCRIPTION                    
    "The number of failed calls with bandwidth greater than RTD min bandwidth."
  ::= { nncRoutingStatsBorderTotal15MinIntervalEntry 11 }

 nncBTotal15MinIntervalCrankbackReceivedAsAnEntryBorderNode         	OBJECT-TYPE
    SYNTAX                                          			Counter32
    MAX-ACCESS                                      			read-only
    STATUS                                          			current
    DESCRIPTION                    
    "The number of crankback received as an entry border node."
  ::= { nncRoutingStatsBorderTotal15MinIntervalEntry 12 }

 nncBTotal15MinIntervalLowerLvlDTLsGenDueToRecdCrankback     		OBJECT-TYPE
    SYNTAX                                          			Counter32
    MAX-ACCESS                                      			read-only
    STATUS                                          			current
    DESCRIPTION                    
    "The number of lower level DTLs generated due to received crankback."
  ::= { nncRoutingStatsBorderTotal15MinIntervalEntry 13 }

  nncBTotal15MinIntervalCallsRecdOverAnOutsideLink			OBJECT-TYPE
    SYNTAX                                         			Counter32
    MAX-ACCESS                                      			read-only
    STATUS                                          			current
    DESCRIPTION                    
    "The number of calls received over an outside link."
  ::= { nncRoutingStatsBorderTotal15MinIntervalEntry 14 }

 nncBTotal15MinIntervalCallsTransmittedOverAnOutsideLink     		OBJECT-TYPE
    SYNTAX                                          			Counter32
    MAX-ACCESS                                      			read-only
    STATUS                                          			current
    DESCRIPTION                    
    "The number of calls transmitted over an outside link."
  ::= { nncRoutingStatsBorderTotal15MinIntervalEntry 15 }

  nncBTotal15MinIntervalCrankbksRecdOverAnOutsideLink			OBJECT-TYPE
    SYNTAX                                         			Counter32
    MAX-ACCESS                                      			read-only
    STATUS                                          			current
    DESCRIPTION                    
    "The number of crankbacks received over an outside link."
  ::= { nncRoutingStatsBorderTotal15MinIntervalEntry 16 }

nncBTotal15MinIntervalSucdEndBlocCrankbksRecdOverOutsideLink		OBJECT-TYPE
    SYNTAX                                         			Counter32
    MAX-ACCESS                                      			read-only
    STATUS                                          			current
    DESCRIPTION                    
    "The number of succeeding end blocked crankbacks received over an outside link."
  ::= { nncRoutingStatsBorderTotal15MinIntervalEntry 17 }

nncBTotal15MinIntervalCrankbkForwdedToPrevPGCrankbkLvlTooHigh		OBJECT-TYPE
    SYNTAX                                         			Counter32
    MAX-ACCESS                                      			read-only
    STATUS                                          			current
    DESCRIPTION                    
    "The number of crankback forwarded to previous PG, crankback level too high."
  ::= { nncRoutingStatsBorderTotal15MinIntervalEntry 18 }


---------------------------------------------------------------------------------------
--  Table 23: Border Node PNNI Routing Total Statistics 24 Hour Current Table
---------------------------------------------------------------------------------------
  nncRoutingStatsBorderTotal24HourCurrentTable OBJECT-TYPE
    SYNTAX       SEQUENCE OF NncRoutingStatsBorderTotal24HourCurrentEntry
    MAX-ACCESS   not-accessible
    STATUS       current
    DESCRIPTION  
    "The nncRoutingStatsBorderTotal24HourCurrentTable contains objects for monitoring the 
     border node PNNI routing total stats during the current 24 hour interval."
  ::= { nncRoutingStatsObjects 23 }


  nncRoutingStatsBorderTotal24HourCurrentEntry OBJECT-TYPE
    SYNTAX      NncRoutingStatsBorderTotal24HourCurrentEntry
    MAX-ACCESS  not-accessible
    STATUS      current
    DESCRIPTION  
    "An entry in the 24 hour current statistics table. Each conceptual row
    contains current total for the border node PNNI routing stats."
    INDEX       { nncCallControlGroupNumber }
  ::= { nncRoutingStatsBorderTotal24HourCurrentTable 1 }


  NncRoutingStatsBorderTotal24HourCurrentEntry ::=
    SEQUENCE {
      
      nncBTotal24HourCurrentState					NncExtIntvlStateType,  
      nncBTotal24HourCurrentAbsoluteIntervalNumber  			Integer32,
      nncBTotal24HourCurrentFailedCallsDueToInitLowerLvlDTLNotGen	Counter32,
      nncBTotal24HourCurrentCallsGeneratingInitLowerLvlDTLs		Counter32,
      nncBTotal24HourCurrentDTLGenCallsSuccessEstWithoutReroute		Counter32,
      nncBTotal24HourCurrentDTLGenCallsSuccessEstWithReroute		Counter32,
      nncBTotal24HourCurrentDTLGenCallsFailedInReRouting		Counter32,
      nncBTotal24HourCurrentSuccessCallsBdwGreaterThanRTDMinBdw		Counter32,
      nncBTotal24HourCurrentFailedCallsBdwGreaterThanRTDMinBdw		Counter32,
      nncBTotal24HourCurrentCrankbackReceivedAsAnEntryBorderNode	Counter32,
      nncBTotal24HourCurrentLowerLvlDTLsGenDueToRecdCrankback		Counter32,
      nncBTotal24HourCurrentCallsRecdOverAnOutsideLink			Counter32,   
      nncBTotal24HourCurrentCallsTransmittedOverAnOutsideLink		Counter32,
      nncBTotal24HourCurrentCrankbksRecdOverAnOutsideLink		Counter32,
      nncBTotal24HourCurrentSucdEndBlocCrankbksRecdOverOutsideLink  	Counter32,
      nncBTotal24HourCurrentCrankbkForwdedToPrevPGCrankbkLvlTooHigh	Counter32
    }

 

 nncBTotal24HourCurrentState						OBJECT-TYPE
    SYNTAX                                         			NncExtIntvlStateType
    MAX-ACCESS                                      			read-only
    STATUS                                          			current
    DESCRIPTION                    
    "The state of the current interval. The object provides a status for those entries
     which have been reset by the user, or have been subject to a wall clock time change."
  ::= { nncRoutingStatsBorderTotal24HourCurrentEntry 2 }


 nncBTotal24HourCurrentAbsoluteIntervalNumber	         		OBJECT-TYPE
    SYNTAX                                          			Integer32
    MAX-ACCESS                                      			read-only
    STATUS                                          			current
    DESCRIPTION                    
    "The absolute interval number of this interval."
  ::= { nncRoutingStatsBorderTotal24HourCurrentEntry 3 }

 nncBTotal24HourCurrentFailedCallsDueToInitLowerLvlDTLNotGen		OBJECT-TYPE
    SYNTAX                                          			Counter32
    MAX-ACCESS                                      			read-only
    STATUS                                          			current
    DESCRIPTION                    
    "The number of failed calls due to initial lower level DTL not generated."
  ::= { nncRoutingStatsBorderTotal24HourCurrentEntry 4 }

  nncBTotal24HourCurrentCallsGeneratingInitLowerLvlDTLs			OBJECT-TYPE
    SYNTAX                                         			Counter32
    MAX-ACCESS                                      			read-only
    STATUS                                          			current
    DESCRIPTION                    
    "The number of calls generating initial lower level DTLs."
  ::= { nncRoutingStatsBorderTotal24HourCurrentEntry 5 }

 nncBTotal24HourCurrentDTLGenCallsSuccessEstWithoutReroute		OBJECT-TYPE
    SYNTAX                                          			Counter32
    MAX-ACCESS                                      			read-only
    STATUS                                          			current
    DESCRIPTION                    
    "The number of DTL generated calls successfully established without reroute."
  ::= { nncRoutingStatsBorderTotal24HourCurrentEntry 6 }

 nncBTotal24HourCurrentDTLGenCallsSuccessEstWithReroute			OBJECT-TYPE
    SYNTAX                                          			Counter32
    MAX-ACCESS                                      			read-only
    STATUS                                          			current
    DESCRIPTION                    
    "The number of DTL generated calls successfully established with reroute."
  ::= { nncRoutingStatsBorderTotal24HourCurrentEntry 7 }

  nncBTotal24HourCurrentDTLGenCallsFailedInReRouting      		OBJECT-TYPE
    SYNTAX                                         			Counter32
    MAX-ACCESS                                      			read-only
    STATUS                                          			current
    DESCRIPTION                    
    "The number of DTL generated calls failed in rerouting."
  ::= { nncRoutingStatsBorderTotal24HourCurrentEntry 8 }

 nncBTotal24HourCurrentSuccessCallsBdwGreaterThanRTDMinBdw		OBJECT-TYPE
    SYNTAX                                          			Counter32
    MAX-ACCESS                                      			read-only
    STATUS                                          			current
    DESCRIPTION                    
    "The number of successful calls with bandwidth greater than RTD min bandwidth."
  ::= { nncRoutingStatsBorderTotal24HourCurrentEntry 9 }

 nncBTotal24HourCurrentFailedCallsBdwGreaterThanRTDMinBdw     		OBJECT-TYPE
    SYNTAX                                          			Counter32
    MAX-ACCESS                                      			read-only
    STATUS                                          			current
    DESCRIPTION                    
    "The number of failed calls with bandwidth greater than RTD min bandwidth."
  ::= { nncRoutingStatsBorderTotal24HourCurrentEntry 10 }

 nncBTotal24HourCurrentCrankbackReceivedAsAnEntryBorderNode	        OBJECT-TYPE
    SYNTAX                                         			Counter32
    MAX-ACCESS                                      			read-only
    STATUS                                          			current
    DESCRIPTION                    
    "The number of crankback received as an entry border node."
  ::= { nncRoutingStatsBorderTotal24HourCurrentEntry 11 }

 nncBTotal24HourCurrentLowerLvlDTLsGenDueToRecdCrankback         	OBJECT-TYPE
    SYNTAX                                          			Counter32
    MAX-ACCESS                                      			read-only
    STATUS                                          			current
    DESCRIPTION                    
    "The number of lower level DTLs generated due to received crankback."
  ::= { nncRoutingStatsBorderTotal24HourCurrentEntry 12 }

 nncBTotal24HourCurrentCallsRecdOverAnOutsideLink     			OBJECT-TYPE
    SYNTAX                                          			Counter32
    MAX-ACCESS                                      			read-only
    STATUS                                          			current
    DESCRIPTION                    
    "The number of calls received over an outside link."
  ::= { nncRoutingStatsBorderTotal24HourCurrentEntry 13 }

  nncBTotal24HourCurrentCallsTransmittedOverAnOutsideLink		OBJECT-TYPE
    SYNTAX                                         			Counter32
    MAX-ACCESS                                      			read-only
    STATUS                                          			current
    DESCRIPTION                    
    "The number of calls transmitted over an outside link."
  ::= { nncRoutingStatsBorderTotal24HourCurrentEntry 14 }

 nncBTotal24HourCurrentCrankbksRecdOverAnOutsideLink     		OBJECT-TYPE
    SYNTAX                                          			Counter32
    MAX-ACCESS                                      			read-only
    STATUS                                          			current
    DESCRIPTION                    
    "The number of crankbacks received over an outside link."
  ::= { nncRoutingStatsBorderTotal24HourCurrentEntry 15 }

  nncBTotal24HourCurrentSucdEndBlocCrankbksRecdOverOutsideLink		OBJECT-TYPE
    SYNTAX                                         			Counter32
    MAX-ACCESS                                      			read-only
    STATUS                                          			current
    DESCRIPTION                    
    "The number of succeeding end blocked crankbacks received over an outside link."
  ::= { nncRoutingStatsBorderTotal24HourCurrentEntry 16 }

nncBTotal24HourCurrentCrankbkForwdedToPrevPGCrankbkLvlTooHigh		OBJECT-TYPE
    SYNTAX                                         			Counter32
    MAX-ACCESS                                      			read-only
    STATUS                                          			current
    DESCRIPTION                    
    "The number of crankback forwarded to previous PG, crankback level too high."
  ::= { nncRoutingStatsBorderTotal24HourCurrentEntry 17 }


---------------------------------------------------------------------------------------
--  Table 24: Border Node PNNI Routing Total Statistics 24 Hour Interval Table
---------------------------------------------------------------------------------------
  nncRoutingStatsBorderTotal24HourIntervalTable OBJECT-TYPE
    SYNTAX       SEQUENCE OF NncRoutingStatsBorderTotal24HourIntervalEntry
    MAX-ACCESS   not-accessible
    STATUS       current
    DESCRIPTION  
    "The nncRoutingStatsBorderTotal24HourIntervalTable contains objects for monitoring the 
     border node PNNI routing total stats during the 24 hour interval."
  ::= { nncRoutingStatsObjects 24 }


  nncRoutingStatsBorderTotal24HourIntervalEntry OBJECT-TYPE
    SYNTAX      NncRoutingStatsBorderTotal24HourIntervalEntry
    MAX-ACCESS  not-accessible
    STATUS      current
    DESCRIPTION  
    "An entry in the 24 hour interval statistics table. Each conceptual row
    contains current total for the border node PNNI routing stats."
    INDEX       { nncCallControlGroupNumber,
                  nncBTotal24HourIntervalNumber }
  ::= { nncRoutingStatsBorderTotal24HourIntervalTable 1 }


  NncRoutingStatsBorderTotal24HourIntervalEntry ::=
    SEQUENCE {
      
      nncBTotal24HourIntervalNumber					Integer32,
      nncBTotal24HourIntervalState					NncExtIntvlStateType,  
      nncBTotal24HourIntervalAbsoluteIntervalNumber  			Integer32,
      nncBTotal24HourIntervalFailedCallsDueToInitLowerLvlDTLNotGen	Counter32,
      nncBTotal24HourIntervalCallsGeneratingInitLowerLvlDTLs		Counter32,
      nncBTotal24HourIntervalDTLGenCallsSuccessEstWithoutReroute	Counter32,
      nncBTotal24HourIntervalDTLGenCallsSuccessEstWithReroute		Counter32,
      nncBTotal24HourIntervalDTLGenCallsFailedInReRouting		Counter32,
      nncBTotal24HourIntervalSuccessCallsBdwGreaterThanRTDMinBdw	Counter32,
      nncBTotal24HourIntervalFailedCallsBdwGreaterThanRTDMinBdw		Counter32,
      nncBTotal24HourIntervalCrankbackReceivedAsAnEntryBorderNode	Counter32,
      nncBTotal24HourIntervalLowerLvlDTLsGenDueToRecdCrankback		Counter32,
      nncBTotal24HourIntervalCallsRecdOverAnOutsideLink			Counter32,   
      nncBTotal24HourIntervalCallsTransmittedOverAnOutsideLink		Counter32,
      nncBTotal24HourIntervalCrankbksRecdOverAnOutsideLink		Counter32,
      nncBTotal24HourIntervalSucdEndBlocCrankbksRecdOverOutsideLink  	Counter32,
      nncBTotal24HourIntervalCrankbkFwdToPrevPGCrankbkLvlTooHigh	Counter32
    }

 
 nncBTotal24HourIntervalNumber				        	OBJECT-TYPE
    SYNTAX                                         			Integer32
    MAX-ACCESS                                      			not-accessible
    STATUS                                          			current
    DESCRIPTION                    
    "The interval number of the statistics in this row."
  ::= { nncRoutingStatsBorderTotal24HourIntervalEntry 2}


 nncBTotal24HourIntervalState	         				OBJECT-TYPE
    SYNTAX                                          			NncExtIntvlStateType
    MAX-ACCESS                                      			read-only
    STATUS                                          			current
    DESCRIPTION                    
    "The state of the interval represented by this row. The object provides a status for those
     entries which have been reset by the user, or have been subject to a wall clock time change."
  ::= { nncRoutingStatsBorderTotal24HourIntervalEntry 3 }

 nncBTotal24HourIntervalAbsoluteIntervalNumber		     		OBJECT-TYPE
    SYNTAX                                          			Integer32
    MAX-ACCESS                                      			read-only
    STATUS                                          			current
    DESCRIPTION                    
    "The absolute interval number of this interval."
  ::= { nncRoutingStatsBorderTotal24HourIntervalEntry 4 }

  nncBTotal24HourIntervalFailedCallsDueToInitLowerLvlDTLNotGen		OBJECT-TYPE
    SYNTAX                                         			Counter32
    MAX-ACCESS                                      			read-only
    STATUS                                          			current
    DESCRIPTION                    
    "The number of failed calls due to initial lower level DTL not generated."
  ::= { nncRoutingStatsBorderTotal24HourIntervalEntry 5 }

 nncBTotal24HourIntervalCallsGeneratingInitLowerLvlDTLs			OBJECT-TYPE
    SYNTAX                                          			Counter32
    MAX-ACCESS                                      			read-only
    STATUS                                          			current
    DESCRIPTION                    
    "The number of calls generating initial lower level DTLs."
  ::= { nncRoutingStatsBorderTotal24HourIntervalEntry 6 }

 nncBTotal24HourIntervalDTLGenCallsSuccessEstWithoutReroute		OBJECT-TYPE
    SYNTAX                                          			Counter32
    MAX-ACCESS                                      			read-only
    STATUS                                          			current
    DESCRIPTION                    
    "The number of DTL generated calls successfully established without reroute."
  ::= { nncRoutingStatsBorderTotal24HourIntervalEntry 7 }

  nncBTotal24HourIntervalDTLGenCallsSuccessEstWithReroute      		OBJECT-TYPE
    SYNTAX                                         			Counter32
    MAX-ACCESS                                      			read-only
    STATUS                                          			current
    DESCRIPTION                    
    "The number of DTL generated calls successfully established with reroute."
  ::= { nncRoutingStatsBorderTotal24HourIntervalEntry 8 }

 nncBTotal24HourIntervalDTLGenCallsFailedInReRouting			OBJECT-TYPE
    SYNTAX                                          			Counter32
    MAX-ACCESS                                      			read-only
    STATUS                                          			current
    DESCRIPTION                    
    "The number of DTL generated calls failed in rerouting."
  ::= { nncRoutingStatsBorderTotal24HourIntervalEntry 9 }

 nncBTotal24HourIntervalSuccessCallsBdwGreaterThanRTDMinBdw     	OBJECT-TYPE
    SYNTAX                                          			Counter32
    MAX-ACCESS                                      			read-only
    STATUS                                          			current
    DESCRIPTION                    
    "The number of successful calls with bandwidth greater than RTD min bandwidth."
  ::= { nncRoutingStatsBorderTotal24HourIntervalEntry 10 }

 nncBTotal24HourIntervalFailedCallsBdwGreaterThanRTDMinBdw	        OBJECT-TYPE
    SYNTAX                                         			Counter32
    MAX-ACCESS                                      			read-only
    STATUS                                          			current
    DESCRIPTION                    
    "The number of failed calls with bandwidth greater than RTD min bandwidth."
  ::= { nncRoutingStatsBorderTotal24HourIntervalEntry 11 }

 nncBTotal24HourIntervalCrankbackReceivedAsAnEntryBorderNode         	OBJECT-TYPE
    SYNTAX                                          			Counter32
    MAX-ACCESS                                      			read-only
    STATUS                                          			current
    DESCRIPTION                    
    "The number of crankback received as an entry border node."
  ::= { nncRoutingStatsBorderTotal24HourIntervalEntry 12 }

 nncBTotal24HourIntervalLowerLvlDTLsGenDueToRecdCrankback     		OBJECT-TYPE
    SYNTAX                                          			Counter32
    MAX-ACCESS                                      			read-only
    STATUS                                          			current
    DESCRIPTION                    
    "The number of lower level DTLs generated due to received crankback."
  ::= { nncRoutingStatsBorderTotal24HourIntervalEntry 13 }

  nncBTotal24HourIntervalCallsRecdOverAnOutsideLink			OBJECT-TYPE
    SYNTAX                                         			Counter32
    MAX-ACCESS                                      			read-only
    STATUS                                          			current
    DESCRIPTION                    
    "The number of calls received over an outside link."
  ::= { nncRoutingStatsBorderTotal24HourIntervalEntry 14 }

 nncBTotal24HourIntervalCallsTransmittedOverAnOutsideLink     		OBJECT-TYPE
    SYNTAX                                          			Counter32
    MAX-ACCESS                                      			read-only
    STATUS                                          			current
    DESCRIPTION                    
    "The number of calls transmitted over an outside link."
  ::= { nncRoutingStatsBorderTotal24HourIntervalEntry 15 }

  nncBTotal24HourIntervalCrankbksRecdOverAnOutsideLink			OBJECT-TYPE
    SYNTAX                                         			Counter32
    MAX-ACCESS                                      			read-only
    STATUS                                          			current
    DESCRIPTION                    
    "The number of crankbacks received over an outside link."
  ::= { nncRoutingStatsBorderTotal24HourIntervalEntry 16 }

 nncBTotal24HourIntervalSucdEndBlocCrankbksRecdOverOutsideLink		OBJECT-TYPE
    SYNTAX                                         			Counter32
    MAX-ACCESS                                      			read-only
    STATUS                                          			current
    DESCRIPTION                    
    "The number of succeeding end blocked crankbacks received over an outside link."
  ::= { nncRoutingStatsBorderTotal24HourIntervalEntry 17 }

 nncBTotal24HourIntervalCrankbkFwdToPrevPGCrankbkLvlTooHigh		OBJECT-TYPE
    SYNTAX                                         			Counter32
    MAX-ACCESS                                      			read-only
    STATUS                                          			current
    DESCRIPTION                    
    "The number of crankback forwarded to previous PG, crankback level too high."
  ::= { nncRoutingStatsBorderTotal24HourIntervalEntry 18 }



--------------------------------------------------------------------------------
--  Raw counters of the stats.
--   
--  25- Raw Counters for Static and PNNI Routing Common Statistic Table
--  26- Raw Counters for Static Routing Specific Statistic Table

--  27- Raw Counters for Non Border Node PNNI Per Routing Table Statistics Table
--  28- Raw Counters for Border Node PNNI Per Routing Table Statistics Table


--  29- Raw Counters for Non-Border Node PNNI Total Statistics Table
--  30- Raw Counters for Border Node PNNI Total Statistics Table

--------------------------------------------------------------------------------
--Table 25 Raw Counters for Static and PNNI Routing Common Statistic Table
--------------------------------------------------------------------------------

  nncRoutingStatsRawCommonTable OBJECT-TYPE
    SYNTAX       SEQUENCE OF NncRoutingStatsRawCommonEntry
    MAX-ACCESS   not-accessible
    STATUS       current
    DESCRIPTION  
    "The nncRoutingStatsRawCommonTable contains objects for monitoring the 
     raw counters for static and PNNI routing common stats."
  ::= { nncRoutingStatsObjects 25 }


  nncRoutingStatsRawCommonEntry OBJECT-TYPE
    SYNTAX      NncRoutingStatsRawCommonEntry
    MAX-ACCESS  not-accessible
    STATUS      current
    DESCRIPTION  
    "An entry in the nncRoutingStatsRawCommonTable. Each conceptual row
    contains the raw counter for static and PNNI routing common stats."
    INDEX       { nncCallControlGroupNumber }
  ::= { nncRoutingStatsRawCommonTable 1 }


  NncRoutingStatsRawCommonEntry ::=
    SEQUENCE {
      
      nncRoutingStatsRawCommonSuccessRoutedCallsOrigFromLocalSubs    Counter32,
      nncRoutingStatsRawCommonSuccessRtedCallsTransitedViaThisNode	Counter32,
      nncRoutingStatsRawCommonSuccessRoutedCallsTermToLocalSubs		Counter32,
      nncRoutingStatsRawCommonSuccessRoutedLocalCalls	 		Counter32,
      nncRoutingStatsRawCommonCallsOrigFromLocalCalls			Counter32,
      nncRoutingStatsRawCommonCallsTermToLocalCalls			Counter32,
      nncRoutingStatsRawCommonLocalCallAttempts				Counter32,
      nncRoutingStatsRawCommonCallsClearedDueToNoRoutingTabEntry     Counter32,
      nncRoutingStatsRawCommonCrankbacksGeneratedByThisNode		Counter32,
      nncRoutingStatsRawCommonFailedCallsAtLocalSubs			Counter32,
      nncRoutingStatsRawCommonCallsSuccessRerouted		 	Counter32,
      nncRoutingStatsRawCommonCallsFailedInRerouting			Counter32
    }

  


  nncRoutingStatsRawCommonSuccessRoutedCallsOrigFromLocalSubs        	OBJECT-TYPE
    SYNTAX                                          			Counter32
    MAX-ACCESS                                      			read-only
    STATUS                                          			current
    DESCRIPTION                    
    "Raw counter for the number of successfully routed calls originated from local subscribers."
  ::= { nncRoutingStatsRawCommonEntry 2}

   nncRoutingStatsRawCommonSuccessRtedCallsTransitedViaThisNode      	OBJECT-TYPE
    SYNTAX                                          			Counter32
    MAX-ACCESS                                      			read-only
    STATUS                                          			current
    DESCRIPTION                    
    "Raw counter for the number of successfully routed calls transited via this node."
  ::= { nncRoutingStatsRawCommonEntry 3 }

  nncRoutingStatsRawCommonSuccessRoutedCallsTermToLocalSubs         	OBJECT-TYPE
    SYNTAX                                          			Counter32
    MAX-ACCESS                                      			read-only
    STATUS                                          		 	current
    DESCRIPTION                    
    "Raw counter for the number of successfully routed calls terminated to local subscribers."
  ::= { nncRoutingStatsRawCommonEntry 4 }

  nncRoutingStatsRawCommonSuccessRoutedLocalCalls                    	OBJECT-TYPE
    SYNTAX                                          			Counter32
    MAX-ACCESS                                      			read-only
    STATUS                                          			current
    DESCRIPTION                    
    "Raw counter for the number of successfully routed local calls."
  ::= { nncRoutingStatsRawCommonEntry 5 }

  nncRoutingStatsRawCommonCallsOrigFromLocalCalls  		        OBJECT-TYPE
    SYNTAX                                          			Counter32
    MAX-ACCESS                                      			read-only
    STATUS                                          			current
    DESCRIPTION                    
    "Raw counter for the number of calls originated from local calls."
  ::= { nncRoutingStatsRawCommonEntry 6 }

  nncRoutingStatsRawCommonCallsTermToLocalCalls		        	OBJECT-TYPE
    SYNTAX                                          			Counter32
    MAX-ACCESS                                      			read-only
    STATUS                                          			current
    DESCRIPTION                    
    "Raw counters for the number of calls terminated to local subscribers."
  ::= { nncRoutingStatsRawCommonEntry 7 }

  nncRoutingStatsRawCommonLocalCallAttempts 			        OBJECT-TYPE
    SYNTAX                                          			Counter32
    MAX-ACCESS                                      			read-only
    STATUS                                          			current
    DESCRIPTION                    
    "Raw counter for the number of local call attempts."
  ::= { nncRoutingStatsRawCommonEntry 8 }

  nncRoutingStatsRawCommonCallsClearedDueToNoRoutingTabEntry         	OBJECT-TYPE
    SYNTAX                                          			Counter32
    MAX-ACCESS                                      			read-only
    STATUS                                          			current
    DESCRIPTION                    
    "Raw counter for the number of calls cleared due to no routing table entry."
  ::= { nncRoutingStatsRawCommonEntry 9 }

  nncRoutingStatsRawCommonCrankbacksGeneratedByThisNode	        	OBJECT-TYPE
    SYNTAX                                          			Counter32
    MAX-ACCESS                                      			read-only
    STATUS                                          			current
    DESCRIPTION                    
    "Raw counter for the number of crankbacks generated by this node."
  ::= { nncRoutingStatsRawCommonEntry 10 }

  nncRoutingStatsRawCommonFailedCallsAtLocalSubs		        OBJECT-TYPE
    SYNTAX                                          			Counter32
    MAX-ACCESS                                      			read-only
    STATUS                                          			current
    DESCRIPTION                    
    "Raw counter for the number of failed calls at local subscribers."
  ::= { nncRoutingStatsRawCommonEntry 11 }

  nncRoutingStatsRawCommonCallsSuccessRerouted		        	OBJECT-TYPE
    SYNTAX                                          			Counter32
    MAX-ACCESS                                      			read-only
    STATUS                                          			current
    DESCRIPTION                    
    "Raw counter for the number of calls successfully rerouted."
  ::= { nncRoutingStatsRawCommonEntry 12 }

  nncRoutingStatsRawCommonCallsFailedInRerouting		        OBJECT-TYPE
    SYNTAX                                          			Counter32
    MAX-ACCESS                                      			read-only
    STATUS                                          			current
    DESCRIPTION                    
    "Raw counter for the number of calls failed in rerouting."
  ::= { nncRoutingStatsRawCommonEntry 13 }

  
--------------------------------------------------------------------------------
--Table 26 Raw Counters for Static Routing Specific Statistic Table
--------------------------------------------------------------------------------

  nncRoutingStatsRawSpecificTable OBJECT-TYPE
    SYNTAX       SEQUENCE OF NncRoutingStatsRawSpecificEntry
    MAX-ACCESS   not-accessible
    STATUS       current
    DESCRIPTION  
    "The nncRoutingStatsRawSpecificTable contains objects for monitoring the 
     raw counters for static routing specific stats."
  ::= { nncRoutingStatsObjects 26 }


  nncRoutingStatsRawSpecificEntry OBJECT-TYPE
    SYNTAX      NncRoutingStatsRawSpecificEntry
    MAX-ACCESS  not-accessible
    STATUS      current
    DESCRIPTION  
    "An entry in the nncRoutingStatsRawSpecificTable. Each conceptual row
    contains the raw counter for static routing specific stats."
    INDEX       { nncCallControlGroupNumber }
  ::= { nncRoutingStatsRawSpecificTable 1 }


  NncRoutingStatsRawSpecificEntry ::=
    SEQUENCE {
      
      nncRoutingStatsRawSpecificCallsStaticallyRoutedByThisNode     	Counter32,
      nncRoutingStatsRawSpecificCrankbacksReceivedByThisNode		Counter32,
      nncRoutingStatsRawSpecificRerouteAttempts				Counter32,
      nncRoutingStatsRawSpecificRoutingLoopsDetectedByThisNode		Counter32
  }

 

  nncRoutingStatsRawSpecificCallsStaticallyRoutedByThisNode         	OBJECT-TYPE
    SYNTAX                                          			Counter32
    MAX-ACCESS                                      			read-only
    STATUS                                          			current
    DESCRIPTION                    
    "Raw counter for the nhe number of calls statically routed by this node."
  ::= { nncRoutingStatsRawSpecificEntry 2 }

  nncRoutingStatsRawSpecificCrankbacksReceivedByThisNode	       	OBJECT-TYPE
    SYNTAX                                          			Counter32
    MAX-ACCESS                                      			read-only
    STATUS                                          			current
    DESCRIPTION                    
    "Raw counter for the number ofcrankbacks received by this node."
  ::= { nncRoutingStatsRawSpecificEntry 3 }

nncRoutingStatsRawSpecificRerouteAttempts		         	OBJECT-TYPE
    SYNTAX                                          			Counter32
    MAX-ACCESS                                      			read-only
    STATUS                                          			current
    DESCRIPTION                    
    "Raw counter for the number of rerouted attempts."
  ::= { nncRoutingStatsRawSpecificEntry 4 }

  nncRoutingStatsRawSpecificRoutingLoopsDetectedByThisNode       	OBJECT-TYPE
    SYNTAX                                          			Counter32
    MAX-ACCESS                                      			read-only
    STATUS                                          			current
    DESCRIPTION                    
    "Raw counter for the number of routing loops detected by this node."
  ::= { nncRoutingStatsRawSpecificEntry 5 }



----------------------------------------------------------------------------------------
--  Table 27  Raw Counters for Non Border Node PNNI Per Routing Table Statistics Table ----------------------------------------------------------------------------------------
  nncRoutingStatsRawNonBorderPerTblTable OBJECT-TYPE
    SYNTAX       SEQUENCE OF NncRoutingStatsRawNonBorderPerTblEntry
    MAX-ACCESS   not-accessible
    STATUS       current
    DESCRIPTION  
    "The nncRoutingStatsRawNonBorderPerTblTable contains objects for monitoring the 
     raw counters for non border node PNNI per routing table stats."
  ::= { nncRoutingStatsObjects 27 }


  nncRoutingStatsRawNonBorderPerTblEntry OBJECT-TYPE
    SYNTAX      NncRoutingStatsRawNonBorderPerTblEntry
    MAX-ACCESS  not-accessible
    STATUS      current
    DESCRIPTION  
    "An entry in the nncRoutingStatsRawNonBorderPerTblEntry. Each conceptual row
    contains the raw counter for non border node PNNI per routing table stats."
    INDEX       { nncCallControlGroupNumber, 
                  nncRawNBPerTbleTableDescriptor }
  ::= { nncRoutingStatsRawNonBorderPerTblTable 1 }


  NncRoutingStatsRawNonBorderPerTblEntry ::=
    SEQUENCE {
      
      nncRawNBPerTbleTableDescriptor					INTEGER,
      nncRawNBPerTbleFailedCallsDueToInitDTLNotGenerated		Counter32,
      nncRawNBPerTbleCallsGeneratingAnInitDTL				Counter32,
      nncRawNBPerTbleDTLOrigCallsSuccessEstWithoutReroute		Counter32,
      nncRawNBPerTbleDTLOrigCallsSuccessEstWithReroute			Counter32,
      nncRawNBPerTbleDTLOrigCallsFailedInReRouting			Counter32,
      nncRawNBPerTbleSuccessCallsBdwGreaterThanRTDMinBdw		Counter32,
      nncRawNBPerTbleFailedCallsBdwGreaterThanRTDMinBdw			Counter32,
      nncRawNBPerTbleCrankbackReceivedAsDTLOriginator			Counter32,
      nncRawNBPerTbleDTLsGeneratedDueToCrankback			Counter32
    }

 

 nncRawNBPerTbleTableDescriptor	         				OBJECT-TYPE
    SYNTAX                                          			INTEGER(0..6)
    MAX-ACCESS                                      			not-accessible
    STATUS                                          			current
    DESCRIPTION                    
    "nncTableDescriptor determines a routing table number whose stats are to be displayed."
  ::= { nncRoutingStatsRawNonBorderPerTblEntry 2}


 nncRawNBPerTbleFailedCallsDueToInitDTLNotGenerated			OBJECT-TYPE
    SYNTAX                                          			Counter32
    MAX-ACCESS                                      			read-only
    STATUS                                          			current
    DESCRIPTION                    
    "Raw counter for the number of failed calls due to initial DTL not generated."
  ::= { nncRoutingStatsRawNonBorderPerTblEntry 3 }

 nncRawNBPerTbleCallsGeneratingAnInitDTL		        	OBJECT-TYPE
    SYNTAX                                          			Counter32
    MAX-ACCESS                                      			read-only
    STATUS                                          			current
    DESCRIPTION                    
    "Raw counter for The number of calls generating an initial DTL."
  ::= { nncRoutingStatsRawNonBorderPerTblEntry 4 }

  nncRawNBPerTbleDTLOrigCallsSuccessEstWithoutReroute     		OBJECT-TYPE
    SYNTAX                                         			Counter32
    MAX-ACCESS                                      			read-only
    STATUS                                          			current
    DESCRIPTION                    
    "Raw counter for the number of DTL originated calls successfully established without reroute."
  ::= { nncRoutingStatsRawNonBorderPerTblEntry 5 }

 nncRawNBPerTbleDTLOrigCallsSuccessEstWithReroute			OBJECT-TYPE
    SYNTAX                                          			Counter32
    MAX-ACCESS                                      			read-only
    STATUS                                          			current
    DESCRIPTION                    
    "Raw counter for the number of DTL originated calls successfully established with reroute."
  ::= { nncRoutingStatsRawNonBorderPerTblEntry 6 }

 nncRawNBPerTbleDTLOrigCallsFailedInReRouting     			OBJECT-TYPE
    SYNTAX                                          			Counter32
    MAX-ACCESS                                      			read-only
    STATUS                                          			current
    DESCRIPTION                    
    "Raw counter for the number of DTL originated calls failed in rerouting."
  ::= { nncRoutingStatsRawNonBorderPerTblEntry 7 }

 nncRawNBPerTbleSuccessCallsBdwGreaterThanRTDMinBdw	        	OBJECT-TYPE
    SYNTAX                                         			Counter32
    MAX-ACCESS                                      			read-only
    STATUS                                          			current
    DESCRIPTION                    
    "Raw counter for the number of successful calls with bandwidth greater than RTD min bandwidth."
  ::= { nncRoutingStatsRawNonBorderPerTblEntry 8 }

 nncRawNBPerTbleFailedCallsBdwGreaterThanRTDMinBdw         		OBJECT-TYPE
    SYNTAX                                          			Counter32
    MAX-ACCESS                                      			read-only
    STATUS                                          			current
    DESCRIPTION                    
    "Raw counter for the number of failed calls with bandwidth greater than RTD min bandwidth."
  ::= { nncRoutingStatsRawNonBorderPerTblEntry 9 }

 nncRawNBPerTbleCrankbackReceivedAsDTLOriginator     			OBJECT-TYPE
    SYNTAX                                          			Counter32
    MAX-ACCESS                                      			read-only
    STATUS                                          			current
    DESCRIPTION                    
    "Raw counter for the number of crankback received as DTL originator."
  ::= { nncRoutingStatsRawNonBorderPerTblEntry 10 }

  nncRawNBPerTbleDTLsGeneratedDueToCrankback				OBJECT-TYPE
    SYNTAX                                         			Counter32
    MAX-ACCESS                                      			read-only
    STATUS                                          			current
    DESCRIPTION                    
    "Raw counter for the number of DTSs generated due to crankback."
  ::= { nncRoutingStatsRawNonBorderPerTblEntry 11 }


---------------------------------------------------------------------------------------
--  Table 28- Raw Counters for Border Node PNNI Per Routing Table Statistics Table
---------------------------------------------------------------------------------------
  nncRoutingStatsRawBorderPerTblTable OBJECT-TYPE
    SYNTAX       SEQUENCE OF NncRoutingStatsRawBorderPerTblEntry
    MAX-ACCESS   not-accessible
    STATUS       current
    DESCRIPTION  
    "The nncRoutingStatsRawBorderPerTblTable contains objects for monitoring the 
     raw counters for border node PNNI per routing table stats."
  ::= { nncRoutingStatsObjects 28 }


  nncRoutingStatsRawBorderPerTblEntry OBJECT-TYPE
    SYNTAX      NncRoutingStatsRawBorderPerTblEntry
    MAX-ACCESS  not-accessible
    STATUS      current
    DESCRIPTION  
    "An entry in the nncRoutingStatsRawNonBorderPerTblEntry. Each conceptual row
    contains the raw counter for border node PNNI per routing table stats."
    INDEX       { nncCallControlGroupNumber, nncRawBPerTblTableDescriptor }
  ::= { nncRoutingStatsRawBorderPerTblTable 1 }


  NncRoutingStatsRawBorderPerTblEntry ::=
    SEQUENCE {
      
      nncRawBPerTblTableDescriptor				        INTEGER,
      nncRawBPerTblFailedCallsDueInitLowerLvlDTLsNotGen			Counter32,
      nncRawBPerTblCallsGeneratingInitLowerLvlDTLs			Counter32,
      nncRawBPerTblDTLGenCallsSuccessEstWithoutReroute			Counter32,
      nncRawBPerTblDTLGenCallsSuccessEstWithReroute			Counter32,
      nncRawBPerTblDTLGenCallsFailedInReRouting				Counter32,
      nncRawBPerTblSuccessCallsBdwGreaterThanRTDMinBdw			Counter32,
      nncRawBPerTblFailedCallsBdwGreaterThanRTDMinBdw			Counter32,
      nncRawBPerTblCrankbackReceivedAsAnEntryBorderNode			Counter32,
      nncRawBPerTblLowerLvlDTLsGenDueToRecdCrankback			Counter32
    }

 

 nncRawBPerTblTableDescriptor	         				OBJECT-TYPE
    SYNTAX                                          			INTEGER(0..6)
    MAX-ACCESS                                      			not-accessible
    STATUS                                          			current
    DESCRIPTION                    
    "nncTableDescriptor determines a routing table number whose stats are to be displayed."
  ::= { nncRoutingStatsRawBorderPerTblEntry 2 }


 nncRawBPerTblFailedCallsDueInitLowerLvlDTLsNotGen			OBJECT-TYPE
    SYNTAX                                          			Counter32
    MAX-ACCESS                                      			read-only
    STATUS                                          			current
    DESCRIPTION                    
    "Raw counter for the number of failed calls generating initial lower level DTLs."
  ::= { nncRoutingStatsRawBorderPerTblEntry 3 }

 nncRawBPerTblCallsGeneratingInitLowerLvlDTLs				OBJECT-TYPE
    SYNTAX                                          			Counter32
    MAX-ACCESS                                      			read-only
    STATUS                                          			current
    DESCRIPTION                    
    "Raw counter for the number of calls generating initial lower level DTLs."
  ::= { nncRoutingStatsRawBorderPerTblEntry 4 }

  nncRawBPerTblDTLGenCallsSuccessEstWithoutReroute     			OBJECT-TYPE
    SYNTAX                                         			Counter32
    MAX-ACCESS                                      			read-only
    STATUS                                          			current
    DESCRIPTION                    
    "Raw counter for the number of DTL generated calls successfully established without reroute."
  ::= { nncRoutingStatsRawBorderPerTblEntry 5 }

 nncRawBPerTblDTLGenCallsSuccessEstWithReroute				OBJECT-TYPE
    SYNTAX                                          			Counter32
    MAX-ACCESS                                      			read-only
    STATUS                                          			current
    DESCRIPTION                    
    "Raw counter for the number of DTL generated calls successfully established with reroute."
  ::= { nncRoutingStatsRawBorderPerTblEntry 6 }

 nncRawBPerTblDTLGenCallsFailedInReRouting     				OBJECT-TYPE
    SYNTAX                                          			Counter32
    MAX-ACCESS                                      			read-only
    STATUS                                          			current
    DESCRIPTION                    
    "Raw counter for the number of DTL generated calls failed in rerouting."
  ::= { nncRoutingStatsRawBorderPerTblEntry 7 }

 nncRawBPerTblSuccessCallsBdwGreaterThanRTDMinBdw	        	OBJECT-TYPE
    SYNTAX                                         			Counter32
    MAX-ACCESS                                      			read-only
    STATUS                                          			current
    DESCRIPTION                    
    "Raw counter for the number of successful calls with bandwidth greater than RTD min bandwidth."
  ::= { nncRoutingStatsRawBorderPerTblEntry 8 }

 nncRawBPerTblFailedCallsBdwGreaterThanRTDMinBdw         		OBJECT-TYPE
    SYNTAX                                          			Counter32
    MAX-ACCESS                                      			read-only
    STATUS                                          			current
    DESCRIPTION                    
    "Raw counter for the number of failed calls with bandwidth greater than RTD min bandwidth."
  ::= { nncRoutingStatsRawBorderPerTblEntry 9 }

 nncRawBPerTblCrankbackReceivedAsAnEntryBorderNode     			OBJECT-TYPE
    SYNTAX                                          			Counter32
    MAX-ACCESS                                      			read-only
    STATUS                                          			current
    DESCRIPTION                    
    "Raw counter for the number of crankback received as an entry border node."
  ::= { nncRoutingStatsRawBorderPerTblEntry 10 }

  nncRawBPerTblLowerLvlDTLsGenDueToRecdCrankback			OBJECT-TYPE
    SYNTAX                                         			Counter32
    MAX-ACCESS                                      			read-only
    STATUS                                          			current
    DESCRIPTION                    
    "Raw counters for the number of lower level DTLs generated due to received crankback."
  ::= { nncRoutingStatsRawBorderPerTblEntry 11 }


 
---------------------------------------------------------------------------------------
--  Table 29: Raw Counters for Non-Border Node PNNI Total Statistics Table
---------------------------------------------------------------------------------------
  nncRoutingStatsRawNonBorderTotalTable OBJECT-TYPE
    SYNTAX       SEQUENCE OF NncRoutingStatsRawNonBorderTotalEntry
    MAX-ACCESS   not-accessible
    STATUS       current
    DESCRIPTION  
    "The nncRoutingStatsRawNonBorderTotalTable contains objects for monitoring the 
     raw counters for non border node PNNI routing total stats."
  ::= { nncRoutingStatsObjects 29 }


  nncRoutingStatsRawNonBorderTotalEntry OBJECT-TYPE
    SYNTAX      NncRoutingStatsRawNonBorderTotalEntry
    MAX-ACCESS  not-accessible
    STATUS      current
    DESCRIPTION  
    "An entry in the nncRoutingStatsRawNonBorderTotalTable. Each conceptual row
    contains the raw counter for non border node PNNI routing total stats."
    INDEX       { nncCallControlGroupNumber }
  ::= { nncRoutingStatsRawNonBorderTotalTable 1 }


  NncRoutingStatsRawNonBorderTotalEntry ::=
    SEQUENCE {
      
      nncRawNBTotalFailedCallsDueToInitDTLNotGenerated		Counter32,
      nncRawNBTotalCallsGeneratingAnInitDTL			Counter32,
      nncRawNBTotalDTLOrigCallsSuccessEstWithoutReroute		Counter32,
      nncRawNBTotalDTLOrigCallsSuccessEstWithReroute		Counter32,
      nncRawNBTotalDTLOrigCallsFailedInReRouting		Counter32,
      nncRawNBTotalSuccessCallsBdwGreaterThanRTDMinBdw		Counter32,
      nncRawNBTotalFailedCallsBdwGreaterThanRTDMinBdw		Counter32,
      nncRawNBTotalCrankbackReceivedAsDTLOriginator		Counter32,
      nncRawNBTotalDTLsGeneratedDueToCrankback			Counter32,
      nncRawNBTotalCallsRecdAsTransitNodeOverInsideLinks	Counter32,
      nncRawNBTotalCrnkbksRecdAsTransitNodeOvInsideLnks		Counter32,
      nncRawNBTotalSucdEndBlocCrnkbksRecdOvInsideLnks		Counter32
    }

  
  nncRawNBTotalFailedCallsDueToInitDTLNotGenerated		OBJECT-TYPE
    SYNTAX                                         		Counter32
    MAX-ACCESS                                      		read-only
    STATUS                                       		current
    DESCRIPTION                    
    "Raw counter for the total number of failed calls due to initial DTL not generated."
  ::= { nncRoutingStatsRawNonBorderTotalEntry 2 }

 nncRawNBTotalCallsGeneratingAnInitDTL				OBJECT-TYPE
    SYNTAX                                         		Counter32
    MAX-ACCESS                                      		read-only
    STATUS                                          		current
    DESCRIPTION                    
    "Raw counter for the total number of calls generating an initail DTL."
  ::= { nncRoutingStatsRawNonBorderTotalEntry 3 }

 nncRawNBTotalDTLOrigCallsSuccessEstWithoutReroute		OBJECT-TYPE
    SYNTAX                                          		Counter32
    MAX-ACCESS                                      		read-only
    STATUS                                          		current
    DESCRIPTION                    
    "Raw counter for the total number of DTL originated calls successfully established without reroute."
  ::= { nncRoutingStatsRawNonBorderTotalEntry 4 }

  nncRawNBTotalDTLOrigCallsSuccessEstWithReroute      		OBJECT-TYPE
    SYNTAX                                         		Counter32
    MAX-ACCESS                                      		read-only
    STATUS                                          		current
    DESCRIPTION                    
    "Raw counter for the total number of DTL originated calls successfully established with reroute."
  ::= { nncRoutingStatsRawNonBorderTotalEntry 5 }

 nncRawNBTotalDTLOrigCallsFailedInReRouting			OBJECT-TYPE
    SYNTAX                                          		Counter32
    MAX-ACCESS                                      		read-only
    STATUS                                          		current
    DESCRIPTION                    
    "Raw counter for the total number of DTL originated calls failed in rerouting."
  ::= { nncRoutingStatsRawNonBorderTotalEntry 6 }

 nncRawNBTotalSuccessCallsBdwGreaterThanRTDMinBdw     		OBJECT-TYPE
    SYNTAX                                          		Counter32
    MAX-ACCESS                                      		read-only
    STATUS                                          		current
    DESCRIPTION                    
    "Raw counter for the total number of of successful calls with bandwidth greater than RTD min bandwidth."
  ::= { nncRoutingStatsRawNonBorderTotalEntry 7 }

 nncRawNBTotalFailedCallsBdwGreaterThanRTDMinBdw	        OBJECT-TYPE
    SYNTAX                                         		Counter32
    MAX-ACCESS                                      		read-only
    STATUS                                          		current
    DESCRIPTION                    
    "Raw counter for the total number of of failed calls with bandwidth greater than RTD min bandwidth."
  ::= { nncRoutingStatsRawNonBorderTotalEntry 8 }

 nncRawNBTotalCrankbackReceivedAsDTLOriginator         		OBJECT-TYPE
    SYNTAX                                          		Counter32
    MAX-ACCESS                                      		read-only
    STATUS                                          		current
    DESCRIPTION                    
    "Raw counter for the number of crankback received as DTL originator."
  ::= { nncRoutingStatsRawNonBorderTotalEntry 9 }

 nncRawNBTotalDTLsGeneratedDueToCrankback     			OBJECT-TYPE
    SYNTAX                                          		Counter32
    MAX-ACCESS                                      		read-only
    STATUS                                          		current
    DESCRIPTION                    
    "Raw counter for the total number of of DTLs generated due to crankback."
  ::= { nncRoutingStatsRawNonBorderTotalEntry 10 }

  nncRawNBTotalCallsRecdAsTransitNodeOverInsideLinks		OBJECT-TYPE
    SYNTAX                                         		Counter32
    MAX-ACCESS                                      		read-only
    STATUS                                          		current
    DESCRIPTION                    
    "Raw counter for the total number of of calls received as transit node over inside links."
  ::= { nncRoutingStatsRawNonBorderTotalEntry 11 }

 nncRawNBTotalCrnkbksRecdAsTransitNodeOvInsideLnks     		OBJECT-TYPE
    SYNTAX                                          		Counter32
    MAX-ACCESS                                      		read-only
    STATUS                                          		current
    DESCRIPTION                    
    "Raw counter for the number of calls received as transit node over inside links."
  ::= { nncRoutingStatsRawNonBorderTotalEntry 12 }

  nncRawNBTotalSucdEndBlocCrnkbksRecdOvInsideLnks		OBJECT-TYPE
    SYNTAX                                         		Counter32
    MAX-ACCESS                                      		read-only
    STATUS                                          		current
    DESCRIPTION                    
    "Raw counter for the number of succeeding end blocked crankbacks received over inside links."
  ::= { nncRoutingStatsRawNonBorderTotalEntry 13 }


---------------------------------------------------------------------------------------
--  Table 30: Raw Counters for Border Node PNNI Total Statistics Table
---------------------------------------------------------------------------------------
  nncRoutingStatsRawBorderTotalTable OBJECT-TYPE
    SYNTAX       SEQUENCE OF NncRoutingStatsRawBorderTotalEntry
    MAX-ACCESS   not-accessible
    STATUS       current
    DESCRIPTION  
    "The nncRoutingStatsRawNonBorderTotalTable contains objects for monitoring the 
     raw counters for border node PNNI routing total stats."
  ::= { nncRoutingStatsObjects 30 }


  nncRoutingStatsRawBorderTotalEntry OBJECT-TYPE
    SYNTAX      NncRoutingStatsRawBorderTotalEntry
    MAX-ACCESS  not-accessible
    STATUS      current
    DESCRIPTION  
    "An entry in the nncRoutingStatsRawBorderTotalTable. Each conceptual row
    contains the raw counter for border node PNNI routing total stats."
    INDEX       { nncCallControlGroupNumber }
  ::= { nncRoutingStatsRawBorderTotalTable 1 }


  NncRoutingStatsRawBorderTotalEntry ::=
    SEQUENCE {
      
      nncRawBTotalFailedCallsDueToInitLowerLvlDTLNotGen		Counter32,
      nncRawBTotalCallsGeneratingInitLowerLvlDTLs		Counter32,
      nncRawBTotalDTLGenCallsSuccessEstWithoutReroute		Counter32,
      nncRawBTotalDTLGenCallsSuccessEstWithReroute		Counter32,
      nncRawBTotalDTLGenCallsFailedInReRouting			Counter32,
      nncRawBTotalSuccessCallsBdwGreaterThanRTDMinBdw		Counter32,
      nncRawBTotalFailedCallsBdwGreaterThanRTDMinBdw		Counter32,
      nncRawBTotalCrankbackReceivedAsAnEntryBorderNode		Counter32,
      nncRawBTotalLowerLvlDTLsGenDueToRecdCrankback		Counter32,
      nncRawBTotalCallsRecdOverAnOutsideLink			Counter32,   
      nncRawBTotalCallsTransmittedOverAnOutsideLink		Counter32,
      nncRawBTotalCrankbksRecdOverAnOutsideLink			Counter32,
      nncRawBTotalSucdEndBlocCrankbksRecdOverOutsideLink 	Counter32,
      nncRawBTotalCrankbkForwdedToPrevPGCrankbkLvlTooHigh	Counter32
    }


 nncRawBTotalFailedCallsDueToInitLowerLvlDTLNotGen		     	OBJECT-TYPE
    SYNTAX                                          			Counter32
    MAX-ACCESS                                      			read-only
    STATUS                                          			current
    DESCRIPTION                    
    "Raw counter for the total number of of failed calls due to initial lower level DTL not generated."
  ::= { nncRoutingStatsRawBorderTotalEntry 2 }

  nncRawBTotalCallsGeneratingInitLowerLvlDTLs				OBJECT-TYPE
    SYNTAX                                         			Counter32
    MAX-ACCESS                                      			read-only
    STATUS                                          			current
    DESCRIPTION                    
    "Raw counter for the total number of calls generating initial lower level DTLs."
  ::= { nncRoutingStatsRawBorderTotalEntry 3 }

 nncRawBTotalDTLGenCallsSuccessEstWithoutReroute			OBJECT-TYPE
    SYNTAX                                          			Counter32
    MAX-ACCESS                                      			read-only
    STATUS                                          			current
    DESCRIPTION                    
    "Raw counter for the total number of DTL generated calls successfully established without reroute."
  ::= { nncRoutingStatsRawBorderTotalEntry 4 }

 nncRawBTotalDTLGenCallsSuccessEstWithReroute				OBJECT-TYPE
    SYNTAX                                          			Counter32
    MAX-ACCESS                                      			read-only
    STATUS                                          			current
    DESCRIPTION                    
    "Raw counter for the total number of DTL generated calls successfully established with reroute."
  ::= { nncRoutingStatsRawBorderTotalEntry 5 }

  nncRawBTotalDTLGenCallsFailedInReRouting      			OBJECT-TYPE
    SYNTAX                                         			Counter32
    MAX-ACCESS                                      			read-only
    STATUS                                          			current
    DESCRIPTION                    
    "Raw counter for the total number of DTL generated calls failed in rerouting."
  ::= { nncRoutingStatsRawBorderTotalEntry 6 }

 nncRawBTotalSuccessCallsBdwGreaterThanRTDMinBdw			OBJECT-TYPE
    SYNTAX                                          			Counter32
    MAX-ACCESS                                      			read-only
    STATUS                                          			current
    DESCRIPTION                    
    "Raw counter for the total number of of successful calls with bandwidth greater than RTD min bandwidth."
  ::= { nncRoutingStatsRawBorderTotalEntry 7 }

 nncRawBTotalFailedCallsBdwGreaterThanRTDMinBdw     			OBJECT-TYPE
    SYNTAX                                          			Counter32
    MAX-ACCESS                                      			read-only
    STATUS                                          			current
    DESCRIPTION                    
    "Raw counter for the total number of failed calls with bandwidth greater than RTD min bandwidth."
  ::= { nncRoutingStatsRawBorderTotalEntry 8 }

 nncRawBTotalCrankbackReceivedAsAnEntryBorderNode	        	OBJECT-TYPE
    SYNTAX                                         			Counter32
    MAX-ACCESS                                      			read-only
    STATUS                                          			current
    DESCRIPTION                    
    "Raw counter for the total number of crankback received as an entry border node.."
  ::= { nncRoutingStatsRawBorderTotalEntry 9 }

 nncRawBTotalLowerLvlDTLsGenDueToRecdCrankback         			OBJECT-TYPE
    SYNTAX                                          			Counter32
    MAX-ACCESS                                      			read-only
    STATUS                                          			current
    DESCRIPTION                    
    "Raw counter for the total  number of lower level DTLs generated due to received crankback."
  ::= { nncRoutingStatsRawBorderTotalEntry 10 }

 nncRawBTotalCallsRecdOverAnOutsideLink     				OBJECT-TYPE
    SYNTAX                                          			Counter32
    MAX-ACCESS                                      			read-only
    STATUS                                          			current
    DESCRIPTION                    
    "Raw counter for the total  number of calls received over an outside link."
  ::= { nncRoutingStatsRawBorderTotalEntry 11 }

  nncRawBTotalCallsTransmittedOverAnOutsideLink				OBJECT-TYPE
    SYNTAX                                         			Counter32
    MAX-ACCESS                                      			read-only
    STATUS                                          			current
    DESCRIPTION                    
    "Raw counter for the total  number of calls transmitted over an outside link."
  ::= { nncRoutingStatsRawBorderTotalEntry 12 }

 nncRawBTotalCrankbksRecdOverAnOutsideLink     				OBJECT-TYPE
    SYNTAX                                          			Counter32
    MAX-ACCESS                                      			read-only
    STATUS                                          			current
    DESCRIPTION                    
    "Raw counter for the total  counter for the crankbacks received over an outside link."
  ::= { nncRoutingStatsRawBorderTotalEntry 13 }

  nncRawBTotalSucdEndBlocCrankbksRecdOverOutsideLink			OBJECT-TYPE
    SYNTAX                                         			Counter32
    MAX-ACCESS                                      			read-only
    STATUS                                          			current
    DESCRIPTION                    
    "Raw counter for the total number of succeeding end blocked crankbacks received over an outside link."
  ::= { nncRoutingStatsRawBorderTotalEntry 14 }

nncRawBTotalCrankbkForwdedToPrevPGCrankbkLvlTooHigh			OBJECT-TYPE
    SYNTAX                                         			Counter32
    MAX-ACCESS                                      			read-only
    STATUS                                          			current
    DESCRIPTION                    
    "Raw counter for the total number of of crankback forwarded to previous PG, crankback level too high."
  ::= { nncRoutingStatsRawBorderTotalEntry 15 }



--------------------------------------------------------------------------------
-- Conformance Group Definitions
--------------------------------------------------------------------------------
--1-4
        nncRoutingStatsCommon15MinCurrentGroup         OBJECT-GROUP 
                OBJECTS {
      			nncCallControlGroupNumber,
                        nncCommon15MinCurrentAbsoluteIntervalNumber,
      			nncCommon15MinCurrentSuccessRoutedCallsOrigFromLocalSubs,
      			nncCommon15MinCurrentSuccessRoutedCallsTransitedViaThisNode,
      			nncCommon15MinCurrentSuccessRoutedCallsTermToLocalSubs,
      			nncCommon15MinCurrentSuccessRoutedLocalCalls,
      			nncCommon15MinCurrentCallsOrigFromLocalCalls,
      			nncCommon15MinCurrentCallsTermToLocalCalls,
      			nncCommon15MinCurrentLocalCallAttempts,
      			nncCommon15MinCurrentCallsClearedDueToNoRoutingTabEntry,
      			nncCommon15MinCurrentCrankbacksGeneratedByThisNode,
      			nncCommon15MinCurrentFailedCallsAtLocalSubs,
      			nncCommon15MinCurrentCallsSuccessRerouted,
      			nncCommon15MinCurrentCallsFailedInRerouting		
                	}
                STATUS          current
                DESCRIPTION     "A collection of objects providing 15 minute
                                current statistics for static and PNNI routing common stats."
        ::= { nncRoutingStatsGroups 1 }

        nncRoutingStatsCommon15MinIntervalGroup         OBJECT-GROUP 
                OBJECTS {
      			
                        nncCommon15MinIntervalAbsoluteIntervalNumber,
      			nncCommon15MinIntervalSuccessRoutedCallsOrigFromLocalSubs,
      			nncCommon15MinIntervalSuccessRoutedCallsTransitedViaThisNode,
      			nncCommon15MinIntervalSuccessRoutedCallsTermToLocalSubs,
      			nncCommon15MinIntervalSuccessRoutedLocalCalls,
      			nncCommon15MinIntervalCallsOrigFromLocalCalls,
      			nncCommon15MinIntervalCallsTermToLocalCalls,
      			nncCommon15MinIntervalLocalCallAttempts,
      			nncCommon15MinIntervalCallsClearedDueToNoRoutingTabEntry,
      			nncCommon15MinIntervalCrankbacksGeneratedByThisNode,
      			nncCommon15MinIntervalFailedCallsAtLocalSubs,
      			nncCommon15MinIntervalCallsSuccessRerouted,
      			nncCommon15MinIntervalCallsFailedInRerouting		
                	}
                STATUS          current
                DESCRIPTION     "A collection of objects providing 15 minute
                                interval statistics for static and PNNI routing common stats."
        ::= { nncRoutingStatsGroups 2 }


        nncRoutingStatsCommon24HourCurrentGroup         OBJECT-GROUP 
                OBJECTS {
      			
                        nncCommon24HourCurrentAbsoluteIntervalNumber,
      			nncCommon24HourCurrentSuccessRoutedCallsOrigFromLocalSubs,
      			nncCommon24HourCurrentSuccessRoutedCallsTransitedViaThisNode,
      			nncCommon24HourCurrentSuccessRoutedCallsTermToLocalSubs,
      			nncCommon24HourCurrentSuccessRoutedLocalCalls,
      			nncCommon24HourCurrentCallsOrigFromLocalCalls,
      			nncCommon24HourCurrentCallsTermToLocalCalls,
      			nncCommon24HourCurrentLocalCallAttempts,
      			nncCommon24HourCurrentCallsClearedDueToNoRoutingTabEntry,
      			nncCommon24HourCurrentCrankbacksGeneratedByThisNode,
      			nncCommon24HourCurrentFailedCallsAtLocalSubs,
      			nncCommon24HourCurrentCallsSuccessRerouted,
      			nncCommon24HourCurrentCallsFailedInRerouting		
                	}
                STATUS          current
                DESCRIPTION     "A collection of objects providing 24 hour
                                current statistics for static and PNNI routing common stats."
        ::= { nncRoutingStatsGroups 3 }


        nncRoutingStatsCommon24HourIntervalGroup         OBJECT-GROUP 
                OBJECTS {
      			
                        nncCommon24HourIntervalAbsoluteIntervalNumber,
      			nncCommon24HourIntervalSuccessRoutedCallsOrigFromLocalSubs,
      			nncCommon24HourIntervalSuccessRoutedCallsTransitedViaThisNode,
      			nncCommon24HourIntervalSuccessRoutedCallsTermToLocalSubs,
      			nncCommon24HourIntervalSuccessRoutedLocalCalls,
      			nncCommon24HourIntervalCallsOrigFromLocalCalls,
      			nncCommon24HourIntervalCallsTermToLocalCalls,
      			nncCommon24HourIntervalLocalCallAttempts,
      			nncCommon24HourIntervalCallsClearedDueToNoRoutingTabEntry,
      			nncCommon24HourIntervalCrankbacksGeneratedByThisNode,
      			nncCommon24HourIntervalFailedCallsAtLocalSubs,
      			nncCommon24HourIntervalCallsSuccessRerouted,
      			nncCommon24HourIntervalCallsFailedInRerouting		
                	}
                STATUS          current
                DESCRIPTION     "A collection of objects providing 24 hour
                                interval statistics for static and PNNI routing common stats."
        ::= { nncRoutingStatsGroups 4 }


--5-8
        nncRoutingStatsSpecific15MinCurrentGroup         OBJECT-GROUP 
                OBJECTS {
      			
      			nncSpecific15MinCurrentAbsoluteIntervalNumber,
      			nncSpecific15MinCurrentCallsStaticallyRoutedByThisNode,
      			nncSpecific15MinCurrentCrankbacksReceivedByThisNode,
      			nncSpecific15MinCurrentRerouteAttempts,
      			nncSpecific15MinCurrentRoutingLoopsDetectedByThisNode
               		}
                STATUS          current
                DESCRIPTION     "A collection of objects providing 15 minute
                                current statistics for static specific stats."
        ::= { nncRoutingStatsGroups 5 }

        nncRoutingStatsSpecific15MinIntervalGroup         OBJECT-GROUP 
                OBJECTS {
      			
      			nncSpecific15MinIntervalAbsoluteIntervalNumber,
      			nncSpecific15MinIntervalCallsStaticallyRoutedByThisNode,
      			nncSpecific15MinIntervalCrankbacksReceivedByThisNode,
      			nncSpecific15MinIntervalRerouteAttempts,
      			nncSpecific15MinIntervalRoutingLoopsDetectedByThisNode
                	}
                STATUS          current
                DESCRIPTION     "A collection of objects providing 15 minute
                                interval statistics for static specific stats."
        ::= { nncRoutingStatsGroups 6 }

        nncRoutingStatsSpecific24HourCurrentGroup         OBJECT-GROUP 
                OBJECTS {
      			
      			nncSpecific24HourCurrentAbsoluteIntervalNumber,
      			nncSpecific24HourCurrentCallsStaticallyRoutedByThisNode,
      			nncSpecific24HourCurrentCrankbacksReceivedByThisNode,
      			nncSpecific24HourCurrentRerouteAttempts,
      			nncSpecific24HourCurrentRoutingLoopsDetectedByThisNode
                	}
                STATUS          current
                DESCRIPTION     "A collection of objects providing 24 hour
                                current statistics for static specific stats."
        ::= { nncRoutingStatsGroups 7 }

        nncRoutingStatsSpecific24HourIntervalGroup         OBJECT-GROUP 
                OBJECTS {
      			
      			nncSpecific24HourIntervalAbsoluteIntervalNumber,
      			nncSpecific24HourIntervalCallsStaticallyRoutedByThisNode,
      			nncSpecific24HourIntervalCrankbacksReceivedByThisNode,
      			nncSpecific24HourIntervalRerouteAttempts,
      			nncSpecific24HourIntervalRoutingLoopsDetectedByThisNode
                	}
                STATUS          current
                DESCRIPTION     "A collection of objects providing 24 hour
                                interval statistics for static specific stats."
        ::= { nncRoutingStatsGroups 8 }

--9-12
        nncRoutingStatsNonBorderPerTbl15MinCurrentGroup         OBJECT-GROUP 
                OBJECTS {
      			
                        nncNBPerTbl15MinCurrentTableDescriptor,
			nncNBPerTbl15MinCurrentAbsoluteIntervalNumber  ,
      			nncNBPerTbl15MinCurrentFailedCallsDueToInitDTLNotGenerated	,
      			nncNBPerTbl15MinCurrentCallsGeneratingAnInitDTL	,
      			nncNBPerTble15MinCurrentDTLOrigCallsSuccessEstWithoutReroute	,
      			nncNBPerTbl15MinCurrentDTLOrigCallsSuccessEstWithReroute	,
      			nncNBPerTbl15MinCurrentDTLOrigCallsFailedInReRouting		,
      			nncNBPerTbl15MinCurrentSuccessCallsBdwGreaterThanRTDMinBdw	,
      			nncNBPerTbl15MinCurrentFailedCallsBdwGreaterThanRTDMinBdw	,
      			nncNBPerTbl15MinCurrentCrankbackReceivedAsDTLOriginator	,
      			nncNBPerTbl15MinCurrentDTLsGeneratedDueToCrankback	           
			}
                STATUS          current
                DESCRIPTION     "A collection of objects providing 15 minute
                                current statistics for Non-border per routing table stats."
        ::= { nncRoutingStatsGroups 9 }

       nncRoutingStatsNonBorderPerTbl15MinIntervalGroup         OBJECT-GROUP 
                OBJECTS {
      			
                        nncNBPerTbl15MinIntervalTableDescriptor,
			nncNBPerTbl15MinIntervalAbsoluteIntervalNumber  ,
      			nncNBPerTbl15MinIntervalFailedCallsDueToInitDTLNotGenerated	,
      			nncNBPerTbl15MinIntervalCallsGeneratingAnInitDTL		,
      			nncNBPerTbl15MinIntervalDTLOrigCallsSuccessEstWithoutReroute	,
      			nncNBPerTbl15MinIntervalDTLOrigCallsSuccessEstWithReroute	,
      			nncNBPerTbl15MinIntervalDTLOrigCallsFailedInReRouting	,
      			nncNBPerTbl15MinIntervalSuccessCallsBdwGreaterThanRTDMinBdw	,
      			nncNBPerTbl15MinIntervalFailedCallsBdwGreaterThanRTDMinBdw	,
      			nncNBPerTbl15MinIntervalCrankbackReceivedAsDTLOriginator	,
      			nncNBPerTbl15MinIntervalDTLsGeneratedDueToCrankback	                
			}
                STATUS          current
                DESCRIPTION     "A collection of objects providing 15 minute
                                interval statistics for Non-border per routing table stats."
        ::= { nncRoutingStatsGroups 10 }

        nncRoutingStatsNonBorderPerTbl24HourCurrentGroup         OBJECT-GROUP 
                OBJECTS {
      			
                        nncNBPerTbl24HourCurrentTableDescriptor,
			nncNBPerTbl24HourCurrentAbsoluteIntervalNumber,
      			nncNBPerTbl24HourCurrentFailedCallsDueToInitDTLNotGenerated,
      			nncNBPerTbl24HourCurrentCallsGeneratingAnInitDTL,
     	 		nncNBPerTbl24HourCurrentDTLOrigCallsSuccessEstWithoutReroute,
      			nncNBPerTbl24HourCurrentDTLOrigCallsSuccessEstWithReroute,
     	 		nncNBPerTbl24HourCurrentDTLOrigCallsFailedInReRouting,
    	  		nncNBPerTbl24HourCurrentSuccessCallsBdwGreaterThanRTDMinBdw,
   	   		nncNBPerTbl24HourCurrentFailedCallsBdwGreaterThanRTDMinBdw,
  	    		nncNBPerTbl24HourCurrentCrankbackReceivedAsDTLOriginator,
 	     		nncNBPerTbl24HourCurrentDTLsGeneratedDueToCrankback	                
			}
                STATUS          current
                DESCRIPTION     "A collection of objects providing 24 hour
                                current statistics for Non-border per routing table stats."
        ::= { nncRoutingStatsGroups 11 }

       nncRoutingStatsNonBorderPerTbl24HourIntervalGroup         OBJECT-GROUP 
                OBJECTS {
      			
                        nncNBPerTbl24HourIntervalTableDescriptor,
			nncNBPerTbl24HourIntervalAbsoluteIntervalNumber,
      			nncNBPerTbl24HourIntervalFailedCallsDueToInitDTLNotGenerated,
      			nncNBPerTbl24HourIntervalCallsGeneratingAnInitDTL,
     		 	nncNBPerTbl24HourIntervalDTLOrigCallsSuccessEstWithoutReroute,
      			nncNBPerTbl24HourIntervalDTLOrigCallsSuccessEstWithReroute,
      			nncNBPerTbl24HourIntervalDTLOrigCallsFailedInReRouting,
      			nncNBPerTbl24HourIntervalSuccessCallsBdwGreaterThanRTDMinBdw,
     	 		nncNBPerTbl24HourIntervalFailedCallsBdwGreaterThanRTDMinBdw,
    	  		nncNBPerTbl24HourIntervalCrankbackReceivedAsDTLOriginator,
   	   		nncNBPerTbl24HourIntervalDTLsGeneratedDueToCrankback	                
			}
                STATUS          current
                DESCRIPTION     "A collection of objects providing 24 hour
                                interval statistics for Non-border per routing table stats."
        ::= { nncRoutingStatsGroups 12 }

--13-16
        nncRoutingStatsBorderPerTbl15MinCurrentGroup         OBJECT-GROUP 
                OBJECTS {
      			
                        nncBPerTbl15MinCurrentTableDescriptor,
			nncBPerTbl15MinCurrentAbsoluteIntervalNumber,
      			nncBPerTbl15MinCurrentFailedCallsDueInitLowerLvlDTLsNotGen	,
     			nncBPerTbl15MinCurrentCallsGeneratingInitLowerLvlDTLs	,
      			nncBPerTbl15MinCurrentDTLGenCallsSuccessEstWithoutReroute	,
      			nncBPerTbl15MinCurrentDTLGenCallsSuccessEstWithReroute	,
      			nncBPerTbl15MinCurrentDTLGenCallsFailedInReRouting		,
      			nncBPerTbl15MinCurrentSuccessCallsBdwGreaterThanRTDMinBdw	,
      			nncBPerTbl15MinCurrentFailedCallsBdwGreaterThanRTDMinBdw	,
      			nncBPerTbl15MinCurrentCrankbackReceivedAsAnEntryBorderNode	,
      			nncBPerTbl15MinCurrentLowerLvlDTLsGenDueToRecdCrankback	           
			}
                STATUS          current
                DESCRIPTION     "A collection of objects providing 15 minute
                                current statistics for border per routing table stats."
        ::= { nncRoutingStatsGroups 13 }

       nncRoutingStatsBorderPerTbl15MinIntervalGroup         OBJECT-GROUP 
                OBJECTS {
      			
                        nncBPerTbl15MinIntervalTableDescriptor,
			nncBPerTbl15MinIntervalAbsoluteIntervalNumber,
      			nncBPerTbl15MinIntervalFailedCallsDueInitLowerLvlDTLsNotGen,
      			nncBPerTbl15MinIntervalCallsGeneratingInitLowerLvlDTLs	,
      			nncBPerTbl15MinIntervalDTLGenCallsSuccessEstWithoutReroute	,
      			nncBPerTbl15MinIntervalDTLGenCallsSuccessEstWithReroute	,
      			nncBPerTbl15MinIntervalDTLGenCallsFailedInReRouting		,
      			nncBPerTbl15MinIntervalSuccessCallsBdwGreaterThanRTDMinBdw	,
      			nncBPerTbl15MinIntervalFailedCallsBdwGreaterThanRTDMinBdw	,
      			nncBPerTbl15MinIntervalCrankbackReceivedAsAnEntryBorderNode	,
      			nncBPerTbl15MinIntervalLowerLvlDTLsGenDueToRecdCrankback	                
			}
                STATUS          current
                DESCRIPTION     "A collection of objects providing 15 minute
                                interval statistics for border per routing table stats."
        ::= { nncRoutingStatsGroups 14 }

        nncRoutingStatsBorderPerTbl24HourCurrentGroup         OBJECT-GROUP 
                OBJECTS {
      			
			nncBPerTbl24HourCurrentTableDescriptor,
      			nncBPerTbl24HourCurrentState	,
      			nncBPerTbl24HourCurrentAbsoluteIntervalNumber,
      			nncBPerTbl24HourCurrentFailedCallsDueInitLowerLvlDTLsNotGen,
      			nncBPerTbl24HourCurrentCallsGeneratingInitLowerLvlDTLs	,
      			nncBPerTbl24HourCurrentDTLGenCallsSuccessEstWithoutReroute	,
      			nncBPerTbl24HourCurrentDTLGenCallsSuccessEstWithReroute	,
      			nncBPerTbl24HourCurrentDTLGenCallsFailedInReRouting		,
      			nncBPerTbl24HourCurrentSuccessCallsBdwGreaterThanRTDMinBdw	,
      			nncBPerTbl24HourCurrentFailedCallsBdwGreaterThanRTDMinBdw	,
      			nncBPerTbl24HourCurrentCrankbackReceivedAsAnEntryBorderNode	,
      			nncBPerTbl24HourCurrentLowerLvlDTLsGenDueToRecdCrankback		                
				}
                STATUS          current
                DESCRIPTION     "A collection of objects providing 24 hour
                                current statistics for border per routing table stats."
        ::= { nncRoutingStatsGroups 15 }

       nncRoutingStatsBorderPerTbl24HourIntervalGroup         OBJECT-GROUP 
                OBJECTS {
      			
                        nncBPerTbl24HourIntervalTableDescriptor,
			nncBPerTbl24HourIntervalAbsoluteIntervalNumber  		,
      			nncBPerTbl24HourIntervalFailedCallsDueInitLowerLvlDTLsNotGen	,
      			nncBPerTbl24HourIntervalCallsGeneratingInitLowerLvlDTLs	,
      			nncBPerTbl24HourIntervalDTLGenCallsSuccessEstWithoutReroute	,
      			nncBPerTbl24HourIntervalDTLGenCallsSuccessEstWithReroute	,
      			nncBPerTbl24HourIntervalDTLGenCallsFailedInReRouting		,
      			nncBPerTbl24HourIntervalSuccessCallsBdwGreaterThanRTDMinBdw	,
      			nncBPerTbl24HourIntervalFailedCallsBdwGreaterThanRTDMinBdw	,
      			nncBPerTbl24HourIntervalCrankbackReceivedAsAnEntryBorderNode	,
      			nncBPerTbl24HourIntervalLowerLvlDTLsGenDueToRecdCrankback                
			}
                STATUS          current
                DESCRIPTION     "A collection of objects providing 24 hour 
                                interval statistics for border per routing table stats."
        ::= { nncRoutingStatsGroups 16 }

-- 17-20

     nncPNNIStatNonBorderTotal15MinCurrentGroup         OBJECT-GROUP 
                OBJECTS {
      			
      			nncNBTotal15MinCurrentAbsoluteIntervalNumber,
      			nncNBTotal15MinCurrentFailedCallsDueToInitDTLNotGenerated,
      			nncNBTotal15MinCurrentCallsGeneratingAnInitDTL,
   	  	 	nncNBTotal15MinCurrentDTLOrigCallsSuccessEstWithoutReroute,
      			nncNBTotal15MinCurrentDTLOrigCallsSuccessEstWithReroute,
      			nncNBTotal15MinCurrentDTLOrigCallsFailedInReRouting,
      			nncNBTotal15MinCurrentSuccessCallsBdwGreaterThanRTDMinBdw,
      			nncNBTotal15MinCurrentFailedCallsBdwGreaterThanRTDMinBdw,
      			nncNBTotal15MinCurrentCrankbackReceivedAsDTLOriginator,
      			nncNBTotal15MinCurrentDTLsGeneratedDueToCrankback,
     	 		nncNBTotal15MinCurrentCallsRecdAsTransitNodeOverInsideLinks,
    	  		nncNBTotal15MinCurrentCrnkbksRecdAsTransitNodeOvInsideLnks,
   	   		nncNBTotal15MinCurrentSucdEndBlocCrnkbksRecdOvInsideLnks  
	                }
                STATUS          current
                DESCRIPTION     "A collection of objects providing 15 minute 
                                current statistics for non-border total stats."
        ::= { nncRoutingStatsGroups 17 }

     nncPNNIStatNonBorderTotal15MinIntervalGroup         OBJECT-GROUP 
                OBJECTS {
      			
      			nncNBTotal15MinIntervalAbsoluteIntervalNumber,
      			nncNBTotal15MinIntervalFailedCallsDueToInitDTLNotGenerated,
      			nncNBTotal15MinIntervalCallsGeneratingAnInitDTL,
   	   		nncNBTotal15MinIntervalDTLOrigCallsSuccessEstWithoutReroute,
      			nncNBTotal15MinIntervalDTLOrigCallsSuccessEstWithReroute,
      			nncNBTotal15MinIntervalDTLOrigCallsFailedInReRouting,
      			nncNBTotal15MinIntervalSuccessCallsBdwGreaterThanRTDMinBdw,
      			nncNBTotal15MinIntervalFailedCallsBdwGreaterThanRTDMinBdw,
      			nncNBTotal15MinIntervalCrankbackReceivedAsDTLOriginator,
      			nncNBTotal15MinIntervalDTLsGeneratedDueToCrankback,
      			nncNBTotal15MinIntervalCallsRecdAsTransitNodeOverInsideLinks,
      			nncNBTotal15MinIntervalCrnkbksRecdAsTransitNodeOvInsideLnks,
      			nncNBTotal15MinIntervalSucdEndBlocCrnkbksRecdOvInsideLnks    
            	}
                STATUS          current
                DESCRIPTION     "A collection of objects providing 15 minute 
                                interval statistics for non-border total stats."
        ::= { nncRoutingStatsGroups 18 }

    nncPNNIStatNonBorderTotal24HourCurrentGroup         OBJECT-GROUP 
                OBJECTS {
      			
      			nncNBTotal24HourCurrentAbsoluteIntervalNumber,
      			nncNBTotal24HourCurrentFailedCallsDueToInitDTLNotGenerated,
      			nncNBTotal24HourCurrentCallsGeneratingAnInitDTL,
   	   		nncNBTotal24HourCurrentDTLOrigCallsSuccessEstWithoutReroute,
      			nncNBTotal24HourCurrentDTLOrigCallsSuccessEstWithReroute,
      			nncNBTotal24HourCurrentDTLOrigCallsFailedInReRouting,
      			nncNBTotal24HourCurrentSuccessCallsBdwGreaterThanRTDMinBdw,
      			nncNBTotal24HourCurrentFailedCallsBdwGreaterThanRTDMinBdw,
     	 		nncNBTotal24HourCurrentCrankbackReceivedAsDTLOriginator,
    	  		nncNBTotal24HourCurrentDTLsGeneratedDueToCrankback,
   	   		nncNBTotal24HourCurrentCallsRecdAsTransitNodeOverInsideLinks,
  	    		nncNBTotal24HourCurrentCrnkbksRecdAsTransNodeOvInsideLnks,
 	     		nncNBTotal24HourCurrentSucdEndBlocCrnkbksRecdOverInsideLinks 
	               }
                STATUS          current
                DESCRIPTION     "A collection of objects providing 24 hour 
                                current statistics for  non-border total stats."
        ::= { nncRoutingStatsGroups 19 }

     nncPNNIStatNonBorderTotal24HourIntervalGroup         OBJECT-GROUP 
                OBJECTS {
      			
      			nncNBTotal24HourIntervalAbsoluteIntervalNumber,
      			nncNBTotal24HourIntervalFailedCallsDueToInitDTLNotGenerated,
      			nncNBTotal24HourIntervalCallsGeneratingAnInitDTL,
   	   		nncNBTotal24HourIntervalDTLOrigCallsSuccessEstWithoutReroute,
      			nncNBTotal24HourIntervalDTLOrigCallsSuccessEstWithReroute,
      			nncNBTotal24HourIntervalDTLOrigCallsFailedInReRouting,
      			nncNBTotal24HourIntervalSuccessCallsBdwGreaterThanRTDMinBdw,
      			nncNBTotal24HourIntervalFailedCallsBdwGreaterThanRTDMinBdw,
      			nncNBTotal24HourIntervalCrankbackReceivedAsDTLOriginator,
      			nncNBTotal24HourIntervalDTLsGeneratedDueToCrankback,
      			nncNBTotal24HourIntervalCallsRecdAsTransitNodeOverInsideLinks,
      			nncNBTotal24HourIntervalCrnkbksRecdAsTransNodeOverInsideLnks,
      			nncNBTotal24HourIntervalSucdEndBlocCrnkbksRecdOverInsideLnks                
			}
                STATUS          current
                DESCRIPTION     "A collection of objects providing 24 hour 
                                interval statistics for  non-border total stats."
        ::= { nncRoutingStatsGroups 20 }

--21-24
    nncPNNIStatBorderTotal15MinCurrentGroup         OBJECT-GROUP 
                OBJECTS {
      			
      			nncBTotal15MinCurrentAbsoluteIntervalNumber  ,
      			nncBTotal15MinCurrentFailedCallsDueToInitLowerLvlDTLNotGen	,
      			nncBTotal15MinCurrentCallsGeneratingInitLowerLvlDTLs		,
      			nncBTotal15MinCurrentDTLGenCallsSuccessEstWithoutReroute	,
      			nncBTotal15MinCurrentDTLGenCallsSuccessEstWithReroute	,
     			nncBTotal15MinCurrentDTLGenCallsFailedInReRouting		,
      			nncBTotal15MinCurrentSuccessCallsBdwGreaterThanRTDMinBdw	,
      			nncBTotal15MinCurrentFailedCallsBdwGreaterThanRTDMinBdw	,
      			nncBTotal15MinCurrentCrankbackReceivedAsAnEntryBorderNode	,
      			nncBTotal15MinCurrentLowerLvlDTLsGenDueToRecdCrankback	,
      			nncBTotal15MinCurrentCallsRecdOverAnOutsideLink		,  
      			nncBTotal15MinCurrentCallsTransmittedOverAnOutsideLink	,
      			nncBTotal15MinCurrentCrankbksRecdOverAnOutsideLink		,
      			nncBTotal15MinCurreSucdEndBlocCrankbksRecdOverOutsideLink ,
      			nncBTotal15MinCurrentCrankbkForwdedToPrevPGCrankbkLvlTooHigh     
			}
                STATUS          current
                DESCRIPTION     "A collection of objects providing 15 minute 
                                current statistics for border total stats."
        ::= { nncRoutingStatsGroups 21 }

     nncPNNIStatBorderTotal15MinIntervalGroup         OBJECT-GROUP 
                OBJECTS {
      			
      			nncBTotal15MinIntervalAbsoluteIntervalNumber,
      			nncBTotal15MinIntervalFailedCallsDueToInitLowerLvlDTLNotGen	,
      			nncBTotal15MinIntervalCallsGeneratingInitLowerLvlDTLs	,
      			nncBTotal15MinIntervalDTLGenCallsSuccessEstWithoutReroute	,
      			nncBTotal15MinIntervalDTLGenCallsSuccessEstWithReroute	,
      			nncBTotal15MinIntervalDTLGenCallsFailedInReRouting		,
      			nncBTotal15MinIntervalSuccessCallsBdwGreaterThanRTDMinBdw	,
      			nncBTotal15MinIntervalFailedCallsBdwGreaterThanRTDMinBdw	,
      			nncBTotal15MinIntervalCrankbackReceivedAsAnEntryBorderNode	,
      			nncBTotal15MinIntervalLowerLvlDTLsGenDueToRecdCrankback	,
      			nncBTotal15MinIntervalCallsRecdOverAnOutsideLink		,   
      			nncBTotal15MinIntervalCallsTransmittedOverAnOutsideLink	,
      			nncBTotal15MinIntervalCrankbksRecdOverAnOutsideLink		,
      			nncBTotal15MinIntervalSucdEndBlocCrankbksRecdOverOutsideLink  ,
      			nncBTotal15MinIntervalCrankbkForwdedToPrevPGCrankbkLvlTooHigh	
	     	        }
                STATUS          current
                DESCRIPTION     "A collection of objects providing 15 minute 
                                interval statistics for border total stats."
        ::= { nncRoutingStatsGroups 22 }

    nncPNNIStatBorderTotal24HourCurrentGroup         OBJECT-GROUP 
                OBJECTS {
      			
      			nncNBTotal24HourCurrentAbsoluteIntervalNumber,
      			nncNBTotal24HourCurrentFailedCallsDueToInitDTLNotGenerated,
      			nncNBTotal24HourCurrentCallsGeneratingAnInitDTL,
   	   		nncNBTotal24HourCurrentDTLOrigCallsSuccessEstWithoutReroute,
      			nncNBTotal24HourCurrentDTLOrigCallsSuccessEstWithReroute,
      			nncNBTotal24HourCurrentDTLOrigCallsFailedInReRouting,
      			nncNBTotal24HourCurrentSuccessCallsBdwGreaterThanRTDMinBdw,
      			nncNBTotal24HourCurrentFailedCallsBdwGreaterThanRTDMinBdw,
     	 		nncNBTotal24HourCurrentCrankbackReceivedAsDTLOriginator,
    	  		nncNBTotal24HourCurrentDTLsGeneratedDueToCrankback,
   	   		nncNBTotal24HourCurrentCallsRecdAsTransitNodeOverInsideLinks,
  	    		nncNBTotal24HourCurrentCrnkbksRecdAsTransNodeOvInsideLnks,
 	     		nncNBTotal24HourCurrentSucdEndBlocCrnkbksRecdOverInsideLinks                
			}
                STATUS          current
                DESCRIPTION     "A collection of objects providing 24 hour 
                                current statistics for  border total stats."
        ::= { nncRoutingStatsGroups 23 }

     nncPNNIStatBorderTotal24HourIntervalGroup         OBJECT-GROUP 
                OBJECTS {
      			
      			nncBTotal24HourIntervalAbsoluteIntervalNumber  ,
      			nncBTotal24HourIntervalFailedCallsDueToInitLowerLvlDTLNotGen	,
      			nncBTotal24HourIntervalCallsGeneratingInitLowerLvlDTLs	,
      			nncBTotal24HourIntervalDTLGenCallsSuccessEstWithoutReroute	,
      			nncBTotal24HourIntervalDTLGenCallsSuccessEstWithReroute	,
      			nncBTotal24HourIntervalDTLGenCallsFailedInReRouting		,
      			nncBTotal24HourIntervalSuccessCallsBdwGreaterThanRTDMinBdw	,
      			nncBTotal24HourIntervalFailedCallsBdwGreaterThanRTDMinBdw	,
      			nncBTotal24HourIntervalCrankbackReceivedAsAnEntryBorderNode	,
      			nncBTotal24HourIntervalLowerLvlDTLsGenDueToRecdCrankback	,
      			nncBTotal24HourIntervalCallsRecdOverAnOutsideLink		,   
      			nncBTotal24HourIntervalCallsTransmittedOverAnOutsideLink	,
      			nncBTotal24HourIntervalCrankbksRecdOverAnOutsideLink		,
      			nncBTotal24HourCurrentSucdEndBlocCrankbksRecdOverOutsideLink  ,
      			nncBTotal24HourIntervalCrankbkFwdToPrevPGCrankbkLvlTooHigh                
			}
                STATUS          current
                DESCRIPTION     "A collection of objects providing 24 hour 
                                interval statistics for  border total stats."
        ::= { nncRoutingStatsGroups 24 }

--25-30

     nncRoutingStatsRawCommonGroup         OBJECT-GROUP 
                OBJECTS {
      			
      			nncRoutingStatsRawCommonSuccessRoutedCallsOrigFromLocalSubs,     
      			nncRoutingStatsRawCommonSuccessRtedCallsTransitedViaThisNode,	
      			nncRoutingStatsRawCommonSuccessRoutedCallsTermToLocalSubs,	 	
      			nncRoutingStatsRawCommonSuccessRoutedLocalCalls,		 	
      			nncRoutingStatsRawCommonCallsOrigFromLocalCalls,		 
      			nncRoutingStatsRawCommonCallsTermToLocalCalls,			
      			nncRoutingStatsRawCommonLocalCallAttempts,			 	
     		 	nncRoutingStatsRawCommonCallsClearedDueToNoRoutingTabEntry,      	
      			nncRoutingStatsRawCommonCrankbacksGeneratedByThisNode,		
      			nncRoutingStatsRawCommonFailedCallsAtLocalSubs,			
      			nncRoutingStatsRawCommonCallsSuccessRerouted,		 	
      			nncRoutingStatsRawCommonCallsFailedInRerouting	               
			}
                STATUS          current
                DESCRIPTION     "A collection of objects providing raw counters 
                                 for static and PNNI routing common stats."
        ::= { nncRoutingStatsGroups 25 }

     ncExtRoutingStatsRawSpecificGroup         OBJECT-GROUP 
                OBJECTS {
      			
           		nncRoutingStatsRawSpecificCallsStaticallyRoutedByThisNode,     	
      			nncRoutingStatsRawSpecificCrankbacksReceivedByThisNode,	
      			nncRoutingStatsRawSpecificRerouteAttempts,			 
      			nncRoutingStatsRawSpecificRoutingLoopsDetectedByThisNode	
               		}
                STATUS          current
                DESCRIPTION     "A collection of objects providing raw counters 
                                 for static routing specific stats."
        ::= { nncRoutingStatsGroups 26 }


     nncRoutingStatsRawNonBorderPerTblGroup         OBJECT-GROUP 
                OBJECTS {
      			
                        nncRawNBPerTbleTableDescriptor,
       			nncRawNBPerTbleFailedCallsDueToInitDTLNotGenerated,	
      			nncRawNBPerTbleCallsGeneratingAnInitDTL,		
      			nncRawNBPerTbleDTLOrigCallsSuccessEstWithoutReroute,	
      			nncRawNBPerTbleDTLOrigCallsSuccessEstWithReroute,	
      			nncRawNBPerTbleDTLOrigCallsFailedInReRouting,		
      			nncRawNBPerTbleSuccessCallsBdwGreaterThanRTDMinBdw,	
      			nncRawNBPerTbleFailedCallsBdwGreaterThanRTDMinBdw,	
      			nncRawNBPerTbleCrankbackReceivedAsDTLOriginator,	
      			nncRawNBPerTbleDTLsGeneratedDueToCrankback	               
			}
                STATUS          current
                DESCRIPTION     "A collection of objects providing raw counters 
                                 for  non-border node per table stats."
        ::= { nncRoutingStatsGroups 27 }

     nncRoutingStatsRawBorderPerTblGroup         OBJECT-GROUP 
                OBJECTS {
      			
                        nncRawBPerTblTableDescriptor,
     			nncRawBPerTblFailedCallsDueInitLowerLvlDTLsNotGen,	
      			nncRawBPerTblCallsGeneratingInitLowerLvlDTLs,		
      			nncRawBPerTblDTLGenCallsSuccessEstWithoutReroute,	
      			nncRawBPerTblDTLGenCallsSuccessEstWithReroute,	
      			nncRawBPerTblDTLGenCallsFailedInReRouting,		
      			nncRawBPerTblSuccessCallsBdwGreaterThanRTDMinBdw,	
      			nncRawBPerTblFailedCallsBdwGreaterThanRTDMinBdw,	
      			nncRawBPerTblCrankbackReceivedAsAnEntryBorderNode,	
      			nncRawBPerTblLowerLvlDTLsGenDueToRecdCrankback	              
 			}
                STATUS          current
                DESCRIPTION     "A collection of objects providing raw counters 
                                 for border node per table stats."
        ::= { nncRoutingStatsGroups 28 }

     nncPNNIStatRawNonBorderTotalGroup         OBJECT-GROUP 
                OBJECTS {
      			
      			nncRawNBTotalFailedCallsDueToInitDTLNotGenerated,	
      			nncRawNBTotalCallsGeneratingAnInitDTL,			
     			nncRawNBTotalDTLOrigCallsSuccessEstWithoutReroute,	
     			nncRawNBTotalDTLOrigCallsSuccessEstWithReroute,	
    			nncRawNBTotalDTLOrigCallsFailedInReRouting,		
     			nncRawNBTotalSuccessCallsBdwGreaterThanRTDMinBdw,	
      			nncRawNBTotalFailedCallsBdwGreaterThanRTDMinBdw,	
      			nncRawNBTotalCrankbackReceivedAsDTLOriginator,		
      			nncRawNBTotalDTLsGeneratedDueToCrankback,		
      			nncRawNBTotalCallsRecdAsTransitNodeOverInsideLinks,	
      			nncRawNBTotalCrnkbksRecdAsTransitNodeOvInsideLnks,	
      			nncRawNBTotalSucdEndBlocCrnkbksRecdOvInsideLnks
			}		               				
                STATUS          current
                DESCRIPTION     "A collection of objects providing raw counters 
                                 for  non-border node total stats."
        ::= { nncRoutingStatsGroups 29 }

     nncRoutingStatsRawBorderTotalGroup         OBJECT-GROUP 
                OBJECTS {
      			
  			nncRawBTotalFailedCallsDueToInitLowerLvlDTLNotGen,	
      			nncRawBTotalCallsGeneratingInitLowerLvlDTLs,		
      			nncRawBTotalDTLGenCallsSuccessEstWithoutReroute,	
      			nncRawBTotalDTLGenCallsSuccessEstWithReroute,		
      			nncRawBTotalDTLGenCallsFailedInReRouting,		
      			nncRawBTotalSuccessCallsBdwGreaterThanRTDMinBdw,	
      			nncRawBTotalFailedCallsBdwGreaterThanRTDMinBdw,		
      			nncRawBTotalCrankbackReceivedAsAnEntryBorderNode,	
      			nncRawBTotalLowerLvlDTLsGenDueToRecdCrankback,		
      			nncRawBTotalCallsRecdOverAnOutsideLink,			  
      			nncRawBTotalCallsTransmittedOverAnOutsideLink,		
      			nncRawBTotalCrankbksRecdOverAnOutsideLink,		
      			nncRawBTotalSucdEndBlocCrankbksRecdOverOutsideLink, 
      			nncRawBTotalCrankbkForwdedToPrevPGCrankbkLvlTooHigh	      
		        }
                STATUS          current
                DESCRIPTION     "A collection of objects providing raw counters 
                                 for border node total stats."
        ::= { nncRoutingStatsGroups 30 }





--------------------------------------------------------------------------------
-- Compliance Statements (mandatory)
--------------------------------------------------------------------------------
  nncRoutingStatsCompliances1  MODULE-COMPLIANCE
    STATUS    current
    DESCRIPTION  
      "The compliance statement for Newbridge SNMP entities
       which PNNI stats."
    MODULE 
    MANDATORY-GROUPS  	{ 
      			nncRoutingStatsCommon15MinCurrentGroup,
     			nncRoutingStatsCommon24HourCurrentGroup,
      			nncRoutingStatsSpecific15MinCurrentGroup,
      			nncRoutingStatsSpecific24HourCurrentGroup,
      			nncRoutingStatsNonBorderPerTbl15MinCurrentGroup,
      			nncRoutingStatsNonBorderPerTbl24HourCurrentGroup,
      			nncRoutingStatsBorderPerTbl15MinCurrentGroup,
      			nncRoutingStatsBorderPerTbl24HourCurrentGroup,
      			nncPNNIStatNonBorderTotal15MinCurrentGroup,
      			nncPNNIStatNonBorderTotal24HourCurrentGroup,
      			nncPNNIStatBorderTotal15MinCurrentGroup,
      			nncPNNIStatBorderTotal24HourCurrentGroup
    			}
  ::= { nncRoutingStatsCompliances 1 } 

 nncRoutingStatsCompliances2  MODULE-COMPLIANCE
    STATUS    current
    DESCRIPTION  
      "The compliance statement for Newbridge SNMP entities
       which PNNI stats."
    MODULE 
    MANDATORY-GROUPS  	{ 
      			nncRoutingStatsCommon15MinIntervalGroup,
      			nncRoutingStatsCommon24HourIntervalGroup,
      			nncRoutingStatsSpecific15MinIntervalGroup,
      			nncRoutingStatsSpecific24HourIntervalGroup,
      			nncRoutingStatsNonBorderPerTbl15MinIntervalGroup,
      			nncRoutingStatsNonBorderPerTbl24HourIntervalGroup,
      			nncRoutingStatsBorderPerTbl15MinIntervalGroup,
      			nncRoutingStatsBorderPerTbl24HourIntervalGroup,
      			nncPNNIStatNonBorderTotal15MinIntervalGroup,
      			nncPNNIStatNonBorderTotal24HourIntervalGroup,
      			nncPNNIStatBorderTotal15MinIntervalGroup,
      			nncPNNIStatBorderTotal24HourIntervalGroup
    			}
  ::= { nncRoutingStatsCompliances 2 } 

 nncRoutingStatsCompliances3  MODULE-COMPLIANCE
    STATUS    current
    DESCRIPTION  
      "The compliance statement for Newbridge SNMP entities
       which PNNI stats."
    MODULE 
    MANDATORY-GROUPS  	{ 
      			nncRoutingStatsRawCommonGroup,
      			ncExtRoutingStatsRawSpecificGroup,
      			nncRoutingStatsRawNonBorderPerTblGroup,
      			nncRoutingStatsRawBorderPerTblGroup,
      			nncPNNIStatRawNonBorderTotalGroup,
      			nncRoutingStatsRawBorderTotalGroup
 			}
  ::= { nncRoutingStatsCompliances 3 } 


-------------------------------------------------------------------------------
--  Review Minutes 
-------------------------------------------------------------------------------

-- MINUTES-BEGIN
-- REVIEW-DATE  "2000.04.10."
-- BODY  "
--
--
-- TO:  Fernando Bello*, Bryan Lockie*, Carl Rajsic*, George Soccar*,
--      John Sullivan*, Mark Weedmark*, George Yu*, Jiaou Li*,
--      Yi Fang*, Adrian Tsang*, William McConnochie*, Jack Sinclair*
-- CC:  Numbers Admin,Peter Dippe,Shawn McCallister,Dave Watkinson,
--      Mairi McKissock,David Maxwell,Chris Anastasiadis,
--      Carmen Wong, Bruce Brown,Randy Jones
-- FROM:  Yi Fang*

-- A formal review meeting was held on Monday, April 10th 2000, to review
-- the CallRoutingStats MIB. 
-- Attendees are marked with * in the TO and CC list above.

-- Action Items:
-- 1). George Yu and Carl Rajsic to find out whether the entPhysicalIndex
-- has active/inactive info and resolve the issue of whether to use the
-- CallControl group as the index
-- status: closed

-- 2). Carl Rajsic to find out for 1+1 hot redundancy, whether the inactive
-- CallP card has the same stats as the active one
-- status: closed


-- 3). Yi Fang to put a description up front in the MIB for the following 6
--   category of tables:
--     Static and PNNI Common Statistic
--     Static Routing Specific Statistic
--     Non-Border Node PNNI Per Routing Table Statistics
--     Border Node PNNI Per Routing Table Statistics
--     Non-Border Node PNNI Total Statistics
--     Border Node PNNI Total Statistics
-- status: closed


-- 4). Adrian Tsang to update the FS (31FS0100) for the index once action
-- items 1 and 2 have been resolved
-- status: closed



--
-- An EDR was closed on 2000.04.28 to review the updated CallRoutingStats.mib.
-- 
--
-- Outcome
--
-- It was the consensus of the review team that this file is acceptable 
-- as is.
--
--  "
--
-- END-MINUTES
--

END -- DEFINITION OF NNCCALLROUTINGSTATS-MIB
