Wellfleet-ASYNC-MIB DEFINITIONS ::= BEGIN

-- Created by mdl2asn version 3.1
-- Creation date: Wed Aug 30 16:36:49 EDT 1995


    IMPORTS

      IpAddress, Counter, Gauge, TimeTicks, Opaque, enterprises, mgmt
        FROM RFC1155-SMI
      OBJECT-TYPE
        FROM RFC-1212
      TRAP-TYPE
        FROM RFC-1215
      DisplayString, mib-2
        FROM RFC1213-MIB
      wfLine
        FROM Wellfleet-COMMON-MIB;


    wfAsyncTable OBJECT-TYPE
        SYNTAX	SEQUENCE OF WfAsyncEntry
        ACCESS	not-accessible
        STATUS	mandatory
        DESCRIPTION
                "ASYNC  line record"
        ::= { wfLine 3 }

    wfAsyncEntry OBJECT-TYPE
        SYNTAX	WfAsyncEntry
        ACCESS	not-accessible
        STATUS	mandatory
        DESCRIPTION
                "An entry in the ASYNC table"
        INDEX	{ wfAsyncSlot,
    		  wfAsyncConnector }
        ::= { wfAsyncTable 1 }

    WfAsyncEntry ::= SEQUENCE {
    	    wfAsyncDelete
    		INTEGER,
    	    wfAsyncDisable
    		INTEGER,
    	    wfAsyncState
    		INTEGER,
    	    wfAsyncSlot
    		INTEGER,
    	    wfAsyncConnector
    		INTEGER,
    	    wfAsyncCct
    		INTEGER,
    	    wfAsyncMtu
    		INTEGER,
    	    wfAsyncMadr
    		OCTET STRING,
    	    wfAsyncStartProtocol
    		INTEGER,
    	    wfAsyncRxOctets
    		Counter,
    	    wfAsyncTxOctets
    		Counter,
    	    wfAsyncRxErrors
    		Counter,
    	    wfAsyncTxErrors
    		Counter,
    	    wfAsyncRxLackRescs
    		Counter,
    	    wfAsyncTxLackRescs
    		Counter,
    	    wfAsyncTxUnderFlows
    		Counter,
    	    wfAsyncTxRejects
    		Counter,
    	    wfAsyncRxRejects
    		Counter,
    	    wfAsyncRxOverFlows
    		Counter,
    	    wfAsyncRxBadOctets
    		Counter,
    	    wfAsyncRxRunts
    		Counter,
    	    wfAsyncTxQueueLength
    		INTEGER,
    	    wfAsyncRxQueueLength
    		INTEGER,
    	    wfAsyncRxReplenMisses
    		Counter,
    	    wfAsyncLineNumber
    		INTEGER,
    	    wfAsyncRemoteAddress
    		IpAddress,
    	    wfAsyncRemotePort
    		INTEGER,
    	    wfAsyncLocalPort
    		INTEGER,
    	    wfAsyncBaud
    		INTEGER,
    	    wfAsyncIdleTimer
    		INTEGER,
    	    wfAsyncRxWindow
    		INTEGER,
    	    wfAsyncMinRxWindows
    		Counter,
    	    wfASyncSecTxQmaxs
    		Counter,
    	    wfASyncSecTxQlens
    		Counter,
    	    wfAsyncTCPKeepalive
    		INTEGER,
    	    wfAsyncTCPInactivityLimit
    		INTEGER,
    	    wfAsyncCfgTxQueueLength
    		INTEGER,
    	    wfAsyncCfgRxQueueLength
    		INTEGER
        }

    wfAsyncDelete OBJECT-TYPE
        SYNTAX	INTEGER {
    		    created(1),
    		    deleted(2)
    		}
        ACCESS	read-write
        STATUS	mandatory
        DESCRIPTION
                "Create/Delete parameter"
        DEFVAL	{ created }
        ::= { wfAsyncEntry 1 }

    wfAsyncDisable OBJECT-TYPE
        SYNTAX	INTEGER {
    		    enabled(1),
    		    disabled(2)
    		}
        ACCESS	read-write
        STATUS	mandatory
        DESCRIPTION
                "Enable/Disable parameter"
        DEFVAL	{ enabled }
        ::= { wfAsyncEntry 2 }

    wfAsyncState OBJECT-TYPE
        SYNTAX	INTEGER {
    		    up(1),
    		    down(2),
    		    init(3),
    		    notpresent(4),
    		    dsrwait(5)
    		}
        ACCESS	read-only
        STATUS	mandatory
        DESCRIPTION
                "Line Driver state variable, Not Present, DSR Wait,
                Init, Down, Up"
        DEFVAL	{ notpresent }
        ::= { wfAsyncEntry 3 }

    wfAsyncSlot OBJECT-TYPE
        SYNTAX	INTEGER
        ACCESS	read-only
        STATUS	mandatory
        DESCRIPTION
                "Instance ID Slot, filled in by driver"
        ::= { wfAsyncEntry 4 }

    wfAsyncConnector OBJECT-TYPE
        SYNTAX	INTEGER {
    		    one(1),
    		    two(2),
    		    three(3),
    		    four(4)
    		}
        ACCESS	read-only
        STATUS	mandatory
        DESCRIPTION
                "Instance ID Connector, filled in by driver. For the ASN
                this attribute is an encoded value and is equal to
                'module'*10 + 'connector'. Where 'module' is defined in
                attribute 86 and 'connector' is defined in attribute 78
                of this table. For non-ASN platforms this attribute is
                the physical connector number on the slot."
        ::= { wfAsyncEntry 5 }

    wfAsyncCct OBJECT-TYPE
        SYNTAX	INTEGER(1..1023)
        ACCESS	read-write
        STATUS	mandatory
        DESCRIPTION
                "CCT number for this line instance"
        ::= { wfAsyncEntry 6 }

    wfAsyncMtu OBJECT-TYPE
        SYNTAX	INTEGER(3..1580)
        ACCESS	read-write
        STATUS	mandatory
        DESCRIPTION
                "MTU parameter, this is buffer size for ASYNC media, fixed"
        DEFVAL	{ 1000 }
        ::= { wfAsyncEntry 7 }

    wfAsyncMadr OBJECT-TYPE
        SYNTAX	OCTET STRING
        ACCESS	read-only
        STATUS	mandatory
        DESCRIPTION
                "Line MAC address, fixed - line driver fills in from the 48 bit
                address stored in the serial number prom for this connector."
        ::= { wfAsyncEntry 8 }

    wfAsyncStartProtocol OBJECT-TYPE
        SYNTAX	INTEGER {
    		    loop(1),
    		    originate(2),
    		    answer(3)
    		}
        ACCESS	read-write
        STATUS	mandatory
        DESCRIPTION
                "Start protocol selection is provided via this parameter. The
                supported protocols can be selected per interface."
        DEFVAL	{ answer }
        ::= { wfAsyncEntry 9 }

    wfAsyncRxOctets OBJECT-TYPE
        SYNTAX	Counter
        ACCESS	read-only
        STATUS	mandatory
        DESCRIPTION
                "Number of octets received without error"
        ::= { wfAsyncEntry 10 }

    wfAsyncTxOctets OBJECT-TYPE
        SYNTAX	Counter
        ACCESS	read-only
        STATUS	mandatory
        DESCRIPTION
                "Number of octets transmitted without error"
        ::= { wfAsyncEntry 11 }

    wfAsyncRxErrors OBJECT-TYPE
        SYNTAX	Counter
        ACCESS	read-only
        STATUS	mandatory
        DESCRIPTION
                "Number of receive errors"
        ::= { wfAsyncEntry 12 }

    wfAsyncTxErrors OBJECT-TYPE
        SYNTAX	Counter
        ACCESS	read-only
        STATUS	mandatory
        DESCRIPTION
                "Number of transmission errors"
        ::= { wfAsyncEntry 13 }

    wfAsyncRxLackRescs OBJECT-TYPE
        SYNTAX	Counter
        ACCESS	read-only
        STATUS	mandatory
        DESCRIPTION
                "Number of Rx frames dropped due to lack of buffer resources"
        ::= { wfAsyncEntry 14 }

    wfAsyncTxLackRescs OBJECT-TYPE
        SYNTAX	Counter
        ACCESS	read-only
        STATUS	mandatory
        DESCRIPTION
                "Number of frames clipped in driver's transmit routine due to transmit
                congestion."
        ::= { wfAsyncEntry 15 }

    wfAsyncTxUnderFlows OBJECT-TYPE
        SYNTAX	Counter
        ACCESS	read-only
        STATUS	mandatory
        DESCRIPTION
                "Number of transmission underflows, device FIFO went empty before
                next DMA request was granted."
        ::= { wfAsyncEntry 16 }

    wfAsyncTxRejects OBJECT-TYPE
        SYNTAX	Counter
        ACCESS	read-only
        STATUS	mandatory
        DESCRIPTION
                "Number of reject frames which were transmitted"
        ::= { wfAsyncEntry 17 }

    wfAsyncRxRejects OBJECT-TYPE
        SYNTAX	Counter
        ACCESS	read-only
        STATUS	mandatory
        DESCRIPTION
                "Number of reject frames which were received"
        ::= { wfAsyncEntry 18 }

    wfAsyncRxOverFlows OBJECT-TYPE
        SYNTAX	Counter
        ACCESS	read-only
        STATUS	mandatory
        DESCRIPTION
                "Number of receive overflows, device FIFO overflowed before next
                DMA cycle granted.  No buffer resources available."
        ::= { wfAsyncEntry 19 }

    wfAsyncRxBadOctets OBJECT-TYPE
        SYNTAX	Counter
        ACCESS	read-only
        STATUS	mandatory
        DESCRIPTION
                "Number of bad receive frames, caused by FCS errors or non octet aligned."
        ::= { wfAsyncEntry 20 }

    wfAsyncRxRunts OBJECT-TYPE
        SYNTAX	Counter
        ACCESS	read-only
        STATUS	mandatory
        DESCRIPTION
                "Number of runt frames received"
        ::= { wfAsyncEntry 21 }

    wfAsyncTxQueueLength OBJECT-TYPE
        SYNTAX	INTEGER
        ACCESS	read-only
        STATUS	mandatory
        DESCRIPTION
                "Current Transmit Queue Length."
        ::= { wfAsyncEntry 22 }

    wfAsyncRxQueueLength OBJECT-TYPE
        SYNTAX	INTEGER
        ACCESS	read-only
        STATUS	mandatory
        DESCRIPTION
                "Current Receive Queue Length."
        ::= { wfAsyncEntry 23 }

    wfAsyncRxReplenMisses OBJECT-TYPE
        SYNTAX	Counter
        ACCESS	read-only
        STATUS	mandatory
        DESCRIPTION
                "Number of packet buffer misses while attempting to replenish driver
                receive ring."
        ::= { wfAsyncEntry 24 }

    wfAsyncLineNumber OBJECT-TYPE
        SYNTAX	INTEGER
        ACCESS	read-write
        STATUS	mandatory
        DESCRIPTION
                "line number for this line instance"
        ::= { wfAsyncEntry 25 }

    wfAsyncRemoteAddress OBJECT-TYPE
        SYNTAX	IpAddress
        ACCESS	read-write
        STATUS	mandatory
        DESCRIPTION
                "Remote TCP host  IP address"
        ::= { wfAsyncEntry 26 }

    wfAsyncRemotePort OBJECT-TYPE
        SYNTAX	INTEGER {
    		    port(7)
    		}
        ACCESS	read-write
        STATUS	mandatory
        DESCRIPTION
                "Remote  port  for TCP connection"
        DEFVAL	{ port }
        ::= { wfAsyncEntry 27 }

    wfAsyncLocalPort OBJECT-TYPE
        SYNTAX	INTEGER {
    		    default(2100)
    		}
        ACCESS	read-write
        STATUS	mandatory
        DESCRIPTION
                "Local  port  for TCP connection"
        DEFVAL	{ default }
        ::= { wfAsyncEntry 28 }

    wfAsyncBaud OBJECT-TYPE
        SYNTAX	INTEGER {
    		    r300(300),
    		    r1200(1200),
    		    r2400(2400),
    		    r4800(4800),
    		    r9600(9600),
    		    r19200(19200)
    		}
        ACCESS	read-write
        STATUS	mandatory
        DESCRIPTION
                "Async  line  speed"
        DEFVAL	{ r9600 }
        ::= { wfAsyncEntry 29 }

    wfAsyncIdleTimer OBJECT-TYPE
        SYNTAX	INTEGER(1..300)
        ACCESS	read-write
        STATUS	mandatory
        DESCRIPTION
                "Async  line Idle timer"
        DEFVAL	{ 20 }
        ::= { wfAsyncEntry 30 }

    wfAsyncRxWindow OBJECT-TYPE
        SYNTAX	INTEGER(512..65535)
        ACCESS	read-write
        STATUS	mandatory
        DESCRIPTION
                "Configured TCP receive window"
        DEFVAL	{ 4096 }
        ::= { wfAsyncEntry 31 }

    wfAsyncMinRxWindows OBJECT-TYPE
        SYNTAX	Counter
        ACCESS	read-only
        STATUS	mandatory
        DESCRIPTION
                "Low-water mark of receive window (for latest connection)"
        ::= { wfAsyncEntry 32 }

    wfASyncSecTxQmaxs OBJECT-TYPE
        SYNTAX	Counter
        ACCESS	read-only
        STATUS	mandatory
        DESCRIPTION
                "secondary TX queue hi-water mark (for this connection)"
        ::= { wfAsyncEntry 33 }

    wfASyncSecTxQlens OBJECT-TYPE
        SYNTAX	Counter
        ACCESS	read-only
        STATUS	mandatory
        DESCRIPTION
                "secondary TX queue present value"
        ::= { wfAsyncEntry 34 }

    wfAsyncTCPKeepalive OBJECT-TYPE
        SYNTAX	INTEGER(3..180)
        ACCESS	read-write
        STATUS	mandatory
        DESCRIPTION
                "Keepalive timer. A keepalive (probe) message is sent out
                if there is no activity in this number of seconds."
        DEFVAL	{ 8 }
        ::= { wfAsyncEntry 35 }

    wfAsyncTCPInactivityLimit OBJECT-TYPE
        SYNTAX	INTEGER(-65536..65535)
        ACCESS	read-write
        STATUS	mandatory
        DESCRIPTION
                "Inactivity limit. Connection (eligable for) reset
                if no activity in this number of seconds."
        DEFVAL	{ 300 }
        ::= { wfAsyncEntry 36 }

    wfAsyncCfgTxQueueLength OBJECT-TYPE
        SYNTAX	INTEGER(0..255)
        ACCESS	read-write
        STATUS	mandatory
        DESCRIPTION
                "Configured Transmit Queue Length. Values other than zero over-ride the
                router selected values.  A value of zero has a special meaning.  Zero
                causes router based default values to be used.  Values larger than the
                compiled ring size are truncated to the compiled ring size. "
        ::= { wfAsyncEntry 37 }

    wfAsyncCfgRxQueueLength OBJECT-TYPE
        SYNTAX	INTEGER(0..255)
        ACCESS	read-write
        STATUS	mandatory
        DESCRIPTION
                "Configured Receive Queue Length. Values other than zero over-ride the
                router selected values.  A value of zero has a special meaning.  Zero
                causes router based default values to be used.  Values larger than the
                compiled ring size are truncated to the compiled ring size. "
        ::= { wfAsyncEntry 38 }

    END  -- Wellfleet-ASYNC-MIB
