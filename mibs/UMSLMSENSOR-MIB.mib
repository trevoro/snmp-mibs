UMSLMSENSOR-MIB DEFINITIONS ::= BEGIN

IMPORTS
   OBJECT-TYPE
      FROM RFC-1212

   TRAP-TYPE
      FROM RFC-1215

   ibmpsgLMSensor,
   Boolean, Uint8, Sint8, Uint16, Sint16, Uint32,
   Sint32, Uint64, Sint64, Real32, Real64, String, Datetime
      FROM UMS-MIB;

iBMPSGTemperatureSensorTable OBJECT-TYPE
   SYNTAX         SEQUENCE OF IBMPSGTemperatureSensorEntry
   ACCESS         not-accessible
   STATUS         mandatory
   DESCRIPTION    "The IBMPSG_TemperatureSensor class represents an IBM managed Temperature Sensor."
   REFERENCE      "IBMPSG_TemperatureSensor"
::= { ibmpsgLMSensor 1 }

iBMPSGTemperatureSensorEntry OBJECT-TYPE
   SYNTAX         IBMPSGTemperatureSensorEntry
   ACCESS         not-accessible
   STATUS         mandatory
   DESCRIPTION    ""
   INDEX          { iBMPSGTemperatureSensorKeyIndex }
::= { iBMPSGTemperatureSensorTable 1 }

IBMPSGTemperatureSensorEntry ::= SEQUENCE
{
   iBMPSGTemperatureSensorKeyIndex String,   
   iBMPSGTemperatureSensorCurrentReading Sint32,
   iBMPSGTemperatureSensorNominalReading Sint32,
   iBMPSGTemperatureSensorNormalMax Sint32,
   iBMPSGTemperatureSensorNormalMin Sint32,
   iBMPSGTemperatureSensorMaxReadable Sint32,
   iBMPSGTemperatureSensorMinReadable Sint32,
   iBMPSGTemperatureSensorResolution Uint32,
   iBMPSGTemperatureSensorTolerance Sint32,
   iBMPSGTemperatureSensorAccuracy Sint32,
   iBMPSGTemperatureSensorLowerThresholdNonCritical Sint32,
   iBMPSGTemperatureSensorUpperThresholdNonCritical Sint32,
   iBMPSGTemperatureSensorLowerThresholdCritical Sint32,
   iBMPSGTemperatureSensorUpperThresholdCritical Sint32,
   iBMPSGTemperatureSensorLowerThresholdFatal Sint32,
   iBMPSGTemperatureSensorUpperThresholdFatal Sint32,
   iBMPSGTemperatureSensorTempLocation Uint32,
   iBMPSGTemperatureSensorEventsEnabled Boolean,
   iBMPSGTemperatureSensorPollingInterval Uint32,
   iBMPSGTemperatureSensorEventAutoClearEnabled Boolean,
   iBMPSGTemperatureSensorStatus String
}

iBMPSGTemperatureSensorKeyIndex OBJECT-TYPE
   SYNTAX         String
   ACCESS         read-write
   STATUS         mandatory
   DESCRIPTION    ""
   REFERENCE      "IBMPSG_TemperatureSensor.KeyIndex"
::= { iBMPSGTemperatureSensorEntry 1 }

iBMPSGTemperatureSensorCurrentReading OBJECT-TYPE
   SYNTAX         Sint32
   ACCESS         read-write
   STATUS         mandatory
   DESCRIPTION    ""
   REFERENCE      "IBMPSG_TemperatureSensor.CurrentReading"
::= { iBMPSGTemperatureSensorEntry 2 }

iBMPSGTemperatureSensorNominalReading OBJECT-TYPE
   SYNTAX         Sint32
   ACCESS         read-write
   STATUS         mandatory
   DESCRIPTION    ""
   REFERENCE      "IBMPSG_TemperatureSensor.NominalReading"
::= { iBMPSGTemperatureSensorEntry 3 }

iBMPSGTemperatureSensorNormalMax OBJECT-TYPE
   SYNTAX         Sint32
   ACCESS         read-write
   STATUS         mandatory
   DESCRIPTION    ""
   REFERENCE      "IBMPSG_TemperatureSensor.NormalMax"
::= { iBMPSGTemperatureSensorEntry 4 }

iBMPSGTemperatureSensorNormalMin OBJECT-TYPE
   SYNTAX         Sint32
   ACCESS         read-write
   STATUS         mandatory
   DESCRIPTION    ""
   REFERENCE      "IBMPSG_TemperatureSensor.NormalMin"
::= { iBMPSGTemperatureSensorEntry 5 }

iBMPSGTemperatureSensorMaxReadable OBJECT-TYPE
   SYNTAX         Sint32
   ACCESS         read-write
   STATUS         mandatory
   DESCRIPTION    ""
   REFERENCE      "IBMPSG_TemperatureSensor.MaxReadable"
::= { iBMPSGTemperatureSensorEntry 6 }

iBMPSGTemperatureSensorMinReadable OBJECT-TYPE
   SYNTAX         Sint32
   ACCESS         read-write
   STATUS         mandatory
   DESCRIPTION    ""
   REFERENCE      "IBMPSG_TemperatureSensor.MinReadable"
::= { iBMPSGTemperatureSensorEntry 7 }

iBMPSGTemperatureSensorResolution OBJECT-TYPE
   SYNTAX         Uint32
   ACCESS         read-write
   STATUS         mandatory
   DESCRIPTION    ""
   REFERENCE      "IBMPSG_TemperatureSensor.Resolution"
::= { iBMPSGTemperatureSensorEntry 8 }

iBMPSGTemperatureSensorTolerance OBJECT-TYPE
   SYNTAX         Sint32
   ACCESS         read-write
   STATUS         mandatory
   DESCRIPTION    ""
   REFERENCE      "IBMPSG_TemperatureSensor.Tolerance"
::= { iBMPSGTemperatureSensorEntry 9 }

iBMPSGTemperatureSensorAccuracy OBJECT-TYPE
   SYNTAX         Sint32
   ACCESS         read-write
   STATUS         mandatory
   DESCRIPTION    ""
   REFERENCE      "IBMPSG_TemperatureSensor.Accuracy"
::= { iBMPSGTemperatureSensorEntry 10 }

iBMPSGTemperatureSensorLowerThresholdNonCritical OBJECT-TYPE
   SYNTAX         Sint32
   ACCESS         read-write
   STATUS         mandatory
   DESCRIPTION    ""
   REFERENCE      "IBMPSG_TemperatureSensor.LowerThresholdNonCritical"
::= { iBMPSGTemperatureSensorEntry 11 }

iBMPSGTemperatureSensorUpperThresholdNonCritical OBJECT-TYPE
   SYNTAX         Sint32
   ACCESS         read-write
   STATUS         mandatory
   DESCRIPTION    ""
   REFERENCE      "IBMPSG_TemperatureSensor.UpperThresholdNonCritical"
::= { iBMPSGTemperatureSensorEntry 12 }

iBMPSGTemperatureSensorLowerThresholdCritical OBJECT-TYPE
   SYNTAX         Sint32
   ACCESS         read-write
   STATUS         mandatory
   DESCRIPTION    ""
   REFERENCE      "IBMPSG_TemperatureSensor.LowerThresholdCritical"
::= { iBMPSGTemperatureSensorEntry 13 }

iBMPSGTemperatureSensorUpperThresholdCritical OBJECT-TYPE
   SYNTAX         Sint32
   ACCESS         read-write
   STATUS         mandatory
   DESCRIPTION    ""
   REFERENCE      "IBMPSG_TemperatureSensor.UpperThresholdCritical"
::= { iBMPSGTemperatureSensorEntry 14 }

iBMPSGTemperatureSensorLowerThresholdFatal OBJECT-TYPE
   SYNTAX         Sint32
   ACCESS         read-write
   STATUS         mandatory
   DESCRIPTION    ""
   REFERENCE      "IBMPSG_TemperatureSensor.LowerThresholdFatal"
::= { iBMPSGTemperatureSensorEntry 15 }

iBMPSGTemperatureSensorUpperThresholdFatal OBJECT-TYPE
   SYNTAX         Sint32
   ACCESS         read-write
   STATUS         mandatory
   DESCRIPTION    ""
   REFERENCE      "IBMPSG_TemperatureSensor.UpperThresholdFatal"
::= { iBMPSGTemperatureSensorEntry 16 }

iBMPSGTemperatureSensorTempLocation OBJECT-TYPE
   SYNTAX         Uint32
   ACCESS         read-write
   STATUS         mandatory
   DESCRIPTION    "The current temperature sensor location"
   REFERENCE      "IBMPSG_TemperatureSensor.TempLocation"
::= { iBMPSGTemperatureSensorEntry 17 }

iBMPSGTemperatureSensorEventsEnabled OBJECT-TYPE
   SYNTAX         Boolean
   ACCESS         read-write
   STATUS         mandatory
   DESCRIPTION    "Event generation status."
   REFERENCE      "IBMPSG_TemperatureSensor.EventsEnabled"
::= { iBMPSGTemperatureSensorEntry 18 }

iBMPSGTemperatureSensorPollingInterval OBJECT-TYPE
   SYNTAX         Uint32
   ACCESS         read-write
   STATUS         mandatory
   DESCRIPTION    "Polling interval is measured in seconds.  Value of zero indicates do it once and quit.  Minimum polling interval is ten seconds."
   REFERENCE      "IBMPSG_TemperatureSensor.PollingInterval"
::= { iBMPSGTemperatureSensorEntry 19 }

iBMPSGTemperatureSensorEventAutoClearEnabled OBJECT-TYPE
   SYNTAX         Boolean
   ACCESS         read-write
   STATUS         mandatory
   DESCRIPTION    "False means that events are only generated on state changes.  True means that events are generated on state changes and periodically when the object is in a non-normal state."
   REFERENCE      "IBMPSG_TemperatureSensor.EventAutoClearEnabled"
::= { iBMPSGTemperatureSensorEntry 20 }

iBMPSGTemperatureSensorStatus OBJECT-TYPE
   SYNTAX         String
   ACCESS         read-write
   STATUS         mandatory
   DESCRIPTION    "The Status property is a string indicating the current status of the object. Various operational and non-operational statuses can be defined. Operational statuses are OK, Degraded and Pred Fail. Pred Fail indicates that an element may be functioning properly but predicting a failure in the near future. An example is a SMART-enabled hard drive. Non-operational statuses can also be specified. These are Error, Starting, Stopping and Service. The latter, Service, could apply during mirror-resilvering of a disk, reload of a user permissions list, or other administrative work. Not all such work is on-line, yet the managed element is neither OK nor in one of the other states."
   REFERENCE      "IBMPSG_TemperatureSensor.Status"
::= { iBMPSGTemperatureSensorEntry 21 }

iBMPSGVoltageSensorTable OBJECT-TYPE
   SYNTAX         SEQUENCE OF IBMPSGVoltageSensorEntry
   ACCESS         not-accessible
   STATUS         mandatory
   DESCRIPTION    "The IBMPSG_VoltageSensor class represents an IBM managed voltage Sensor"
   REFERENCE      "IBMPSG_VoltageSensor"
::= { ibmpsgLMSensor 2 }

iBMPSGVoltageSensorEntry OBJECT-TYPE
   SYNTAX         IBMPSGVoltageSensorEntry
   ACCESS         not-accessible
   STATUS         mandatory
   DESCRIPTION    ""
   INDEX          { iBMPSGVoltageSensorKeyIndex }
::= { iBMPSGVoltageSensorTable 1 }

IBMPSGVoltageSensorEntry ::= SEQUENCE
{
   iBMPSGVoltageSensorKeyIndex String,   
   iBMPSGVoltageSensorCurrentReading Sint32,
   iBMPSGVoltageSensorNominalReading Sint32,
   iBMPSGVoltageSensorNormalMax Sint32,
   iBMPSGVoltageSensorNormalMin Sint32,
   iBMPSGVoltageSensorMaxReadable Sint32,
   iBMPSGVoltageSensorMinReadable Sint32,
   iBMPSGVoltageSensorResolution Uint32,
   iBMPSGVoltageSensorTolerance Sint32,
   iBMPSGVoltageSensorAccuracy Sint32,
   iBMPSGVoltageSensorLowerThresholdNonCritical Sint32,
   iBMPSGVoltageSensorUpperThresholdNonCritical Sint32,
   iBMPSGVoltageSensorLowerThresholdCritical Sint32,
   iBMPSGVoltageSensorUpperThresholdCritical Sint32,
   iBMPSGVoltageSensorLowerThresholdFatal Sint32,
   iBMPSGVoltageSensorUpperThresholdFatal Sint32,
   iBMPSGVoltageSensorVoltageType Uint32,
   iBMPSGVoltageSensorEventsEnabled Boolean,
   iBMPSGVoltageSensorPollingInterval Uint32,
   iBMPSGVoltageSensorEventAutoClearEnabled Boolean,
   iBMPSGVoltageSensorStatus String
}

iBMPSGVoltageSensorKeyIndex OBJECT-TYPE
   SYNTAX         String
   ACCESS         read-write
   STATUS         mandatory
   DESCRIPTION    ""
   REFERENCE      "IBMPSG_VoltageSensor.KeyIndex"
::= { iBMPSGVoltageSensorEntry 1 }

iBMPSGVoltageSensorCurrentReading OBJECT-TYPE
   SYNTAX         Sint32
   ACCESS         read-write
   STATUS         mandatory
   DESCRIPTION    ""
   REFERENCE      "IBMPSG_VoltageSensor.CurrentReading"
::= { iBMPSGVoltageSensorEntry 2 }

iBMPSGVoltageSensorNominalReading OBJECT-TYPE
   SYNTAX         Sint32
   ACCESS         read-write
   STATUS         mandatory
   DESCRIPTION    ""
   REFERENCE      "IBMPSG_VoltageSensor.NominalReading"
::= { iBMPSGVoltageSensorEntry 3 }

iBMPSGVoltageSensorNormalMax OBJECT-TYPE
   SYNTAX         Sint32
   ACCESS         read-write
   STATUS         mandatory
   DESCRIPTION    ""
   REFERENCE      "IBMPSG_VoltageSensor.NormalMax"
::= { iBMPSGVoltageSensorEntry 4 }

iBMPSGVoltageSensorNormalMin OBJECT-TYPE
   SYNTAX         Sint32
   ACCESS         read-write
   STATUS         mandatory
   DESCRIPTION    ""
   REFERENCE      "IBMPSG_VoltageSensor.NormalMin"
::= { iBMPSGVoltageSensorEntry 5 }

iBMPSGVoltageSensorMaxReadable OBJECT-TYPE
   SYNTAX         Sint32
   ACCESS         read-write
   STATUS         mandatory
   DESCRIPTION    ""
   REFERENCE      "IBMPSG_VoltageSensor.MaxReadable"
::= { iBMPSGVoltageSensorEntry 6 }

iBMPSGVoltageSensorMinReadable OBJECT-TYPE
   SYNTAX         Sint32
   ACCESS         read-write
   STATUS         mandatory
   DESCRIPTION    ""
   REFERENCE      "IBMPSG_VoltageSensor.MinReadable"
::= { iBMPSGVoltageSensorEntry 7 }

iBMPSGVoltageSensorResolution OBJECT-TYPE
   SYNTAX         Uint32
   ACCESS         read-write
   STATUS         mandatory
   DESCRIPTION    ""
   REFERENCE      "IBMPSG_VoltageSensor.Resolution"
::= { iBMPSGVoltageSensorEntry 8 }

iBMPSGVoltageSensorTolerance OBJECT-TYPE
   SYNTAX         Sint32
   ACCESS         read-write
   STATUS         mandatory
   DESCRIPTION    ""
   REFERENCE      "IBMPSG_VoltageSensor.Tolerance"
::= { iBMPSGVoltageSensorEntry 9 }

iBMPSGVoltageSensorAccuracy OBJECT-TYPE
   SYNTAX         Sint32
   ACCESS         read-write
   STATUS         mandatory
   DESCRIPTION    ""
   REFERENCE      "IBMPSG_VoltageSensor.Accuracy"
::= { iBMPSGVoltageSensorEntry 10 }

iBMPSGVoltageSensorLowerThresholdNonCritical OBJECT-TYPE
   SYNTAX         Sint32
   ACCESS         read-write
   STATUS         mandatory
   DESCRIPTION    ""
   REFERENCE      "IBMPSG_VoltageSensor.LowerThresholdNonCritical"
::= { iBMPSGVoltageSensorEntry 11 }

iBMPSGVoltageSensorUpperThresholdNonCritical OBJECT-TYPE
   SYNTAX         Sint32
   ACCESS         read-write
   STATUS         mandatory
   DESCRIPTION    ""
   REFERENCE      "IBMPSG_VoltageSensor.UpperThresholdNonCritical"
::= { iBMPSGVoltageSensorEntry 12 }

iBMPSGVoltageSensorLowerThresholdCritical OBJECT-TYPE
   SYNTAX         Sint32
   ACCESS         read-write
   STATUS         mandatory
   DESCRIPTION    ""
   REFERENCE      "IBMPSG_VoltageSensor.LowerThresholdCritical"
::= { iBMPSGVoltageSensorEntry 13 }

iBMPSGVoltageSensorUpperThresholdCritical OBJECT-TYPE
   SYNTAX         Sint32
   ACCESS         read-write
   STATUS         mandatory
   DESCRIPTION    ""
   REFERENCE      "IBMPSG_VoltageSensor.UpperThresholdCritical"
::= { iBMPSGVoltageSensorEntry 14 }

iBMPSGVoltageSensorLowerThresholdFatal OBJECT-TYPE
   SYNTAX         Sint32
   ACCESS         read-write
   STATUS         mandatory
   DESCRIPTION    ""
   REFERENCE      "IBMPSG_VoltageSensor.LowerThresholdFatal"
::= { iBMPSGVoltageSensorEntry 15 }

iBMPSGVoltageSensorUpperThresholdFatal OBJECT-TYPE
   SYNTAX         Sint32
   ACCESS         read-write
   STATUS         mandatory
   DESCRIPTION    ""
   REFERENCE      "IBMPSG_VoltageSensor.UpperThresholdFatal"
::= { iBMPSGVoltageSensorEntry 16 }

iBMPSGVoltageSensorVoltageType OBJECT-TYPE
   SYNTAX         Uint32
   ACCESS         read-write
   STATUS         mandatory
   DESCRIPTION    "The Voltage Description"
   REFERENCE      "IBMPSG_VoltageSensor.VoltageType"
::= { iBMPSGVoltageSensorEntry 17 }

iBMPSGVoltageSensorEventsEnabled OBJECT-TYPE
   SYNTAX         Boolean
   ACCESS         read-write
   STATUS         mandatory
   DESCRIPTION    "Event generation status."
   REFERENCE      "IBMPSG_VoltageSensor.EventsEnabled"
::= { iBMPSGVoltageSensorEntry 18 }

iBMPSGVoltageSensorPollingInterval OBJECT-TYPE
   SYNTAX         Uint32
   ACCESS         read-write
   STATUS         mandatory
   DESCRIPTION    "Polling interval is measured in seconds.  Value of zero indicates do it once and quit.  Minimum polling interval is ten seconds."
   REFERENCE      "IBMPSG_VoltageSensor.PollingInterval"
::= { iBMPSGVoltageSensorEntry 19 }

iBMPSGVoltageSensorEventAutoClearEnabled OBJECT-TYPE
   SYNTAX         Boolean
   ACCESS         read-write
   STATUS         mandatory
   DESCRIPTION    "False means that events are only generated on state changes.  True means that events are generated on state changes and periodically when the object is in a non-normal state."
   REFERENCE      "IBMPSG_VoltageSensor.EventAutoClearEnabled"
::= { iBMPSGVoltageSensorEntry 20 }

iBMPSGVoltageSensorStatus OBJECT-TYPE
   SYNTAX         String
   ACCESS         read-write
   STATUS         mandatory
   DESCRIPTION    "The Status property is a string indicating the current status of the object. Various operational and non-operational statuses can be defined. Operational statuses are OK, Degraded and Pred Fail. Pred Fail indicates that an element may be functioning properly but predicting a failure in the near future. An example is a SMART-enabled hard drive. Non-operational statuses can also be specified. These are Error, Starting, Stopping and Service. The latter, Service, could apply during mirror-resilvering of a disk, reload of a user permissions list, or other administrative work. Not all such work is on-line, yet the managed element is neither OK nor in one of the other states."
   REFERENCE      "IBMPSG_VoltageSensor.Status"
::= { iBMPSGVoltageSensorEntry 21 }

iBMPSGFanTable OBJECT-TYPE
   SYNTAX         SEQUENCE OF IBMPSGFanEntry
   ACCESS         not-accessible
   STATUS         mandatory
   DESCRIPTION    "The IBMPSG_Fan class represents an IBM managed fan sensor"
   REFERENCE      "IBMPSG_Fan"
::= { ibmpsgLMSensor 3 }

iBMPSGFanEntry OBJECT-TYPE
   SYNTAX         IBMPSGFanEntry
   ACCESS         not-accessible
   STATUS         mandatory
   DESCRIPTION    ""
   INDEX          { iBMPSGFanKeyIndex }
::= { iBMPSGFanTable 1 }

IBMPSGFanEntry ::= SEQUENCE
{
   iBMPSGFanKeyIndex String,
   iBMPSGFanVariableSpeed Boolean,
   iBMPSGFanDesiredSpeed String,
   iBMPSGFanActiveCooling Boolean,
   iBMPSGFanFanType Uint32,
   iBMPSGFanEventsEnabled Boolean,
   iBMPSGFanPollingInterval Uint32,
   iBMPSGFanEventAutoClearEnabled Boolean,
   iBMPSGFanStatus String
}

iBMPSGFanKeyIndex OBJECT-TYPE
   SYNTAX         String
   ACCESS         read-write
   STATUS         mandatory
   DESCRIPTION    ""
   REFERENCE      "IBMPSG_Fan.KeyIndex"
::= { iBMPSGFanEntry 1 }

iBMPSGFanVariableSpeed OBJECT-TYPE
   SYNTAX         Boolean
   ACCESS         read-write
   STATUS         mandatory
   DESCRIPTION    ""
   REFERENCE      "IBMPSG_Fan.VariableSpeed"
::= { iBMPSGFanEntry 2 }

iBMPSGFanDesiredSpeed OBJECT-TYPE
   SYNTAX         String
   ACCESS         read-write
   STATUS         mandatory
   DESCRIPTION    ""
   REFERENCE      "IBMPSG_Fan.DesiredSpeed"
::= { iBMPSGFanEntry 3 }

iBMPSGFanActiveCooling OBJECT-TYPE
   SYNTAX         Boolean
   ACCESS         read-write
   STATUS         mandatory
   DESCRIPTION    ""
   REFERENCE      "IBMPSG_Fan.ActiveCooling"
::= { iBMPSGFanEntry 4 }

iBMPSGFanFanType OBJECT-TYPE
   SYNTAX         Uint32
   ACCESS         read-write
   STATUS         mandatory
   DESCRIPTION    "The current fan type"
   REFERENCE      "IBMPSG_Fan.FanType"
::= { iBMPSGFanEntry 5 }

iBMPSGFanEventsEnabled OBJECT-TYPE
   SYNTAX         Boolean
   ACCESS         read-write
   STATUS         mandatory
   DESCRIPTION    "Event generation status."
   REFERENCE      "IBMPSG_Fan.EventsEnabled"
::= { iBMPSGFanEntry 6 }

iBMPSGFanPollingInterval OBJECT-TYPE
   SYNTAX         Uint32
   ACCESS         read-write
   STATUS         mandatory
   DESCRIPTION    "Polling interval is measured in seconds.  Value of zero indicates do it once and quit.  Minimum polling interval is ten seconds."
   REFERENCE      "IBMPSG_Fan.PollingInterval"
::= { iBMPSGFanEntry 7 }

iBMPSGFanEventAutoClearEnabled OBJECT-TYPE
   SYNTAX         Boolean
   ACCESS         read-write
   STATUS         mandatory
   DESCRIPTION    "False means that events are only generated on state changes.  True means that events are generated on state changes and periodically when the object is in a non-normal state."
   REFERENCE      "IBMPSG_Fan.EventAutoClearEnabled"
::= { iBMPSGFanEntry 8 }

iBMPSGFanStatus OBJECT-TYPE
   SYNTAX         String
   ACCESS         read-write
   STATUS         mandatory
   DESCRIPTION    "The Status property is a string indicating the current status of the object. Various operational and non-operational statuses can be defined. Operational statuses are OK, Degraded and Pred Fail. Pred Fail indicates that an element may be functioning properly but predicting a failure in the near future. An example is a SMART-enabled hard drive. Non-operational statuses can also be specified. These are Error, Starting, Stopping and Service. The latter, Service, could apply during mirror-resilvering of a disk, reload of a user permissions list, or other administrative work. Not all such work is on-line, yet the managed element is neither OK nor in one of the other states."
   REFERENCE      "IBMPSG_Fan.Status"
::= { iBMPSGFanEntry 9 }

iBMPSGSystemEnclosureTable OBJECT-TYPE
   SYNTAX         SEQUENCE OF IBMPSGSystemEnclosureEntry
   ACCESS         not-accessible
   STATUS         mandatory
   DESCRIPTION    "The IBMPSG_SystemEnclosure class represents an IBM chassis sensor"
   REFERENCE      "IBMPSG_SystemEnclosure"
::= { ibmpsgLMSensor 4 }

iBMPSGSystemEnclosureEntry OBJECT-TYPE
   SYNTAX         IBMPSGSystemEnclosureEntry
   ACCESS         not-accessible
   STATUS         mandatory
   DESCRIPTION    ""
   INDEX          { iBMPSGSystemEnclosureKeyIndex }
::= { iBMPSGSystemEnclosureTable 1 }

IBMPSGSystemEnclosureEntry ::= SEQUENCE
{
   iBMPSGSystemEnclosureKeyIndex String,   
   iBMPSGSystemEnclosureIntrusionStatus Uint32,
   iBMPSGSystemEnclosureIntrusionType Uint32,
   iBMPSGSystemEnclosureEventsEnabled Boolean,
   iBMPSGSystemEnclosurePollingInterval Uint32,
   iBMPSGSystemEnclosureACLineStatus Uint16,
   iBMPSGSystemEnclosureDockingStatus Uint16,
   iBMPSGSystemEnclosureEventAutoClearEnabled Boolean,
   iBMPSGSystemEnclosureStatus String
}

iBMPSGSystemEnclosureKeyIndex OBJECT-TYPE
   SYNTAX         String
   ACCESS         read-write
   STATUS         mandatory
   DESCRIPTION    ""
   REFERENCE      "IBMPSG_SystemEnclosure.KeyIndex"
::= { iBMPSGSystemEnclosureEntry 1 }

iBMPSGSystemEnclosureIntrusionStatus OBJECT-TYPE
   SYNTAX         Uint32
   ACCESS         read-write
   STATUS         mandatory
   DESCRIPTION    "The intrusion status"
   REFERENCE      "IBMPSG_SystemEnclosure.IntrusionStatus"
::= { iBMPSGSystemEnclosureEntry 2 }

iBMPSGSystemEnclosureIntrusionType OBJECT-TYPE
   SYNTAX         Uint32
   ACCESS         read-write
   STATUS         mandatory
   DESCRIPTION    "The intrusion status"
   REFERENCE      "IBMPSG_SystemEnclosure.IntrusionType"
::= { iBMPSGSystemEnclosureEntry 3 }

iBMPSGSystemEnclosureEventsEnabled OBJECT-TYPE
   SYNTAX         Boolean
   ACCESS         read-write
   STATUS         mandatory
   DESCRIPTION    "Event generation status."
   REFERENCE      "IBMPSG_SystemEnclosure.EventsEnabled"
::= { iBMPSGSystemEnclosureEntry 4 }

iBMPSGSystemEnclosurePollingInterval OBJECT-TYPE
   SYNTAX         Uint32
   ACCESS         read-write
   STATUS         mandatory
   DESCRIPTION    "Polling interval is measured in seconds.  Value of zero indicates do it once and quit.  Minimum polling interval is ten seconds."
   REFERENCE      "IBMPSG_SystemEnclosure.PollingInterval"
::= { iBMPSGSystemEnclosureEntry 5 }

iBMPSGSystemEnclosureACLineStatus OBJECT-TYPE
   SYNTAX         Uint16
   ACCESS         read-write
   STATUS         mandatory
   DESCRIPTION    "This group defines status information about the AC line in the notebook"
   REFERENCE      "IBMPSG_SystemEnclosure.ACLineStatus"
::= { iBMPSGSystemEnclosureEntry 7 }

iBMPSGSystemEnclosureDockingStatus OBJECT-TYPE
   SYNTAX         Uint16
   ACCESS         read-write
   STATUS         mandatory
   DESCRIPTION    "This defines whether system is docked or not"
   REFERENCE      "IBMPSG_SystemEnclosure.DockingStatus"
::= { iBMPSGSystemEnclosureEntry 6 }

iBMPSGSystemEnclosureEventAutoClearEnabled OBJECT-TYPE
   SYNTAX         Boolean
   ACCESS         read-write
   STATUS         mandatory
   DESCRIPTION    "False means that events are only generated on state changes.  True means that events are generated on state changes and periodically when the object is in a non-normal state."
   REFERENCE      "IBMPSG_SystemEnclosure.EventAutoClearEnabled"
::= { iBMPSGSystemEnclosureEntry 8 }

iBMPSGSystemEnclosureStatus OBJECT-TYPE
   SYNTAX         String
   ACCESS         read-write
   STATUS         mandatory
   DESCRIPTION    "The Status property is a string indicating the current status of the object. Various operational and non-operational statuses can be defined. Operational statuses are OK, Degraded and Pred Fail. Pred Fail indicates that an element may be functioning properly but predicting a failure in the near future. An example is a SMART-enabled hard drive. Non-operational statuses can also be specified. These are Error, Starting, Stopping and Service. The latter, Service, could apply during mirror-resilvering of a disk, reload of a user permissions list, or other administrative work. Not all such work is on-line, yet the managed element is neither OK nor in one of the other states."
   REFERENCE      "IBMPSG_SystemEnclosure.Status"
::= { iBMPSGSystemEnclosureEntry 9 }

iBMPSGTachometerTable OBJECT-TYPE
   SYNTAX         SEQUENCE OF IBMPSGTachometerEntry
   ACCESS         not-accessible
   STATUS         mandatory
   DESCRIPTION    "The IBMPSG_Tachometer class represents an IBM managed Fan speed Sensor"
   REFERENCE      "IBMPSG_Tachometer"
::= { ibmpsgLMSensor 5 }

iBMPSGTachometerEntry OBJECT-TYPE
   SYNTAX         IBMPSGTachometerEntry
   ACCESS         not-accessible
   STATUS         mandatory
   DESCRIPTION    ""
   INDEX          { iBMPSGTachometerKeyIndex }
::= { iBMPSGTachometerTable 1 }

IBMPSGTachometerEntry ::= SEQUENCE
{
   iBMPSGTachometerKeyIndex String,   
   iBMPSGTachometerCurrentReading Sint32,
   iBMPSGTachometerNominalReading Sint32,
   iBMPSGTachometerNormalMax Sint32,
   iBMPSGTachometerNormalMin Sint32,
   iBMPSGTachometerMaxReadable Sint32,
   iBMPSGTachometerMinReadable Sint32,
   iBMPSGTachometerResolution Uint32,
   iBMPSGTachometerTolerance Sint32,
   iBMPSGTachometerLowerThresholdNonCritical Sint32,
   iBMPSGTachometerUpperThresholdNonCritical Sint32,
   iBMPSGTachometerLowerThresholdCritical Sint32,
   iBMPSGTachometerUpperThresholdCritical Sint32,
   iBMPSGTachometerLowerThresholdFatal Sint32,
   iBMPSGTachometerUpperThresholdFatal Sint32,
   iBMPSGTachometerFanDescrip Uint32,
   iBMPSGTachometerFanType Uint32,
   iBMPSGTachometerEventsEnabled Boolean,
   iBMPSGTachometerEventAutoClearEnabled Boolean,
   iBMPSGTachometerStatus String
}

iBMPSGTachometerKeyIndex OBJECT-TYPE
   SYNTAX         String
   ACCESS         read-write
   STATUS         mandatory
   DESCRIPTION    ""
   REFERENCE      "IBMPSG_Tachometer.KeyIndex"
::= { iBMPSGTachometerEntry 1 }

iBMPSGTachometerCurrentReading OBJECT-TYPE
   SYNTAX         Sint32
   ACCESS         read-write
   STATUS         mandatory
   DESCRIPTION    ""
   REFERENCE      "IBMPSG_Tachometer.CurrentReading"
::= { iBMPSGTachometerEntry 2 }

iBMPSGTachometerNominalReading OBJECT-TYPE
   SYNTAX         Sint32
   ACCESS         read-write
   STATUS         mandatory
   DESCRIPTION    ""
   REFERENCE      "IBMPSG_Tachometer.NominalReading"
::= { iBMPSGTachometerEntry 3 }

iBMPSGTachometerNormalMax OBJECT-TYPE
   SYNTAX         Sint32
   ACCESS         read-write
   STATUS         mandatory
   DESCRIPTION    ""
   REFERENCE      "IBMPSG_Tachometer.NormalMax"
::= { iBMPSGTachometerEntry 4 }

iBMPSGTachometerNormalMin OBJECT-TYPE
   SYNTAX         Sint32
   ACCESS         read-write
   STATUS         mandatory
   DESCRIPTION    ""
   REFERENCE      "IBMPSG_Tachometer.NormalMin"
::= { iBMPSGTachometerEntry 5 }

iBMPSGTachometerMaxReadable OBJECT-TYPE
   SYNTAX         Sint32
   ACCESS         read-write
   STATUS         mandatory
   DESCRIPTION    ""
   REFERENCE      "IBMPSG_Tachometer.MaxReadable"
::= { iBMPSGTachometerEntry 6 }

iBMPSGTachometerMinReadable OBJECT-TYPE
   SYNTAX         Sint32
   ACCESS         read-write
   STATUS         mandatory
   DESCRIPTION    ""
   REFERENCE      "IBMPSG_Tachometer.MinReadable"
::= { iBMPSGTachometerEntry 7 }

iBMPSGTachometerResolution OBJECT-TYPE
   SYNTAX         Uint32
   ACCESS         read-write
   STATUS         mandatory
   DESCRIPTION    ""
   REFERENCE      "IBMPSG_Tachometer.Resolution"
::= { iBMPSGTachometerEntry 8 }

iBMPSGTachometerTolerance OBJECT-TYPE
   SYNTAX         Sint32
   ACCESS         read-write
   STATUS         mandatory
   DESCRIPTION    ""
   REFERENCE      "IBMPSG_Tachometer.Tolerance"
::= { iBMPSGTachometerEntry 9 }

iBMPSGTachometerLowerThresholdNonCritical OBJECT-TYPE
   SYNTAX         Sint32
   ACCESS         read-write
   STATUS         mandatory
   DESCRIPTION    ""
   REFERENCE      "IBMPSG_Tachometer.LowerThresholdNonCritical"
::= { iBMPSGTachometerEntry 10 }

iBMPSGTachometerUpperThresholdNonCritical OBJECT-TYPE
   SYNTAX         Sint32
   ACCESS         read-write
   STATUS         mandatory
   DESCRIPTION    ""
   REFERENCE      "IBMPSG_Tachometer.UpperThresholdNonCritical"
::= { iBMPSGTachometerEntry 11 }

iBMPSGTachometerLowerThresholdCritical OBJECT-TYPE
   SYNTAX         Sint32
   ACCESS         read-write
   STATUS         mandatory
   DESCRIPTION    ""
   REFERENCE      "IBMPSG_Tachometer.LowerThresholdCritical"
::= { iBMPSGTachometerEntry 12 }

iBMPSGTachometerUpperThresholdCritical OBJECT-TYPE
   SYNTAX         Sint32
   ACCESS         read-write
   STATUS         mandatory
   DESCRIPTION    ""
   REFERENCE      "IBMPSG_Tachometer.UpperThresholdCritical"
::= { iBMPSGTachometerEntry 13 }

iBMPSGTachometerLowerThresholdFatal OBJECT-TYPE
   SYNTAX         Sint32
   ACCESS         read-write
   STATUS         mandatory
   DESCRIPTION    ""
   REFERENCE      "IBMPSG_Tachometer.LowerThresholdFatal"
::= { iBMPSGTachometerEntry 14 }

iBMPSGTachometerUpperThresholdFatal OBJECT-TYPE
   SYNTAX         Sint32
   ACCESS         read-write
   STATUS         mandatory
   DESCRIPTION    ""
   REFERENCE      "IBMPSG_Tachometer.UpperThresholdFatal"
::= { iBMPSGTachometerEntry 15 }

iBMPSGTachometerFanDescrip OBJECT-TYPE
   SYNTAX         Uint32
   ACCESS         read-write
   STATUS         mandatory
   DESCRIPTION    "The Fan Description"
   REFERENCE      "IBMPSG_Tachometer.FanDescrip"
::= { iBMPSGTachometerEntry 16 }

iBMPSGTachometerFanType OBJECT-TYPE
   SYNTAX         Uint32
   ACCESS         read-write
   STATUS         mandatory
   DESCRIPTION    "The current fan type"
   REFERENCE      "IBMPSG_Tachometer.FanType"
::= { iBMPSGTachometerEntry 17 }

iBMPSGTachometerEventsEnabled OBJECT-TYPE
   SYNTAX         Boolean
   ACCESS         read-write
   STATUS         mandatory
   DESCRIPTION    "Event generation status."
   REFERENCE      "IBMPSG_Tachometer.EventsEnabled"
::= { iBMPSGTachometerEntry 18 }

iBMPSGTachometerEventAutoClearEnabled OBJECT-TYPE
   SYNTAX         Boolean
   ACCESS         read-write
   STATUS         mandatory
   DESCRIPTION    "False means that events are only generated on state changes.  True means that events are generated on state changes and periodically when the object is in a non-normal state."
   REFERENCE      "IBMPSG_Tachometer.EventAutoClearEnabled"
::= { iBMPSGTachometerEntry 19 }

iBMPSGTachometerStatus OBJECT-TYPE
   SYNTAX         String
   ACCESS         read-write
   STATUS         mandatory
   DESCRIPTION    "The Status property is a string indicating the current status of the object. Various operational and non-operational statuses can be defined. Operational statuses are OK, Degraded and Pred Fail. Pred Fail indicates that an element may be functioning properly but predicting a failure in the near future. An example is a SMART-enabled hard drive. Non-operational statuses can also be specified. These are Error, Starting, Stopping and Service. The latter, Service, could apply during mirror-resilvering of a disk, reload of a user permissions list, or other administrative work. Not all such work is on-line, yet the managed element is neither OK nor in one of the other states."
   REFERENCE      "IBMPSG_Tachometer.Status"
::= { iBMPSGTachometerEntry 20 }

END
