XYLAN-ATMLSM-MIB DEFINITIONS ::= BEGIN

     --  RCSID information

     --  $RCSfile: atm.mib,v $
     --  $Revision: 1.6 $		$State: Exp $
     --  $Date: 1998/05/08 18:46:40 $
     --  $Author: lsl $


     --  xylan-atm.mib
     --  Revision: 1.00
     --  Date: Feb 6, 1995

     --  Alcatel Internetworking, Inc.
     --  26801 W. Agoura Road
     --  Calabasas, CA 91301
     --  (818) 880-3500
     --  support@ind.alcatel.com

     --  This module provides authoritative definitions for Alcatel Internetworking, Inc.
     --  enterprise-specific atm MIB.

     --  This module will be extended, as needed.


     --  Alcatel Internetworking, Inc. reserves the right to make changes in 
     --  specification and other information contained in this document 
     --  without prior notice.  The reader should consult Alcatel Internetworking,
     --  Inc. to determine whether any such changes have been made.

     --  In no event shall Alcatel Internetworking, Inc. be liable for any incidental, 
     --  indirect, special, or consequential damages whatsoever (including 
     --  but not limited to lost profits) arising out of or related to this
     --  document or the information contained in it, even if Alcatel Internetworking,
     --  Inc. has been advised of, known, or should have known, the 
     --  possibility of such damages.
     --  Alcatel Internetworking, Inc. grants vendors, end-users, and other interested
     --  parties a non-exclusive license to use this Specification in connection
     --  with the management of Alcatel Internetworking, Inc. products.

     --  Copyright (C) 1995, Alcatel Internetworking, Inc. All Rights Reserved.

     
     	IMPORTS
		OBJECT-TYPE
			FROM RFC-1212
-- LC 10-19-99
--	        xylanAtmArch
--			FROM XYLAN-BASE-MIB
	        atmxLsmGroup 
			FROM XYLAN-ATM-MIB

			;

	-- All representations of MAC addresses in this MIB Module
	-- use, as a textual convention (i.e. this convention does
	-- not affect their encoding), the data type:


     -- Textual Conventions
     
     -- All representations of ATM addresses in this MIB Module use,
     -- the data type:

     -- Note this data type is used only by the deprecated object
     -- atmfPortAddress. Another definition (a refined one) is 
     -- specified in the separate MIB for Address Registration
    
     -- Object Identifier defintions

	
	AtmForumLaneAddress ::= OCTET STRING (SIZE (20))

     --
     --                    The MIB groups
     --

     -- Defined in xylan-atm.mib LC 10-19-99 PR25736
     -- atmxLsmGroup     OBJECT IDENTIFIER ::= { xylanAtmArch 13 }

     
     --
     --		The ATM LSM Group
     --
     -- ------------------------------------------------------------- --
     --
     -- LES/BUS configuration group
     --

         atmxLesConfTable OBJECT-TYPE
             SYNTAX       SEQUENCE OF AtmxLesConfEntry
             ACCESS       not-accessible
             STATUS       mandatory
             DESCRIPTION
                     "This table contains all the configuration
                      parameters for a LAN Emulation client. "
             ::= { atmxLsmGroup 1 }

         atmxLesConfEntry OBJECT-TYPE
             SYNTAX       AtmxLesConfEntry
             ACCESS       not-accessible
             STATUS       mandatory
             DESCRIPTION
                     "Each table entry contains configuration information
                      for one LAN Emulation Client.

                      Most of the objects are derived from Initial State
                      Parameters in the LAN Emulation specification."
             INDEX   { atmxlesConfIndex }
             ::= { atmxLesConfTable 1 }

         AtmxLesConfEntry ::=
             SEQUENCE {
                 --  Table index
                 atmxlesConfIndex		INTEGER,
		 atmxLesRedundancyRole		INTEGER,
                 atmxSecondaryLESAtmAddr	AtmForumLaneAddress
             }

         atmxlesConfIndex  OBJECT-TYPE
             SYNTAX        INTEGER
             ACCESS	   not-accessible
             STATUS        mandatory
             DESCRIPTION
                  "A value which uniquely identifies a
                  conceptual row in the lesConfTable.

                  If the conceptual row identified by this value
                  of lesConfIndex is recreated following an agent
                  restart, the same value of lesConfIndex must be
                  used to identify the recreated row."
             ::= { atmxLesConfEntry 1 }
 
	 atmxLesRedundancyEnabled OBJECT-TYPE
             SYNTAX      INTEGER
             ACCESS      read-write
             STATUS      mandatory
             DESCRIPTION
                     "This is to enable or disable redundency.
                        1 = ENABLE
                        2 = DISABLE"
             DEFVAL { 1 }
             ::= { atmxLesConfEntry 19 }
         
	 atmxLesRedundancyRole OBJECT-TYPE
             SYNTAX      INTEGER
             ACCESS      read-write
             STATUS      mandatory
             DESCRIPTION
                     "This is to specify redundency.
                        1 = Primary
                        2 = Secondary"
             ::= { atmxLesConfEntry 20 }
         
         atmxSecondaryLESAtmAddr OBJECT-TYPE
             SYNTAX      AtmForumLaneAddress
             ACCESS      read-write
             STATUS      mandatory
             DESCRIPTION
                     "This is to specify the secondary LES' Atm Address.
		      It is valid only if atmxLesRedundancyRole = 2."
             ::= { atmxLesConfEntry 21 }

    END
