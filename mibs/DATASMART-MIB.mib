--
-- Copyright 1994-1997 ADC Telecommunications, Inc.  All rights reserved.
--
-- ADC Telecommunications, Inc. Confidential and Proprietary
-- This work contains valuable confidential and proprietary information.
-- Disclosure, use or reproduction without the written authorization of ADC
-- Telecommunications, Inc. is prohibited.  This unpublished work by ADC
-- Telecommunications, Inc. is protected by the laws of the United States and
-- other countries.
--

DATASMART-MIB DEFINITIONS ::= BEGIN

IMPORTS
    enterprises, Gauge, IpAddress, Counter, TimeTicks
        FROM RFC1155-SMI
    OBJECT-TYPE
        FROM RFC-1212
--	DisplayString
--		FROM RFC1213-MIB
--    ifIndex, ifDescr
--        FROM RFC1213-MIB
--    dsx1LineStatus, dsx1CurrentESs, dsx1CurrentUASs
--        FROM RFC1406-MIB
    TRAP-TYPE
        FROM RFC-1215;

-- Internal Datatypes
-- 0..DLCINumber from RFC1315
   DLCI ::= INTEGER (1..1023)

-- From SNMPv2-SMI (SimpleTest can't compile if mix v1 & v2)
   Counter32 ::= Counter


    -- This type was added so that sunnet manager would display strings
    -- as strings instead of their ascii value.
    DisplayString ::=
        OCTET STRING
--------------------------------------------------------------------------
--  The ADC Kentrox DataSMART Enterprise MIB Module.
--------------------------------------------------------------------------
--  internet(1).private(4).enterprises(1).adcKentrox(181).ktxMibs(2).DataSMART(2)
datasmart   OBJECT IDENTIFIER
    ::= { enterprises adcKentrox(181) ktxMibs(2) 2 }

--------------------------------------------------------------------------
--  Groups in the ADC Kentrox DataSMART Enterprise MIB Module.
--------------------------------------------------------------------------

dsSs    OBJECT IDENTIFIER ::= { datasmart 1 }
dsRp    OBJECT IDENTIFIER ::= { datasmart 2 }
dsLm    OBJECT IDENTIFIER ::= { datasmart 3 }
dsRm    OBJECT IDENTIFIER ::= { datasmart 4 }
dsAc    OBJECT IDENTIFIER ::= { datasmart 5 }
dsCc    OBJECT IDENTIFIER ::= { datasmart 6 }
dsDc    OBJECT IDENTIFIER ::= { datasmart 7 }
dsFc    OBJECT IDENTIFIER ::= { datasmart 8 }
dsFmc   OBJECT IDENTIFIER ::= { datasmart 9 }
dsMc    OBJECT IDENTIFIER ::= { datasmart 10 }
dsNc    OBJECT IDENTIFIER ::= { datasmart 11 }
dsSc    OBJECT IDENTIFIER ::= { datasmart 12 }
dsTc    OBJECT IDENTIFIER ::= { datasmart 13 }
dsFp    OBJECT IDENTIFIER ::= { datasmart 14 }


--------------------------------------------------------------------
--  BEGIN -  datasmart System Status MIB variables
--------------------------------------------------------------------
dsSsAlarmSource OBJECT-TYPE
             SYNTAX  INTEGER {
                         ssSourceNone   (1),
                         ssSourceNi     (2),
                         ssSourceTi     (3),
                         ssSourceDp1    (4),
                         ssSourceDp2    (5),
                         ssSourceSystem (6)
                     }
              ACCESS  read-only
              STATUS  mandatory
              DESCRIPTION
                      "If the alarm is occuring on a port, this object
                      states which port."
              ::= { dsSs 1 }
 
dsSsAlarmState  OBJECT-TYPE
             SYNTAX  INTEGER {
                         ssStateNone  (1),
                         ssStateEcf   (2),
                         ssStateLos   (3),
                         ssStateAis   (4),
                         ssStateOof   (5),
                         ssStateBer   (6),
                         ssStateYel   (7),
                         ssStateRfa   (8),
                         ssStateRma   (9),
                         ssStateOmf   (10),
                         ssStateEer   (11),
                         ssStateDds   (12),
                         ssStateOos   (13)
                     }
              ACCESS  read-only
              STATUS  mandatory
              DESCRIPTION
                      "The alarm state the system is currently in."
              ::= { dsSs 2 }
 
dsSsLoopback    OBJECT-TYPE
             SYNTAX  INTEGER {
                         ssLbkNone   (1),
                         ssLbkRemLlb (2),
                         ssLbkRemPlb (3),
                         ssLbkRemDp1 (4),
                         ssLbkRemDp2 (5),
                         ssLbkLlb    (6),
                         ssLbkLoc    (7),
                         ssLbkPlb    (8),
                         ssLbkTlb    (9),
                         ssLbkDp1    (10),
                         ssLbkDp2    (11),
                         ssLbkDt1    (12),
                         ssLbkDt2    (13),
                         ssLbkCsu    (14),
                         ssLbkDsu    (15),
                         ssLbkDpdt   (16)
                     }
              ACCESS  read-only
              STATUS  mandatory
              DESCRIPTION
                      "The loopback the system is currently performing."
              ::= { dsSs 3 }
 
dsSsPowerStatus   OBJECT-TYPE
              SYNTAX  INTEGER {
              ssBothOff     (1),
              ssAOnBOff     (2),
              ssAOffBOn     (3),
              ssBothOn      (4)
              }
              ACCESS  read-only
              STATUS  mandatory
              DESCRIPTION
                      "The status of the A and B power inputs on the 
                      universal shelf.
                      The possible values are:

                      VALUE             DESCRIPTION
                      ssBothOff(1)      A off, B off
                      ssAOnBOff(2)      A on,  B off
                      ssAOffBOn(3)      A off, B on
                      ssBothOn(4)       A on,  B on
                      This is only available on models 558 and 538"
              ::= { dsSs 4 }

--------------------------------------------------------------------
--  END -  datasmart System Status MIB variables
--------------------------------------------------------------------
 
--------------------------------------------------------------------
--  BEGIN -  datasmart Reports MIB variables
--------------------------------------------------------------------
 
dsRpUsr         OBJECT IDENTIFIER ::= { dsRp 1 }
dsRpCar         OBJECT IDENTIFIER ::= { dsRp 2 }
dsRpStat    OBJECT IDENTIFIER ::= { dsRp 3 }
dsRpPl          OBJECT IDENTIFIER ::= { dsRp 4 }
dsRpFr          OBJECT IDENTIFIER ::= { dsRp 10 }

--------------------------------------------------------------------

dsRpUsrTmCntTable   OBJECT-TYPE

             SYNTAX  SEQUENCE OF DsRpUsrTmCntEntry
              ACCESS  not-accessible
              STATUS  mandatory
              DESCRIPTION
                      "The User Time Counts Table. This table contains
                      information about the number of seconds in the
                      current 15-minute interval, the number of complete
                      15-minute intervals in the Interval tabl, and
                      the number of days in the Day table."
              ::= { dsRpUsr 1 }

dsRpUsrTmCntEntry   OBJECT-TYPE
             SYNTAX  DsRpUsrTmCntEntry
              ACCESS  not-accessible
              STATUS  mandatory
              DESCRIPTION
                      "An entry in the User Time Counts Table."
             INDEX { dsRpUsrTmCntIndex }
             ::= { dsRpUsrTmCntTable 1 }

DsRpUsrTmCntEntry ::= SEQUENCE {
             dsRpUsrTmCntIndex        INTEGER,
             dsRpUsrTmCntSecs         INTEGER,
             dsRpUsrTmCnt15Mins       INTEGER,
             dsRpUsrTmCntDays         INTEGER
             }

dsRpUsrTmCntIndex      OBJECT-TYPE
             SYNTAX  INTEGER (1..3)
             ACCESS  read-only
             STATUS  mandatory
             DESCRIPTION
                      "The index to the User Time Counts Table. The
                      valid indices are:

                      VALUE            DESCRIPTION
                      1                Network Interface
                      2                Terminal Interface
                      3                Far End Network Interface"
             ::= { dsRpUsrTmCntEntry 1 }


dsRpUsrTmCntSecs    OBJECT-TYPE
             SYNTAX  INTEGER (0..899)
             ACCESS  read-only
             STATUS  mandatory
             DESCRIPTION
                     "The number of seconds in the current 15-minute
                     interval."
             ::= { dsRpUsrTmCntEntry 2 }

dsRpUsrTmCnt15Mins    OBJECT-TYPE
             SYNTAX  INTEGER (0..96)
             ACCESS  read-only
             STATUS  mandatory
             DESCRIPTION
                     "The number of completed 15-minute intervals
                     in the Interval Table."
             ::= { dsRpUsrTmCntEntry 3 }

dsRpUsrTmCntDays      OBJECT-TYPE
             SYNTAX  INTEGER (0..7)
             ACCESS  read-only
             STATUS  mandatory
             DESCRIPTION
                     "The number of completed days in the Day Table."
             ::= { dsRpUsrTmCntEntry 4 }

--------------------------------------------------------------------


dsRpUsrCurTable OBJECT-TYPE

             SYNTAX  SEQUENCE OF DsRpUsrCurEntry
              ACCESS  not-accessible
              STATUS  mandatory
              DESCRIPTION
                      "The User Current Table. This table contains 
                      performance information from the current 15-minute
                      interval for the Network, Terminal, and Far End
                      Network Interfaces."
              ::= { dsRpUsr 2 }

dsRpUsrCurEntry OBJECT-TYPE
             SYNTAX  DsRpUsrCurEntry
              ACCESS  not-accessible
              STATUS  mandatory
              DESCRIPTION
                      "An entry in the User Current Table."
             INDEX { dsRpUsrCurIndex }
             ::= { dsRpUsrCurTable 1 }

DsRpUsrCurEntry ::= SEQUENCE {
             dsRpUsrCurIndex        INTEGER,
             dsRpUsrCurEE           Gauge,
             dsRpUsrCurES           Gauge,
             dsRpUsrCurBES          Gauge,
             dsRpUsrCurSES          Gauge,
             dsRpUsrCurUAS          Gauge,
             dsRpUsrCurCSS          Gauge,
             dsRpUsrCurDM           Gauge,
             dsRpUsrCurStatus       DisplayString
             }

dsRpUsrCurIndex      OBJECT-TYPE
             SYNTAX  INTEGER (1..3)
             ACCESS  read-only
             STATUS  mandatory
             DESCRIPTION
                      "The index for the User Current Table. The valid
                      values for this index are:

                      VALUE         DESCRIPTION
                      1             Network Interface
                      2             Terminal Interface
                      3             Far End Network Interface"
             ::= { dsRpUsrCurEntry 1 }

dsRpUsrCurEE      OBJECT-TYPE
             SYNTAX  Gauge
             ACCESS  read-only
             STATUS  mandatory
             DESCRIPTION
                      "The number of Event Errors encountered by a DS1/E1
                      interface in the current 15-minute interval."
             ::= { dsRpUsrCurEntry 2 }

dsRpUsrCurES      OBJECT-TYPE
             SYNTAX  Gauge
             ACCESS  read-only
             STATUS  mandatory
             DESCRIPTION
                      "The number of Errored Seconds encountered by a DS1/E1
                      interface in the current 15-minute interval."
             ::= { dsRpUsrCurEntry 3 }

dsRpUsrCurBES      OBJECT-TYPE
             SYNTAX  Gauge
             ACCESS  read-only
             STATUS  mandatory
             DESCRIPTION
                      "The number of Bursty Errored Seconds encountered
                      by a DS1/E1 interface in the current 15-minute interval."
             ::= { dsRpUsrCurEntry 4 }

dsRpUsrCurSES      OBJECT-TYPE
             SYNTAX  Gauge
             ACCESS  read-only
             STATUS  mandatory
             DESCRIPTION
                      "The number of Severely Srrored Seconds encountered
                      by a DS1/E1 intervace in the current 15-minute interval."
             ::= { dsRpUsrCurEntry 5 }

dsRpUsrCurUAS      OBJECT-TYPE
             SYNTAX  Gauge
             ACCESS  read-only
             STATUS  mandatory
             DESCRIPTION
                      "The number of Unavailable Seconds encountered by
                      a DS1/E1 interface in the current 15-minute interval."
             ::= { dsRpUsrCurEntry 6 }

dsRpUsrCurCSS      OBJECT-TYPE
             SYNTAX  Gauge
             ACCESS  read-only
             STATUS  mandatory
             DESCRIPTION
                      "The number of Controlled Slip Seconds encountered
                      by a DS1/E1 interface in the current 15-minute interval."
             ::= { dsRpUsrCurEntry 7 }

dsRpUsrCurDM      OBJECT-TYPE
             SYNTAX  Gauge
             ACCESS  read-only
             STATUS  mandatory
             DESCRIPTION
                      "The number of Degraded Minutes encountered by a 
                      DS1/E1 interface in the current 15-minute interval."
             ::= { dsRpUsrCurEntry 8 }

dsRpUsrCurStatus      OBJECT-TYPE
             SYNTAX  DisplayString (SIZE (0..10))
             ACCESS  read-only
             STATUS  mandatory
             DESCRIPTION
                      "The error conditions encountered by a DS1/E1
                      interface in the current 15-minute interval.
                      The error conditions are signified by a single
                      character. The possible values are:

                      VALUE  DESCRIPTION
                      C      A CRC error has been detected on the 
                             received T1/E1 signal
                      B      A bipolar (line) violation has occurred
                             on the received T1/E1 signal
                      L      A LOS condition (but not necessarily an 
                             alarm) has occurred on the received 
                             T1/E1 signal
                      O      An OOF condition (but not necessarily an
                             alarm) has occurred on the received
                             T1/E1
                      E      An EER condition (but not necessarily an
                             alarm) has occurred on the received 
                             T1/E1 signal
                      A      An AIS condition (but not necessarily an
                             alarm) has occurred on the received
                             T1/E1 signal
                      Y      A Yellow alarm has occurred on the received
                             T1/E1 signal
                      @      There is an active alarm 
                      T      There is a loop back, code generation,
                             or BERT active   
                      N      The unit was without power"
             ::= { dsRpUsrCurEntry 9 }

--------------------------------------------------------------------

dsRpUsrIntvlTable   OBJECT-TYPE

             SYNTAX  SEQUENCE OF DsRpUsrIntvlEntry
              ACCESS  not-accessible
              STATUS  mandatory
              DESCRIPTION
                      "The User Interval Table. This table contains
                      performance information for the past 24 hours,
                      broken down by 15-minute intervals for the Network,
                      Terminal, and Far End Network Interfaces."
              ::= { dsRpUsr 3 }

dsRpUsrIntvlEntry   OBJECT-TYPE
             SYNTAX  DsRpUsrIntvlEntry
              ACCESS  not-accessible
              STATUS  mandatory
              DESCRIPTION
                      "An entry in the User Interval Table."
             INDEX { dsRpUsrIntvlIndex, dsRpUsrIntvlNum }
             ::= { dsRpUsrIntvlTable 1 }

DsRpUsrIntvlEntry ::= SEQUENCE {
             dsRpUsrIntvlIndex        INTEGER,
             dsRpUsrIntvlNum          INTEGER,
             dsRpUsrIntvlEE           Gauge,
             dsRpUsrIntvlES           Gauge,
             dsRpUsrIntvlBES          Gauge,
             dsRpUsrIntvlSES          Gauge,
             dsRpUsrIntvlUAS          Gauge,
             dsRpUsrIntvlCSS          Gauge,
             dsRpUsrIntvlDM           Gauge,
             dsRpUsrIntvlStatus       DisplayString
             }

dsRpUsrIntvlIndex      OBJECT-TYPE
             SYNTAX  INTEGER
             ACCESS  read-only
             STATUS  mandatory
             DESCRIPTION
                      "The index for the User Interval Table. The valid
                      values for this index are:

                      VALUE   DESCRIPTION
                      1       Network Interface
                      2       Terminal Interface
                      3       Far End Network Interface"
             ::= { dsRpUsrIntvlEntry 1 }

dsRpUsrIntvlNum      OBJECT-TYPE
             SYNTAX  INTEGER (1..96)
             ACCESS  read-only
             STATUS  mandatory
             DESCRIPTION
                      "This is the interval number of the User Interval Table.
                      It will be the number of completed 15-minute 
                      intervals since the unit has been powered up. After
                      24 hours, this value remains constant at 96 intervals."
             ::= { dsRpUsrIntvlEntry 2 }


dsRpUsrIntvlEE      OBJECT-TYPE
             SYNTAX  Gauge
             ACCESS  read-only
             STATUS  mandatory
             DESCRIPTION
                      "The number of Event Errors encountered by a DS1/E1
                      interface in one of the previous 96 15-minute
                      intervals."
             ::= { dsRpUsrIntvlEntry 3 }


dsRpUsrIntvlES      OBJECT-TYPE
             SYNTAX  Gauge
             ACCESS  read-only
             STATUS  mandatory
             DESCRIPTION
                      "The number of Errored Seconds encountered by a DS1/E1
                      interface in one of the previous 96 15-minute
                      intervals."
             ::= { dsRpUsrIntvlEntry 4 }


dsRpUsrIntvlBES      OBJECT-TYPE
             SYNTAX  Gauge
             ACCESS  read-only
             STATUS  mandatory
             DESCRIPTION
                      "The number of Bursty Errored Seconds encountered 
                      by a DS1/E1 interface in one of the pervious 96
                      15-minute intervals."
             ::= { dsRpUsrIntvlEntry 5 }


dsRpUsrIntvlSES      OBJECT-TYPE
             SYNTAX  Gauge
             ACCESS  read-only
             STATUS  mandatory
             DESCRIPTION
                      "The number of Severely Errored Seconds encountered
                      by a DS1/E1 interface in one of the previous 96 
                      15-minute intervals."
             ::= { dsRpUsrIntvlEntry 6 }


dsRpUsrIntvlUAS      OBJECT-TYPE
             SYNTAX  Gauge
             ACCESS  read-only
             STATUS  mandatory
             DESCRIPTION
                      "The number of Unavailable Seconds encountered by
                      a DS1/E1 interface in one of the previous 96
                      15-minute intervals."
             ::= { dsRpUsrIntvlEntry 7 }


dsRpUsrIntvlCSS      OBJECT-TYPE
             SYNTAX  Gauge
             ACCESS  read-only
             STATUS  mandatory
             DESCRIPTION
                      "The number of Controlled Slip Seconds encountered
                      by a DS1/E1 interface in one of the previous 96
                      15-minute intervals."
             ::= { dsRpUsrIntvlEntry 8 }


dsRpUsrIntvlDM      OBJECT-TYPE
             SYNTAX  Gauge
             ACCESS  read-only
             STATUS  mandatory
             DESCRIPTION
                      "The number of Degraded Minutes encountered by 
                      a DS1/E1 interface in one of the previous 96
                      15-minute intervals."
             ::= { dsRpUsrIntvlEntry 9 }


dsRpUsrIntvlStatus      OBJECT-TYPE
             SYNTAX  DisplayString (SIZE (0..10))
             ACCESS  read-only
             STATUS  mandatory
             DESCRIPTION
                      "The error conditions encountered by a DS1/E1
                      interface in one of the pervious 96 15-minute 
                      intervals. The error conditions are signified by 
                      a single character. The possible values are:

                      VALUE  DESCRIPTION
                      C      A CRC error has been detected on the 
                             received T1/E1 signal
                      B      A bipolar (line) violation has occurred
                             on the received T1/E1 signal
                      L      A LOS condition (but not necessarily an 
                             alarm) has occurred on the received 
                             T1/E1 signal
                      O      An OOF condition (but not necessarily an
                             alarm) has occurred on the received
                             T1/E1
                      E      An EER condition (but not necessarily an
                             alarm) has occurred on the received 
                             T1/E1 signal
                      A      An AIS condition (but not necessarily an
                             alarm) has occurred on the received
                             T1/E1 signal
                      Y      A Yellow alarm has occurred on the received
                             T1/E1 signal
                      S      A controlled slip has occurred on the 
                             received T1/E1 signal
                      @      There is an active alarm 
                      T      There is a loop back, code generation,
                             or BERT active   
                      N      The unit was without power"
             ::= { dsRpUsrIntvlEntry 10 }


--------------------------------------------------------------------

dsRpUsrTotalTable   OBJECT-TYPE

             SYNTAX  SEQUENCE OF DsRpUsrTotalEntry
              ACCESS  not-accessible
              STATUS  mandatory
              DESCRIPTION
                      "The User Total Table. This table contains
                      performance information for the past 24-hours,
                      for the Network, Terminal, and Far End Network
                      Interfaces.
 
                      This is a rolling count. When the current 
                      15-minute interval is up, the last entry in the 
                      interval table will be removed and the completed 
                      15-minute interval added. At this point the Total 
                      Table will be re-calculated."
              ::= { dsRpUsr 4 }

dsRpUsrTotalEntry   OBJECT-TYPE
             SYNTAX  DsRpUsrTotalEntry
              ACCESS  not-accessible
              STATUS  mandatory
              DESCRIPTION
                      "An entry in the User Total Table."
             INDEX { dsRpUsrTotalIndex }
             ::= { dsRpUsrTotalTable 1 }

DsRpUsrTotalEntry ::= SEQUENCE {
             dsRpUsrTotalIndex        INTEGER,
             dsRpUsrTotalEE           Gauge,
             dsRpUsrTotalES           Gauge,
             dsRpUsrTotalBES          Gauge,
             dsRpUsrTotalSES          Gauge,
             dsRpUsrTotalUAS          Gauge,
             dsRpUsrTotalCSS          Gauge,
             dsRpUsrTotalDM           Gauge,
             dsRpUsrTotalStatus       DisplayString
             }

dsRpUsrTotalIndex      OBJECT-TYPE
             SYNTAX  INTEGER
             ACCESS  read-only
             STATUS  mandatory
             DESCRIPTION
                      "The index for the User Total Table. The valid
                      indices are:

                      VALUE   DESCRIPTION
                      1       Network Interface
                      2       Terminal Interface
                      3       Far End Network Interface"
             ::= { dsRpUsrTotalEntry 1 }

dsRpUsrTotalEE      OBJECT-TYPE
             SYNTAX  Gauge
             ACCESS  read-only
             STATUS  mandatory
             DESCRIPTION
                      "The number of Event Errors encountered by a DS1/E1
                      interface in the past 24-hours."
             ::= { dsRpUsrTotalEntry 2 }

dsRpUsrTotalES      OBJECT-TYPE
             SYNTAX  Gauge
             ACCESS  read-only
             STATUS  mandatory
             DESCRIPTION
                      "The number of Errored Seconds encountered by a DS1/E1
                      interface in the past 24-hours."
             ::= { dsRpUsrTotalEntry 3 }

dsRpUsrTotalBES      OBJECT-TYPE
             SYNTAX  Gauge
             ACCESS  read-only
             STATUS  mandatory
             DESCRIPTION
                      "The number of Bursty Errored Seconds encountered 
                      by a DS1/E1 interface in the past 24-hours."
             ::= { dsRpUsrTotalEntry 4 }

dsRpUsrTotalSES      OBJECT-TYPE
             SYNTAX  Gauge
             ACCESS  read-only
             STATUS  mandatory
             DESCRIPTION
                      "The number of Severely Errored Seconds encountered
                      by a DS1/E1 interface in the past 24-hours."
             ::= { dsRpUsrTotalEntry 5 }

dsRpUsrTotalUAS      OBJECT-TYPE
             SYNTAX  Gauge
             ACCESS  read-only
             STATUS  mandatory
             DESCRIPTION
                      "The number of Unavailable Seconds encountered by 
                      a DS1/E1 interface in the past 24-hours."
             ::= { dsRpUsrTotalEntry 6 }


dsRpUsrTotalCSS      OBJECT-TYPE
             SYNTAX  Gauge
             ACCESS  read-only
             STATUS  mandatory
             DESCRIPTION
                      "The number of Controlled Slip Seconds encountered 
                      by a DS1/E1 interface in the past 24-hours."
             ::= { dsRpUsrTotalEntry 7 }

dsRpUsrTotalDM      OBJECT-TYPE
             SYNTAX  Gauge
             ACCESS  read-only
             STATUS  mandatory
             DESCRIPTION
                      "The number of Degraded Minutes encountered by
                      a DS1/E1 interface in the past 24-hours."
             ::= { dsRpUsrTotalEntry 8 }

dsRpUsrTotalStatus      OBJECT-TYPE
             SYNTAX  DisplayString (SIZE (0..10))
             ACCESS  read-only
             STATUS  mandatory
             DESCRIPTION
                      "The error conditions encountered by a DS1/E1
                      interface in the past 24-hours. The error conditions 
                      are signified by a single character. The possible 
                      values are:

                      VALUE  DESCRIPTION
                      C      A CRC error has been detected on the 
                             received T1/E1 signal
                      B      A bipolar (line) violation has occurred
                             on the received T1/E1 signal
                      L      A LOS condition (but not necessarily an 
                             alarm) has occurred on the received 
                             T1/E1 signal
                      O      An OOF condition (but not necessarily an
                             alarm) has occurred on the received
                             T1/E1
                      E      An EER condition (but not necessarily an
                             alarm) has occurred on the received 
                             T1/E1 signal
                      A      An AIS condition (but not necessarily an
                             alarm) has occurred on the received
                             T1/E1 signal
                      Y      A Yellow alarm has occurred on the received
                             T1/E1 signal
                      S      A controlled slip has occurred on the 
                             received T1/E1 signal
                      @      There is an active alarm 
                      T      There is a loop back, code generation,
                             or BERT active   
                      N      The unit was without power"
             ::= { dsRpUsrTotalEntry 9 }

--------------------------------------------------------------------

dsRpUsrDayTable OBJECT-TYPE

             SYNTAX  SEQUENCE OF DsRpUsrDayEntry
              ACCESS  not-accessible
              STATUS  mandatory
              DESCRIPTION
                      "After the unit has been powered up for 24 hours,
                       the values from the User Total Table are moved into 
                       the first slot in the User Day Table. There are seven
                       entries in the User Day Table, so an entire week's
                       history is maintained. The previous day is always
                       in slot 1."
              ::= { dsRpUsr 5 }

dsRpUsrDayEntry OBJECT-TYPE
             SYNTAX  DsRpUsrDayEntry
              ACCESS  not-accessible
              STATUS  mandatory
              DESCRIPTION
                      "This is an entry in the User Day Table."
             INDEX { dsRpUsrDayIndex, dsRpUsrDayNum }
             ::= { dsRpUsrDayTable 1 }

DsRpUsrDayEntry ::= SEQUENCE {
             dsRpUsrDayIndex        INTEGER,
             dsRpUsrDayNum          INTEGER,
             dsRpUsrDayEE           Gauge,
             dsRpUsrDayES           Gauge,
             dsRpUsrDayBES          Gauge,
             dsRpUsrDaySES          Gauge,
             dsRpUsrDayUAS          Gauge,
             dsRpUsrDayCSS          Gauge,
             dsRpUsrDayDM           Gauge,
             dsRpUsrDayStatus       DisplayString
             }

dsRpUsrDayIndex      OBJECT-TYPE
             SYNTAX  INTEGER
             ACCESS  read-only
             STATUS  mandatory
             DESCRIPTION
                     "The User Day Table interface index. 
                     The valid indices are:

                     VALUE   DESCRIPTION
                     1       Network Interface
                     2       Terminal Interface
                     3       Far End Network Interface"
             ::= { dsRpUsrDayEntry 1 }

dsRpUsrDayNum      OBJECT-TYPE
             SYNTAX  INTEGER (1..7)
             ACCESS  read-only
             STATUS  mandatory
             DESCRIPTION
                      "The User Day Table day index. The valid
                      values are 1 day to 7 days."
             ::= { dsRpUsrDayEntry 2 }

dsRpUsrDayEE      OBJECT-TYPE
             SYNTAX  Gauge
             ACCESS  read-only
             STATUS  mandatory
             DESCRIPTION
                      "The number of Event Errors encountered by a DS1/E1
                      interface in one of the previous days."
             ::= { dsRpUsrDayEntry 3 }

dsRpUsrDayES      OBJECT-TYPE
             SYNTAX  Gauge
             ACCESS  read-only
             STATUS  mandatory
             DESCRIPTION
                      "The number of Errored Seconds encountered by a 
                      DS1/E1 interface in one of the previous days."
             ::= { dsRpUsrDayEntry 4 }

dsRpUsrDayBES      OBJECT-TYPE
             SYNTAX  Gauge
             ACCESS  read-only
             STATUS  mandatory
             DESCRIPTION
                      "The number of Bursty Errored Seconds encountered 
                      by a DS1/E1 interface in one of the previous days."
             ::= { dsRpUsrDayEntry 5 }

dsRpUsrDaySES      OBJECT-TYPE
             SYNTAX  Gauge
             ACCESS  read-only
             STATUS  mandatory
             DESCRIPTION
                      "The number of Severely Errored Seconds encountered
                      by a DS1/E1 interface in one of the previous days."
             ::= { dsRpUsrDayEntry 6 }

dsRpUsrDayUAS      OBJECT-TYPE
             SYNTAX  Gauge
             ACCESS  read-only
             STATUS  mandatory
             DESCRIPTION
                      "The number of Unavailable Seconds encountered by
                      a DS1/E1 interface in one of the previous days."
             ::= { dsRpUsrDayEntry 7 }


dsRpUsrDayCSS      OBJECT-TYPE
             SYNTAX  Gauge
             ACCESS  read-only
             STATUS  mandatory
             DESCRIPTION
                      "The number of Controlled Slip Seconds encountered
                      by a DS1/E1 interface in one of the previous days."
             ::= { dsRpUsrDayEntry 8 }

dsRpUsrDayDM      OBJECT-TYPE
             SYNTAX  Gauge
             ACCESS  read-only
             STATUS  mandatory
             DESCRIPTION
                      "The number of Degraded Minutes encountered by
                      a DS1/E1 interface in one of the previous days."
             ::= { dsRpUsrDayEntry 9 }

dsRpUsrDayStatus      OBJECT-TYPE
             SYNTAX  DisplayString (SIZE (0..10))
             ACCESS  read-only
             STATUS  mandatory
             DESCRIPTION
                      "The error conditions encountered by a DS1/E1
                      interface in one of the previous days. The error 
                      conditions are signified by a single character. 
                      The possible values are:

                      VALUE  DESCRIPTION
                      C      A CRC error has been detected on the 
                             received T1/E1 signal
                      B      A bipolar (line) violation has occurred
                             on the received T1/E1 signal
                      L      A LOS condition (but not necessarily an 
                             alarm) has occurred on the received 
                             T1/E1 signal
                      O      An OOF condition (but not necessarily an
                             alarm) has occurred on the received
                             T1/E1
                      E      An EER condition (but not necessarily an
                             alarm) has occurred on the received 
                             T1/E1 signal
                      A      An AIS condition (but not necessarily an
                             alarm) has occurred on the received
                             T1/E1 signal
                      Y      A Yellow alarm has occurred on the received
                             T1/E1 signal
                      S      A controlled slip has occurred on the 
                             received T1/E1 signal
                      @      There is an active alarm 
                      T      There is a loop back, code generation,
                             or BERT active   
                      N      The unit was without power"
             ::= { dsRpUsrDayEntry 10 }

--------------------------------------------------------------------

dsRpCarCntSecs  OBJECT-TYPE
             SYNTAX  INTEGER (0..899)
              ACCESS  read-only
              STATUS  mandatory
              DESCRIPTION
                      "The number of seconds that have elapsed in the 
                      current interval."

              ::= { dsRpCar 1 }

dsRpCarCnt15Mins    OBJECT-TYPE
             SYNTAX  INTEGER (0..96)
              ACCESS  read-only
              STATUS  mandatory
              DESCRIPTION
                      "The number of 15-minute intervals that have 
                      elapsed in the current 24-hours."
              ::= { dsRpCar 2 }

dsRpCarCur  OBJECT IDENTIFIER ::= { dsRpCar 3 }

dsRpCarCurEE    OBJECT-TYPE
             SYNTAX  Gauge
              ACCESS  read-only
              STATUS  mandatory
              DESCRIPTION
                      "The number of Event Errors encountered by the
                      Network Interface in the current 15-minute interval."
              ::= { dsRpCarCur 1 }

dsRpCarCurES    OBJECT-TYPE
             SYNTAX  Gauge
              ACCESS  read-only
              STATUS  mandatory
              DESCRIPTION
                      "The number of Errored Seconds encountered by the
                      Network Interface in the current 15-minute interval."
              ::= { dsRpCarCur 2 }

dsRpCarCurBES   OBJECT-TYPE
             SYNTAX  Gauge
              ACCESS  read-only
              STATUS  mandatory
              DESCRIPTION
                      "The number of Bursty Errored Seconds encountered by 
                      the Network Interface in the current 15-minute 
                      interval."
              ::= { dsRpCarCur 3 }

dsRpCarCurSES   OBJECT-TYPE
             SYNTAX  Gauge
              ACCESS  read-only
              STATUS  mandatory
              DESCRIPTION
                      "The number of Severely Errored Seconds encountered
                      by the Network Interface in the current 15-minute
                      interval."
              ::= { dsRpCarCur 4 }

dsRpCarCurUAS   OBJECT-TYPE
             SYNTAX  Gauge
              ACCESS  read-only
              STATUS  mandatory
              DESCRIPTION
                      "The number of Unavailable Seconds encountered by
                      the Network Interface in the current 15-minute
                      interval."
              ::= { dsRpCarCur 5 }

dsRpCarCurCSS   OBJECT-TYPE
             SYNTAX  Gauge
              ACCESS  read-only
              STATUS  mandatory
              DESCRIPTION
                      "The number of Controlled Slip Seconds encountered
                      by the Network Interface in the current 15-minute
                      interval."
              ::= { dsRpCarCur 6 }

dsRpCarCurLOFC  OBJECT-TYPE
             SYNTAX  Gauge
              ACCESS  read-only
              STATUS  mandatory
              DESCRIPTION
                      "The Loss of Frame Count for the Network Interface 
                      in the current 15-minute interval."
              ::= { dsRpCarCur 7 }

--------------------------------------------------------------------

dsRpCarIntvlTable   OBJECT-TYPE
             SYNTAX  SEQUENCE OF DsRpCarIntvlEntry
              ACCESS  not-accessible
              STATUS  mandatory
              DESCRIPTION
                      "This is the Carrier Interval Table. This table
                      contains performance information about the
                      Network Interface."
              ::= { dsRpCar 4 }

dsRpCarIntvlEntry   OBJECT-TYPE
             SYNTAX  DsRpCarIntvlEntry
              ACCESS  not-accessible
              STATUS  mandatory
              DESCRIPTION
                      "This is an entry in the Carrier Interval Table."
             INDEX { dsRpCarIntvlNum }
             ::= { dsRpCarIntvlTable 1 }

DsRpCarIntvlEntry ::= SEQUENCE {
             dsRpCarIntvlNum     INTEGER,
             dsRpCarIntvlEE        Gauge,
             dsRpCarIntvlES        Gauge,
             dsRpCarIntvlBES       Gauge,
             dsRpCarIntvlSES       Gauge,
             dsRpCarIntvlUAS       Gauge,
             dsRpCarIntvlCSS       Gauge,
             dsRpCarIntvlLOFC      Gauge
             }

dsRpCarIntvlNum OBJECT-TYPE
             SYNTAX  INTEGER (1..96)
              ACCESS  read-only
              STATUS  mandatory
              DESCRIPTION
                      "The number of the 15-minute interval (1-96) from
                      the previous 24-hour period. 1 is the most recent."
              ::= { dsRpCarIntvlEntry 1 }


dsRpCarIntvlEE  OBJECT-TYPE
             SYNTAX  Gauge 
              ACCESS  read-only
              STATUS  mandatory
              DESCRIPTION
                      "The number of Event Errors encountered by the
                      Network Interface in one of the previous 96 
                      15-minute intervals."
              ::= { dsRpCarIntvlEntry 2 }


dsRpCarIntvlES  OBJECT-TYPE
             SYNTAX  Gauge 
              ACCESS  read-only
              STATUS  mandatory
              DESCRIPTION
                      "The number of Errored Seconds encountered by 
                      the Network Interface in one of the previous 96
                      15-minute intervals."
              ::= { dsRpCarIntvlEntry 3 }


dsRpCarIntvlBES OBJECT-TYPE
             SYNTAX  Gauge 
              ACCESS  read-only
              STATUS  mandatory
              DESCRIPTION
                      "The number of Bursty Errored Seconds encountered 
                      by the Network Interface in one of the previous 96
                      15-minute intervals."
              ::= { dsRpCarIntvlEntry 4 }


dsRpCarIntvlSES OBJECT-TYPE
             SYNTAX  Gauge 
              ACCESS  read-only
              STATUS  mandatory
              DESCRIPTION
                      "The number of Severely Errored Seconds encountered
                      by the Network Interface in one of the previous 96
                      15-minute intervals."
              ::= { dsRpCarIntvlEntry 5 }


dsRpCarIntvlUAS OBJECT-TYPE
             SYNTAX  Gauge 
              ACCESS  read-only
              STATUS  mandatory
              DESCRIPTION
                      "The number of Unavailable Seconds encountered
                      by the Network Interface in one of the previous 96
                      15-minute intervals."
              ::= { dsRpCarIntvlEntry 6 }

dsRpCarIntvlCSS OBJECT-TYPE
             SYNTAX  Gauge 
              ACCESS  read-only
              STATUS  mandatory
              DESCRIPTION
                      "The number of Controlled Slip Seconds encountered
                      by the Network Interface in one of the previous 96
                      15-minute intervals."
              ::= { dsRpCarIntvlEntry 7 }


dsRpCarIntvlLOFC    OBJECT-TYPE
             SYNTAX  Gauge 
              ACCESS  read-only
              STATUS  mandatory
              DESCRIPTION
                      "The Loss of Frame Count fo the Network Interface 
                      for one of the previous 96 15-minute intervals."

              ::= { dsRpCarIntvlEntry 8 }

--------------------------------------------------------------------

dsRpCarTotal  OBJECT IDENTIFIER ::= { dsRpCar 5 }

dsRpCarTotalEE  OBJECT-TYPE
             SYNTAX  Gauge
              ACCESS  read-only
              STATUS  mandatory
              DESCRIPTION
                      "The number of Errored Events encountered by the
                      Network Interface in the past 24-hours."
              ::= { dsRpCarTotal 1 }

dsRpCarTotalES  OBJECT-TYPE
             SYNTAX  Gauge
              ACCESS  read-only
              STATUS  mandatory
              DESCRIPTION
                      "The number of Errored Seconds encountered by the
                      Network Interface in the past 24-hours."
              ::= { dsRpCarTotal 2 }

dsRpCarTotalBES OBJECT-TYPE
             SYNTAX  Gauge
              ACCESS  read-only
              STATUS  mandatory
              DESCRIPTION
                      "The number of Bursty Errored Seconds encountered
                      by the Network Interface in the past 24-hours."
              ::= { dsRpCarTotal 3 }

dsRpCarTotalSES OBJECT-TYPE
             SYNTAX  Gauge
              ACCESS  read-only
              STATUS  mandatory
              DESCRIPTION
                      "The number of Severely Errored Seconds encountered
                      by the Network Interface in the past 24-hours."
              ::= { dsRpCarTotal 4 }

dsRpCarTotalUAS OBJECT-TYPE
             SYNTAX  Gauge
              ACCESS  read-only
              STATUS  mandatory
              DESCRIPTION
                      "The number of Unavailable Seconds encountered
                      by the Network Interface in the past 24-hours."
              ::= { dsRpCarTotal 5 }

dsRpCarTotalCSS OBJECT-TYPE
             SYNTAX  Gauge
              ACCESS  read-only
              STATUS  mandatory
              DESCRIPTION
                      "The number of Controlled Slip Seconds encountered
                      by the Network Interface in the past 24-hours."
              ::= { dsRpCarTotal 6 }

dsRpCarTotalLOFC    OBJECT-TYPE
             SYNTAX  Gauge
              ACCESS  read-only
              STATUS  mandatory
              DESCRIPTION
                      "The Loss of Frame Count for the Network Interface 
                      for one of the previous 96 15-minute intervals."
              ::= { dsRpCarTotal 7 }

--------------------------------------------------------------------

dsRpStTable OBJECT-TYPE
             SYNTAX  SEQUENCE OF DsRpStEntry
              ACCESS  not-accessible
              STATUS  mandatory
              DESCRIPTION
                      "The Statistics Table. This table consists of 
                      statistical error counts of various DS1/E1
                      line conditions. These counts are maintained 
                      between power-cycles."
              ::= { dsRpStat 1 }

dsRpStEntry OBJECT-TYPE
             SYNTAX  DsRpStEntry
              ACCESS  not-accessible
              STATUS  mandatory
              DESCRIPTION
                      "An entry in the Statistics Table."
             INDEX { dsRpStIndex }
             ::= { dsRpStTable 1 }

DsRpStEntry ::= SEQUENCE {
             dsRpStIndex           INTEGER,
             dsRpStEsfErrors        Counter,
             dsRpStCrcErrors        Counter,
             dsRpStOofErrors        Counter,
             dsRpStFrameBitErrors   Counter,
             dsRpStBPVs             Counter,
             dsRpStControlledSlips  Counter,
             dsRpStYellowEvents     Counter,
             dsRpStAISEvents        Counter,
             dsRpStLOFEvents        Counter,
             dsRpStLOSEvents        Counter,
             dsRpStFarEndBlkErrors  Counter,
             dsRpStRemFrameAlmEvts  Counter,
             dsRpStRemMFrameAlmEvts Counter,
             dsRpStLOTS16MFrameEvts Counter,
             dsRpStZeroCounters     INTEGER
             }

dsRpStIndex OBJECT-TYPE
             SYNTAX  INTEGER (1..3)
              ACCESS  read-only
              STATUS  mandatory
              DESCRIPTION
                      "The index into the Statistics Table. The valid
                      indices are:

                      VALUE   DESCRIPTION
                      1       Network Interface
                      2       Terminal Interface
                      3       Far End Network Interface"
              ::= { dsRpStEntry 1 }


dsRpStEsfErrors OBJECT-TYPE
             SYNTAX  Counter 
              ACCESS  read-only
              STATUS  mandatory
              DESCRIPTION
                      "The total number of Error Free Seconds since
                      the counters have last been cleared."
              ::= { dsRpStEntry 2 }

dsRpStCrcErrors OBJECT-TYPE
             SYNTAX  Counter 
              ACCESS  read-only
              STATUS  mandatory
              DESCRIPTION
                      "The total number of CRC errors since the 
                      counters have last been cleared."
              ::= { dsRpStEntry 3 }


dsRpStOofErrors OBJECT-TYPE
             SYNTAX  Counter 
              ACCESS  read-only
              STATUS  mandatory
              DESCRIPTION
                      "The total number of Out Of Frame errors since
                       the counters have last been cleared."
              ::= { dsRpStEntry 4 }


dsRpStFrameBitErrors    OBJECT-TYPE
             SYNTAX  Counter 
              ACCESS  read-only
              STATUS  mandatory
              DESCRIPTION
                      "The total number of Frame Bit errors since
                      the counters have last been cleared."
              ::= { dsRpStEntry 5 }

dsRpStBPVs  OBJECT-TYPE
             SYNTAX  Counter 
              ACCESS  read-only
              STATUS  mandatory
              DESCRIPTION
                      "The total number of Bipolar Violations since
                      the counters have last been cleared."
              ::= { dsRpStEntry 6 }

dsRpStControlledSlips  OBJECT-TYPE
             SYNTAX  Counter 
              ACCESS  read-only
              STATUS  mandatory
              DESCRIPTION
                      "The total number of Controlled Slips since the
                      counters have last been cleared."
              ::= { dsRpStEntry 7 }

dsRpStYellowEvents  OBJECT-TYPE
             SYNTAX  Counter 
              ACCESS  read-only
              STATUS  mandatory
              DESCRIPTION
                      "The total number of Yellow Events since the
                      counters have last been cleared."
              ::= { dsRpStEntry 8 }

dsRpStAISEvents  OBJECT-TYPE
             SYNTAX  Counter 
              ACCESS  read-only
              STATUS  mandatory
              DESCRIPTION
                      "The total number of Alarm Indication Siganl
                      events since the counters have last been cleared."
              ::= { dsRpStEntry 9 }

dsRpStLOFEvents  OBJECT-TYPE
             SYNTAX  Counter 
              ACCESS  read-only
              STATUS  mandatory
              DESCRIPTION
                      "The total number of Loss of Frame events since
                      the counters have last been cleared."
              ::= { dsRpStEntry 10 }

dsRpStLOSEvents  OBJECT-TYPE
             SYNTAX  Counter 
              ACCESS  read-only
              STATUS  mandatory
              DESCRIPTION
                      "The total number of Loss of Signal events since
                      the counters have last been cleared."
              ::= { dsRpStEntry 11 }

dsRpStFarEndBlkErrors  OBJECT-TYPE
             SYNTAX  Counter 
              ACCESS  read-only
              STATUS  mandatory
              DESCRIPTION
                      "The total number of Far End Block Errors since
                      the counters were last cleared."
              ::= { dsRpStEntry 12 }

dsRpStRemFrameAlmEvts  OBJECT-TYPE
             SYNTAX  Counter 
              ACCESS  read-only
              STATUS  mandatory
              DESCRIPTION
                      "The total number of Remote Frame Alarm events
                      since the counters were last cleared."
              ::= { dsRpStEntry 13 }

dsRpStRemMFrameAlmEvts  OBJECT-TYPE
             SYNTAX  Counter 
              ACCESS  read-only
              STATUS  mandatory
              DESCRIPTION
                      "The total number of Remote MultiFrame Alarm
                      events since the counters were last cleared."
              ::= { dsRpStEntry 14 }

dsRpStLOTS16MFrameEvts  OBJECT-TYPE
             SYNTAX  Counter 
              ACCESS  read-only
              STATUS  mandatory
              DESCRIPTION
                      "The total number of Loss of TS16MultiFrame events
                      since the counters have been cleared."
              ::= { dsRpStEntry 15 }

dsRpStZeroCounters  OBJECT-TYPE
             SYNTAX  INTEGER {
                         rpStZeroCountersIdle   (1),
                         rpStZeroCountersStart  (2)
                     }
              ACCESS  read-write
              STATUS  mandatory
              DESCRIPTION
                      "This object will clear the Statistics Table counters
                      when it is set to rpStZeroCounterStart(2). Once the
                      counters have been cleraed, it will return to its
                      normal state of rpStZeroCountersIdle(1)."
              ::= { dsRpStEntry 16 }


--------------------------------------------------------------------

dsPlBreak   OBJECT-TYPE
             SYNTAX  INTEGER {
                         rpPlLineFeed    (1),
                         rpPlMorePrompt  (2)
                     }
              ACCESS  read-write
              STATUS  mandatory
              DESCRIPTION
                      "This object determines if the user interface 
                      uses page breaks or 'more' prompts when displaying 
                      information which is longer than the defined page 
                      length (e.g., output from UNLR or SCV). A page length 
                      of 0 will disable both page breaks and 'more' prompts.
 
                      VALUE  DESCRIPTION
                      rpPlLineFeed(1)   Use linefeeds for page breaks
                      rpPlMorePrompt(2) Use 'more' prompts for page breaks"
              ::= { dsRpPl 1 }

dsPlLen OBJECT-TYPE
             SYNTAX  INTEGER ( 0 .. 70 )
              ACCESS  read-write
              STATUS  mandatory
              DESCRIPTION
                      "The length of a 'page' of information. When the set 
                      number of lines have been displayed, a 'more' prompt 
                      or linefeed will be inserted (defined by dsPlBreak). 
                      A page length of 0 causes output to scroll continuously 
                      without page breaks or 'more' prompts."
              ::= { dsRpPl 2 }

--------------------------------------------------------------------

dsRpAhrTable    OBJECT-TYPE
             SYNTAX  SEQUENCE OF DsRpAhrEntry
              ACCESS  not-accessible
              STATUS  mandatory
              DESCRIPTION
                      "This is the Alarm History Table. It contains 
                      the text messages of the last 20 alarms."
              ::= { dsRp 5 }

dsRpAhrEntry    OBJECT-TYPE
             SYNTAX  DsRpAhrEntry
              ACCESS  not-accessible
              STATUS  mandatory
              DESCRIPTION
                      "An entry in the Alarm History Table."
             INDEX { dsRpAhrIndex }
             ::= { dsRpAhrTable 1 }

DsRpAhrEntry ::= SEQUENCE {
             dsRpAhrIndex      INTEGER,
             dsRpAhrStr  DisplayString
             }

dsRpAhrIndex    OBJECT-TYPE
             SYNTAX  INTEGER (1..20)
              ACCESS  read-only
              STATUS  mandatory
              DESCRIPTION
                      "The Alarm History Table index. Index 1 is the
                      most recent alarm."
              ::= { dsRpAhrEntry 1 }


dsRpAhrStr  OBJECT-TYPE
             SYNTAX  DisplayString (SIZE (0..80)) 
              ACCESS  read-only
              STATUS  mandatory
              DESCRIPTION
                      "The alarm message in USER format."
              ::= { dsRpAhrEntry 2 }

--------------------------------------------------------------------

dsRpShrTable    OBJECT-TYPE
              SYNTAX  SEQUENCE OF DsRpShrEntry
              ACCESS  not-accessible
              STATUS  mandatory
              DESCRIPTION
                      "This is the Security History Report table. It contains 
                      entries for events which are considered important
                      from a security standpoint. Examples of such events
                      are 1) incorrect Telnet password entered and 2) source 
                      IP address not on IP Screen List.
                      The entries are placed in chronological order, with
                      most recent event first."
              ::= { dsRp 6 }

dsRpShrEntry    OBJECT-TYPE
              SYNTAX  DsRpShrEntry
              ACCESS  not-accessible
              STATUS  mandatory
              DESCRIPTION
                      "An entry in the Security History Report table."
             INDEX { dsRpShrIndex }
             ::= { dsRpShrTable 1 }

DsRpShrEntry ::= SEQUENCE {
             dsRpShrIndex      INTEGER,
             dsRpShrDateTime   DisplayString,
             dsRpShrEventType  INTEGER,
             dsRpShrComments   DisplayString
             }

dsRpShrIndex    OBJECT-TYPE
              SYNTAX  INTEGER
              ACCESS  read-only
              STATUS  mandatory
              DESCRIPTION
                      "The Security History Report table index. Events are in
                      chronological order. This number ranges between 1 and
                      the value of dsRpShrNumber. Index 1 is the most
                      recent event."
              ::= { dsRpShrEntry 1 }

dsRpShrDateTime OBJECT-TYPE
              SYNTAX  DisplayString (SIZE (0..80))
              ACCESS  read-only
              STATUS  mandatory
              DESCRIPTION
                      "Display string showing date & time that the
                      security related event occurred."
              ::= { dsRpShrEntry 2 }

dsRpShrEventType    OBJECT-TYPE
              SYNTAX  INTEGER {
                  rpShrTelnetPassword (1),
                  rpShrSrcIpAddressScreen (2),
                  rpShrReadCommString (3),
                  rpShrWriteCommString (4)
              }
              ACCESS  read-only
              STATUS  mandatory
              DESCRIPTION
                      "Shows what type of security related event occurred.
 
                             VALUE              DESCRIPTION
                      rpShrTelnetPassword (1)
                                - Incorrect Telnet password entered
                      rpShrSrcIpAddressScreen (2)
                                - Source IP address not on IP Screen List
                      rpShrReadCommString (3)
                                - Incorrect SNMP Read Community String
                      rpShrWriteCommString (4)
                                - Incorrect SNMP Write Community String"
              ::= { dsRpShrEntry 3 }

dsRpShrComments OBJECT-TYPE
              SYNTAX  DisplayString (SIZE (0..80))
              ACCESS  read-only
              STATUS  mandatory
              DESCRIPTION
                      "Display string showing additional information specific
                      to the type of event. For example, for events of
                      type rpShrTelnetPassword, the IP address of the
                      remote host is given."
              ::= { dsRpShrEntry 4 }

--------------------------------------------------------------------

dsRpBes   OBJECT-TYPE
              SYNTAX  INTEGER (2..63999)
              ACCESS  read-write
              STATUS  mandatory
              DESCRIPTION
                      "The error threshold for Bursty Errored Seconds."
              ::= { dsRp 7 }

dsRpSes   OBJECT-TYPE
              SYNTAX  INTEGER (3..64000)
              ACCESS  read-write
              STATUS  mandatory
              DESCRIPTION
                      "The threshold for Severely Errored Seconds."
              ::= { dsRp 8 }

dsRpDm   OBJECT-TYPE
              SYNTAX  INTEGER (1..64000)
              ACCESS  read-write
              STATUS  mandatory
              DESCRIPTION
                      "The threshold for Degraded Minutes."
              ::= { dsRp 9 }

--------------------------------------------------------------------
dsRpFrTmCntTable    OBJECT-TYPE
             SYNTAX  SEQUENCE OF DsRpFrTmCntEntry
              ACCESS  not-accessible
              STATUS  mandatory
              DESCRIPTION
                      "The FRIB Time Counts Table. This table contains
                      information for the number of seconds in the
                      current 2-hour interval, the number of complete
                      2-hour intervals in the Interval table, and
                      the number of days in the Day table."
              ::= { dsRpFr 1 }

dsRpFrTmCntEntry    OBJECT-TYPE
             SYNTAX  DsRpFrTmCntEntry
              ACCESS  not-accessible
              STATUS  mandatory
              DESCRIPTION
                      "An entry in the FRIB Time Counts Table."
             INDEX { dsRpFrTmCntDir }
             ::= { dsRpFrTmCntTable 1 }

DsRpFrTmCntEntry ::= SEQUENCE {
             dsRpFrTmCntDir          INTEGER,
             dsRpFrTmCntSecs         INTEGER,
             dsRpFrTmCnt2Hrs         INTEGER,
             dsRpFrTmCntDays         INTEGER
             }

dsRpFrTmCntDir      OBJECT-TYPE
             SYNTAX  INTEGER (1..2)
             ACCESS  read-only
             STATUS  mandatory
             DESCRIPTION
                      "The direction index to the FRIB Time Counts Table. The
                      valid indices are:

                      VALUE            DESCRIPTION
                      1                Transmit
                      2                Receive"
             ::= { dsRpFrTmCntEntry 1 }

dsRpFrTmCntSecs    OBJECT-TYPE
             SYNTAX  INTEGER (0..7200)
             ACCESS  read-only
             STATUS  mandatory
             DESCRIPTION
                     "The number of seconds in the current 2-hour interval."
             ::= { dsRpFrTmCntEntry 2 }

dsRpFrTmCnt2Hrs    OBJECT-TYPE
             SYNTAX  INTEGER (0..12)
             ACCESS  read-only
             STATUS  mandatory
             DESCRIPTION
                     "The number of completed 2-hour intervals
                     in the Interval Table."
             ::= { dsRpFrTmCntEntry 3 }

dsRpFrTmCntDays      OBJECT-TYPE
             SYNTAX  INTEGER (0..7)
             ACCESS  read-only
             STATUS  mandatory
             DESCRIPTION
                     "The number of completed days in the Day Table."
             ::= { dsRpFrTmCntEntry 4 }

--------------------------------------------------------------------
dsRpFrPre15MTable   OBJECT-TYPE
             SYNTAX  SEQUENCE OF DsRpFrPre15MEntry
              ACCESS  not-accessible
              STATUS  mandatory
              DESCRIPTION
                      "The FRIB Previous 15 Min Table. This table contains 
                      performance information from the previous 15-minute
                      interval for both the transmit and receive directions
                      of each VC at the Network Interface."
              ::= { dsRpFr 2 }

dsRpFrPre15MEntry   OBJECT-TYPE
             SYNTAX  DsRpFrPre15MEntry
              ACCESS  not-accessible
              STATUS  mandatory
              DESCRIPTION
                      "An entry in the FRIB Previous 15 Min Table."
             INDEX { dsRpFrPre15MDir, dsRpFrPre15MVcIndex }
             ::= { dsRpFrPre15MTable 1 }

DsRpFrPre15MEntry ::= SEQUENCE {
             dsRpFrPre15MDir          INTEGER,
             dsRpFrPre15MVcIndex      INTEGER,
             dsRpFrPre15MVc           INTEGER,
             dsRpFrPre15MFrames       Counter,
             dsRpFrPre15MOctets       Counter,
             dsRpFrPre15MKbps         Gauge,
             dsRpFrPre15MFpMax        Counter,
             dsRpFrPre15MFpAvg        Gauge,
             dsRpFrPre15MFpLost       Counter,
             dsRpFrPre15MFpSent       Counter,
             dsRpFrPre15MStatus       DisplayString
             }

dsRpFrPre15MDir      OBJECT-TYPE
             SYNTAX  INTEGER (1..2)
             ACCESS  read-only
             STATUS  mandatory
             DESCRIPTION
                      "The direction index to the FRIB Previous 15 Min Table.

                      VALUE            DESCRIPTION
                      1                Transmit
                      2                Receive"
             ::= { dsRpFrPre15MEntry 1 }

dsRpFrPre15MVcIndex      OBJECT-TYPE
             SYNTAX  INTEGER (1..65)
             ACCESS  read-only
             STATUS  mandatory
             DESCRIPTION
                      "The VC index to the FRIB Previous 15 Min Table. The
                      table has 64 entries for indiviual VCs, a value of
                      1 through 64, and 1 entry for all other VCs, a value
                      of 65."
             ::= { dsRpFrPre15MEntry 2 }

dsRpFrPre15MVc      OBJECT-TYPE
             SYNTAX  INTEGER (1..8388607)
             ACCESS  read-only
             STATUS  mandatory
             DESCRIPTION
                      "The VC for this entry in the FRIB Previous 15 Min
                       Table."
             ::= { dsRpFrPre15MEntry 3 }

dsRpFrPre15MFrames      OBJECT-TYPE
             SYNTAX  Counter
             ACCESS  read-only
             STATUS  mandatory
             DESCRIPTION
                      "The number of Frame Relay packets transmitted or
                       received during the previous 15-minute interval."
             ::= { dsRpFrPre15MEntry 4 }

dsRpFrPre15MOctets      OBJECT-TYPE
             SYNTAX  Counter
             ACCESS  read-only
             STATUS  mandatory
             DESCRIPTION
                      "The number of octets transmitted or
                       received during the previous 15-minute interval."
             ::= { dsRpFrPre15MEntry 5 }

dsRpFrPre15MKbps      OBJECT-TYPE
             SYNTAX  Gauge
             ACCESS  read-only
             STATUS  mandatory
             DESCRIPTION
                      "The Kilobit/sec rate for data transmitted or
                       received during the previous 15-minute interval."
             ::= { dsRpFrPre15MEntry 6 }

dsRpFrPre15MFpMax      OBJECT-TYPE
             SYNTAX  Counter
             ACCESS  read-only
             STATUS  mandatory
             DESCRIPTION
                      "The maximum FPING roundtrip time (in msec) of all
                       FPINGs on this VC during the previous 15-minute
                       interval."
             ::= { dsRpFrPre15MEntry 7 }

dsRpFrPre15MFpAvg      OBJECT-TYPE
             SYNTAX  Gauge
             ACCESS  read-only
             STATUS  mandatory
             DESCRIPTION
                      "The average FPING roundtrip time (in msec) of all
                       FPINGs on this VC during the previous 15-minute
                       interval."
             ::= { dsRpFrPre15MEntry 8 }

dsRpFrPre15MFpLost      OBJECT-TYPE
             SYNTAX  Counter
             ACCESS  read-only
             STATUS  mandatory
             DESCRIPTION
                      "The number of FPINGs responses that were not returned
                       on this VC during the previous 15-minute interval."
             ::= { dsRpFrPre15MEntry 9 }

dsRpFrPre15MFpSent      OBJECT-TYPE
             SYNTAX  Counter
             ACCESS  read-only
             STATUS  mandatory
             DESCRIPTION
                      "The number of FPINGs transmitted on this VC
                       during the previous 15-minute interval."
             ::= { dsRpFrPre15MEntry 10 }

dsRpFrPre15MStatus      OBJECT-TYPE
             SYNTAX  DisplayString (SIZE (0..7))
             ACCESS  read-only
             STATUS  mandatory
             DESCRIPTION
                      "The status summary of this VC during the previous
                       15-minute interval:

                       VALUE  DESCRIPTION
                       U      VC link is UP
                       D      VC link is DOWN
                       B      At least one frame had the BECN bit set
                       F      At least one frame had the FECN bit set
                       E      At least one frame had the DE bit set
                       P      The total pipe threshold for utilization
                              was exceeded
                       V      The roundtrip threshold for this VC was exceeded"
             ::= { dsRpFrPre15MEntry 11 }

--------------------------------------------------------------------
dsRpFrCur15MTable   OBJECT-TYPE
             SYNTAX  SEQUENCE OF DsRpFrCur15MEntry
              ACCESS  not-accessible
              STATUS  mandatory
              DESCRIPTION
                      "The FRIB Current 15 Min Table. This table contains 
                      performance information from the current 15-minute
                      interval for both the transmit and receive directions
                      of each VC at the Network Interface."
              ::= { dsRpFr 3 }

dsRpFrCur15MEntry   OBJECT-TYPE
             SYNTAX  DsRpFrCur15MEntry
              ACCESS  not-accessible
              STATUS  mandatory
              DESCRIPTION
                      "An entry in the FRIB Current 15 Min Table."
             INDEX { dsRpFrCur15MDir, dsRpFrCur15MVcIndex }
             ::= { dsRpFrCur15MTable 1 }

DsRpFrCur15MEntry ::= SEQUENCE {
             dsRpFrCur15MDir          INTEGER,
             dsRpFrCur15MVcIndex      INTEGER,
             dsRpFrCur15MVc           INTEGER,
             dsRpFrCur15MFrames       Counter,
             dsRpFrCur15MOctets       Counter,
             dsRpFrCur15MKbps         Gauge,
             dsRpFrCur15MFpMax        Counter,
             dsRpFrCur15MFpAvg        Gauge,
             dsRpFrCur15MFpLost       Counter,
             dsRpFrCur15MFpSent       Counter,
             dsRpFrCur15MFpRmtIp      IpAddress,
             dsRpFrCur15MFpRmtVc      INTEGER,
             dsRpFrCur15MStatus       DisplayString
             }

dsRpFrCur15MDir      OBJECT-TYPE
             SYNTAX  INTEGER (1..2)
             ACCESS  read-only
             STATUS  mandatory
             DESCRIPTION
                      "The direction index to the FRIB Current 15 Min Table.

                      VALUE            DESCRIPTION
                      1                Transmit
                      2                Receive"
             ::= { dsRpFrCur15MEntry 1 }

dsRpFrCur15MVcIndex      OBJECT-TYPE
             SYNTAX  INTEGER (1..65)
             ACCESS  read-only
             STATUS  mandatory
             DESCRIPTION
                      "The VC index to the FRIB Current 15 Min Table. The
                      table has 64 entries for indiviual VCs and the 65th entry 
                      for all other VCs including errored frames."
             ::= { dsRpFrCur15MEntry 2 }

dsRpFrCur15MVc      OBJECT-TYPE
             SYNTAX  INTEGER (1..8388607)
             ACCESS  read-only
             STATUS  mandatory
             DESCRIPTION
                      "The VC for this entry in the FRIB Current 15 Min Table."
             ::= { dsRpFrCur15MEntry 3 }

dsRpFrCur15MFrames      OBJECT-TYPE
             SYNTAX  Counter
             ACCESS  read-only
             STATUS  mandatory
             DESCRIPTION
                      "The number of Frame Relay packets transmitted or
                       received during the current 15-minute interval."
             ::= { dsRpFrCur15MEntry 4 }

dsRpFrCur15MOctets      OBJECT-TYPE
             SYNTAX  Counter
             ACCESS  read-only
             STATUS  mandatory
             DESCRIPTION
                      "The number of octets transmitted or
                       received during the current 15-minute interval."
             ::= { dsRpFrCur15MEntry 5 }

dsRpFrCur15MKbps      OBJECT-TYPE
             SYNTAX  Gauge
             ACCESS  read-only
             STATUS  mandatory
             DESCRIPTION
                      "The Kilobit/sec rate for data transmitted or
                       received during the current 15-minute interval."
             ::= { dsRpFrCur15MEntry 6 }

dsRpFrCur15MFpMax      OBJECT-TYPE
             SYNTAX  Counter
             ACCESS  read-only
             STATUS  mandatory
             DESCRIPTION
                      "The maximum FPING roundtrip time (in msec) of all
                       FPINGs on this VC during the current 15-minute
                       interval."
             ::= { dsRpFrCur15MEntry 7 }

dsRpFrCur15MFpAvg      OBJECT-TYPE
             SYNTAX  Gauge
             ACCESS  read-only
             STATUS  mandatory
             DESCRIPTION
                      "The average FPING roundtrip time (in msec) of all
                       FPINGs on this VC during the current 15-minute
                       interval."
             ::= { dsRpFrCur15MEntry 8 }

dsRpFrCur15MFpLost      OBJECT-TYPE
             SYNTAX  Counter
             ACCESS  read-only
             STATUS  mandatory
             DESCRIPTION
                      "The number of FPINGs responses received on this
                       VC during the current 15-minute interval."
             ::= { dsRpFrCur15MEntry 9 }

dsRpFrCur15MFpSent      OBJECT-TYPE
             SYNTAX  Counter
             ACCESS  read-only
             STATUS  mandatory
             DESCRIPTION
                      "The number of FPINGs transmitted on this VC
                       during the current 15-minute interval."
             ::= { dsRpFrCur15MEntry 10 }

dsRpFrCur15MFpRmtIp      OBJECT-TYPE
             SYNTAX  IpAddress
             ACCESS  read-only
             STATUS  mandatory
             DESCRIPTION
                      "The IP Address of the unit at the remote end of the VC."
             ::= { dsRpFrCur15MEntry 11 }

dsRpFrCur15MFpRmtVc      OBJECT-TYPE
             SYNTAX  INTEGER (0..8388607)
             ACCESS  read-only
             STATUS  mandatory
             DESCRIPTION
                      "The VC number at the remote end of the VC."
             ::= { dsRpFrCur15MEntry 12 }

dsRpFrCur15MStatus      OBJECT-TYPE
             SYNTAX  DisplayString (SIZE (0..7))
             ACCESS  read-only
             STATUS  mandatory
             DESCRIPTION
                      "The status summary of this VC during the current
                       15-minute interval:

                       VALUE  DESCRIPTION
                       U      VC link is UP
                       D      VC link is DOWN
                       B      At least one frame had the BECN bit set
                       F      At least one frame had the FECN bit set
                       E      At least one frame had the DE bit set
                       P      The total pipe threshold for utilization
                              was exceeded
                       V      The roundtrip threshold for this VC was exceeded"
             ::= { dsRpFrCur15MEntry 13 }

--------------------------------------------------------------------
dsRpFrCur2HTable    OBJECT-TYPE
             SYNTAX  SEQUENCE OF DsRpFrCur2HEntry
              ACCESS  not-accessible
              STATUS  mandatory
              DESCRIPTION
                      "The FRIB Current 2Hr Table. This table contains 
                      performance information from the current 2-hour
                      interval for both the transmit and receive directions
                      of each VC at the Network Interface."
              ::= { dsRpFr 4 }

dsRpFrCur2HEntry    OBJECT-TYPE
             SYNTAX  DsRpFrCur2HEntry
              ACCESS  not-accessible
              STATUS  mandatory
              DESCRIPTION
                      "An entry in the FRIB Current 2Hr Table."
             INDEX { dsRpFrCur2HDir, dsRpFrCur2HVcIndex }
             ::= { dsRpFrCur2HTable 1 }

DsRpFrCur2HEntry ::= SEQUENCE {
             dsRpFrCur2HDir          INTEGER,
             dsRpFrCur2HVcIndex      INTEGER,
             dsRpFrCur2HVc           INTEGER,
             dsRpFrCur2HFrames       Counter,
             dsRpFrCur2HOctets       Counter,
             dsRpFrCur2HKbps         Gauge,
             dsRpFrCur2HFpMax        Counter,
             dsRpFrCur2HFpAvg        Gauge,
             dsRpFrCur2HFpLost       Counter,
             dsRpFrCur2HFpSent       Counter,
             dsRpFrCur2HStatus       DisplayString
             }

dsRpFrCur2HDir      OBJECT-TYPE
             SYNTAX  INTEGER (1..2)
             ACCESS  read-only
             STATUS  mandatory
             DESCRIPTION
                      "The direction index to the FRIB Current 2Hr Table.

                      VALUE            DESCRIPTION
                      1                Transmit
                      2                Receive"
             ::= { dsRpFrCur2HEntry 1 }

dsRpFrCur2HVcIndex      OBJECT-TYPE
             SYNTAX  INTEGER (1..65)
             ACCESS  read-only
             STATUS  mandatory
             DESCRIPTION
                      "The VC index to the FRIB Current 2Hr Table. The
                      table has 64 entries for indiviual VCs and 1 entry 
                      for all other VCs."
             ::= { dsRpFrCur2HEntry 2 }

dsRpFrCur2HVc      OBJECT-TYPE
             SYNTAX  INTEGER (1..8388607)
             ACCESS  read-only
             STATUS  mandatory
             DESCRIPTION
                      "The VC for this entry in the FRIB Current 2Hr Table."
             ::= { dsRpFrCur2HEntry 3 }

dsRpFrCur2HFrames      OBJECT-TYPE
             SYNTAX  Counter
             ACCESS  read-only
             STATUS  mandatory
             DESCRIPTION
                      "The number of Frame Relay packets transmitted or
                       received during the current 2-hour interval."
             ::= { dsRpFrCur2HEntry 4 }

dsRpFrCur2HOctets      OBJECT-TYPE
             SYNTAX  Counter
             ACCESS  read-only
             STATUS  mandatory
             DESCRIPTION
                      "The number of octets transmitted or
                       received during the current 2-hour interval."
             ::= { dsRpFrCur2HEntry 5 }

dsRpFrCur2HKbps      OBJECT-TYPE
             SYNTAX  Gauge
             ACCESS  read-only
             STATUS  mandatory
             DESCRIPTION
                      "The Kilobit/sec rate for data transmitted or
                       received during the current 2-hour interval."
             ::= { dsRpFrCur2HEntry 6 }

dsRpFrCur2HFpMax      OBJECT-TYPE
             SYNTAX  Counter
             ACCESS  read-only
             STATUS  mandatory
             DESCRIPTION
                      "The maximum FPING roundtrip time (in msec) of all
                       FPINGs on this VC during the current 2-hour interval."
             ::= { dsRpFrCur2HEntry 7 }

dsRpFrCur2HFpAvg      OBJECT-TYPE
             SYNTAX  Gauge
             ACCESS  read-only
             STATUS  mandatory
             DESCRIPTION
                      "The average FPING roundtrip time (in msec) of all
                       FPINGs on this VC during the current 2-hour interval."
             ::= { dsRpFrCur2HEntry 8 }

dsRpFrCur2HFpLost      OBJECT-TYPE
             SYNTAX  Counter
             ACCESS  read-only
             STATUS  mandatory
             DESCRIPTION
                      "The number of FPINGs responses received on this
                       VC during the current 2-hour interval."
             ::= { dsRpFrCur2HEntry 9 }

dsRpFrCur2HFpSent      OBJECT-TYPE
             SYNTAX  Counter
             ACCESS  read-only
             STATUS  mandatory
             DESCRIPTION
                      "The number of FPINGs transmitted on this VC
                       during the current 2-hour interval."
             ::= { dsRpFrCur2HEntry 10 }

dsRpFrCur2HStatus      OBJECT-TYPE
             SYNTAX  DisplayString (SIZE (0..7))
             ACCESS  read-only
             STATUS  mandatory
             DESCRIPTION
                      "The status summary of this VC during the current
                       2-hour interval:

                       VALUE  DESCRIPTION
                       U      VC link is UP
                       D      VC link is DOWN
                       B      At least one frame had the BECN bit set
                       F      At least one frame had the FECN bit set
                       E      At least one frame had the DE bit set
                       P      The total pipe threshold for utilization
                              was exceeded
                       V      The roundtrip threshold for this VC was exceeded"
             ::= { dsRpFrCur2HEntry 11 }

--------------------------------------------------------------------
dsRpFrIntvl2HTable  OBJECT-TYPE
             SYNTAX  SEQUENCE OF DsRpFrIntvl2HEntry
              ACCESS  not-accessible
              STATUS  mandatory
              DESCRIPTION
                      "The User 2H Interval Table. This table contains
                      performance information for the past 24 hours,
                      broken down by 2-hour intervals."
              ::= { dsRpFr 5 }

dsRpFrIntvl2HEntry  OBJECT-TYPE
             SYNTAX  DsRpFrIntvl2HEntry
              ACCESS  not-accessible
              STATUS  mandatory
              DESCRIPTION
                      "An entry in the FRIB 2H Interval Table."
             INDEX { dsRpFrIntvl2HDir, dsRpFrIntvl2HVcIndex, dsRpFrIntvl2HNum }
             ::= { dsRpFrIntvl2HTable 1 }

DsRpFrIntvl2HEntry ::= SEQUENCE {
             dsRpFrIntvl2HDir          INTEGER,
             dsRpFrIntvl2HVcIndex      INTEGER,
             dsRpFrIntvl2HNum          INTEGER,
             dsRpFrIntvl2HVc           INTEGER,
             dsRpFrIntvl2HFrames       Counter,
             dsRpFrIntvl2HOctets       Counter,
             dsRpFrIntvl2HKbps         Gauge,
             dsRpFrIntvl2HFpMax        Counter,
             dsRpFrIntvl2HFpAvg        Gauge,
             dsRpFrIntvl2HFpLost       Counter,
             dsRpFrIntvl2HFpSent       Counter,
             dsRpFrIntvl2HStatus       DisplayString
             }

dsRpFrIntvl2HDir      OBJECT-TYPE
             SYNTAX  INTEGER (1..2)
             ACCESS  read-only
             STATUS  mandatory
             DESCRIPTION
                      "The direction index to the FRIB 2H Interval Table.

                      VALUE            DESCRIPTION
                      1                Transmit
                      2                Receive"
             ::= { dsRpFrIntvl2HEntry 1 }

dsRpFrIntvl2HVcIndex      OBJECT-TYPE
             SYNTAX  INTEGER (1..65)
             ACCESS  read-only
             STATUS  mandatory
             DESCRIPTION
                      "The VC index to the FRIB 2H Interval Table. The
                      table has 64 entries for indiviual VCs and 1 entry 
                      for all other VCs."
             ::= { dsRpFrIntvl2HEntry 2 }

dsRpFrIntvl2HNum      OBJECT-TYPE
             SYNTAX  INTEGER (1..12)
             ACCESS  read-only
             STATUS  mandatory
             DESCRIPTION
                      "This is the interval number of the FRIB 2H Interval
                       Table.  It will be the number of completed 2-hour 
                      intervals since the unit has been powered up. After
                      24 hours, this value remains constant at 12 intervals.
                      1 is the most recent interval."
             ::= { dsRpFrIntvl2HEntry 3 }

dsRpFrIntvl2HVc      OBJECT-TYPE
             SYNTAX  INTEGER (1..8388607)
             ACCESS  read-only
             STATUS  mandatory
             DESCRIPTION
                      "The VC for this entry in the FRIB 2H Interval Table."
             ::= { dsRpFrIntvl2HEntry 4 }

dsRpFrIntvl2HFrames      OBJECT-TYPE
             SYNTAX  Counter
             ACCESS  read-only
             STATUS  mandatory
             DESCRIPTION
                      "The number of Frame Relay packets transmitted or
                       received during one of the previous 12 2-hour
                       intervals."
             ::= { dsRpFrIntvl2HEntry 5 }

dsRpFrIntvl2HOctets      OBJECT-TYPE
             SYNTAX  Counter
             ACCESS  read-only
             STATUS  mandatory
             DESCRIPTION
                      "The number of octets transmitted or
                       received during one of the previous 12 2-hour
                       intervals."
             ::= { dsRpFrIntvl2HEntry 6 }

dsRpFrIntvl2HKbps      OBJECT-TYPE
             SYNTAX  Gauge
             ACCESS  read-only
             STATUS  mandatory
             DESCRIPTION
                      "The Kilobit/sec rate for data transmitted or
                       received during one of the previous 12 2-hour
                       intervals."
             ::= { dsRpFrIntvl2HEntry 7 }

dsRpFrIntvl2HFpMax      OBJECT-TYPE
             SYNTAX  Counter
             ACCESS  read-only
             STATUS  mandatory
             DESCRIPTION
                      "The maximum FPING roundtrip time (in msec) of all
                       FPINGs on this VC during one of the previous 12 2-hour
                       intervals."
             ::= { dsRpFrIntvl2HEntry 8 }

dsRpFrIntvl2HFpAvg      OBJECT-TYPE
             SYNTAX  Gauge
             ACCESS  read-only
             STATUS  mandatory
             DESCRIPTION
                      "The average FPING roundtrip time (in msec) of all
                       FPINGs on this VC during one of the previous 12 2-hour
                       intervals."
             ::= { dsRpFrIntvl2HEntry 9 }

dsRpFrIntvl2HFpLost      OBJECT-TYPE
             SYNTAX  Counter
             ACCESS  read-only
             STATUS  mandatory
             DESCRIPTION
                      "The number of FPINGs responses received on this
                       VC during one of the previous 12 2-hour intervals."
             ::= { dsRpFrIntvl2HEntry 10 }

dsRpFrIntvl2HFpSent      OBJECT-TYPE
             SYNTAX  Counter
             ACCESS  read-only
             STATUS  mandatory
             DESCRIPTION
                      "The number of FPINGs transmitted on this VC
                       during one of the previous 12 2-hour intervals."
             ::= { dsRpFrIntvl2HEntry 11 }

dsRpFrIntvl2HStatus      OBJECT-TYPE
             SYNTAX  DisplayString (SIZE (0..7))
             ACCESS  read-only
             STATUS  mandatory
             DESCRIPTION
                      "The status summary of this VC during the one of 
                       the previous 12 2-hour intervals:

                       VALUE  DESCRIPTION
                       U      VC link is UP
                       D      VC link is DOWN
                       B      At least one frame had the BECN bit set
                       F      At least one frame had the FECN bit set
                       E      At least one frame had the DE bit set
                       P      The total pipe threshold for utilization
                              was exceeded
                       V      The roundtrip threshold for this VC was exceeded"
             ::= { dsRpFrIntvl2HEntry 12 }

--------------------------------------------------------------------
dsRpFrTotalTable    OBJECT-TYPE
             SYNTAX  SEQUENCE OF DsRpFrTotalEntry
              ACCESS  not-accessible
              STATUS  mandatory
              DESCRIPTION
                      "The FRIB Total Table. This table contains
                      performance information for the past 24-hours
                      for Frame Relay data being passed throught the NI
                      Interface.
 
                      This is a rolling count. When the current 
                      2-hour interval is up, the last entry in the 
                      interval table will be removed and the completed 
                      2-hour interval added. At this point the Total 
                      Table will be re-calculated."
              ::= { dsRpFr 6 }

dsRpFrTotalEntry    OBJECT-TYPE
             SYNTAX  DsRpFrTotalEntry
              ACCESS  not-accessible
              STATUS  mandatory
              DESCRIPTION
                      "An entry in the FRIB Total Table."
             INDEX { dsRpFrTotalDir, dsRpFrTotalVcIndex }
             ::= { dsRpFrTotalTable 1 }

DsRpFrTotalEntry ::= SEQUENCE {
             dsRpFrTotalDir          INTEGER,
             dsRpFrTotalVcIndex      INTEGER,
             dsRpFrTotalVc           INTEGER,
             dsRpFrTotalFrames       Counter,
             dsRpFrTotalOctets       Counter,
             dsRpFrTotalKbps         Gauge,
             dsRpFrTotalFpMax        Counter,
             dsRpFrTotalFpAvg        Gauge,
             dsRpFrTotalFpLost       Counter,
             dsRpFrTotalFpSent       Counter,
             dsRpFrTotalStatus       DisplayString
             }

dsRpFrTotalDir      OBJECT-TYPE
             SYNTAX  INTEGER (1..2)
             ACCESS  read-only
             STATUS  mandatory
             DESCRIPTION
                      "The direction index to the FRIB Total Table.

                      VALUE            DESCRIPTION
                      1                Transmit
                      2                Receive"
             ::= { dsRpFrTotalEntry 1 }

dsRpFrTotalVcIndex      OBJECT-TYPE
             SYNTAX  INTEGER (1..65)
             ACCESS  read-only
             STATUS  mandatory
             DESCRIPTION
                      "The VC index to the FRIB Total Table. The
                      table has 64 entries for indiviual VCs and 1 entry 
                      for all other VCs."
             ::= { dsRpFrTotalEntry 2 }

dsRpFrTotalVc      OBJECT-TYPE
             SYNTAX  INTEGER (1..8388607)
             ACCESS  read-only
             STATUS  mandatory
             DESCRIPTION
                      "The VC for this entry in the FRIB Total Table."
             ::= { dsRpFrTotalEntry 3 }

dsRpFrTotalFrames      OBJECT-TYPE
             SYNTAX  Counter
             ACCESS  read-only
             STATUS  mandatory
             DESCRIPTION
                      "The number of Frame Relay packets transmitted or
                       received during the past 24 hours."
             ::= { dsRpFrTotalEntry 4 }

dsRpFrTotalOctets      OBJECT-TYPE
             SYNTAX  Counter
             ACCESS  read-only
             STATUS  mandatory
             DESCRIPTION
                      "The number of octets transmitted or
                       received during the past 24 hours."
             ::= { dsRpFrTotalEntry 5 }

dsRpFrTotalKbps      OBJECT-TYPE
             SYNTAX  Gauge
             ACCESS  read-only
             STATUS  mandatory
             DESCRIPTION
                      "The Kilobit/sec rate for data transmitted or
                       received during the past 24 hours."
             ::= { dsRpFrTotalEntry 6 }

dsRpFrTotalFpMax      OBJECT-TYPE
             SYNTAX  Counter
             ACCESS  read-only
             STATUS  mandatory
             DESCRIPTION
                      "The maximum FPING roundtrip time (in msec) of all
                       FPINGs on this VC during the past 24 hours."
             ::= { dsRpFrTotalEntry 7 }

dsRpFrTotalFpAvg      OBJECT-TYPE
             SYNTAX  Gauge
             ACCESS  read-only
             STATUS  mandatory
             DESCRIPTION
                      "The average FPING roundtrip time (in msec) of all
                       FPINGs on this VC during the past 24 hours."
             ::= { dsRpFrTotalEntry 8 }

dsRpFrTotalFpLost      OBJECT-TYPE
             SYNTAX  Counter
             ACCESS  read-only
             STATUS  mandatory
             DESCRIPTION
                      "The number of FPINGs responses received on this
                       VC during the past 24 hours."
             ::= { dsRpFrTotalEntry 9 }

dsRpFrTotalFpSent      OBJECT-TYPE
             SYNTAX  Counter
             ACCESS  read-only
             STATUS  mandatory
             DESCRIPTION
                      "The number of FPINGs transmitted on this VC
                       during the past 24 hours."
             ::= { dsRpFrTotalEntry 10 }

dsRpFrTotalStatus      OBJECT-TYPE
             SYNTAX  DisplayString (SIZE (0..7))
             ACCESS  read-only
             STATUS  mandatory
             DESCRIPTION
                      "The status summary of this VC during the past 24 hours:

                       VALUE  DESCRIPTION
                       U      VC link is UP
                       D      VC link is DOWN
                       B      At least one frame had the BECN bit set
                       F      At least one frame had the FECN bit set
                       E      At least one frame had the DE bit set
                       P      The total pipe threshold for utilization
                              was exceeded
                       V      The roundtrip threshold for this VC was exceeded"
             ::= { dsRpFrTotalEntry 11 }

--------------------------------------------------------------------
dsRpFrDayTable  OBJECT-TYPE
             SYNTAX  SEQUENCE OF DsRpFrDayEntry
              ACCESS  not-accessible
              STATUS  mandatory
              DESCRIPTION
                      "After the unit has been powered up for 24 hours,
                       the values from the FRIB Total Table are moved into 
                       the first slot in the FRIB Day Table. There are seven
                       entries in the FRIB Day Table, so an entire week's
                       history is maintained. The previous day is always
                       in slot 1."
              ::= { dsRpFr 7 }

dsRpFrDayEntry  OBJECT-TYPE
             SYNTAX  DsRpFrDayEntry
              ACCESS  not-accessible
              STATUS  mandatory
              DESCRIPTION
                      "This is an entry in the FRIB Day Table."
             INDEX { dsRpFrDayDir, dsRpFrDayVcIndex, dsRpFrDayNum }
             ::= { dsRpFrDayTable 1 }

DsRpFrDayEntry ::= SEQUENCE {
             dsRpFrDayDir          INTEGER,
             dsRpFrDayVcIndex      INTEGER,
             dsRpFrDayNum          INTEGER,
             dsRpFrDayVc           INTEGER,
             dsRpFrDayFrames       Counter,
             dsRpFrDayOctets       Counter,
             dsRpFrDayKbps         Gauge,
             dsRpFrDayFpMax        Counter,
             dsRpFrDayFpAvg        Gauge,
             dsRpFrDayFpLost       Counter,
             dsRpFrDayFpSent       Counter,
             dsRpFrDayStatus       DisplayString
             }

dsRpFrDayDir      OBJECT-TYPE
             SYNTAX  INTEGER (1..2)
             ACCESS  read-only
             STATUS  mandatory
             DESCRIPTION
                      "The direction index to the FRIB Day Table.

                      VALUE            DESCRIPTION
                      1                Transmit
                      2                Receive"
             ::= { dsRpFrDayEntry 1 }

dsRpFrDayVcIndex      OBJECT-TYPE
             SYNTAX  INTEGER (1..65)
             ACCESS  read-only
             STATUS  mandatory
             DESCRIPTION
                      "The VC index to the FRIB Day Table. The
                      table has 64 entries for indiviual VCs and 1 entry 
                      for all other VCs."
             ::= { dsRpFrDayEntry 2 }

dsRpFrDayNum      OBJECT-TYPE
             SYNTAX  INTEGER (1..12)
             ACCESS  read-only
             STATUS  mandatory
             DESCRIPTION
                      "The FRIB Day Table index.  The valid values are
                       1 to 7 days.  1 is the most recent interval."
             ::= { dsRpFrDayEntry 3 }

dsRpFrDayVc      OBJECT-TYPE
             SYNTAX  INTEGER (1..8388607)
             ACCESS  read-only
             STATUS  mandatory
             DESCRIPTION
                      "The VC for this entry in the FRIB Day Table."
             ::= { dsRpFrDayEntry 4 }

dsRpFrDayFrames      OBJECT-TYPE
             SYNTAX  Counter
             ACCESS  read-only
             STATUS  mandatory
             DESCRIPTION
                      "The number of Frame Relay packets transmitted or
                       received during one of the previous days."
             ::= { dsRpFrDayEntry 5 }

dsRpFrDayOctets      OBJECT-TYPE
             SYNTAX  Counter
             ACCESS  read-only
             STATUS  mandatory
             DESCRIPTION
                      "The number of octets transmitted or
                       received during one of the previous days."
             ::= { dsRpFrDayEntry 6 }

dsRpFrDayKbps      OBJECT-TYPE
             SYNTAX  Gauge
             ACCESS  read-only
             STATUS  mandatory
             DESCRIPTION
                      "The Kilobit/sec rate for data transmitted or
                       received during one of the previous days."
             ::= { dsRpFrDayEntry 7 }

dsRpFrDayFpMax      OBJECT-TYPE
             SYNTAX  Counter
             ACCESS  read-only
             STATUS  mandatory
             DESCRIPTION
                      "The maximum FPING roundtrip time (in msec) of all
                       FPINGs on this VC during one of the previous days."
             ::= { dsRpFrDayEntry 8 }

dsRpFrDayFpAvg      OBJECT-TYPE
             SYNTAX  Gauge
             ACCESS  read-only
             STATUS  mandatory
             DESCRIPTION
                      "The average FPING roundtrip time (in msec) of all
                       FPINGs on this VC during one of the previous days."
             ::= { dsRpFrDayEntry 9 }

dsRpFrDayFpLost      OBJECT-TYPE
             SYNTAX  Counter
             ACCESS  read-only
             STATUS  mandatory
             DESCRIPTION
                      "The number of FPINGs responses received on this
                       VC during one of the previous days."
             ::= { dsRpFrDayEntry 10 }

dsRpFrDayFpSent      OBJECT-TYPE
             SYNTAX  Counter
             ACCESS  read-only
             STATUS  mandatory
             DESCRIPTION
                      "The number of FPINGs transmitted on this VC
                       during one of the previous days."
             ::= { dsRpFrDayEntry 11 }

dsRpFrDayStatus      OBJECT-TYPE
             SYNTAX  DisplayString (SIZE (0..7))
             ACCESS  read-only
             STATUS  mandatory
             DESCRIPTION
                      "The status summary of this VC during the one of 
                       the previous days:

                       VALUE  DESCRIPTION
                       U      VC link is UP
                       D      VC link is DOWN
                       B      At least one frame had the BECN bit set
                       F      At least one frame had the FECN bit set
                       E      At least one frame had the DE bit set
                       P      The total pipe threshold for utilization
                              was exceeded
                       V      The roundtrip threshold for this VC was exceeded"
             ::= { dsRpFrDayEntry 12 }

--------------------------------------------------------------------

dsRpFrUrTable OBJECT-TYPE
              SYNTAX  SEQUENCE OF DsRpFrUrEntry
              ACCESS  not-accessible
              STATUS  mandatory
              DESCRIPTION
                      "This is a utilization report on non-flag octets that
                       have been transmitted out the network interface for each
                       VC."
              ::= { dsRpFr 8 }

dsRpFrUrEntry  OBJECT-TYPE
             SYNTAX  DsRpFrUrEntry
              ACCESS  not-accessible
              STATUS  mandatory
              DESCRIPTION
                      "This is an entry in the FRIB Ur Table."
             INDEX { dsRpFrUrDir, dsRpFrUrVcIndex }
             ::= { dsRpFrUrTable 1 }

DsRpFrUrEntry ::= SEQUENCE {
             dsRpFrUrDir                 INTEGER,
             dsRpFrUrVcIndex             INTEGER,
             dsRpFrUrVc                  INTEGER,
             dsRpFrUrCIRExceeded         Counter,
             dsRpFrUrCIRExceededOctets   Counter,
             dsRpFrUrEIRExceeded         Counter,
             dsRpFrUrEIRExceededOctets   Counter
             }

dsRpFrUrDir      OBJECT-TYPE
             SYNTAX  INTEGER (1..2)
             ACCESS  read-only
             STATUS  mandatory
             DESCRIPTION
                      "The direction index to the FRIB Ur Table. Receive is
                       currently not supported and will return a 0 for the 
                       Counter values.

                      VALUE            DESCRIPTION
                      1                Transmit
                      2                Receive"
             ::= { dsRpFrUrEntry 1 }

dsRpFrUrVcIndex      OBJECT-TYPE
             SYNTAX  INTEGER (1..65)
             ACCESS  read-only
             STATUS  mandatory
             DESCRIPTION
                      "The VC index to the FRIB Ur Table. The
                      table has 64 entries for indiviual VCs"
             ::= { dsRpFrUrEntry 2 }

dsRpFrUrVc      OBJECT-TYPE
             SYNTAX  INTEGER (1..8388607)
             ACCESS  read-only
             STATUS  mandatory
             DESCRIPTION
                      "The VC for this entry in the FRIB Ur Table."
             ::= { dsRpFrUrEntry 3 }

dsRpFrUrCIRExceeded      OBJECT-TYPE
             SYNTAX  Counter
             ACCESS  read-only
             STATUS  mandatory
             DESCRIPTION
                      "The number of times the CIR threshold was exceeded, but
                       the EIR threshold was not crossed."
             ::= { dsRpFrUrEntry 4 }

dsRpFrUrCIRExceededOctets      OBJECT-TYPE
             SYNTAX  Counter
             ACCESS  read-only
             STATUS  mandatory
             DESCRIPTION
                      "The number of octets that exceeded the CIR threshold,
                       but were less then the EIR threshold."
             ::= { dsRpFrUrEntry 5 }

dsRpFrUrEIRExceeded      OBJECT-TYPE
             SYNTAX  Counter
             ACCESS  read-only
             STATUS  mandatory
             DESCRIPTION
                      "The number of times the EIR threshold was exceeded."
             ::= { dsRpFrUrEntry 6 }

dsRpFrUrEIRExceededOctets      OBJECT-TYPE
             SYNTAX  Counter
             ACCESS  read-only
             STATUS  mandatory
             DESCRIPTION
                      "The number of octets that exceeded the EIR threshold."
             ::= { dsRpFrUrEntry 7 }

dsRpDdsDuration		OBJECT-TYPE
             SYNTAX  TimeTicks
             ACCESS  read-only
             STATUS  mandatory
             DESCRIPTION
                      "."
             ::= { dsRp 11 }


dsRpDdsTable	OBJECT-TYPE
              SYNTAX  SEQUENCE OF DsRpDdsEntry
              ACCESS  not-accessible
              STATUS  mandatory
              DESCRIPTION
                      "This is the table of DDS statistical data."
              ::= { dsRp 12 }

dsRpDdsEntry OBJECT-TYPE
             SYNTAX  DsRpDdsEntry
              ACCESS  not-accessible
              STATUS  mandatory
              DESCRIPTION
                      "This is an entry in the DDS Table."
             INDEX { dsRpDdsIfIndex }
             ::= { dsRpDdsTable 1 }

DsRpDdsEntry ::= SEQUENCE {
             dsRpDdsIfIndex                 INTEGER,
             dsRpDdsAvailableSecs        Counter32,
             dsRpDdsTotalSecs            Counter32,
             dsRpDdsBPVs                 Counter32
             }

dsRpDdsIfIndex      OBJECT-TYPE
             SYNTAX  INTEGER
             ACCESS  read-only
             STATUS  mandatory
             DESCRIPTION
                      "The index into the table. This is mib-II's ifIndex."
             ::= { dsRpDdsEntry 1 }

dsRpDdsAvailableSecs      OBJECT-TYPE
             SYNTAX  Counter32
             ACCESS  read-only
             STATUS  mandatory
             DESCRIPTION
                      "."
             ::= { dsRpDdsEntry 2 }

dsRpDdsTotalSecs      OBJECT-TYPE
             SYNTAX  Counter32
             ACCESS  read-only
             STATUS  mandatory
             DESCRIPTION
                      "."
             ::= { dsRpDdsEntry 3 }

dsRpDdsBPVs      OBJECT-TYPE
             SYNTAX  Counter32
             ACCESS  read-only
             STATUS  mandatory
             DESCRIPTION
                      "."
             ::= { dsRpDdsEntry 4 }



--------------------------------------------------------------------
--  END -  datasmart Reports MIB variables
--------------------------------------------------------------------

 
--------------------------------------------------------------------
--  BEGIN -  datasmart Local Maintenance MIB variables
--------------------------------------------------------------------
 
dsLmLoopback    OBJECT-TYPE
             SYNTAX  INTEGER {
             lmLbkNone (1),
             lmLbkLine (2),
             lmLbkPayload (3),
             lmLbkLocal (4),
             lmLbkTiTest (5),
             lmLbkDp1 (6),
             lmLbkDp2 (7),
             lmLbkDt1 (8),
             lmLbkDt2 (9),
             lmLbkCsu (10),
             lmLbkDsu (11),
             lmLbkDpdt (12)
             }
              ACCESS  read-write
              STATUS  mandatory
              DESCRIPTION
                      "This is the type of loopback that is currently
                      active. The values have the following meanings:
               
                      VALUE            DESCRIPTION
                      lmLbkNone(1)     No loopback is set
                      lmLbkLine(2)     Line loopback is set
                      lmLbkPayload(3)  Payload loopback is set
                      lmLbkLocal(4)    Local loopback is set
                      lmLbkTiTest(5)   TI looback is set
                      lmLbkDp1(6)      Data port 1 loopback is set
                      lmLbkDp2(7)      Data port 2 loopback is set
                      lmLbkDt1(8)    Data terminal loopback on data
                                       port 1 is set
                      lmLbkDt2(9)    Data terminal loopback on data
                                       port 2 is set
                      lmLbkCsu(10)     CSU Loopback (DDS)
                      lmLbkDsu(11)     DSU Loopback (DDS)
                      lmLbkDpdt(12)    Data-Port/Data-Terminal LB"
              ::= { dsLm 1 }

dsLmSelfTestState   OBJECT-TYPE
             SYNTAX  INTEGER {
                 lmSelfTestIdle (1),
                 lmSelfTestStart (2)
             }
              ACCESS  read-write
              STATUS  mandatory
              DESCRIPTION
                      "This object will start a self test operation when
                      set to lmSelfTestStart(2). At the completion of the
                      test, it will return to its normal state of
                      lmSelfTestIdle(1)."
              ::= { dsLm 2 }

dsLmSelfTestResults OBJECT-TYPE
             SYNTAX  DisplayString (SIZE (0..255 ))
              ACCESS  read-only
              STATUS  mandatory
              DESCRIPTION
                      "The results of the last self test operation."
              ::= { dsLm 3 }

--------------------------------------------------------------------
--  END -  datasmart Local Maintenance MIB variables
--------------------------------------------------------------------

 
--------------------------------------------------------------------
--  BEGIN -  datasmart Remote Maintenance MIB variables
--------------------------------------------------------------------
 
dsRmLbkCode OBJECT-TYPE
             SYNTAX  INTEGER {
             rmRNone    (1),
             rmRst1     (2),
             rmRLine    (3),
             rmRPayload (4),
             rmRDp1     (5),
             rmRDp2     (6)
             }
             ACCESS  read-write
             STATUS  mandatory
             DESCRIPTION
                      "The type of remote loopback that is currently set.
                      The possible values are:

                      VALUE             DESCRIPTION
                      rmRNone(1)        No loopback is set
                      rmRst1(2)         A remote loopback reset code is
                                        currenlty being sent
                      rmRLine(3)        A remote Line loopback is set
                      rmRPayload(4)     A remote Payload loopback is set
                      rmRDp1(5)         A remote Data Port 1 loopback is set
                      rmRDp2(6)         A remote Data Port 2 loopback is set"
             ::= { dsRm 1 }

dsRmTestCode    OBJECT-TYPE
             SYNTAX  INTEGER {
             rmTestNone     (1),
             rmTestQrs      (2),
             rmTest324      (3),
             rmTestOnes     (4),
             rmTestZeros    (5),
             rmTest511Dp1   (6),
             rmTest511Dp2   (7),
             rmTest2047Dp1  (8),
             rmTest2047Dp2  (9),
             rmTest2toThe23 (10),
             rmTest2toThe15 (11)
             }
             ACCESS  read-write
             STATUS  mandatory
             DESCRIPTION
                      "The type of remote test code that is currently being
                      sent. The possible values are:

                      VALUE             DESCRIPTION
                      rmTestNone(1)     No test code is being sent
                      rmTestQrs(2)      QRS is being sent
                      rmTest324(3)      3-in-24 is being sent
                      rmTestOnes(4)     All ones is being sent
                      rmTestZeros(5)    All zeros is being sent
                      rmTest511Dp1(6)   511 is being sent out data port 1
                      rmTest511Dp2(7)   511 is being sent out data port 2
                      rmTest2047Dp1(8)  2047 is being sent out data port 1
                      rmTest2047Dp2(9)  2047 is being sent out data port 2
                      rmTest2toThe23(10) 2 to the 23 is being sent
                      rmTest2toThe15(11) 2 to the 15 is being sent"
             ::= { dsRm 2 }

dsRmBertState   OBJECT-TYPE
             SYNTAX  INTEGER {
             rmBertIdle       (1),
             rmBertOtherStart (2),
             rmBertSearching  (3),
             rmBertFound      (4)
             }
             ACCESS  read-only
             STATUS  mandatory
             DESCRIPTION
                      "The current BERT state. The possible values are:

                      VALUE               DESCRIPTION
                      rmBertIdle(1)       No BERT test is active
                      rmBertOtherStart(2) BERT was started from the control
                                          port, front panel, or Telnet
                      rmBertSearching(3)  BERT was started from the agent
                                          and has not yet detected the code
                      rmBertFound(4)      BERT was started from the agent
                                          and has detected the code"
             ::= { dsRm 3 }

dsRmBertCode    OBJECT-TYPE
             SYNTAX  INTEGER {
             rmBertNone     (1),
             rmBertQrs      (2),
             rmBert324      (3),
             rmBertOnes     (4),
             rmBertZeros    (5),
             rmBert511Dp1   (6),
             rmBert511Dp2   (7),
             rmBert2047Dp1  (8),
             rmBert2047Dp2  (9),
             rmTest2toThe23 (10),
             rmTest2toThe15 (11)
             }
             ACCESS  read-write
             STATUS  mandatory
             DESCRIPTION
                      "This object controls the activation of BERT tests.
                      The possible values are:

                      VALUE             DESCRIPTION
                      rmBertNone(1)      No BERT test is active
                      rmBertQrs(2)       BERT for QRS
                      rmBert324(3)       BERT for 3-in-24
                      rmBertOnes(4)      BERT for all ones
                      rmBertZeros(5)     BERT for all zeros
                      rmBert511Dp1(6)    BERT for 511 on data port 1
                      rmBert511Dp2(7)    BERT for 511 on data port 2
                      rmBert2047Dp1(8)   BERT for 2047 on data port 1
                      rmBert2047Dp2(9)   BERT for 2047 on data port 2
                      rmTest2toThe23(10) BERT for 2 to the 23
                      rmTest2toThe15(11) BERT for 2 to the 15"   
             ::= { dsRm 4 }

dsRmBertTestSecs    OBJECT-TYPE
             SYNTAX  INTEGER (0..2147483647)
             ACCESS  read-only
             STATUS  mandatory
             DESCRIPTION
                      "The number of seconds the requested test code has
                      been detected since the start of the BERT."
             ::= { dsRm 5 }

dsRmBertBitErrors   OBJECT-TYPE
             SYNTAX  INTEGER (0..2147483647)
             ACCESS  read-only
             STATUS  mandatory
             DESCRIPTION
                      "The number of bit errors detected since the start
                      of the BERT."
             ::= { dsRm 6 }

dsRmBertErrdSecs    OBJECT-TYPE
             SYNTAX  INTEGER (0..2147483647)
             ACCESS  read-only
             STATUS  mandatory
             DESCRIPTION
                      "The number of errored seconds detected since the
                      start of the BERT."
             ::= { dsRm 7 }

dsRmBertTotalErrors OBJECT-TYPE
             SYNTAX  INTEGER (0..2147483647)
             ACCESS  read-only
             STATUS  mandatory
             DESCRIPTION
                      "The number of total errors detected since the start
                      of the BERT."
             ::= { dsRm 8 }

dsRmBertReSync  OBJECT-TYPE
             SYNTAX  INTEGER (0..2147483647)
             ACCESS  read-only
             STATUS  mandatory
             DESCRIPTION
                      "The number of times BERT has lost and 
                      re-aquired the pattern."
             ::= { dsRm 9 }

dsRmFping         OBJECT IDENTIFIER ::= { dsRm 10 }

--------------------------------------------------------------------
--  END -  datasmart Remote Maintenance MIB variables
--------------------------------------------------------------------

--------------------------------------------------------------------
--  BEGIN -  datasmart FPING Configuration MIB variables
--------------------------------------------------------------------
 
--
--  datasmart(2).dsRm(4).dsRmFping(10)-The dsRmFping subgroup of the dsRm group
--

dsRmFpingAction OBJECT-TYPE
              SYNTAX  INTEGER {
                        rmFpingStart (1),
                        rmFpingStop (2)
                        }
              ACCESS  read-write
              STATUS  mandatory
              DESCRIPTION
                        "The control actions for the FPING test.  Possible
                        values are:

                        VALUE                 DESCRIPTION
                        rmFpingStart(1)       Start sending FPINGs
                        rmFpingStop(2)        Stop sending FPINGs"
              ::= { dsRmFping 1 }

dsRmFpingState  OBJECT-TYPE
              SYNTAX  INTEGER {
                        rmFpingIdle (1),
                        rmFpingOtherStart (2),
                        rmFpingRunning (3)
                        }
              ACCESS  read-only
              STATUS  mandatory
              DESCRIPTION
                        "The current state of the FPING tester.  Possible
                        values are:

                        VALUE                 DESCRIPTION
                        rmFpingIdle(1)        No FPINGs are being generated
                        rmFpingOtherStart(2)  FPINGs are being generated.
                                              The test was started via one
                                              of the other management
                                              interfaces.
                        rmFpingRunning(3)     FPINGs are being generated.
                                              The test was started via SNMP."
              ::= { dsRmFping 2 }

dsRmFpingVc  OBJECT-TYPE
              SYNTAX  INTEGER (0..8388607)
              ACCESS  read-write
              STATUS  mandatory
              DESCRIPTION
                        "The VC that FPINGs will be sent on.  VC values
                        range from (0..1023) if the Frame Relay address
                        length is 2 octets and (0..8388607) if the address
                        length is 4 octets. Default is 500. "
              ::= { dsRmFping 3 }

dsRmFpingFreq  OBJECT-TYPE
              SYNTAX  INTEGER (5..255)
              ACCESS  read-write
              STATUS  mandatory
              DESCRIPTION
                        "The frequency (in seconds) that FPING packets will
                        be transmitted.  The range is (5..255). Default is 5."
              ::= { dsRmFping 4 }

dsRmFpingLen  OBJECT-TYPE
              SYNTAX  INTEGER (0..1400)
              ACCESS  read-write
              STATUS  mandatory
              DESCRIPTION
                        "The length (in octets) of the payload portion
                        of the FPING packets.  The range is (0..1400).
                        Default is 0."
              ::= { dsRmFping 5 }

dsRmFpingCur  OBJECT-TYPE
              SYNTAX  INTEGER (0..2000)
              ACCESS  read-only
              STATUS  mandatory
              DESCRIPTION
                        "The roundtrip time (in msec) of the last FPING sent."
              ::= { dsRmFping 6 }

dsRmFpingMin  OBJECT-TYPE
              SYNTAX  INTEGER (0..2000)
              ACCESS  read-only
              STATUS  mandatory
              DESCRIPTION
                        "The minimum roundtrip time (in msec) of all
                        FPINGs sent during this test."
              ::= { dsRmFping 7 }

dsRmFpingMax  OBJECT-TYPE
              SYNTAX  INTEGER (0..2000)
              ACCESS  read-only
              STATUS  mandatory
              DESCRIPTION
                        "The maximum roundtrip time (in msec) of all
                        FPINGs sent during this test."
              ::= { dsRmFping 8 }

dsRmFpingAvg  OBJECT-TYPE
              SYNTAX  INTEGER (0..2000)
              ACCESS  read-only
              STATUS  mandatory
              DESCRIPTION
                        "The average roundtrip time (in msec) of all
                        FPINGs sent during this test."
              ::= { dsRmFping 9 }

dsRmFpingLost  OBJECT-TYPE
              SYNTAX  INTEGER (0..65535)
              ACCESS  read-only
              STATUS  mandatory
              DESCRIPTION
                        "The number of FPING packets lost during
                        this test."
              ::= { dsRmFping 10 }

dsRmFpingTotal  OBJECT-TYPE
              SYNTAX  INTEGER (0..65535)
              ACCESS  read-only
              STATUS  mandatory
              DESCRIPTION
                        "The total number of FPING packets transmitted
                        during this test."
              ::= { dsRmFping 11 }

dsRmFpingRmtVc  OBJECT-TYPE
              SYNTAX  DisplayString (SIZE (0..8))
              ACCESS  read-only
              STATUS  mandatory
              DESCRIPTION
                        "The VC used at the remote end of the circuit."
              ::= { dsRmFping 12 }

dsRmFpingRmtIp  OBJECT-TYPE
              SYNTAX  IpAddress
              ACCESS  read-only
              STATUS  mandatory
              DESCRIPTION
                      "The IP address of the unit responding to FPINGs."
              ::= { dsRmFping 13 }

dsRmInsertBitError	OBJECT-TYPE
              SYNTAX  INTEGER {
                        insertBitError (1),
                        noInsertBitError (2)
                        }
              ACCESS  read-write
              STATUS  mandatory
              DESCRIPTION
                        "
                        Possible values are:

                        VALUE                 DESCRIPTION
                        insertBitError(1)       Start sending FPINGs
                        noInsertBitError(2)     Stop sending FPINGs"
              ::= { dsRm 11 }

--------------------------------------------------------------------
--  END -  datasmart FPING Configuration MIB variables
--------------------------------------------------------------------
 
--------------------------------------------------------------------
--  BEGIN -  datasmart Alarm Configuration MIB variables
--------------------------------------------------------------------

dsAcAlmMsg  OBJECT-TYPE
              SYNTAX  INTEGER {
              acAlmMsgEnable (1),
              acAlmMsgDisable (2)
              }
              ACCESS  read-write
              STATUS  mandatory
              DESCRIPTION
                      "This object controls the displaying/sending of
                      alarm messages. Alarm messages will be sent in the
                      format determined by dsAcAlmFormat if dsAcAlmMsg is
                      set to acAlmMsgEnable(1). Alarm messages will not be
                      sent if this object is set to acAlmMsgDisable(2)."
              ::= { dsAc 1 }

dsAcYelAlm  OBJECT-TYPE
              SYNTAX  INTEGER {
              acYelAlmEnable (1),
              acYelAlmDisable (2)
              }
              ACCESS  read-write
              STATUS  mandatory
              DESCRIPTION
                      "This object determines if incoming Yellow Alarm
                      will cause an alarm message to be sent. Setting this
                      object to acYelAlmEnable(1) causes an alarm to be
                      sent when Yellow Alarm is received on the Network
                      or Terminal Interface. Setting this object to 
                      acYelAlmDisable(2) will not send an alarm when 
                      Yellow Alarm is received."
              ::= { dsAc 2 }

dsAcDeact   OBJECT-TYPE
              SYNTAX  INTEGER ( 1..15 )
              ACCESS  read-write
              STATUS  mandatory
              DESCRIPTION
                      "This object controls the number of seconds an
                      alarm condition must remain clear before the unit
                      declares it cleared. The range is from 0 to 15
                      seconds."
              ::= { dsAc 3 }

dsAcEst OBJECT-TYPE
              SYNTAX  INTEGER ( 0..900 )
              ACCESS  read-write
              STATUS  mandatory
              DESCRIPTION
                      "This object determines the threshold of errored
                      seconds that triggers an Excessive Error Rate (EER)
                      alarm. Setting this object to zero disables errored
                      seconds causing an EER alarm."
              ::= { dsAc 4 }

dsAcUst OBJECT-TYPE
              SYNTAX  INTEGER ( 0..900 )
              ACCESS  read-write
              STATUS  mandatory
              DESCRIPTION
                      "This object determines the threshold of uavailable
                      seconds that triggers an Excessive Error Rate (EER)
                      alarm. Setting this object to zero disables unavailable
                      seconds causing an EER alarm."
              ::= { dsAc 5 }

dsAcSt     OBJECT-TYPE
              SYNTAX  INTEGER {
              acSt15 (1),
              acSt60 (2)
              }
              ACCESS  read-write
              STATUS  mandatory
              DESCRIPTION
                      "This object determines the window used to calculate
                      whether an Excessive Error Rate (EER) alarm should be
                      generated from errored seconds or unavailable seconds.
                      Setting this object to acSt15(1) establishes a 
                      15-minute sliding window. Setting this object to 
                      acSt60(2) establishes a 60-minute sliding window."
              ::= { dsAc 6 }

dsAcBerAlm     OBJECT-TYPE
              SYNTAX  INTEGER {
              acBerAlmEnable (1),
              acBerAlmDisable (2)
              }
              ACCESS  read-write
              STATUS  mandatory
              DESCRIPTION
                      "This object controls the sending of a Bit Error
                      Rate (BER) alarm. The possible values are:

                      VALUE               DESCRIPTION
                      acBerAlmEnable(1)   Enable sending BER alarms
                      acBerAlmDisable(2)  Disable sending BER alarms"

              ::= { dsAc 7 }

dsAcRfaAlm     OBJECT-TYPE
              SYNTAX  INTEGER {
              acRfaAlmEnable (1),
              acRfaAlmDisable (2)
              }
              ACCESS  read-write
              STATUS  mandatory
              DESCRIPTION
                      "This object controls the sending of a Remote Frame
                      Alarm (RFA). The possible values are:

                      VALUE               DESCRIPTION
                      acRfaAlmEnable(1)   Enable sending RFA alarms
                      acRfaAlmDisable(2)  Disable sending RFA alarms"
              ::= { dsAc 8 }

dsAcAisAlm     OBJECT-TYPE
              SYNTAX  INTEGER {
              acAisAlmEnable (1),
              acAisAlmDisable (2)
              }
              ACCESS  read-write
              STATUS  mandatory
              DESCRIPTION
                      "This object controls the sending of Alarm Indication
                      Signal (AIS) alarms. The possible values are: 

                      VALUE               DESCRIPTION
                      acAisAlmEnable(1)   Enable sending AIS alarms
                      acAisAlmDisable(2)  Disable sending AIS alarms"
              ::= { dsAc 9 }

-- Not Supported in FRIB56
--dsAcSetNiExcessErrorRate TRAP-TYPE
--    ENTERPRISE      datasmart
--    VARIABLES       { ifIndex, ifDescr,
--                      dsx1LineStatus, dsx1CurrentESs, dsx1CurrentUASs }
--    DESCRIPTION
--                "Set NI Excessive Error Rate (NEER)."
--    ::= 5001
--
--dsAcClearNiExcessErrorRate TRAP-TYPE
--    ENTERPRISE      datasmart
--    VARIABLES       { ifIndex, ifDescr,
--                      dsx1LineStatus, dsx1CurrentESs, dsx1CurrentUASs }
--    DESCRIPTION
--                "Clear NI Excessive Error Rate (NEER)."
--    ::= 5002
--
--dsAcSetTiExcessErrorRate TRAP-TYPE
--    ENTERPRISE      datasmart
--    VARIABLES       { ifIndex, ifDescr,
--                      dsx1LineStatus, dsx1CurrentESs, dsx1CurrentUASs }
--    DESCRIPTION
--                "Set TI Excessive Error Rate (TEER)."
--    ::= 5003
--
--dsAcClearTiExcessErrorRate TRAP-TYPE
--    ENTERPRISE      datasmart
--    VARIABLES       { ifIndex, ifDescr,
--                      dsx1LineStatus, dsx1CurrentESs, dsx1CurrentUASs }
--    DESCRIPTION
--                "Clear TI Excessive Error Rate (TEER)."
--    ::= 5004

dsAcOnPowerTransition TRAP-TYPE
    ENTERPRISE      datasmart
    VARIABLES       { dsSsPowerStatus }
    DESCRIPTION
                "A/B On Power Transition on DataSMART 558 and MPATH 538"
    ::= 5005

dsAcOffPowerTransition TRAP-TYPE
    ENTERPRISE      datasmart
    VARIABLES       { dsSsPowerStatus }
    DESCRIPTION
                "A/B Off Power Transition on DataSMART 558 and MPATH 538"
    ::= 5006

--------------------------------------------------------------------
--  END -  datasmart Alarm Configuration MIB variables
--------------------------------------------------------------------

 
--------------------------------------------------------------------
--  BEGIN -  datasmart Control Port Configuration MIB variables
--------------------------------------------------------------------
 
dsCcEcho   OBJECT-TYPE
              SYNTAX  INTEGER {
              ccEchoEnable (1),
              ccEchoDisable (2)
              }
              ACCESS  read-write
              STATUS  mandatory
              DESCRIPTION
                      "This object controls character echo on the 
                      control port. The possible values are:

                      VALUE             DESCRIPTION
                      ccEchoEnable(1)   Enable control port echo
                      ccEchoDisable(2)  Disable control port echo"
              ::= { dsCc 1 }

dsCcControlPort   OBJECT-TYPE
              SYNTAX  INTEGER {
              ccDce (1),
              ccDte (2)
              }
              ACCESS  read-write
              STATUS  mandatory
              DESCRIPTION
                      "This object determines whether the control port
                      is the DCE or DTE port. The possible values are:

                      VALUE             DESCRIPTION
                      ccDce(1)          The control port is the DCE port
                      ccDte(2)          The control port is the DTE port"
              ::= { dsCc 2 }

dsCcBaud   OBJECT-TYPE
              SYNTAX  INTEGER {
              cc2400  (1),
              cc9600  (2),
              cc19200 (3),
              cc38400 (4)
              }
              ACCESS  read-only
              STATUS  mandatory
              DESCRIPTION
                      "The baud rate of the control port. The possible
                      values are: 

                      VALUE             DESCRIPTION
                      cc2400(1)         2400 baud
                      cc9600(2)         9600 baud
                      cc19200(3)        19200 baud
                      cc38400(4)        38400 baud"
              ::= { dsCc 3 }

dsCcParity   OBJECT-TYPE
              SYNTAX  INTEGER {
              ccNone (1),
              ccEven (2),
              ccOdd  (3)
              }
              ACCESS  read-only
              STATUS  mandatory
              DESCRIPTION
                      "The parity of the control port. The possible
                      values are:

                      VALUE             DESCRIPTION
                      ccNone(1)         No parity
                      ccEven(2)         Even parity
                      ccOdd(3)          Odd parity"
              ::= { dsCc 4 }

dsCcDataBits   OBJECT-TYPE
              SYNTAX  INTEGER {
              cc7Bit (1),
              cc8Bit (2)
              }
              ACCESS  read-only
              STATUS  mandatory
              DESCRIPTION
                      "The number of data bits for the control port. The
                      possible values are:

                      VALUES            DESCRIPTION
                      cc7Bit(1)         7 data bits
                      cc8Bit(2)         8 data bits"
              ::= { dsCc 5 }

dsCcStopBits   OBJECT-TYPE
              SYNTAX  INTEGER {
              cc1Bit (1),
              cc2Bit (2)
              }
              ACCESS  read-only
              STATUS  mandatory
              DESCRIPTION
                      "The number of stop bits for the control port. The
                      possible values are:

                      VALUE             DESCRIPTION
                      cc1Bit(1)         1 stop bit
                      cc2Bit(2)         2 stop bits"
              ::= { dsCc 6 }

dsCcDceIn   OBJECT-TYPE
              SYNTAX  INTEGER {
              ccBothOff     (1),
              ccRtsOnDtrOff (2),
              ccRtsOffDtrOn (3),
              ccBothOn      (4)
              }
              ACCESS  read-only
              STATUS  mandatory
              DESCRIPTION
                      "The input status of the DCE signals RTS and DTR. 
                      The possible valuesa re:

                      VALUE             DESCRIPTION
                      ccBothOff(1)      RTS off, DTR off
                      ccRtsOnDtrOff(2)  RTS on,  DTR off
                      ccRtsOffDtrOn(3)  RTS off, DTR on
                      ccBothOn(4)       RTS on,  DTR on"
              ::= { dsCc 7 }

dsCcDteIn   OBJECT-TYPE
              SYNTAX  INTEGER {
              ccBothOff     (1),
              ccCtsOnDcdOff (2),
              ccCtsOffDcdOn (3),
              ccBothOn      (4)
              }
              ACCESS  read-only
              STATUS  mandatory
              DESCRIPTION
                      "The input status of the DTE signals CTS and DCD.
                      The possible values are: 

                      VALUE             DESCRIPTION
                      ccBothOff(1)      CTS off, DCD off
                      ccCtsOnDcdOff(2)  CTS on,  DCD off
                      ccCTSoffDCDon(3)  CTS off, DCD on
                      ccBothOn(4)       CTS on,  DCD on"
              ::= { dsCc 8 }

--------------------------------------------------------------------
--  END -  datasmart Control Port Configuration MIB variables
--------------------------------------------------------------------

 
--------------------------------------------------------------------
--  BEGIN -  datasmart Data Port Configuration MIB variables
--------------------------------------------------------------------
 
dsDcTable   OBJECT-TYPE

             SYNTAX  SEQUENCE OF DsDcEntry
              ACCESS  not-accessible
              STATUS  mandatory
              DESCRIPTION
                      "The Data Port Configuration Table. This table 
                      contains information on the configuration of each
                      of the unit's data ports."
              ::= { dsDc 1 }

dsDcEntry   OBJECT-TYPE
             SYNTAX  DsDcEntry
              ACCESS  not-accessible
              STATUS  mandatory
              DESCRIPTION
                      "An entry in the Data Port Configuration Table."
             INDEX { dsDcIndex }
             ::= { dsDcTable 1 }

DsDcEntry ::= SEQUENCE {
             dsDcIndex         INTEGER,
             dsDcDataInvert    INTEGER,
             dsDcInterface     INTEGER,
             dsDcClockSource   INTEGER,
             dsDcXmtClkInvert  INTEGER,
             dsDcRcvClkInvert  INTEGER,
             dsDcIdleChar      INTEGER,
             dsDcLOSInput      INTEGER
             }

dsDcIndex      OBJECT-TYPE
             SYNTAX  INTEGER (1..2)
             ACCESS  read-only
             STATUS  mandatory
             DESCRIPTION
                      "The index to the Data Port Configuration Table.
                      The possible values are 1 through 2."
             ::= { dsDcEntry 1 }

dsDcDataInvert   OBJECT-TYPE
              SYNTAX  INTEGER {
              dcDataInvertEnable (1),
              dcDataInvertDisable (2)
              }
              ACCESS  read-write
              STATUS  mandatory
              DESCRIPTION
                      "The data inversion of the data port. The possible
                      values are:

                      VALUE                   DESCRIPTION
                      dcDataInvertEnable(1)   Invert the data port signal
                      dcDataInvertDisable(2)  Don't invert the data port 
                                              signal"
              ::= { dsDcEntry 2 }

dsDcInterface   OBJECT-TYPE
              SYNTAX  INTEGER {
              dcV35Interface (1),
              dcEia530Interface (2),
              dcV35DSInterface (3)
              }
              ACCESS  read-write
              STATUS  mandatory
              DESCRIPTION
                      "The type of electrical interface the data port is
                      using. The possible values are:

                      VALUE                 DESCRIPTION
                      dcV35Interface(1)     V.35 
                      dcEia530Interface(2)  EIA-530
                      dcV35DSInterface (3)  V.35 DataSMART Compatible"
              ::= { dsDcEntry 3 }

dsDcClockSource   OBJECT-TYPE
              SYNTAX  INTEGER {
              dcInternalClock (1),
              dcExternalClock (2)
              }
              ACCESS  read-write
              STATUS  mandatory
              DESCRIPTION
                      "The clock source for the data port. The possible
                      values are:
 
                      VALUE                 DESCRIPTION
                      dcInternalClock(1)    Use the internal clock
                      dcExternalClock(2)    Use the external clock"
              ::= { dsDcEntry 4 }

dsDcXmtClkInvert   OBJECT-TYPE
              SYNTAX  INTEGER {
              dcXClkInvertEnable (1),
              dcXClkInvertDisable (2)
              }
              ACCESS  read-write
              STATUS  mandatory
              DESCRIPTION
                      "The inversion status of the transmit clock signal 
                      for the data port. The possible values are:

                      VALUE                   DESCRIPTION
                      dcXClkInvertEnable(1)   Invert the transmit clock
                                              signal
                      dcXClkInvertDisable(2)  Don't invert the transmit
                                              clock signal"
              ::= { dsDcEntry 5 }

dsDcRcvClkInvert   OBJECT-TYPE
              SYNTAX  INTEGER {
              dcRClkInvertEnable (1),
              dcRClkInvertDisable (2)
              }
              ACCESS  read-write
              STATUS  mandatory
              DESCRIPTION
                      "The inversion status of the received clock signal 
                      for the data port. The possible values are:

                      VALUE                   DESCRIPTION
                      dcRClkInvertEnable(1)   Invert the received clock
                                              signal
                      dcRClkInvertDisable(2)  Don't invert the received
                                              clock signal"
              ::= { dsDcEntry 6 }

dsDcIdleChar   OBJECT-TYPE
              SYNTAX  INTEGER {
              dc7eIdleChar (1),
              dc7fIdleChar (2),
              dcffIdleChar (3)
              }
              ACCESS  read-write
              STATUS  mandatory
              DESCRIPTION
                      "The idle character to use for the data port. The
                      possible values are:

                      VALUE             DESCRIPTION
                      dc7eIdleChar(1)   The idle character is hex 7E
                      dc7fIdleChar(1)   The idle character is hex 7F
                      dcffIdleChar(3)   The idle character is hex FF"
              ::= { dsDcEntry 7 }

dsDcLOSInput   OBJECT-TYPE
              SYNTAX  INTEGER {
              dcLosNone (1),
              dcLosRTS (2),
              dcLosDTR (3),
              dcLosBoth (4)
              }
              ACCESS  read-write
              STATUS  mandatory
              DESCRIPTION
                      "The combination of RTS and DTR that will cause a 
                      data port Loss of Signal alarm. The possible 
                      values are:

                      VALUE          DESCRIPTION
                      dcLosNone(1)   Data port LOS is disabled
                      dcLosRts(2)    LOS is declared when RTS is lost
                      dcLosDtr(3)    LOS is declared when DTR is lost
                      dcLosBoth(4)   LOS is declared when both RTS and DTR
                                     are lost."
              ::= { dsDcEntry 8 }

--------------------------------------------------------------------
--  END -  datasmart Data Port Configuration MIB variables
--------------------------------------------------------------------

 
--------------------------------------------------------------------
--  BEGIN -  datasmart Fractional T1 Configuration MIB variables
--------------------------------------------------------------------
 
dsFcLoadXcute   OBJECT-TYPE
              SYNTAX  INTEGER {
              fcLoadXcuteIdle (1),
              fcLoadXcuteStartA (2),
              fcLoadXcuteStartB (3)
              }
              ACCESS  read-write
              STATUS  mandatory
              DESCRIPTION
                      "The Fractional Table that is active. The possible
                      values are:

                      VALUE                 DESCRIPTION
                      fcLoadXcuteIdle(1)    The normal state
                      fcLoadXcuteStartA(2)  Load and execute table A
                      fcLoadXcuteStartB(3)  Load and execute table B"
              ::= { dsFc 1 }

dsFcTable   OBJECT-TYPE

             SYNTAX  SEQUENCE OF DsFcEntry
              ACCESS  not-accessible
              STATUS  mandatory
              DESCRIPTION
                      "This is the DS1/E1 Fractional Table. This table
                      consists of configuration information about
                      DS1/E1 fractional services."
              ::= { dsFc 2 }

dsFcEntry   OBJECT-TYPE
             SYNTAX  DsFcEntry
              ACCESS  not-accessible
              STATUS  mandatory
              DESCRIPTION
                      "This is an entry in the Fractional Table."
             INDEX { dsFcTableIndex, dsFcChanIndex }
             ::= { dsFcTable 1 }

DsFcEntry ::= SEQUENCE {
             dsFcTableIndex  INTEGER,
             dsFcChanIndex   INTEGER,
             dsFcChanMap     INTEGER
             }

dsFcTableIndex      OBJECT-TYPE
             SYNTAX  INTEGER (1..3)
             ACCESS  read-only
             STATUS  mandatory
             DESCRIPTION
                      "This is the index into the Fractional Table. The
                      possible values are:

                      VALUE  DESCRIPTION
                      1      Stored configuration A
                      2      Stored configuration B
                      3      Currently executing fractional table"
             ::= { dsFcEntry 1 }

dsFcChanIndex      OBJECT-TYPE
             SYNTAX  INTEGER (1..31)
             ACCESS  read-only
             STATUS  mandatory
             DESCRIPTION
                      "This is the index of the fractional channel.
                      DS1 has 24 channels and E1 has 32."
             ::= { dsFcEntry 2 }

dsFcChanMap   OBJECT-TYPE
              SYNTAX  INTEGER {
              fcChanIdle    (1),
              fcChanTiData  (2),
              fcChanTiVoice (3),
              fcChan56Dp1   (4),
              fcChan64Dp1   (5),
              fcChan56Dp2   (6),
              fcChan64Dp2   (7),
              fcChanDLNK    (8),
              fcChanDPDL    (9),
              fcChanUnav    (10)
              }
              ACCESS  read-write
              STATUS  mandatory
              DESCRIPTION
                      "The destination and data rate of the channel. The
                      possible values are:

                      VALUE            DESCRIPTION
                      fcChanIdle(1)    The channel is idle
                      fcChanTiData(2)  The channel carries data and is
                                       mapped to a TI channel
                      fcChanTiVoice(3) The channel carries voice and
                                       is mapped to a TI channel
                      fcChan56Dp1(4)   The cahnnel is set for 56K and is
                                       mapped to data port 1
                      fcChan64Dp1(5)   The channel is set for 64K and is
                                       mapped to data port 1
                      fcChan56Dp2(6)   The channel is set for 56K and is
                                       mapped to data port 2
                      fcChan64Dp2(7)   The channel is set for 64K and is
                                       mapped to data port 2
                      fcChanDLNK(8)    The channel is idle and set for 
                                       data link communications
                      fcChanDPDL(9)    The channel is active and also
                                       set for data link communications
                      fCchanUanv(10)   The channel is unavailable" 
              ::= { dsFcEntry 3 }

dsFcMap16   OBJECT-TYPE
              SYNTAX  INTEGER {
              fcMap16Used (1),
              fcMap16Unused (2)
              }
              ACCESS  read-write
              STATUS  mandatory
              DESCRIPTION
                      "This object determines if channel 16 is available 
                      for user payload data. This is only possible if the 
                      unit is configured for Common Channel Signalling. 
                      The possible values are:
 
                      VALUE             DESCRIPTION
                      fcMap16Used(1)    Channel 16 cannot be used for 
                                        user payload data
                      fcMap16Unused(2)  Channel 16 is available for user
                                        payload data"
              ::= { dsFc 3 }

--------------------------------------------------------------------
--  END -  datasmart Fractional T1 Configuration MIB variables
--------------------------------------------------------------------
 
 
--------------------------------------------------------------------
--  BEGIN -  datasmart Frame Management Configuration MIB variables
--------------------------------------------------------------------
 
dsFmcFrameType  OBJECT-TYPE
              SYNTAX  INTEGER {
              fmcFrNlpid (1),
              fmcFrEther (2),
              fmcAtmNlpid (3),
              fmcAtmLlcSnap (4),
              fmcAtmVcMux (5)
              }
              ACCESS  read-write
              STATUS  mandatory
              DESCRIPTION
                      "The frame type for packets being transmitted and
                       received for IP connectivity.
                       The possible values are:
 
                       VALUE             DESCRIPTION
                       fmcFrNlpid(1)      Frame Relay NLPID encapsulation
                       fmcFrEther(2)      Frame Relay Ethertype encapsulation
                       fmcAtmNlpid(3)     ATM DXI NLPID encapsulation
                       fmcAtmLlcSnap(4)   ATM DXI LLC/SNAP encapsulation
                       fmcAtmVcMux(5)     ATM DXI VC-based multiplexing"
              ::= { dsFmc 1 }
 
dsFmcAddrOctets OBJECT-TYPE
              SYNTAX  INTEGER {
              fmcTwoOctets (1),
              fmcFourOctets (2)
              }
              ACCESS  read-write
              STATUS  mandatory
              DESCRIPTION
                      "The length in octets of the Frame Relay address.
                       The possible values are:
 
                       VALUE             DESCRIPTION
                       fmc2Octets(1)     The address is 2 octets long
                       fmc4Octets(1)     The address is 4 octets long"
              ::= { dsFmc 2 }
 
dsFmcFcsBits    OBJECT-TYPE
              SYNTAX  INTEGER {
              fmc16Bits (1),
              fmc32Bits (2)
              }
              ACCESS  read-write
              STATUS  mandatory
              DESCRIPTION
                      "The length in bits of the Frame Relay FCS.
                       The possible values are:
 
                       VALUE             DESCRIPTION
                       fmc16Bits(1)      The FCS field is 16 bits long
                       fmc32Bits(2)      The FCS field is 32 bits long"
              ::= { dsFmc 3 }
 
dsFmcUpperBW    OBJECT-TYPE
              SYNTAX  INTEGER (5..95)
              ACCESS  read-write
              STATUS  mandatory
              DESCRIPTION
                      "The percent of bandwidth utilization threshold.  If
                       the threshold is exceeded, an event will be recorded
                       in the performance data and a trap (if configured)
                       will be sent.  Valid values are 5-95 in increments
                       of 5."
              ::= { dsFmc 4 }
 
dsFmcFpingOper  OBJECT-TYPE
              SYNTAX  INTEGER {
              fmcFpoEnable (1),
              fmcFpoDisable (2)
              }
              ACCESS  read-write
              STATUS  mandatory
              DESCRIPTION
                      "The enabling and disabling of FPING operation.
                       Valid values are Enable and Disable."
              ::= { dsFmc 5 }
 
dsFmcFpingGen   OBJECT-TYPE
              SYNTAX  INTEGER (0..64)
              ACCESS  read-write
              STATUS  mandatory
              DESCRIPTION
                      "The number of distinct VC to be received on the NI
                       before FPINGs are automatically sent out."
              ::= { dsFmc 6 }
 
dsFmcFpingThres OBJECT-TYPE
              SYNTAX  INTEGER (20..2000)
              ACCESS  read-write
              STATUS  mandatory
              DESCRIPTION
                      "The maximum roundtrip time of a FPING packet in
                       milliseconds.  If the threshold is exceeded, an
                       event will be recorded in the performance data and
                       a trap (if configured) will be sent.  Valid values
                       are 20-2000 in increments of 10."
              ::= { dsFmc 7 }
 
dsFmcFpingRst   OBJECT-TYPE
              SYNTAX  INTEGER (0..8388607)
              ACCESS  read-write
              STATUS  mandatory
              DESCRIPTION
                      "Reset the specified VC to an initial state where
                       FPING connectivity is check for.  Valid values are
                       0-1023 for a 2 octet address field and 0-8388607
                       for a 4 octet address field."
              ::= { dsFmc 8 }
 
dsFmcAddVc  OBJECT-TYPE
              SYNTAX  INTEGER (0..8388607)
              ACCESS  read-write
              STATUS  mandatory
              DESCRIPTION
                      "Add a VC to the list of monitored VCs"
              ::= { dsFmc 9 }
 
dsFmcDelVc  OBJECT-TYPE
              SYNTAX  INTEGER (0..8388607)
              ACCESS  read-write
              STATUS  mandatory
              DESCRIPTION
                      "Del a VC from the list of monitored VCs.  Any
                       statistics related to this VC will be moved to
                       the 'other' category."
              ::= { dsFmc 10 }

dsFmcSetNiRcvUpperBwThresh TRAP-TYPE
    ENTERPRISE      datasmart
    VARIABLES       { dsRpFrCur15MVc }
    DESCRIPTION
                "The total traffic through the unit has exceeded
                the configured threshold for NI Receive."
    ::= 9001

dsFmcClrNiRcvUpperBwThresh TRAP-TYPE
    ENTERPRISE      datasmart
    VARIABLES       { dsRpFrCur15MVc }
    DESCRIPTION
                "The total traffic through the unit has crossed back
                under 20 percent below the configured threshold after
                exceeding the threshold for NI Receive."
    ::= 9002

dsFmcSetNiXmtUpperBwThresh TRAP-TYPE
    ENTERPRISE      datasmart
    VARIABLES       { dsRpFrCur15MVc }
    DESCRIPTION
                "The total traffic through the unit has exceeded
                the configured threshold for NI Transmit."
    ::= 9003

dsFmcClrNiXmtUpperBwThresh TRAP-TYPE
    ENTERPRISE      datasmart
    VARIABLES       { dsRpFrCur15MVc }
    DESCRIPTION
                "The total traffic through the unit has crossed back
                under 20 percent below the configured threshold after
                exceeding the threshold NI Transmit."
    ::= 9004

dsFmcFpingLinkDown TRAP-TYPE
    ENTERPRISE      datasmart
    VARIABLES       { dsRpFrCur15MVc }
    DESCRIPTION
                "A VC has transitioned to a link down since FPINGs are not
                 being returned"
    ::= 9005

dsFmcFpingLinkUp TRAP-TYPE
    ENTERPRISE      datasmart
    VARIABLES       { dsRpFrCur15MVc }
    DESCRIPTION
                "A VC has transitioned to a link up since an FPING was just
                 returned"
    ::= 9006
--------------------------------------------------------------------
--  END -  datasmart Frame Management Configuration MIB variables
--------------------------------------------------------------------

 
--------------------------------------------------------------------
--  BEGIN -  datasmart Management Configuration MIB variables
--------------------------------------------------------------------
 
dsMcNetif   OBJECT-TYPE
              SYNTAX  INTEGER {
              mcNetNone (1),
              mcNetEthernet (2),
              mcNetPppSlip (3),
              mcNetSlip (4),
              mcNetDatalink (5),
              mcNetES (6),
              mcNetED (7),
              mcNetESD (8),
              mcNetPSD (9),
              mcNetSD (10),
              mcNetInband (11)
              }
              ACCESS  read-write
              STATUS  mandatory
              DESCRIPTION
                      "The management access port(s) for Telnet and SNMP.
                      The possible values are:

                      VALUE             DESCRIPTION
                      mcNetNone(1)      No ip interface paths are active
                      mcNetEthernet(2)  The ethernet ip interface is active
                      mcNetPppSlip(3)   The ppp/slip (control ports)
                                        ip interfaces are active
                      mcNetSlip(4)      The slip (control ports) ip interface
                                        is active
                      mcNetDatalink(5)  The data link ip interface is active
                      mcNetES(6)        The ethernet and slip (control ports) 
                                        ip interfaces are active
                      mcNetED(7)        The ethernet and data link 
                                        ip interfaces are active
                      mcNetESD(8)       The ethernet, slip (control ports), and
                                        data link ip interfaces are active
                      mcNetPSD(9)       The ppp/slip (control ports) and
                                        data link ip interfaces are active
                      mcNetSD(10)       The slip (control ports) and data link 
                                        ip interfaces are active
                      mcNetInband(11)   The inband Frame Relay (NI and Data 
                                        Port) ip interface is active"
              ::= { dsMc 1 }

dsMcT1DLPath    OBJECT-TYPE
              SYNTAX  INTEGER {
              mcDLPathFdl     (1),
              mcDLPathTS1-64  (2),
              mcDLPathTS2-64  (3),
              mcDLPathTS3-64  (4),
              mcDLPathTS4-64  (5),
              mcDLPathTS5-64  (6),
              mcDLPathTS6-64  (7),
              mcDLPathTS7-64  (8),
              mcDLPathTS8-64  (9),
              mcDLPathTS9-64  (10),
              mcDLPathTS10-64 (11),
              mcDLPathTS11-64 (12),
              mcDLPathTS12-64 (13),
              mcDLPathTS13-64 (14),
              mcDLPathTS14-64 (15),
              mcDLPathTS15-64 (16),
              mcDLPathTS16-64 (17),
              mcDLPathTS17-64 (18),
              mcDLPathTS18-64 (19),
              mcDLPathTS19-64 (20),
              mcDLPathTS20-64 (21),
              mcDLPathTS21-64 (22),
              mcDLPathTS22-64 (23),
              mcDLPathTS23-64 (24),
              mcDLPathTS24-64 (25),
              mcDLPathTS1-56  (26),
              mcDLPathTS2-56  (27),
              mcDLPathTS3-56  (28),
              mcDLPathTS4-56  (29),
              mcDLPathTS5-56  (30),
              mcDLPathTS6-56  (31),
              mcDLPathTS7-56  (32),
              mcDLPathTS8-56  (33),
              mcDLPathTS9-56  (34),
              mcDLPathTS10-56 (35),
              mcDLPathTS11-56 (36),
              mcDLPathTS12-56 (37),
              mcDLPathTS13-56 (38),
              mcDLPathTS14-56 (39),
              mcDLPathTS15-56 (40),
              mcDLPathTS16-56 (41),
              mcDLPathTS17-56 (42),
              mcDLPathTS18-56 (43),
              mcDLPathTS19-56 (44),
              mcDLPathTS20-56 (45),
              mcDLPathTS21-56 (46),
              mcDLPathTS22-56 (47),
              mcDLPathTS23-56 (48),
              mcDLPathTS24-56 (49)
              }
              ACCESS  read-write
              STATUS  mandatory
              DESCRIPTION
                      "The T1 DataLink value.  This configuration is used if
                      the NETIF has a DataLink component.
                      The possible values are:

                      VALUE            DESCRIPTION
                      mcDLPathFdl(1)   The DataLink will use the FDL.
                      mcDLPathTSn-64   The DataLink will use TSn.  If TSn
                                       is IDLE, the data rate will be set
                                       to 64K.  If TSn is assigned to a
                                       Data Port, the DataLink will use
                                       8K of TSn.
                      mcDLPathTSn-56   The DataLink will use TSn.  If TSn
                                       is IDLE, the data rate will be set
                                       to 56K.  If TSn is assigned to a
                                       Data Port, the DataLink will use
                                       8K of TSn."
              ::= { dsMc 2 }

dsMcDefRoute    OBJECT-TYPE
              SYNTAX  IpAddress
              ACCESS  read-write
              STATUS  mandatory
              DESCRIPTION
                      "The unit's default IP router."
              ::= { dsMc 3 }

dsMcCIpAddr OBJECT-TYPE
              SYNTAX  IpAddress
              ACCESS  read-write
              STATUS  mandatory
              DESCRIPTION
                      "The IP address for the unit's Control Port."
              ::= { dsMc 4 }

dsMcDIpAddr OBJECT-TYPE
              SYNTAX  IpAddress
              ACCESS  read-write
              STATUS  mandatory
              DESCRIPTION
                      "The IP address for the unit's Data Link."
              ::= { dsMc 5 }

dsMcCDIpMask    OBJECT-TYPE
              SYNTAX  IpAddress
              ACCESS  read-write
              STATUS  mandatory
              DESCRIPTION
                      "The IP subnet mask for the unit's Control Port and
                      Data Link."
              ::= { dsMc 6 }

dsMcEIpAddr OBJECT-TYPE
              SYNTAX  IpAddress
              ACCESS  read-write
              STATUS  mandatory
              DESCRIPTION
                      "The IP address for the unit's Ethernet Port."
              ::= { dsMc 7 }

dsMcEIpMask OBJECT-TYPE
              SYNTAX  IpAddress
              ACCESS  read-write
              STATUS  mandatory
              DESCRIPTION
                      "The IP subnet mask for the unit's Ethernet Port."
              ::= { dsMc 8 }

dsMcIIpAddr OBJECT-TYPE
              SYNTAX  IpAddress
              ACCESS  read-write
              STATUS  mandatory
              DESCRIPTION
                      "The IP address for the unit's In-Band Interface."
              ::= { dsMc 9 }

dsMcIIpMask OBJECT-TYPE
              SYNTAX  IpAddress
              ACCESS  read-write
              STATUS  mandatory
              DESCRIPTION
                      "The IP subnet mask for the unit's In-Band Interface."
              ::= { dsMc 10 }


dsAmc   OBJECT IDENTIFIER ::= { dsMc 11 }

--------------------------------------------------------------------
--  END -  datasmart Management Configuration MIB variables
--------------------------------------------------------------------

--------------------------------------------------------------------
--  BEGIN -  datasmart Advanced Management Configuration MIB variables
--------------------------------------------------------------------
 
--
--  datasmart(2).dsMc(9).dsAmc(11) - The dsAmc subgroup of the dsMc group.
--

dsAmcAgent  OBJECT-TYPE
              SYNTAX  INTEGER {
                      amcEnabled (1),
                      amcDisabled (2)
              }
              ACCESS  read-write
              STATUS  mandatory
              DESCRIPTION
                      "The operational status of the SMMP agent. The
                      possible values are:

                        VALUE                     DESCRIPTION.
                      amcEnabled(1)         The SNMP agent is enabled
                      amcDisabled(2)        The SNMP agent is disabled."
              ::= { dsAmc 1 }

dsAmcSourceScreen   OBJECT-TYPE
              SYNTAX  INTEGER {
              mcIpScreen (1),
              mcNoScreen (2)
              }
              ACCESS  read-write
              STATUS  mandatory
              DESCRIPTION
                      "The status of the IP source address screening 
                      security. The possible values are:

                      VALUE             DESCRIPTION
                      mcIpScreen(1)     The screening security is enabled
                      mcNoScreen(2)     The screening security is disabled"
              ::= { dsAmc 2 }

dsAmcTrapTable  OBJECT-TYPE

              SYNTAX  SEQUENCE OF DsAmcTrapEntry
              ACCESS  not-accessible
              STATUS  mandatory
              DESCRIPTION
                      "The SNMP Trap Table. This table lists the different
                      types of traps and allows each type to be individually
                      enabled/disabled. Currently, the types of traps are:
                          Start Traps          - Cold-Start and Warm-Start
                          Link Traps           - Link-Up and Link-Down Traps
                          Authentication Traps - e.g. incorrect Telnet password
                          Enterprise Traps     - e.g. NI EER Trap"
              ::= { dsAmc 3 }

dsAmcTrapEntry  OBJECT-TYPE
              SYNTAX  DsAmcTrapEntry
              ACCESS  not-accessible
              STATUS  mandatory
              DESCRIPTION
                      "An entry in the SNMP Trap Table."
             INDEX { dsAmcTrapType }
             ::= { dsAmcTrapTable 1 }

DsAmcTrapEntry ::= SEQUENCE {
             dsAmcTrapType         INTEGER,
             dsAmcTrapStatus       INTEGER
             }

dsAmcTrapType      OBJECT-TYPE
             SYNTAX  INTEGER {
             mcStartTraps (1),
             mcLinkTraps (2),
             mcAuthenTraps (3),
             mcEnterpriseTraps (4)
             }
             ACCESS  read-only
             STATUS  mandatory
             DESCRIPTION
                      "The type of trap. There is one row in dsAmcTrapTable
                      for each type of trap.
                      The possible values are:

                      VALUE             DESCRIPTION
                      amcStartTraps(1)
                                Cold-Start and Warm-Start Traps.
                      amcLinkTraps(2)
                                Link-Up and Link-Down Traps.
                      amcAuthenTraps(3)
                                Authentication Traps. Sent for:
                                      - Incorrect Telnet password
                                      - Source IP address not on IP Screen List
                                      - Incorrect SNMP Read Community String
                                      - Incorrect SNMP Write Community String
                      amcEnterpriseTraps(4)
                                Enterprise-Specific Traps."
             ::= { dsAmcTrapEntry 1 }

dsAmcTrapStatus   OBJECT-TYPE
              SYNTAX  INTEGER {
                      amcEnabled (1),
                      amcDisabled (2)
              }
              ACCESS  read-write
              STATUS  mandatory
              DESCRIPTION
                      "Indicates whether the particular type of trap is
                      enabled or disabled.
                      The possible values are:

                      VALUE             DESCRIPTION
                      amcEnabled(1)
                                These types of traps are enabled.
                      amcDisabled(2)
                                These types of traps are disabled."
              ::= { dsAmcTrapEntry 2 }

dsAmcScrnTable  OBJECT-TYPE

              SYNTAX  SEQUENCE OF DsAmcScrnEntry
              ACCESS  not-accessible
              STATUS  mandatory
              DESCRIPTION
                      "The Source Address Screening Table. The entries
                      in this table are the IP addresses which are 
                      allowed to access this unit."
              ::= { dsAmc 4 }

dsAmcScrnEntry  OBJECT-TYPE
              SYNTAX  DsAmcScrnEntry
              ACCESS  not-accessible
              STATUS  mandatory
              DESCRIPTION
                      "An entry in the Source Address Screening Table."
             INDEX { dsAmcScrnIndex }
             ::= { dsAmcScrnTable 1 }

DsAmcScrnEntry ::= SEQUENCE {
             dsAmcScrnIndex         INTEGER,
             dsAmcScrnIpAddr        IpAddress,
             dsAmcScrnIpMask        IpAddress
             }

dsAmcScrnIndex      OBJECT-TYPE
             SYNTAX  INTEGER (1..10)
             ACCESS  read-only
             STATUS  mandatory
             DESCRIPTION
                      "The index to the Source Address Screening Table. 
                      Ten entries are possible."
             ::= { dsAmcScrnEntry 1 }

dsAmcScrnIpAddr   OBJECT-TYPE
              SYNTAX  IpAddress
              ACCESS  read-write
              STATUS  mandatory
              DESCRIPTION
                      "An IP Address(es) which will be permitted to access this
                      unit. This object is combined with dsAmcScrnIpMask to
                      allow a single entry to permit access by an
                      entire subnet."
              ::= { dsAmcScrnEntry 2 }

dsAmcScrnIpMask   OBJECT-TYPE
              SYNTAX  IpAddress
              ACCESS  read-write
              STATUS  mandatory
              DESCRIPTION
                      "An IP subnet mask that indicates which portion
                      of dsAmcScrnIpAddr must be matched to permit access.
                      This allows a single entry to provide access by an
                      entire IP subnet.
                         A mask of '255.255.255.0' means that hosts on
                      the subnet of dsAmcScrnIpAddr are permitted access.
                         A mask of '255.255.255.255' means that only the
                      IP address which exactly matches dsAmcScrnIpAddr is
                      permitted access (i.e. only a single host)."
              ::= { dsAmcScrnEntry 3 }

dsAmcTrapDestTable  OBJECT-TYPE

              SYNTAX  SEQUENCE OF DsAmcTrapDestEntry
              ACCESS  not-accessible
              STATUS  mandatory
              DESCRIPTION
                      "The SNMP Trap Destinations Table. This table lists
                      up to 10 addresses to send SNMP traps to when
                      alarm conditions occur."
              ::= { dsAmc 5 }

dsAmcTrapDestEntry  OBJECT-TYPE
              SYNTAX  DsAmcTrapDestEntry
              ACCESS  not-accessible
              STATUS  mandatory
              DESCRIPTION
                      "An entry in the SNMP Trap Destinations Table."
             INDEX { dsAmcTrapDestIndex }
             ::= { dsAmcTrapDestTable 1 }

DsAmcTrapDestEntry ::= SEQUENCE {
             dsAmcTrapDestIndex         INTEGER,
             dsAmcTrapDestIpAddr        IpAddress,
             dsAmcTrapDestVc            INTEGER,
             dsAmcTrapDestPort          INTEGER
             }

dsAmcTrapDestIndex      OBJECT-TYPE
             SYNTAX  INTEGER (1..10)
             ACCESS  read-only
             STATUS  mandatory
             DESCRIPTION
                      "The index to the SNMP Trap Destinations Table."
             ::= { dsAmcTrapDestEntry 1 }

dsAmcTrapDestIpAddr   OBJECT-TYPE
              SYNTAX  IpAddress
              ACCESS  read-write
              STATUS  mandatory
              DESCRIPTION
                      "The IP address portion of a Trap Destination Entry,
                       used when sending SNMP traps."
              ::= { dsAmcTrapDestEntry 2 }

dsAmcTrapDestVc   OBJECT-TYPE
              SYNTAX  INTEGER (0..8388607)
              ACCESS  read-write
              STATUS  mandatory
              DESCRIPTION
                      "The VC portion of a Trap Destination Entry,
                       used when sending SNMP traps."
              ::= { dsAmcTrapDestEntry 3 }

dsAmcTrapDestPort   OBJECT-TYPE
              SYNTAX  INTEGER {
              amcNIPort (1),
              amcDPPort (2)
                          }
              ACCESS  read-write
              STATUS  mandatory
              DESCRIPTION
                      "The Port portion of a Trap Destination Entry,
                        used when sending SNMP traps."
              ::= { dsAmcTrapDestEntry 4 }

dsMcIVc		OBJECT-TYPE
              SYNTAX  DLCI
              ACCESS  read-write
              STATUS  mandatory
              DESCRIPTION
                      "fill in later."
              ::= { dsMc 12 }

dsMcIPort	OBJECT-TYPE
              SYNTAX  INTEGER {
              amcNiPort (1),
              amcDPPort (2)
              }
              ACCESS  read-write
              STATUS  mandatory
              DESCRIPTION
                      "fill in later
                      The possible values are:

                      VALUE             DESCRIPTION
                      amcNiPort(1)      Communicate over NI
                      amcDPPort(2)      communicate over DP"
              ::= { dsMc 13 }

--------------------------------------------------------------------
--  END -  datasmart Advanced Management Configuration MIB variables
--------------------------------------------------------------------

--------------------------------------------------------------------
--  BEGIN -  datasmart Network Interface Configuration MIB variables
--------------------------------------------------------------------
 
dsNcFraming OBJECT-TYPE
              SYNTAX  INTEGER {
              ncSF (1),
              ncESF (2),
              ncEricsson (3)
              }
              ACCESS  read-write
              STATUS  mandatory
              DESCRIPTION
                      "The type of framing being used on the Network
                      Interface. The possible values are:

                      VALUE             DESCRIPTION
                      ncSF(1)           SF (D4) framing
                      ncESF(2)          ESF framing
                      ncEricsson(3)     Ericsson framing"
              ::= { dsNc 1 }

dsNcCoding  OBJECT-TYPE
              SYNTAX  INTEGER {
              ncAmi (1),
              ncB8zs (2)
              }
              ACCESS  read-write
              STATUS  mandatory
              DESCRIPTION
                      "The type of line coding being used on the Network
                      Interface. The possible values are:
 
                      VALUE             DESCRIPTION
                      ncAmi(1)          AMI line coding
                      ncB8zs(2)         B8ZS line coding."
              ::= { dsNc 2 }

dsNcT1403   OBJECT-TYPE
              SYNTAX  INTEGER {
              ncT1403Enable (1),
              ncT1403Disable (2)
              }
              ACCESS  read-write
              STATUS  mandatory
              DESCRIPTION
                      "This object enables/disables the sending of
                      T1.403 PRM messages. The possible values are: 

                      VALUE              DESCRIPTION
                      ncT1403Enable(1)   Enable T1.403 messages
                      ncT1403Disable(2)  Disabled T1.403 messages"
              ::= { dsNc 3 }

dsNcYellow  OBJECT-TYPE
              SYNTAX  INTEGER {
              ncYelEnable (1),
              ncYelDisable (2)
              }
              ACCESS  read-write
              STATUS  mandatory
              DESCRIPTION
                      "This object enables/disables sending Yellow alarm 
                      out the Network Interface upon receipt of an
                      alarm on the Network Interface. The possible values
                      are:
 
                      VALUE             DESCRIPTION
                      ncYelEnable(1)    Enable sending Yellow alarm
                      ncYelDisable(1)   Disable sending Yellow alarm"
              ::= { dsNc 4 }

dsNcAddr54  OBJECT-TYPE
              SYNTAX  INTEGER {
              ncAddrCsu (1),
              ncAddrDsu (2),
              ncAddrBoth (3)
              }
              ACCESS  read-write
              STATUS  mandatory
              DESCRIPTION
                      "If 54016 addressing is enabled, this object 
                      determines what type of addressing the unit responds 
                      to. The possible values are:

                      VALUE             DESCRIPTION
                      ncAddrCsu(1)      CSU addressing mode
                      ncAddrDsu(2)      DSU addressing mode
                      ncAddrBoth(3)     Both CSU and DSU addressing modes"
              ::= { dsNc 5 }

dsNc54016     OBJECT-TYPE
              SYNTAX  INTEGER {
              nc54016Enable (1),
              nc54016Disable (2)
              }
              ACCESS  read-write
              STATUS  mandatory
              DESCRIPTION
                      "This object determines whether the unit responds to
                      54016 addressing modes. The possible values are:

                      VALUE              DESCRIPTION
                      nc54016Enable(1)   Enabled 54016 addressing 
                      nc54016Disable(2)  Disable 54016 addressing"
              ::= { dsNc 6 }

dsNcLbo OBJECT-TYPE
              SYNTAX  INTEGER {
              ncLbo0 (1),
              ncLbo1 (2),
              ncLbo2 (3)
              }
              ACCESS  read-write
              STATUS  mandatory
              DESCRIPTION
                      "The Network Interface Line Build Out setting. 
                      The possible values are:

                      VALUE             DESCRIPTION
                      ncLbo0(1)         0.0dB line attenuation
                      ncLbo1(2)         7.5dB line attenuation
                      ncLbo2(3)         15.0 dB line attenuation"
              ::= { dsNc 7}

dsNcMF16    OBJECT-TYPE
              SYNTAX  INTEGER {
              ncMF16Enable (1),
              ncMF16Disable (2)
              }
              ACCESS  read-write
              STATUS  mandatory
              DESCRIPTION
                      "The E1 network interface Time Slot 16 MultiFrame
                      alignment signal setting. The possible values are:

                      VALUE             DESCRIPTION
                      ncMF16Enable(1)   Enable the Time Slot 16 MultiFrame
                                        alignment signal 
                      ncMF16Disable(2)  Disabled the Time Slot 16 MultiFrame
                                        alignment signal"
              ::= { dsNc 8 }

dsNcCRC OBJECT-TYPE
              SYNTAX  INTEGER {
              ncCrcEnable (1),
              ncCrcDisable (2)
              }
              ACCESS  read-write
              STATUS  mandatory
              DESCRIPTION
                      "The E1 network interface CRC generation/checking
                      setting. The possible values are:

                      VALUE             DESCRIPTION
                      ncCrcEnable(1)    Enable CRC generation/checking
                      ncCrcDisable(2)   Disable CRC generation/checking"
              ::= { dsNc 9 }

dsNcFasAlign     OBJECT-TYPE
              SYNTAX  INTEGER {
              ncFasWord (1),
              ncNonFasWord (2)
              }
              ACCESS  read-write
              STATUS  mandatory
              DESCRIPTION
                      "The E1 network interface Time Slot 0 NOT-FAS Word
                      setting. The possible values are:

                      VALUE             DESCRIPTION
                      ncFasWord(1)      Use the NOT-FAS word
                      ncNonFasWord(2)   Do not use the NOT-FAS word"
              ::= { dsNc 10 }

dsNcE1DLPath    OBJECT-TYPE
              SYNTAX  INTEGER {
              ncSaNone (1),
              ncSaBit4 (2),
              ncSaBit5 (3),
              ncSaBit6 (4),
              ncSaBit7 (5),
              ncSaBit8 (6),
              ncTS1 (7),
              ncTS2 (8),
              ncTS3 (9),
              ncTS4 (10),
              ncTS5 (11),
              ncTS6 (12),
              ncTS7 (13),
              ncTS8 (14),
              ncTS9 (15),
              ncTS10 (16),
              ncTS11 (17),
              ncTS12 (18),
              ncTS13 (19),
              ncTS14 (20),
              ncTS15 (21),
              ncTS16 (22),
              ncTS17 (23),
              ncTS18 (24),
              ncTS19 (25),
              ncTS20 (26),
              ncTS21 (27),
              ncTS22 (28),
              ncTS23 (29),
              ncTS24 (30),
              ncTS25 (31),
              ncTS26 (32),
              ncTS27 (33),
              ncTS28 (34),
              ncTS29 (35),
              ncTS30 (36),
              ncTS31 (37)
              }
              ACCESS  read-write
              STATUS  mandatory
              DESCRIPTION
                      "The E1 network interface Sa bit usage. If Sa bits 
                      are being used for data link communications, both the 
                      near and far end units must agree on which Sa bit to 
                      use. Possible value are:

                      VALUE             DESCRIPTION
                      ncSaNone(1)       No Sa bits are being used for 
                                        data link communications
                      ncSaBit4(2)       Use Sa bit 4 for data link 
                                        communications
                      ncSaBit5(3)       Use Sa bit 5 for data link 
                                        communications
                      ncSaBit6(4)       Use Sa bit 6 for data link 
                                        communications
                      ncSaBit7(5)       Use Sa bit 7 for data link 
                                        communications
                      ncSaBit8(6)       Use Sa bit 8 for data link 
                                        communications
                      ncTSn             Use TimeSlot n for data link 
                                        communications. These are only
                                        available for E1 units with
                                        In-Band Link hardware."
              ::= { dsNc 11 }

dsNcKA     OBJECT-TYPE
              SYNTAX  INTEGER {
              ncFramedKeepAlive (1),
              ncUnFramedKeepAlive (2)
              }
              ACCESS  read-write
              STATUS  mandatory
              DESCRIPTION
                      "The status of sending E1 remote Frame Alarm into
                      the NI during alarms. The Possible values are:
 
                      VALUE              DESCRIPTION
                      ncFramedKeepAlive(1)  Enable Framed Keep Alive
                      ncUnFramedKeepAlive(2) Disabled Unframed Keep Alive"
              ::= { dsNc 12 }
 

dsNcGenRfa     OBJECT-TYPE
              SYNTAX  INTEGER {
              ncGenRfaEnable (1),
              ncGenRfaDisable (2)
              }
              ACCESS  read-write
              STATUS  mandatory
              DESCRIPTION
                      "The status of sending E1 remote Frame Alarm into 
                      the NI during alarms. The Possible values are:

                      VALUE              DESCRIPTION
                      ncGenRfaEnable(1)  Enable RFA insertion 
                      ncGenRfaDisable(2) Disabled RFA insertion"
              ::= { dsNc 13 }

dsNcPassTiRfa   OBJECT-TYPE
              SYNTAX  INTEGER {
              ncPassTiRfaEnable (1),
              ncPassTiRfaDisable (2)
              }
              ACCESS  read-write
              STATUS  mandatory
              DESCRIPTION
                      "The status of sending the RFA received on the 
                      network interface out the terminal interface. This 
                      function is not possible on a DSU only, it must be 
                      an add/drop. This function only works if at least one 
                      channel is assigned to the TI. The Possible values are:

                      VALUE                  DESCRIPTION
                      ncPassTiRfaEnable(1)   Enable RFA re-generation
                      ncPassTiRfaDisable(2)  Disabled RFA re-generation"
              ::= { dsNc 14 }

dsNcIdle    OBJECT-TYPE
              SYNTAX  INTEGER ( 0..255) 
              ACCESS  read-write
              STATUS  mandatory
              DESCRIPTION
                      "The idle code to be transmited in the idle NI and TI 
                      channels. This code is also sent in all TI channels 
                      when the TI is experiencing an OOF."
              ::= { dsNc 15 }

dsNcDdsType	OBJECT-TYPE
              SYNTAX  INTEGER {
              scDds56K (1),
              scDds64K (2)
              }
              ACCESS  read-write
              STATUS  mandatory
              DESCRIPTION
                      "
                      The Possible values are:

                      VALUE                  DESCRIPTION
                      scDds56K(1)            Set unit to 56K Operation
                      scDds64K(2)            Set unit to 56K Operation"
              ::= { dsNc 16 }


--------------------------------------------------------------------
--  END -  datasmart Network Interface Configuration MIB variables
--------------------------------------------------------------------

 
--------------------------------------------------------------------
--  BEGIN -  datasmart System Configuration MIB variables
--------------------------------------------------------------------
dsScMonth   OBJECT-TYPE
              SYNTAX  INTEGER (1..12)
              ACCESS  read-write
              STATUS  mandatory
              DESCRIPTION
                      "The calendar number of the current month. 
                       1 is January."
              ::= { dsSc 1 }

dsScDay OBJECT-TYPE
              SYNTAX  INTEGER (1..31)
              ACCESS  read-write
              STATUS  mandatory
              DESCRIPTION
                      "The number of the current day."
              ::= { dsSc 2 }

dsScYear    OBJECT-TYPE
              SYNTAX  INTEGER (0..99)
              ACCESS  read-write
              STATUS  mandatory
              DESCRIPTION
                      "The number of the current year. 95 is 1995."
              ::= { dsSc 3 }

dsScHour    OBJECT-TYPE
              SYNTAX  INTEGER (0..23)
              ACCESS  read-write
              STATUS  mandatory
              DESCRIPTION
                      "The number of the current hour. 0 is 12:00am."
              ::= { dsSc 4 }

dsScMinutes OBJECT-TYPE
              SYNTAX  INTEGER (0..59)
              ACCESS  read-write
              STATUS  mandatory
              DESCRIPTION
                      "The number of the current minute."
              ::= { dsSc 5 }

dsScName    OBJECT-TYPE
              SYNTAX  DisplayString (SIZE (0..15))
              ACCESS  read-write
              STATUS  mandatory
              DESCRIPTION
                      "The Site Name of the unit."
              ::= { dsSc 6 }

dsScSlotAddr    OBJECT-TYPE
              SYNTAX  INTEGER (0..15)
              ACCESS  read-write
              STATUS  mandatory
              DESCRIPTION
                      "The Kentrox-specific slot address. 
                      The 01 in the address 01:02:003."
              ::= { dsSc 7 }

dsScShelfAddr   OBJECT-TYPE
              SYNTAX  INTEGER (0..15)
              ACCESS  read-write
              STATUS  mandatory
              DESCRIPTION
                      "The Kentrox-specific shelf address.
                      The 02 in the address 01:02:003."
              ::= { dsSc 8 }

dsScGroupAddr   OBJECT-TYPE
              SYNTAX  INTEGER (0..255)
              ACCESS  read-write
              STATUS  mandatory
              DESCRIPTION
                      "The Kentrox-specific group address.
                      The 003 in the address 01:02:003."
              ::= { dsSc 9 }

dsScFrontPanel  OBJECT-TYPE
              SYNTAX  INTEGER {
              scFpEnable (1),
              scFpDisable (2)
              }
              ACCESS  read-write
              STATUS  mandatory
              DESCRIPTION
                      "The status of the front panel buttons. The
                      possible values are:

                      VALUE             DESCRIPTION
                      scFpEnable(1)     Enable the front panel buttons
                      scFpDisable(2)    Disable the front panel buttons"
              ::= { dsSc 10 }

dsScDSCompatible    OBJECT-TYPE
              SYNTAX  INTEGER {
              scDSEnable (1),
              scDSDisable (2)
              }
              ACCESS  read-write
              STATUS  mandatory
              DESCRIPTION
                      "The status of the datasmart compatibility function. 
                       This should be set to scDSEnabled(1) when the far 
                       end unit is a eariler model datasmart, not a 
                       datasmart. The possible values are:

                      VALUE             DESCRIPTION
                      scDSEnable(1)     Enable the datasmart compatibility 
                                        function
                      scDSDisable(2)    Disable the datasmart compatibility
                                        funcation"
              ::= { dsSc 11 }

dsScClockSource     OBJECT-TYPE
              SYNTAX  INTEGER {
              scTerminalTiming (1),
              scThroughTiming (2),
              scInternalTiming (3),
              scLoopTiming (4),
              scDP1Timing (5),
              scDP2Timing (6)
              }
              ACCESS  read-write
              STATUS  mandatory
              DESCRIPTION
                      "The source of the timing clock. The various options
                      are:

                      VALUE                DESCRIPTION
                      scTerminalTiming(1)  Use the clock coming in on 
                                           the Terminal Interface
                      scThroughTiming(2)   Use Through timing NI rx
                                           to Ti tx and TI rx to NI tx
                      scInternalTiming(3)  Use the internal clock
                      scLoopTiming(4)      Use the clock from the network   
                      scDP1Timing(5)       Use the clock coming in on
                                           data port 1
                      scDP2Timing(6)       Use the clock coming in on
                                           data port 2"
              ::= { dsSc 12 }

dsScAutologout  OBJECT-TYPE
              SYNTAX  INTEGER (0..60)
              ACCESS  read-write
              STATUS  mandatory
              DESCRIPTION
                      "The time (in minutes) to wait for a keypress
                      before logging the current user out. If this object
                      is set to 0, autologout is disabled."
              ::= { dsSc 13}

dsScZeroPerData OBJECT-TYPE
              SYNTAX  INTEGER {
              scZallIdle (1),
              scZallStart (2)
              }
              ACCESS  read-write
              STATUS  mandatory
              DESCRIPTION
                      "This object will zero all performance report 
                      counters if it is set to scZallStart(2)."
              ::= { dsSc 14 }

dsScWyv OBJECT-TYPE
              SYNTAX  DisplayString (SIZE (0..255))
              ACCESS  read-only
              STATUS  mandatory
              DESCRIPTION
                      "The string returned by the user interface command
                      WYV, What's Your Version."
              ::= { dsSc 15 }

dsScAutoCfg     OBJECT-TYPE
              SYNTAX  INTEGER {
              scAcEnable (1),
              scAcDisable (2)
              }
              ACCESS  read-write
              STATUS  mandatory
              DESCRIPTION
                      "This object enables/disables the Auto-Configuration
                        feature, which allows units in a daisy chain to be
                        automatically configured by the Daisy Chain Controller.
                        This feature is only available on the plug-in
                        versions of datasmart."
              ::= { dsSc 16 }

dsScTftpSwdl OBJECT-TYPE
        SYNTAX  DisplayString (SIZE (0..255))
        ACCESS  read-write
        STATUS  mandatory
        DESCRIPTION
                "A text string used to initiate or check the status of a TFTP
                file transfer operation for doing a software download.  To
                initiate a TFTP software download, set this variable to the
                value `tswdl:<i>,<f>`, where i represents the IP address of
                the host system, and the f represents the name of the file to
                be downloaded.  Setting this variable to any other value will
                have no affect.  Getting the value of this variable will
                return the status of the TFTP software download."
        ::= { dsSc 17 }

dsScBoot OBJECT-TYPE
        SYNTAX  INTEGER {
                scBootIdle(1),
                scBootActive(2),
                scBootInactive(3)
        }
        ACCESS  read-write
        STATUS  mandatory
        DESCRIPTION
                "This variable is used to force a system reboot:
                 scBootIdle      Does nothing.
                 scBootActive    Reboots from the executing FLASH ROM bank.
                 scBootInactive  Reboots from the non-executing FLASH ROM bank."
        ::= { dsSc 18 }

dsScOperMode   OBJECT-TYPE
        SYNTAX  INTEGER {
                scTransparentMode(1),
                scMonitorMode(2)
        }
        ACCESS  read-write
        STATUS  mandatory
        DESCRIPTION
                "fill in later.
                 scTransparentMode      Unit doesn't monitor FR traffic
                 scMonitorMode          Unit monitors FR traffic"
        ::= { dsSc 19 }

dsScYearExtention   OBJECT-TYPE
        SYNTAX  INTEGER ( 1992..2091 )
        ACCESS  read-write
        STATUS  mandatory
        DESCRIPTION
                "."
        ::= { dsSc 20 }

dsScMonthExtention   OBJECT-TYPE
        SYNTAX  INTEGER ( 1..12 )
        ACCESS  read-write
        STATUS  mandatory
        DESCRIPTION
                "."
        ::= { dsSc 21 }

dsScDayExtention   OBJECT-TYPE
        SYNTAX  INTEGER ( 1..31 )
        ACCESS  read-write
        STATUS  mandatory
        DESCRIPTION
                "."
        ::= { dsSc 22 }

dsScHourExtention   OBJECT-TYPE
        SYNTAX  INTEGER ( 0..24 )
        ACCESS  read-write
        STATUS  mandatory
        DESCRIPTION
                "."
        ::= { dsSc 23 }

dsScMinExtention   OBJECT-TYPE
        SYNTAX  INTEGER ( 0..59 )
        ACCESS  read-write
        STATUS  mandatory
        DESCRIPTION
                "."
        ::= { dsSc 24 }

dsScSecExtention   OBJECT-TYPE
        SYNTAX  INTEGER ( 0..59 )
        ACCESS  read-only
        STATUS  mandatory
        DESCRIPTION
                "."
        ::= { dsSc 25 }


dsScPinK	   OBJECT-TYPE
        SYNTAX  INTEGER {
			pinKEnabled(1),
			pinKDisabled(2)
		}
        ACCESS  read-write
        STATUS  mandatory
        DESCRIPTION
                "."
        ::= { dsSc 26 }


--------------------------------------------------------------------
--  END -  datasmart System Configuration MIB variables
--------------------------------------------------------------------
 
 
--------------------------------------------------------------------
--  BEGIN -  datasmart Terminal Configuration MIB variables
--------------------------------------------------------------------
 
dsTcFraming OBJECT-TYPE
              SYNTAX  INTEGER {
              tcSF (1),
              tcESF (2),
              tcEricsson (3)
              }
              ACCESS  read-write
              STATUS  mandatory
              DESCRIPTION
                      "The line framing for the Terminal Interface.
                      The possible values are:
 
                      VALUE             DESCRIPTION
                      tcSF(1)           SF (D4) framing
                      tcESF(2)          ESF framing
                      tcEricsson(3)     Ericsson framing"
              ::= { dsTc 1 }

dsTcCoding  OBJECT-TYPE
              SYNTAX  INTEGER {
              tcAmi (1),
              tcB8zs (2)
              }
              ACCESS  read-write
              STATUS  mandatory
              DESCRIPTION
                      "The line coding for the Terminal Interface.
                      The possible values are:

                      VALUE             DESCRIPTION
                      tcAmi(1)          AMI line coding
                      tcB8zs(2)         B8ZS line coding"
              ::= { dsTc 2 }

dsTcIdle    OBJECT-TYPE
              SYNTAX  INTEGER ( 0..255) 
              ACCESS  read-write
              STATUS  mandatory
              DESCRIPTION
                      "The code that is sent out the idle DS0 channels
                      of the terminal interface."
              ::= { dsTc 3 }

dsTcEqual   OBJECT-TYPE
              SYNTAX  INTEGER {
              tcTe0 (1),
              tcTe1 (2),
              tcTe2 (3),
              tcTe3 (4),
              tcTe4 (5)
              }
              ACCESS  read-write
              STATUS  mandatory
              DESCRIPTION
                      "The line equalization for the Terminal Interface. The
                      possible values are: 

                      VALUE             DESCRIPTION
                      tcTe0(1)            0-133 feet
                      tcTe1(2)          133-266 feet
                      tcTe2(3)          266-399 feet
                      tcTe3(4)          399-533 feet
                      tcTe4(5)          533-655 feet"
              ::= { dsTc 4 }

dsTcMF16    OBJECT-TYPE
              SYNTAX  INTEGER {
              tcMF16Enable (1),
              tcMF16Disable (2)
              }
              ACCESS  read-write
              STATUS  mandatory
              DESCRIPTION
                      "The E1 terminal interface Time Slot 16 MultiFrame
                      alignment signal setting. The possible values are:

                      VALUE             DESCRIPTION
                      tcMF16Enable(1)   Enable the Time Slot 16 MultiFrame
                                        alignment signal 
                      tcMF16Disable(2)  Disabled the Time Slot 16 MultiFrame
                                        alignment signal"
              ::= { dsTc 5 }

dsTcCRC OBJECT-TYPE
              SYNTAX  INTEGER {
              tcCrcEnable (1),
              tcCrcDisable (2)
              }
              ACCESS  read-write
              STATUS  mandatory
              DESCRIPTION
                      "The E1 terminal interface CRC generation/checking
                      setting. The possible values are:

                      VALUE             DESCRIPTION
                      tcCrcEnable(1)    Enable CRC generation/checking
                      tcCrcDisable(2)   Disable CRC generation/checking"
              ::= { dsTc 6 }

dsTcFasAlign     OBJECT-TYPE
              SYNTAX  INTEGER {
              tcFasWord (1),
              tcNonFasWord (2)
              }
              ACCESS  read-write
              STATUS  mandatory
              DESCRIPTION
                      "The E1 terminal interface Time Slot 0 NOT-FAS Word
                      setting. The possible values are:

                      VALUE             DESCRIPTION
                      tcFasWord(1)      Use the NOT-FAS word
                      tcNonFasWord(2)   Do not use the NOT-FAS word"
              ::= { dsTc 7 }

dsTcAis     OBJECT-TYPE
              SYNTAX  INTEGER {
              tcAisEnable (1),
              tcAisDisable (2)
              }
              ACCESS  read-write
              STATUS  mandatory
              DESCRIPTION
                      "This object controls the sending of Alarm Indication
                      Signal (AIS) alarms. The possible values are: 

                      VALUE             DESCRIPTION
                      tcAisEnable(1)    Enable sending AIS alarms
                      tcAisDisable(2)   Disable sending AIS alarms"
              ::= { dsTc 8 }

dsTcGenRfa     OBJECT-TYPE
              SYNTAX  INTEGER {
              tcGenRfaEnable (1),
              tcGenRfaDisable (2)
              }
              ACCESS  read-write
              STATUS  mandatory
              DESCRIPTION
                      "The status of sending E1 remote Frame Alarm into 
                      the TI during alarms. The Possible values are:

                      VALUE              DESCRIPTION
                      tcGenRfaEnable(1)  Enable RFA insertion 
                      tcGenRfaDisable(2) Disabled RFA insertion"
              ::= { dsTc 9 }

dsTcPassTiRfa     OBJECT-TYPE
              SYNTAX  INTEGER {
              tcPassTiRfaEnable (1),
              tcPassTiRfaDisable (2)
              }
              ACCESS  read-write
              STATUS  mandatory
              DESCRIPTION
                      "The status of sending the RFA received on the 
                      terminal interface out the network interface. This 
                      function is not possible on a DSU only, it must be 
                      an add/drop. This function only works if at least one 
                      channel is assigned to the TI. The Possible values are:

                      VALUE                  DESCRIPTION
                      tcPassTiRfaEnable(1)   Enable RFA re-generation
                      tcPassTiRfaDisable(2)  Disabled RFA re-generation"
              ::= { dsTc 10 }

--------------------------------------------------------------------
--  END -  datasmart Network Interface Configuration MIB variables
--------------------------------------------------------------------

--------------------------------------------------------------------
--  BEGIN -  datasmart Front Panel Configuration MIB variables
--------------------------------------------------------------------
 
dsFpFr56        OBJECT IDENTIFIER ::= { dsFp 1 }


dsFpFr56PwrLed     OBJECT-TYPE
              SYNTAX  INTEGER {
              fpLedIndeterminate (1),
              fpLedOff           (2),
              fpLedOnGreen       (3),
              fpLedBlinkGreen    (4)
              }
              ACCESS  read-only
              STATUS  mandatory
              DESCRIPTION
                      "The current state of the FP PWR LED.
                       The Possible values are:

                      VALUE              DESCRIPTION
                      fpLedIndeterminate (1)  LED is not present on unit
                      fpLedOff           (2)  LED is OFF
                      fpLedOnGreen       (3)  LED is ON and green
                      fpLedBlinkGreen    (4)  LED is blinking green"
              ::= { dsFpFr56 1 }

dsFpFr56DnldFailLed     OBJECT-TYPE
              SYNTAX  INTEGER {
              fpLedIndeterminate (1),
              fpLedOff           (2),
              fpLedOnRed         (3),
              fpLedBlinkRed      (4)
              }
              ACCESS  read-only
              STATUS  mandatory
              DESCRIPTION
                      "The current state of the FP DNLD/FAIL LED.
                       The Possible values are:

                      VALUE              DESCRIPTION
                      fpLedIndeterminate (1)  LED is not present on unit
                      fpLedOff           (2)  LED is OFF
                      fpLedOnRed         (3)  LED is ON and red
                      fpLedBlinkRed      (4)  LED is blinking red"
              ::= { dsFpFr56 2 }

dsFpFr56NiAlarmLed     OBJECT-TYPE
              SYNTAX  INTEGER {
              fpLedIndeterminate (1),
              fpLedOff           (2),
              fpLedOnRed         (3)
              }
              ACCESS  read-only
              STATUS  mandatory
              DESCRIPTION
                      "The current state of the FP NI ALARM LED.
                       The Possible values are:

                      VALUE              DESCRIPTION
                      fpLedIndeterminate (1)  LED is not present on unit
                      fpLedOff           (2)  LED is OFF
                      fpLedOnRed         (3)  LED is ON and red"
              ::= { dsFpFr56 3 }

dsFpFr56NiDataLed     OBJECT-TYPE
              SYNTAX  INTEGER {
              fpLedIndeterminate (1),
              fpLedOff           (2),
              fpLedOnGreen       (3)
              }
              ACCESS  read-only
              STATUS  mandatory
              DESCRIPTION
                      "The current state of the FP NI DATA LED.
                       The Possible values are:

                      VALUE              DESCRIPTION
                      fpLedIndeterminate (1)  LED is not present on unit
                      fpLedOff           (2)  LED is OFF
                      fpLedOnGreen       (3)  LED is ON and green"
              ::= { dsFpFr56 4 }

dsFpFr56TestLed     OBJECT-TYPE
              SYNTAX  INTEGER {
              fpLedIndeterminate (1),
              fpLedOff           (2),
              fpLedOnYellow      (3)
              }
              ACCESS  read-only
              STATUS  mandatory
              DESCRIPTION
                      "The current state of the FP TEST LED.
                       The Possible values are:

                      VALUE              DESCRIPTION
                      fpLedIndeterminate (1)  LED is not present on unit
                      fpLedOff           (2)  LED is OFF
                      fpLedOnYellow      (3)  LED is ON and yellow"
              ::= { dsFpFr56 5 }


dsFpFr56DpCtsTxLed     OBJECT-TYPE
              SYNTAX  INTEGER {
              fpLedIndeterminate (1),
              fpLedOff           (2),
              fpLedOnYellow      (3)
              }
              ACCESS  read-only
              STATUS  mandatory
              DESCRIPTION
                      "The current state of the FP DP CTS TX LED.
                       The Possible values are:

                      VALUE              DESCRIPTION
                      fpLedIndeterminate (1)  LED is not present on unit
                      fpLedOff           (2)  LED is OFF
                      fpLedOnYellow      (3)  LED is ON and yellow"
              ::= { dsFpFr56 6 }

dsFpFr56DpRtsRxLed     OBJECT-TYPE
              SYNTAX  INTEGER {
              fpLedIndeterminate (1),
              fpLedOff           (2),
              fpLedOnYellow      (3)
              }
              ACCESS  read-only
              STATUS  mandatory
              DESCRIPTION
                      "The current state of the FP DP RTS RX LED.
                       The Possible values are:

                      VALUE              DESCRIPTION
                      fpLedIndeterminate (1)  LED is not present on unit
                      fpLedOff           (2)  LED is OFF
                      fpLedOnYellow      (3)  LED is ON and yellow"
              ::= { dsFpFr56 7 }


dsFpFr56FrLinkLed     OBJECT-TYPE
              SYNTAX  INTEGER {
              fpLedIndeterminate (1),
              fpLedOff           (2),
              fpLedOnGreen       (3),
              fpLedBlinkGreen    (4)
              }
              ACCESS  read-only
              STATUS  mandatory
              DESCRIPTION
                      "The current state of the FP FRAME RELAY LINK LED.
                       The Possible values are:

                      VALUE              DESCRIPTION
                      fpLedIndeterminate (1)  LED is not present on unit
                      fpLedOff           (2)  LED is OFF
                      fpLedOnGreen       (3)  LED is ON and green
                      fpLedBlinkGreen    (4)  LED is blinking green"
              ::= { dsFpFr56 8 }

--------------------------------------------------------------------
--  END -  datasmart Front Penel Configuration MIB variables
--------------------------------------------------------------------

END
