-- MIB for ADTX
-- Created on January, 2003 by Jerrell Jay Arreza

ADTX-SMI DEFINITIONS ::= BEGIN

IMPORTS
    enterprises
            FROM RFC1155-SMI;

adtx      OBJECT IDENTIFIER ::= { enterprises 2653 }
-- MODULE-IDENTITY
--  LastUpdated
--    200301220000Z
--  OrgName
--    ADTX (Advanced Technology and Systems Co., Ltd.)
--  ContactInfo
--     Customer Service Officer
--
--     Postal:
--     Yokohama Business Park East Tower 9F
--     134 Goudo-cho, Hodogaya-ku, Yokohama-shi, Kanagawa-ken
--     240-0005
--     Japan
--
--     Tel: +81-45-334-0040
--
--     E-mail: cso@adtx.com
--  Descr
--    The Structure of Management Information for the ADTX enterprise.
--  RevDate
--    200322010000Z
--  RevDescr
--    The initial revision of this MIB module.


adtxReg             OBJECT IDENTIFIER ::= { adtx 1 }
-- Subtree for registrations

adtxGeneric         OBJECT IDENTIFIER ::= { adtx 2 }
-- Subtree for common object and event definitions

adtxProducts        OBJECT IDENTIFIER ::= { adtx 3 }
-- Subtree for specific object and event definitions

adtxExpr            OBJECT IDENTIFIER ::= { adtx 4 }
-- Subtree for experimental definitions



END
