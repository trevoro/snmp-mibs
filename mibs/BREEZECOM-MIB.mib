-- Title:      BREEZECOM  Private MIB
--             This Private MIB supports all BREEZECOM products, currently 
--             the following products are supported:
--             BreezeNet Product Line.
-- Version:    3.9
-- Date:       30 May 2000
-- By:         Guy Ezer.
-- Comments:   BREEZECOM agents also support the following Public MIBs:
--             MIB-II  ( RFC1213 )
--             BRIDGE - MIB  ( RFC1286 )


-- #include "rfc1155.smi"
-- #include "rfc1212.smi"
-- #include "rfc1215.smi"

BREEZECOM-MIB DEFINITIONS ::= BEGIN
   
IMPORTS enterprises FROM RFC1155-SMI
	IpAddress, OBJECT-TYPE FROM RFC1155-SMI
	Counter FROM RFC1155-SMI
	DisplayString FROM SNMPv2-TC
	TRAP-TYPE FROM RFC-1215;

-- IMPORTS
--     NetworkAddress, IpAddress,
--     Counter, Gauge, TimeTicks,  enterprises
-- FROM RFC-1155
--    OBJECT-TYPE, DisplayString
-- FROM RFC1213-MIB;
--    TRAP-TYPE
-- FROM RFC-1215;

--  PhysAddress ::= OCTET STRING (SIZE(6))

-- Some MIB compilers require that the following 6 lines which define the path
-- to BREEZECOM MIB are commented out:

-- mgmt           OBJECT IDENTIFIER ::= { iso org(3) dod(6) internet(1)  mgmt(2) }
-- mib            OBJECT IDENTIFIER ::= { mgmt 1  }
-- directory      OBJECT IDENTIFIER ::= { internet 1  }
-- experimental   OBJECT IDENTIFIER ::= { internet 3  }
-- private        OBJECT IDENTIFIER ::= { internet 4  }
-- enterprises    OBJECT IDENTIFIER ::= { private 1  }

	MacAddress 						  ::= OCTET STRING (SIZE(6))
	breezecom       OBJECT IDENTIFIER ::= { enterprises 710 }
	breezecomPrvRev OBJECT IDENTIFIER ::= { breezecom 3 }
	breezecomOID	OBJECT IDENTIFIER ::= { breezecom 4 }

--	Breezecom Object IDs group

	breezecomAP10	OBJECT IDENTIFIER ::= {	breezecomOID 1 }
	breezecomWB10	OBJECT IDENTIFIER ::= {	breezecomOID 2 }
	breezecomSA10	OBJECT IDENTIFIER ::= {	breezecomOID 3 }
	breezecomSA40	OBJECT IDENTIFIER ::= {	breezecomOID 4 }
--	breezecomSA120	OBJECT IDENTIFIER ::= {	breezecomOID 6 }

   brznetmib 		OBJECT IDENTIFIER ::= {	breezecomPrvRev 2}

-- BREEZENET private MIB parameters, for Wireless LAN systems management

brzSys OBJECT IDENTIFIER ::= {brznetmib 1}

sysCmd OBJECT IDENTIFIER ::= {brzSys 1}


-- *******************************************************************
-- *      General Command variables  
-- *******************************************************************

sysReset OBJECT-TYPE
      SYNTAX  INTEGER {  
		on  (1),
		off (2)
      	}
      ACCESS  read-write    
      STATUS  mandatory
      DESCRIPTION
      "Setting the value of this attribute to ON is interpreted as a reset
      command for the system. "
      ::= { sysCmd 1 }

sysSetDefaults OBJECT-TYPE
      SYNTAX  INTEGER {  
		on  (1),
		off (2)
      	}
      ACCESS  read-write    
      STATUS  mandatory
      DESCRIPTION
      "Setting the value of this attribute to ON will cause the system to 
      set the NVRAM parameters to the factory default values. These values 
      will become active after the next system reset "
      ::= { sysCmd 2 }

sysResetCounters OBJECT-TYPE
      SYNTAX  INTEGER {  
		on  (1),
		off (2)
      	}
      ACCESS  read-write    
      STATUS  mandatory
      DESCRIPTION
      "Setting the value of this attribute to ON will cause the system to 
       clear the performance counters."
      ::= { sysCmd 3 }

sysTrapEnable OBJECT-TYPE
      SYNTAX  INTEGER{			   
      	on  (1),
      	off (2)
      	} 
      ACCESS  read-write    
      STATUS  mandatory
      DESCRIPTION
      "Setting the value of this attribute to OFF will disable the system 
      from sending TRAPs. "
      ::= { sysCmd 4 }

sysTrapCounter OBJECT-TYPE
      SYNTAX  Counter			   
      ACCESS  read-only
      STATUS  mandatory
      DESCRIPTION
      "This attribute counts the total number of traps generated by the device,
       since initialization. "
      ::= { sysCmd 5 }

sysCarrierSense OBJECT-TYPE
		SYNTAX	INTEGER  
		ACCESS read-write
		STATUS mandatory
		DESCRIPTION	 
		"This attribute defines the carrier sense absolute threshold"
		::= { sysCmd 6 }

sysDeltaCarrierSense OBJECT-TYPE
		SYNTAX	INTEGER  
		ACCESS read-write
		STATUS mandatory
		DESCRIPTION	 
		"This attribute defines the carrier sense differential threshold"
		::= { sysCmd 7 }

sysPartialDefaults OBJECT-TYPE
      SYNTAX  INTEGER {  
		on (1),
		off (2)
      	}
      ACCESS  read-write    
      STATUS  mandatory
      DESCRIPTION
      "Setting the value of this attribute to ON will cause the system to 
      set the partial NVRAM parameters to the factory default values. These values 
      will become active after the next system reset "
      ::= { sysCmd 8 }

sysRunFromNonActiveCode OBJECT-TYPE
      SYNTAX  INTEGER{
		off (0),
		on  (1)
		}
      ACCESS  read-write    
      STATUS  mandatory
      DESCRIPTION
      "This attribute make you run from non active code. Automatic switch is
       done if the non active code is valid. To activate set to On.
       If the switch succeed no response will be sent to the SNMP browser."
      ::= { sysCmd 9 }

accessRights OBJECT IDENTIFIER ::= {sysCmd 10}


sysNoiseFloor OBJECT-TYPE
		SYNTAX	INTEGER  
		ACCESS read-write
		STATUS mandatory
		DESCRIPTION	 
		"This attribute defines the low RSSI threshold in DBM units.
		Allowed range is from -120 to -50 dbm."
		::= { sysCmd 11 }

sysExternalAmplifier OBJECT-TYPE
      SYNTAX  INTEGER {  
		on (1),
		off (0)
      	}
		ACCESS read-write
		STATUS mandatory
		DESCRIPTION	 
		"This attribute is set to 1 when external amplifier is connected 
		to the device and set to 0 when device is connected to anntena."
		::= { sysCmd 12 }

sysDisplayAccessRights OBJECT-TYPE
      SYNTAX  INTEGER {
		user(0),
		installer(1),
		authorized-technician(2)
		}
      ACCESS  read-only    
      STATUS  mandatory
      DESCRIPTION
      " This attribute Display the access rights of that station."
	  ::= { accessRights 1 }

sysChangeRightsToUSER OBJECT-TYPE
      SYNTAX  INTEGER {
		unchanged (0),
		change    (1)
		}
      ACCESS  read-write    
      STATUS  mandatory
      DESCRIPTION
      " This attribute let you change the access rights of that station
       to USER."
	  ::= { accessRights 2 }

sysChangeRightsToINSTALLER OBJECT-TYPE
      SYNTAX  DisplayString (SIZE(15))
      ACCESS  read-write    
      STATUS  mandatory
      DESCRIPTION
      " This attribute let you change the access rights of that station
       to INSTALLER.
      Type the Installer password for the desired access right."
	  ::= { accessRights 3 }

sysChangeRightsToTECHNICIAN OBJECT-TYPE
      SYNTAX  DisplayString (SIZE(20))
      ACCESS  read-write    
      STATUS  mandatory
      DESCRIPTION
      " This attribute let you change the access rights of that station
       to AUTHORIZED TECHNICIAN.
      Type the Technician password for the desired access right."
	  ::= { accessRights 4 }

sysChangeInstallerPassword OBJECT-TYPE
      SYNTAX  DisplayString (SIZE(9))
      ACCESS  read-write    
      STATUS  mandatory
      DESCRIPTION
      " This attribute let you change the Installer Password of that station.
      Type the new password, maximum 8 characters."
	  ::= { accessRights 5 }

sysParams OBJECT IDENTIFIER ::= {brzSys 2}


-- *******************************************************************
-- *      System level parameters  
-- *******************************************************************


brzHWMacAddress OBJECT-TYPE
     SYNTAX  MacAddress
     ACCESS  read-only    
     STATUS  mandatory
     DESCRIPTION
     "The Hardware MAC address of the device."
     ::= {sysParams 1 }


brzApplTunneling OBJECT-TYPE
      SYNTAX  INTEGER{
      	ipx (0),
		both (1),
		none (2),
      	apple-talk (3)
      	} 
      ACCESS  read-write    
      STATUS  mandatory
      DESCRIPTION
	  "This attribute specifies	the device tunneling mode, as follows:
	  ipx        -  The device will enable IPX tunneling only. 
	  apple-talk -  The device will enable AppleTalk tunneling only. 
	  none       -  The device will disable tunneling. 
	  both       -  The device will enable only IPX and AppleTalk tunneling."
      ::= { sysParams 2 }


brzPositiveBrg OBJECT-TYPE
      SYNTAX  INTEGER{
      	reject-unknown  (1),
      	forward-unknown (2),
		intelligent     (3),
		na 				(255)
      	} 
      ACCESS  read-write    				 
      STATUS  mandatory
      DESCRIPTION
      "This attribute specifies the Wired to Wireless LAN bridging
      mode at the AP, as follows:
	  reject-unknown  - The AP forwards to the Wireless LAN only 
	  					frames that are destined to associated stations. 
	  forward-unknown - The AP forwards to the Wireless LAN frames 
	  					destined to associated AND unknown addresses.
	  					This value should be used only for Wireless
	  					Bridge installations.  
	  intelligent	  - If connected to a wireless bridge, the AP 
	  				    automatically activates the Forward-Unknown
	  				    option.
	  na			  - A not applicable value, for non-AP devices."
	  ::= { sysParams 3 }


brzIpFilter OBJECT-TYPE
      SYNTAX  INTEGER{
      	on (1),
      	off(2),
		na (255)
      	} 
      ACCESS  read-write    
      STATUS  mandatory
      DESCRIPTION
      "Setting the value of this attribute to ON will cause the 
      system to filter all non-IP traffic to the Wireless LAN.
	  This should be used on environments where only IP (and ARP)
	  traffic is permitted."
--      This option is available ONLY on AP (na value assigned in	non-AP devices."
      ::= { sysParams 4 }


brzTranslationMode OBJECT-TYPE
      SYNTAX  INTEGER{
      	on  (1),
      	off (2)
      	} 
      ACCESS  read-write    
      STATUS  mandatory
      DESCRIPTION
      "When this attribute is set to ON, data frames are being translated
      for the Wireless LAN transmission. If it is set to OFF, tunneling of
      data frames apply.
      All devices within the same Wireless LAN network, must have the same
Translation Mode assigned."
      ::= { sysParams 5 }
					  

brzWIXSupport OBJECT-TYPE
      SYNTAX  INTEGER{
      	on  (1),
      	off (2)
      	} 
      ACCESS  read-write    
      STATUS  mandatory
      DESCRIPTION
      "This attribute applies to installations with collocated APs. When it
      is set to ON, a load balancing algorithm is activated, resulting with
      balanced Basic Service Sets (cells). 
      This option may be set only at some of the stations in the network."     
      ::= { sysParams 6 }


brzWlanNetID OBJECT-TYPE
   	  SYNTAX DisplayString (SIZE(31))
      ACCESS read-write
      STATUS mandatory
      DESCRIPTION
	  "This attribute identifies the Wireless LAN network name 
	  (Extended Service Set ID) for that device. Stations are not
	  allowed to associate to APs with different Net IDs."
	  ::= { sysParams 7 }


brzAuthenticationType OBJECT-TYPE
		SYNTAX	INTEGER  
		ACCESS read-only
		STATUS mandatory
		DESCRIPTION	 
		"This attribute indicates the authentication algorithm used during
		the authentication sequence.
		The value of this attribute is one of the following:
		1  - Open System,
		2  - Shared Key,
		20 - Special Authentication Algorithm (#0),
		21 - Special Authentication Algorithm (#1),
		22 - Special Authentication Algorithm (#2)."
		::= { sysParams 8 }


brzWlanRTNetID OBJECT-TYPE
    SYNTAX DisplayString (SIZE(31))
    ACCESS read-only
    STATUS mandatory
    DESCRIPTION
	  "This attribute identifies the run-time Wireless LAN network name 
	  (Extended Service Set ID) for that device. Stations are not
	  allowed to associate to APs with different Net IDs."
	  ::= { sysParams 9 }


brzApRedundancySupport OBJECT-TYPE
      SYNTAX  INTEGER{
      	on (1),
      	off (2),
		na (255)
      	} 
      ACCESS  read-write    
      STATUS  mandatory
      DESCRIPTION
      "Setting the value of this attribute to ON will cause the 
      Access-Point to discontinue sending beacons to the Wireless LAN
      after no multicast or unicast frames for the cell arrive from 
      the Ethernet during a period of 100 seconds.
      This option is available ONLY on AP (na value assigned in
      non-AP devices)."
      ::= { sysParams 10 }


brzWlanRelayUnicast OBJECT-TYPE
	 SYNTAX	INTEGER {
     	on (1),
     	off (2),
	 	na (255)
     	} 
	 ACCESS read-write
	 STATUS mandatory
	 DESCRIPTION	 
	 "This attribute enables the relaying of unicast frames on the 
	 WLAN within the BSS. Setting this attribute to OFF means that 
	 unicast frames received from the WLAN by the AP can only be 
	 passed to the Distribution System. Applicable only in AP's."
	 ::= { sysParams 11 }

brzWlanRelayBroadcast OBJECT-TYPE
	 SYNTAX	INTEGER  {
     	on (1),
     	off (2),
	 	na (255)
     	} 
	 ACCESS read-write
	 STATUS mandatory
	 DESCRIPTION	 
	 "This attribute enables the relaying of broadcast frames on the 
	 WLAN within the BSS. Setting this attribute to OFF means that 
	 broadcast frames received from the WLAN by the AP can only be 
	 passed to the Distribution System. Applicable only in AP's."
	 ::= { sysParams 12 }

brzApRedundancyLimit OBJECT-TYPE
      SYNTAX  INTEGER
		{na(255)}
      ACCESS  read-write    
      STATUS  mandatory
      DESCRIPTION
      "This attribute sets the time until an Access-Point discontinues 
      sending beacons to the Wireless LAN when no multicast or unicast 
      frames for the cell arrive from the Ethernet.
      This option is available ONLY on AP (na value assigned in
      non-AP devices)."
      ::= { sysParams 13 }

brzStaNumForLargeCW OBJECT-TYPE
      SYNTAX  INTEGER
      ACCESS  read-write    
      STATUS  mandatory
      DESCRIPTION
	  "This attribute sets the minimum number of stations in 
	  this cell that will cause this unit to use large CW,
	  else this unit will use the default CW.
	  (The value is in the range of 1-120)"
      ::= { sysParams 14 }


brzPowerMngMode OBJECT-TYPE
      SYNTAX  INTEGER{
      	disabled (1),
      	enabled (2)
      	} 
      ACCESS  read-write    
      STATUS  mandatory
      DESCRIPTION
      "This attribute describes the current power management mode of 
      the station. The allowed values are ACTIVE (for normal mode
      of operation), and POWER SAVE.
      An STA will always return an ACTIVE value."
      ::= { sysParams 15 }


brzACKDelayed OBJECT-TYPE
      SYNTAX  INTEGER{
      	on  (1),
      	off (2)
      	} 
      ACCESS  read-write    
      STATUS  mandatory
      DESCRIPTION
      "This attribute applies to installations with collocated APs. When it
      is set to ON, a load balancing algorithm is activated, resulting with
      balanced Basic Service Sets (cells). 
      This option may be set only at some of the stations in the network."     
      ::= { sysParams 16 }

brzDTIMPperiod OBJECT-TYPE
      SYNTAX  INTEGER
      ACCESS  read-write    
      STATUS  mandatory
      DESCRIPTION
      "This attribute defines the rate of DTIM frames. The value is expressed 
      in Beacon Intervals. This attribute is applicable only in AP's."     
      ::= { sysParams 17 }

brzPowerMngBitTestMode OBJECT-TYPE
      SYNTAX  INTEGER{
      	disabled (1),
      	enabled (2)
      	} 
      ACCESS  read-write    
      STATUS  mandatory
      DESCRIPTION
      "This attribute describes the current power management bit test mode of 
      the AP. The allowed values are DISABLED (for normal mode
      of operation), and ENABLED."
      ::= { sysParams 18 }

brzBeaconInterval OBJECT-TYPE
      SYNTAX  INTEGER
      ACCESS  read-write    
      STATUS  mandatory
      DESCRIPTION
      " This attribute defines the rate of Beacon frames. The value is expressed 
      in Dwells. This attribute is applicable only in AP's."     
      ::= { sysParams 19 }

brzPowerSaveSupport OBJECT-TYPE
      SYNTAX  INTEGER{
      	disabled (0),
      	enabled (1),
      	enabled-with-pm-bit(2)
      	} 
      ACCESS  read-write    
      STATUS  mandatory
      DESCRIPTION
      " This attribute defines the power save support.
      0 - Power Save support disabled
      1 - Power Save support enabled 
      2 - Enable Power Save support with PM bit test 
      This attribute is applicable only in AP's."     
      ::= { sysParams 20 }

brzWlanAssocAge OBJECT-TYPE
      SYNTAX  INTEGER
      ACCESS  read-write    
      STATUS  mandatory
      DESCRIPTION
      " This attribute defines the Association Aging Period."
      ::= { sysParams 21 }

brzEnableVoice OBJECT-TYPE
      SYNTAX  INTEGER{
      	disable (0),
      	enable  (1)
		}
      ACCESS  read-write    
      STATUS  mandatory
      DESCRIPTION
      " This attribute Enables voice priority over other transmissions.
       This attribute is applicable only in AP's."     
      ::= { sysParams 22 }

brzNonActiveCodeState OBJECT-TYPE
      SYNTAX  DisplayString (SIZE(25))
      ACCESS  read-only    
      STATUS  mandatory
      DESCRIPTION
      "This attribute displays the current non active code state.
      WARNING: Activate this attribute will cause substantial
      degradation in station throughput, also answer is delayed!!!"
      ::= { sysParams 26 }

brzDisplayNonActiveCodeVersion OBJECT-TYPE
      SYNTAX  DisplayString (SIZE(80))
      ACCESS  read-only    
      STATUS  mandatory
      DESCRIPTION
      " This attribute displays the active code version and the 
      non active code version."
      ::= { sysParams 27 }

brzIntelligentBridgingPeriod OBJECT-TYPE
      SYNTAX  INTEGER
      ACCESS  read-write    
      STATUS  mandatory
      DESCRIPTION
      " This attribute defines the Intelligent Bridging Period in seconds."
      ::= { sysParams 28 }


ipParams OBJECT IDENTIFIER ::= {brznetmib 2}

-- *********************************************************************
-- *      IP and SNMP related parameters  
-- *********************************************************************

trapHostsTable OBJECT-TYPE
    SYNTAX  SEQUENCE OF TrapHostsEntry
    ACCESS  not-accessible
    STATUS  mandatory
    DESCRIPTION
    "A list of trap-hosts entries."
    ::= { ipParams 1 }
  
trapHostsEntry OBJECT-TYPE
    SYNTAX  TrapHostsEntry
    ACCESS  not-accessible
    STATUS  mandatory
    DESCRIPTION
    "A trap-receiving host entry, containing
     trap-host objects for a particular host."
    INDEX  { trapHostsIndex }
    ::= { trapHostsTable 1 }

TrapHostsEntry ::=
    SEQUENCE {
    trapHostsIndex      INTEGER,
    trapIPaddress       IpAddress,
    trapCommunity       DisplayString
    }

trapHostsIndex OBJECT-TYPE
    SYNTAX  INTEGER
    ACCESS  read-only
    STATUS  mandatory
    DESCRIPTION
    "A unique value for each trap-host. Its value
    ranges between 1 and 3"
    ::= { trapHostsEntry 1 }

trapIPaddress OBJECT-TYPE
    SYNTAX  IpAddress
    ACCESS  read-write
    STATUS  mandatory
    DESCRIPTION
    "The IP address of the host to be sent all traps"
    ::= { trapHostsEntry 2 }

trapCommunity OBJECT-TYPE
    SYNTAX  DisplayString (SIZE (0..15))
    ACCESS  read-write
    STATUS  mandatory
    DESCRIPTION
    "The community of the host to be sent all traps"
    ::= { trapHostsEntry 3 }


ipAddr OBJECT-TYPE
    SYNTAX  IpAddress
    ACCESS  read-write
    STATUS  mandatory
    DESCRIPTION
    "The IP address of this device, used to access the device through any
     of its LAN Ports (Ethernet or WLAN)."
    ::= { ipParams 2 }

maskIP OBJECT-TYPE
    SYNTAX  IpAddress
    ACCESS  read-write
    STATUS  mandatory
    DESCRIPTION
    "The IP Network mask used by the IP entity when accessing devices through
    any of its LAN Ports (Ethernet or WLAN)."
    ::= { ipParams 3 }

readCommunity OBJECT-TYPE
    SYNTAX  DisplayString --(SIZE (0..20))
    ACCESS  read-write
    STATUS  mandatory
    DESCRIPTION
    "The device read community. If updated, it will be used after the
     next reset."
    ::= { ipParams 4 }

writeCommunity OBJECT-TYPE
    SYNTAX  DisplayString --(SIZE (0..20))
    ACCESS  read-write
    STATUS  mandatory
    DESCRIPTION
    "The device write community. If updated, it will be used after the
     next reset."
    ::= { ipParams 5 }

gatewayIPaddr OBJECT-TYPE
    SYNTAX  IpAddress
    ACCESS  read-write
    STATUS  mandatory
    DESCRIPTION
    "Gateway default IP address."
    ::= { ipParams 6 }

brzIPStack OBJECT-TYPE
      SYNTAX  INTEGER{
		disabled (1),
		enabled (0)
		}
      ACCESS  read-write    
      STATUS  mandatory
      DESCRIPTION
	  " This attribute defines whether to use IP stack or not."
      ::= { ipParams 7 }

brzWlan OBJECT IDENTIFIER ::= { brznetmib 3 }

brzWlanParams OBJECT IDENTIFIER ::= { brzWlan 1 }

-- **********************************************************************
-- *      WLAN parameters, applicable for both AP and STA devices
-- **********************************************************************
		
brzMaxRate  OBJECT-TYPE
		SYNTAX INTEGER (1..3) 
		ACCESS read-write
		STATUS mandatory
		DESCRIPTION	
	    "This attribute indicates the rate (in Mbits per
	    second) at which data will be transmitted across the
	    medium. The default value of this attribute shall be 3."
		::= { brzWlanParams 1 }

brzMobilLvl  OBJECT-TYPE
		SYNTAX INTEGER  {
		low(1),
		medium(2),
		high(3)
		} 
		ACCESS read-write
		STATUS mandatory
		DESCRIPTION	
	    "This attribute indicates the expected mobility level of 
	    the system.	The default value of this attribute is stationary."
		::= { brzWlanParams 2 }

brzAvrgRssi  OBJECT-TYPE
		SYNTAX INTEGER
			{na (255)}
		ACCESS read-only
		STATUS mandatory
		DESCRIPTION	
	    "A value representing the average Signal Strength for packets
	    received from the current AP. 
	    This attribute is applicable only for a station 
	    (An AP will always return a value of 255)."
		::= { brzWlanParams 3 }

brzWlanProtocol  OBJECT-TYPE
		SYNTAX INTEGER  
--		{
--		802-11 (10)
--		} 
		ACCESS read-write
		STATUS mandatory
		DESCRIPTION	
	    "This attribute specifies the MAC/PHY protocol, utilized by this system.
		This attribute is not write accessible for regular users."
		::= { brzWlanParams 4 }

brzWlanTrapThreashold	OBJECT-TYPE
-- (1..?-TBD)brzWlanQuality
   	SYNTAX INTEGER	   
    ACCESS read-write
    STATUS mandatory
    DESCRIPTION
	"This attribute specifies a threshold value, for sending the 
	WlanStatusTRAP. When the Wireless LAN quality drops below
	(or goes above) this value, a trap will be issued." 
		::= { brzWlanParams 5 }

brzWlanQuality	OBJECT-TYPE
   	SYNTAX INTEGER {
		excellent (1),
		good (2),
		medium (3),
		bad (4),
		unknown(10)
	} 
    ACCESS read-only
    STATUS mandatory
    DESCRIPTION
	"A measure for quality (and noise level) of the Wireless LAN."
    ::= { brzWlanParams 6 }

knownAPsTable OBJECT-TYPE  -- aKnownAPs in dot11, with additional quality information.
     SYNTAX  SEQUENCE OF KnownAPsEntry
     ACCESS  not-accessible
     STATUS  mandatory
     DESCRIPTION
     "A table of identities of the most recently known Access
     Points, and their signal quality."
     ::= { brzWlanParams 7 }

knownAPsEntry OBJECT-TYPE
    SYNTAX  KnownAPsEntry
    ACCESS  not-accessible
    STATUS  mandatory
    DESCRIPTION
    "An entry in the Known APs table."
    INDEX { knownAPsIndex }
    ::= { knownAPsTable 1 }

KnownAPsEntry ::=
    SEQUENCE {
    knownAPsIndex			INTEGER,
    knownAPsValue			MacAddress,
    knownAPsQuality			INTEGER,
	knownAPsAvrgRssi		INTEGER,
	knownAPsStatus			INTEGER,
	knownAPsLoadStations	INTEGER,
	knownAPsGoodBeacons		INTEGER,
	knownAPsTotalBeacons	INTEGER,
    knownAPsAvrgDbm			DisplayString (SIZE(10))
    }

knownAPsIndex OBJECT-TYPE
	    SYNTAX  INTEGER
	    ACCESS  read-only
	    STATUS  mandatory
	    DESCRIPTION
	    "A unique value, representing the index of the AP in the
	    Known APs table" 
	    ::= { knownAPsEntry 1 }

knownAPsValue OBJECT-TYPE
	   SYNTAX  MacAddress
	   ACCESS  read-write
	   STATUS  mandatory
	   DESCRIPTION
	   "This attributes specifies the address of a recently known AP. 
	   The default value of this attribute shall be null (an empty entry)." 
	   ::= { knownAPsEntry 2 }

knownAPsQuality OBJECT-TYPE
	   SYNTAX  INTEGER  {
	   poor (1),
	   good (2),
	   unknown (10)
	   }    
	   ACCESS  read-only
	   STATUS  mandatory
	   DESCRIPTION
	   "This attribute specifies the current reception quality of frames, 
	    transmitted by that AP.
	    At a station, a GOOD value indicates that the station can join
	    that AP." 
	   ::= { knownAPsEntry 3 }

knownAPsAvrgRssi  OBJECT-TYPE
		SYNTAX INTEGER    
		ACCESS read-only
		STATUS mandatory
		DESCRIPTION	
	    "A value representing the average Signal Strength for packets
	    received from that AP in RSSI units." 
		::= { knownAPsEntry 4 }

knownAPsStatus OBJECT-TYPE
	   SYNTAX  INTEGER {
	   valid   (1),
	   invalid (2)
	   }
	   ACCESS  read-write
	   STATUS  mandatory
	   DESCRIPTION
	   "The validity of the current entry, either invalid or valid."
	   ::= { knownAPsEntry 5 }

knownAPsLoadStations  OBJECT-TYPE
		SYNTAX INTEGER    
		ACCESS read-only
		STATUS mandatory
		DESCRIPTION	
	    "A value representing the number of stations associated to 
	    that AP." 
		::= { knownAPsEntry 6 }

knownAPsGoodBeacons  OBJECT-TYPE
		SYNTAX INTEGER    
		ACCESS read-only
		STATUS mandatory
		DESCRIPTION	
	    "A value representing the number of beacons received with Strength
	    more then join level from that AP." 
		::= { knownAPsEntry 7 }

knownAPsTotalBeacons  OBJECT-TYPE
		SYNTAX INTEGER    
		ACCESS read-only
		STATUS mandatory
		DESCRIPTION	
	    "A value representing the total number of beacons (good and bad) 
	    received from that AP." 
		::= { knownAPsEntry 8 }

knownAPsAvrgDbm  OBJECT-TYPE
		SYNTAX DisplayString (SIZE(10))    
		ACCESS read-only
		STATUS mandatory
		DESCRIPTION	
	    "A value representing the average Signal Strength for packets
	    received from that AP in DBN units." 
		::= { knownAPsEntry 9 }

brzLastBeacon  OBJECT-TYPE
	SYNTAX INTEGER    
	ACCESS read-only
	STATUS mandatory
	DESCRIPTION	
    "A value representing last dwell to receive beacon from that AP."
	::= { brzWlanParams 8 }

brzBadBeacons  OBJECT-TYPE
	SYNTAX INTEGER    
	ACCESS read-only
	STATUS mandatory
	DESCRIPTION	
    "A value representing the number of beacons received with Strength
    less then join level from that AP." 
	::= { brzWlanParams 9 }

brzLoadStations  OBJECT-TYPE
	SYNTAX INTEGER    
	ACCESS read-only
	STATUS mandatory
	DESCRIPTION	
	    "A value representing the number of stations associated to 
	    that AP." 
	::= { brzWlanParams 10 }

brzAvrgDBm  OBJECT-TYPE
		SYNTAX DisplayString (SIZE(10))
		ACCESS read-only
		STATUS mandatory
		DESCRIPTION	
	    "A value representing the average Signal Strength for packets
	    received from the current AP. 
	    This attribute is applicable only for a station 
	    (An AP will always return a value of -255)."
		::= { brzWlanParams 11 }

brzAP OBJECT IDENTIFIER ::= { brzWlan 2 }


bssInfo	OBJECT IDENTIFIER ::= { brzAP 1 }

-- ***********************************************************************
-- *  BSS related parameters, applicable only for the AP                 
-- ***********************************************************************


bssNumOfStations   	OBJECT-TYPE
      	SYNTAX  INTEGER   
		ACCESS  read-only    
		STATUS  mandatory
		DESCRIPTION
		"This attribute specifies the number of devices, that are
		currently associated with this AP."
		::= { bssInfo 1 }

bssNumOfStationsPeak   OBJECT-TYPE
      	SYNTAX  INTEGER   
		ACCESS  read-only    
		STATUS  mandatory
		DESCRIPTION
		"This attribute contains the maximum value that 
		bssNumOfStations has reached."
		::= { bssInfo 2 }
								 
bssCollectPerStationInfo OBJECT-TYPE
      SYNTAX  INTEGER{	
      	on (1),
      	off (2),
		na (255)  -- Not Applicable
      	} 
      ACCESS  read-write    
      STATUS  mandatory
      DESCRIPTION
      "When this attribute is set to ON, the AP accumulates	Wireless
      Link statistics per each station.   
	  This option is available only for the AP. At stations it is always
	  assigned with na (Not Applicable) value.  
      WARNING: Setting this attribute to ON can cause substantial
      degradation in cell throughput!!!"
      ::= { bssInfo 3 }

bssNumOfBeaconSent   OBJECT-TYPE
      	SYNTAX  INTEGER   
		ACCESS  read-only    
		STATUS  mandatory
		DESCRIPTION
		"This attribute contains the total beacons sent counter."
		::= { bssInfo 4 }
								 
bssNumOfBeaconLost   OBJECT-TYPE
      	SYNTAX  INTEGER   
		ACCESS  read-only    
		STATUS  mandatory
		DESCRIPTION
		"This attribute contains the total beacons lost counter."
		::= { bssInfo 5 }
								 
bssNumOfStationsAuthenticated   	OBJECT-TYPE
      	SYNTAX  INTEGER   
		ACCESS  read-only    
		STATUS  mandatory
		DESCRIPTION
		"This attribute specifies the number of devices, that are
		currently Authenticated with this AP."
		::= { bssInfo 6 }

bssNumOfStationsAuthenticatedPeak   OBJECT-TYPE
      	SYNTAX  INTEGER   
		ACCESS  read-only    
		STATUS  mandatory
		DESCRIPTION
		"This attribute contains the maximum value that 
		bssNumOfStationsAuthenticated has reached."
		::= { bssInfo 7 }
								 

-- **********************************************************************
-- *  The associated stations information, at the AP                 
-- **********************************************************************

bssApAdb	OBJECT IDENTIFIER ::= { brzAP 2 }


adbTable OBJECT-TYPE
		SYNTAX SEQUENCE OF AdbEntry
		ACCESS not-accessible
		STATUS mandatory
		DESCRIPTION
           "A table of the stations associated."
		::= { bssApAdb 1 }

adbEntry  OBJECT-TYPE
		SYNTAX AdbEntry
		ACCESS not-accessible
		STATUS mandatory
        DESCRIPTION
            "An entry in ADB table."
		INDEX { stAddress }
		::= { adbTable 1 }


AdbEntry ::= SEQUENCE {
 		stAddress			MacAddress,
		stType				INTEGER,
 		stCFMode			INTEGER, 
 		stMaxRate   		INTEGER,
 		stCurTxRate			INTEGER,
 		stRssi				INTEGER,
 		stPMMode			INTEGER,
		stTxFragments		Counter,
		stTxRetry			Counter,
		stTxRetryPercent	Counter,
		stTxFragments1M		Counter,
		stReTxFragments1M	Counter,
		stTxFragments2M		Counter,
		stReTxFragments2M	Counter,
		stTxFragments3M		Counter,
		stReTxFragments3M	Counter,
		stTxDroppedPackets	Counter,
		stRxFragments		Counter,
		stWlanStatus		INTEGER,
		stResetCounters		INTEGER,
 		stDbm				DisplayString (SIZE(30))
		}


stAddress  OBJECT-TYPE
		SYNTAX MacAddress 
		ACCESS read-only
		STATUS mandatory
		DESCRIPTION
		"The MAC Address of the station represented by this entry in the Association
		Data Base"
		::= { adbEntry 1 }

stCFMode  OBJECT-TYPE
		SYNTAX INTEGER {
      	on (1),
      	off (2)
		} 
		ACCESS read-only
		STATUS mandatory
		DESCRIPTION
	      "This attribute is set to ON if the station is in the
	      Contention Free Polling list of the AP." 
		::= { adbEntry 4 }

stMaxRate  OBJECT-TYPE
		SYNTAX INTEGER  
		ACCESS read-only
		STATUS mandatory
		DESCRIPTION	
	    "This attribute indicates the maximum rate (in Mbits per
	    second) at which that station transmits data across 
	    the Wireless medium."
		::= { adbEntry 5 }

stCurTxRate	   OBJECT-TYPE
		SYNTAX INTEGER  
		ACCESS read-only
		STATUS mandatory
		DESCRIPTION	 
		"The rate currently used by the AP to transmit packets 
		to this station"
		::= { adbEntry 6 }
		
stRssi	OBJECT-TYPE
		SYNTAX INTEGER  
		ACCESS read-only
		STATUS mandatory
		DESCRIPTION	
	    "A value representing the average Signal Strength for packets
	    received from that station in RSSI units.
	    This attribute is being updated only if sysCollectPerStationInfo
	    is set to ON."
		::= { adbEntry 7 }

stPMMode OBJECT-TYPE
		SYNTAX INTEGER {
		active (1),
		power-saved (2)
		} 
		ACCESS read-only
		STATUS mandatory
		DESCRIPTION
		"The current Power Management mode of this station
         Power saving mode enables WLAN units (such as laptops or hand-held devices)
         to conserve battery power. To enable this feature, first enable power saving 
         for the AP, and then enable power saving in the SA-PCR Card."
		::= { adbEntry 8 }

stTxFragments	OBJECT-TYPE
		SYNTAX Counter 
		ACCESS read-only
		STATUS mandatory
		DESCRIPTION	
		"This attribute counts the total number of fragments (including
		retransmissions), that were	transmitted to that	station over 
		the Wireless LAN.
	    It is updated only if sysCollectPerStationInfo is set to ON."
		::= { adbEntry 9 }

stTxFragments1M	OBJECT-TYPE
		SYNTAX Counter 
		ACCESS read-only
		STATUS mandatory
		DESCRIPTION	
		"This attribute counts the total number of fragments (including
		retransmissions), that were	transmitted to that	station over 
		the Wireless LAN in 1Mbps.
	    It is updated only if sysCollectPerStationInfo is set to ON."
		::= { adbEntry 10 }

stTxFragments2M	OBJECT-TYPE
		SYNTAX Counter 
		ACCESS read-only
		STATUS mandatory
		DESCRIPTION	
		"This attribute counts the total number of fragments (including
		retransmissions), that were	transmitted to that	station over 
		the Wireless LAN in 2Mbps.
	    It is updated only if sysCollectPerStationInfo is set to ON."
		::= { adbEntry 11 }

stTxFragments3M	OBJECT-TYPE
		SYNTAX Counter 
		ACCESS read-only
		STATUS mandatory
		DESCRIPTION	
		"This attribute counts the total number of fragments (including
		retransmissions), that were	transmitted to that	station over 
		the Wireless LAN in 3Mbps.
	    It is updated only if sysCollectPerStationInfo is set to ON."
		::= { adbEntry 12 }

stTxRetry	OBJECT-TYPE
		SYNTAX Counter 
		ACCESS read-only
		STATUS mandatory
		DESCRIPTION	
		"This attribute counts the total number of retransmissions  
		to that station, over  the Wireless LAN.
	    It is updated only if sysCollectPerStationInfo is set to ON."
		::= { adbEntry 13 }		
		
stTxDroppedPackets	 OBJECT-TYPE
		SYNTAX Counter 
		ACCESS read-only
		STATUS mandatory
		DESCRIPTION	
		"This attribute counts the number of transmit frames (data or
		management) to this station, that were dropped because of too
		many retransmissions.
	    It is updated only if sysCollectPerStationInfo is set to ON."
		::= { adbEntry 14 }
		
stRxFragments	 OBJECT-TYPE
		SYNTAX Counter 
		ACCESS read-only
		STATUS mandatory
		DESCRIPTION	
		"This attribute counts the total number of fragments (data and
		management) that have been received successfully from that 
		station, through the Wireless LAN.
	    It is updated only if sysCollectPerStationInfo is set to ON."
		::= { adbEntry 15 }

stWlanStatus OBJECT-TYPE
   SYNTAX  INTEGER  {
   poor (1),
   good (2),
   unknown (10)
   }    
   ACCESS  read-only
   STATUS  mandatory
   DESCRIPTION
   "This attribute specifies the current reception quality of frames, 
    transmitted by that station."
   ::= { adbEntry 16 }

stResetCounters OBJECT-TYPE
      SYNTAX  INTEGER {  
		on(1),
		off(2)
      }
      ACCESS  read-write    
      STATUS  mandatory
      DESCRIPTION
      "Setting the value of this attribute to ON, will clear the station 
      counters at the AP (clear the counters in that adbEntry). 
      Warning: Setting the value of this attribute to ON may cause 
      momentary degradation in performance"
      ::= {  adbEntry 17 }


stType  OBJECT-TYPE
		SYNTAX INTEGER {
      	sa-10      (1),
      	wb-10      (2),
		sa-40      (3),
		sa-pc      (4),
		breeze-new (5),
		unknown    (6)
		} 
		ACCESS read-only
		STATUS mandatory
		DESCRIPTION
	    "This attribute identifies the device type of the station." 
		::= { adbEntry 18 }


stTxRetryPercent   OBJECT-TYPE
		SYNTAX Counter 
		ACCESS read-only
		STATUS mandatory
		DESCRIPTION	
		"This attribute calculate the retransmitted percentage,
		that was retransmitted to that station over 
		the Wireless LAN."
		::= { adbEntry 19 }


stReTxFragments1M	OBJECT-TYPE
		SYNTAX Counter 
		ACCESS read-only
		STATUS mandatory
		DESCRIPTION	
		"This attribute counts the total number of fragments,
		that was retransmitted to that station over 
		the Wireless LAN in 1Mbps.
	    It is updated only if sysCollectPerStationInfo is set to ON."
		::= { adbEntry 20 }


stReTxFragments2M	OBJECT-TYPE
		SYNTAX Counter 
		ACCESS read-only
		STATUS mandatory
		DESCRIPTION	
		"This attribute counts the total number of fragments,
		that was retransmitted to that station over 
		the Wireless LAN in 2Mbps.
	    It is updated only if sysCollectPerStationInfo is set to ON."
		::= { adbEntry 21 }


stReTxFragments3M	OBJECT-TYPE
		SYNTAX Counter 
		ACCESS read-only
		STATUS mandatory
		DESCRIPTION	
		"This attribute counts the total number of fragments,
		that was retransmitted to that station over 
		the Wireless LAN in 2Mbps.
	    It is updated only if sysCollectPerStationInfo is set to ON."
		::= { adbEntry 22 }


stDbm	OBJECT-TYPE
		SYNTAX DisplayString (SIZE(10)) 
		ACCESS read-only
		STATUS mandatory
		DESCRIPTION	
	    "A value representing the average Signal Strength for packets
	    received from that station in DBM units.
	    This attribute is being updated only if sysCollectPerStationInfo
	    is set to ON."
		::= { adbEntry 23 }


brzSTA OBJECT IDENTIFIER ::= { brzWlan 3 }


brzCurrentAPMacAddress OBJECT-TYPE
     SYNTAX  MacAddress
     ACCESS  read-only    
     STATUS  mandatory
     DESCRIPTION
     "Hardware MAC address of the AP currently associated with.
      Available ONLY in station."
     ::= { brzSTA 1 }

brzLastAPMacAddress OBJECT-TYPE
     SYNTAX  MacAddress
     ACCESS  read-only    
     STATUS  mandatory
     DESCRIPTION
     "The Hardware MAC address of the last AP that the station
     was associated with.  
     Available ONLY in stations."
     ::= { brzSTA 2 }


brzPreferredAPMacAddress OBJECT-TYPE
     SYNTAX  MacAddress
     ACCESS  read-write    
     STATUS  mandatory
     DESCRIPTION
     "The Hardware MAC address of the preferred AP, to which the 
     station should associate when ever possible.
     Null value here indicates no preferences. 
     Available ONLY in stations."
     ::= { brzSTA 3 }

brzRoamToAPMacAddress OBJECT-TYPE
     SYNTAX  MacAddress
     ACCESS  read-write    	
     STATUS  mandatory
     DESCRIPTION
     "Setting this attribute to a specific AP MAC address, will 
     cause the station to roam immediately to that AP, if possible.
     Available ONLY for stations."
     ::= { brzSTA 4 }


brzCFMode OBJECT-TYPE
      SYNTAX  INTEGER{
      	on (1),
      	off (2),
		na (255) -- Not Applicable
      	} 
      ACCESS  read-only    
      STATUS  mandatory
      DESCRIPTION
      "This attribute is set to ON if the station required
      Contention Free services from the AP (hence it is in 
      the AP's Contention Free list).  
      This option is available ONLY on stations. A Not Applicable 
      value is returned for all APs."
      ::= { brzSTA 5 }

brzTx1MBitRate OBJECT-TYPE
     SYNTAX  Counter
     ACCESS  read-only    
     STATUS  mandatory
     DESCRIPTION
     "Total transmitted frames in 1 MBit rate."
     ::= { brzSTA 6 }

brzTx2MBitRate OBJECT-TYPE
     SYNTAX  Counter
     ACCESS  read-only    
     STATUS  mandatory
     DESCRIPTION
     "Total transmitted frames in 2 MBit rate."
     ::= { brzSTA 7 }

brzTx3MBitRate OBJECT-TYPE
     SYNTAX  Counter
     ACCESS  read-only    
     STATUS  mandatory
     DESCRIPTION
     "Total transmitted frames in 3 MBit rate."
     ::= { brzSTA 8 }

brzTotalRetx OBJECT-TYPE
     SYNTAX  MacAddress
     ACCESS  read-only    
     STATUS  mandatory
     DESCRIPTION
     "Total Retransmitted frames including all rates."
     ::= { brzSTA 9 }


brzRoamParams OBJECT IDENTIFIER ::= { brzWlan 4 }


brzRoamDecisionWin OBJECT-TYPE
      SYNTAX  INTEGER
      ACCESS  read-write    
      STATUS  mandatory
      DESCRIPTION
      "This parameter defines a minimum number of RSSI samples
      which is required to make a decision about the current
      WLAN channel quality. A new RSSI sample arrives with each
      incoming frame.
      Available ONLY in stations."
      ::= { brzRoamParams 1 }

brzRoamDecisionNumerator OBJECT-TYPE
      SYNTAX  INTEGER
      ACCESS  read-write    
      STATUS  mandatory
      DESCRIPTION
      "This parameter defines a maximum number of RSSI samples 
      that is allowed to be below brzRoamDecisionRSSIThreshold,
      among a number equal to brzRoamDecisionWin of the last arrived 
      samples. If a number of bad samples 
      (i.e. below brzRoamDecisionRSSIThreshold) exceeds one, which is
      defined by this parameter, the channel is considered as bad.
      Available ONLY in stations."
      ::= { brzRoamParams 2 }

brzRoamDecisionRSSIThreshold OBJECT-TYPE
      SYNTAX  INTEGER
      ACCESS  read-write    
      STATUS  mandatory
      DESCRIPTION
      "If an RSSI sample is bellow the value which is defined by 
      this parameter the sample is considered as bad.
      Available ONLY in stations."
      ::= { brzRoamParams 3 }

brzJoinDecisionRSSIThreshold OBJECT-TYPE
      SYNTAX  INTEGER
      ACCESS  read-write    
      STATUS  mandatory
      DESCRIPTION
      "A station will join a new AP only if the AP transmits with
      an RSSI quality above the value which is defined by this parameter.
      Available ONLY in stations.
      In AP's, this is the threshold for sending Bad WLAN Conditions traps. 
      If a station associated with the AP is heard at an RSII level below 
      this threshold, a Bad WLAN Conditions trap is sent by the AP."
      ::= { brzRoamParams 4 }

brzNeighboringBeacons OBJECT-TYPE
      SYNTAX  INTEGER
      ACCESS  read-write    
      STATUS  mandatory
      DESCRIPTION
      "This parameters defines once in how many dwell times the AP will send 
       a neighboring beacon. Available ONLY in AP's."
      ::= { brzRoamParams 5 }

brzNumberOfProbeResponses OBJECT-TYPE
      SYNTAX  INTEGER
      ACCESS  read-write    
      STATUS  mandatory
      DESCRIPTION
      "If a number of good RSSI samples coming from a neighbor is greater 
      than or equal to this parameter the neighbor might be selected for
      joining."
      ::= { brzRoamParams 6 }

brzNumberOfBeaconsForDisconnect OBJECT-TYPE
      SYNTAX  INTEGER
      ACCESS  read-write    
      STATUS  mandatory
      DESCRIPTION
      "This parameter defines a maximum number of consecutive not
      arrived Beacons that is allowed before a disconnect decision.
      Available ONLY in stations."
      ::= { brzRoamParams 7 }

brzMaxNumberOfScanning OBJECT-TYPE
      SYNTAX  INTEGER
      ACCESS  read-write    
      STATUS  mandatory
      DESCRIPTION
      "This parameter defines a maximum number of scanning Attempts 
      to perform before system reset. Zero is value for non reset. 
      Available ONLY in stations."
      ::= { brzRoamParams 8 }

brzNeighboringBeaconRate OBJECT-TYPE
      SYNTAX  INTEGER
      ACCESS  read-write    
      STATUS  mandatory
      DESCRIPTION
      "This parameter defines the Neighboring Beacon Rate in dwells.
      Zero is value for non Neighboring Beacons. 
      Available ONLY in AP's."
      ::= { brzRoamParams 9 }


brzCnt OBJECT IDENTIFIER ::= { brznetmib 4 }

-- *      BreezeCom's accumulating counters, for performance monitoring

-- ******************************************************************
-- *      BreezeCom special Distribution System	Counters
-- ******************************************************************

brzDSCnt OBJECT IDENTIFIER ::= { brzCnt 1 }

brzRxFromDS OBJECT-TYPE
      SYNTAX  Counter					   
      ACCESS  read-only    
      STATUS  mandatory
      DESCRIPTION
		"This attribute counts the total number of frames that have been
		received successfully from the Wired Distribution system."
      ::= { brzDSCnt 1 }

brzRxBadFromDS OBJECT-TYPE				
      SYNTAX  Counter					                    
      ACCESS  read-only    
      STATUS  mandatory
      DESCRIPTION
		"This attribute counts the number errored frames, received from the 
		Wired Distribution system."
      ::= { brzDSCnt 2 }

brzRxOctetsFromDS OBJECT-TYPE		 
      SYNTAX  Counter
      ACCESS  read-only    
      STATUS  mandatory
      DESCRIPTION
		"This attribute counts the total number of octets that have been
		received successfully from the Wired Distribution system."
      ::= { brzDSCnt 3 }

brzTxToDS OBJECT-TYPE						 
      SYNTAX  Counter
      ACCESS  read-only    
      STATUS  mandatory
      DESCRIPTION
		"This attribute counts the total number of frames that have been
		transmitted to the Wired Distribution system."
      ::= { brzDSCnt 4 }

brzMissedFrames OBJECT-TYPE						 
      SYNTAX  Counter
      ACCESS  read-only    
      STATUS  mandatory
      DESCRIPTION
		"This attribute counts the total number of missed frames that have missed
		the transmission to the Ethernet LAN."
      ::= { brzDSCnt 5 }

brzTxOctetsToDS OBJECT-TYPE		 
      SYNTAX  Counter
      ACCESS  read-only    
      STATUS  mandatory
      DESCRIPTION
		"This attribute counts the total number of octets that have been
		transmitted successfully to the Wired Distribution system."
      ::= { brzDSCnt 6 }

brzRxOctetsForwardToWlan OBJECT-TYPE		 
      SYNTAX  Counter
      ACCESS  read-only    
      STATUS  mandatory
      DESCRIPTION
		"This attribute counts the total number of octets that have been
		transmitted successfully to the Wireless LAN."
      ::= { brzDSCnt 7 }

brzRxForwardToWlan OBJECT-TYPE		 
      SYNTAX  Counter
      ACCESS  read-only    
      STATUS  mandatory
      DESCRIPTION
		"This attribute counts the total number of packets that have been
		transmitted successfully to the Wireless LAN."
      ::= { brzDSCnt 8 }

brzWlanCnt OBJECT IDENTIFIER ::= { brzCnt 2 }

-- ********************************************************************
-- *      BreezeCom special Wireless LAN Counters
-- ********************************************************************

brzTxWlanCnt OBJECT IDENTIFIER ::= { brzWlanCnt 1 }

brzTxPacketsToWlan OBJECT-TYPE
      SYNTAX  Counter
      ACCESS  read-only    
      STATUS  mandatory
      DESCRIPTION
		"This attribute counts the total number of frames (data and
		management) that have been transmitted to the Wireless LAN."
      ::= { brzTxWlanCnt 1 }

brzTxMSDUToWlan OBJECT-TYPE
      SYNTAX  Counter
      ACCESS  read-only    
      STATUS  mandatory
      DESCRIPTION
		"This attribute counts the total number of frames (data frames)
		that have been transmitted to the Wireless LAN."
      ::= { brzTxWlanCnt 2 }

brzDiscarded OBJECT-TYPE
      SYNTAX  Counter
      ACCESS  read-only    
      STATUS  mandatory
      DESCRIPTION
		"This attribute counts the number of data frames, that were 
		internally discarded in the system, instead of being transmitted 
		over the Wireless LAN. High values of this counter indicate
		either very high traffic volume, or a noisy environment 
		that prevents Wireless transmissions."
      ::= { brzTxWlanCnt 3 }

brzTxFragToWlan OBJECT-TYPE
      SYNTAX  Counter
      ACCESS  read-only    
      STATUS  mandatory
      DESCRIPTION
		"This attribute counts the total number of fragments (data and
		management) that have been transmitted to the Wireless LAN."
      ::= { brzTxWlanCnt 4 }

brzRetryOnWlan OBJECT-TYPE
      SYNTAX  Counter
      ACCESS  read-only    
      STATUS  mandatory
      DESCRIPTION
		"This attribute counts the total number of retransmitted  
		fragments, on the Wireless LAN."
      ::= { brzTxWlanCnt 5 }

brzFailedCountOnWlan OBJECT-TYPE  -- Equals to the dot11 aFailedCount. 
      SYNTAX  Counter
      ACCESS  read-only    
      STATUS  mandatory
      DESCRIPTION
		"This attribute counts the number of frames that were dropped 
		(not transmitted), due to the number of retransmits attempts
		exceeding the RetryMax value."  
      ::= { brzTxWlanCnt 6 }

brzRetryOnWlanPercent OBJECT-TYPE
      SYNTAX  Counter
      ACCESS  read-only    
      STATUS  mandatory
      DESCRIPTION
		"This attribute calculates the percentage of number frames  
		(to the data and management) that have been transmitted  
		successfully Wireless LAN."
      ::= { brzTxWlanCnt 7 }

brzRetryTxDataToWlan OBJECT-TYPE
      SYNTAX  Counter
      ACCESS  read-only    
      STATUS  mandatory
      DESCRIPTION
		"This attribute counts the total number of data frames
		that have been retransmitted to the Wireless LAN."
      ::= { brzTxWlanCnt 8 }

brzRetryTxDataToWlanPercent OBJECT-TYPE
      SYNTAX  Counter
      ACCESS  read-only    
      STATUS  mandatory
      DESCRIPTION
		"This attribute calculates the percentage of data frames
		that have been transmitted successfully to the Wireless LAN."
      ::= { brzTxWlanCnt 9 }

brzTotalTxPacketsToWlan OBJECT-TYPE
      SYNTAX  Counter
      ACCESS  read-only    
      STATUS  mandatory
      DESCRIPTION
		"This attribute counts the total number frames  
		(data and management) that have been transmitted to the 
		Wireless LAN."
      ::= { brzTxWlanCnt 10 }

brzTxErrTransmitions OBJECT IDENTIFIER ::= { brzTxWlanCnt 15 }

brzTxErrorAckTimeOut OBJECT-TYPE
      SYNTAX  Counter
      ACCESS  read-only    
      STATUS  mandatory
      DESCRIPTION
		"This attribute counts the total number of acknowledge timeouts
		 on the Wireless LAN."
      ::= { brzTxErrTransmitions 1 }

brzTxErrorAckCRC OBJECT-TYPE
      SYNTAX  Counter
      ACCESS  read-only    
      STATUS  mandatory
      DESCRIPTION
		"This attribute counts the total number of acknowledge CRC Errors
		on the Wireless LAN."
      ::= { brzTxErrTransmitions 2 }

brzTxErrorNoTimeUntilHop OBJECT-TYPE
      SYNTAX  Counter
      ACCESS  read-only    
      STATUS  mandatory
      DESCRIPTION
		"This attribute counts the total number of timeouts caused of on
		time until end of hop on the Wireless Cell."
      ::= { brzTxErrTransmitions 3 }

brzTxErrorUnderRunAndCTS OBJECT-TYPE
      SYNTAX  Counter
      ACCESS  read-only    
      STATUS  mandatory
      DESCRIPTION
		"This attribute counts the total number of errors caused by HW
		problems (Under Run)."
      ::= { brzTxErrTransmitions 4 }

brzTxErrorAbort OBJECT-TYPE
      SYNTAX  Counter
      ACCESS  read-only    
      STATUS  mandatory
      DESCRIPTION
		"This attribute counts the total number of errors caused by 
		frame abortion from Boori."
      ::= { brzTxErrTransmitions 5 }

brzTxErrorFrameReceived OBJECT-TYPE
      SYNTAX  Counter
      ACCESS  read-only    
      STATUS  mandatory
      DESCRIPTION
		"This attribute counts the total number of errors caused by 
		frame failure on the Wireless LAN."
      ::= { brzTxErrTransmitions 6 }

brzRxWlanCnt OBJECT IDENTIFIER ::= { brzWlanCnt 2 }
	  
brzRxPacketsFromWlan OBJECT-TYPE
      SYNTAX  Counter					                      
      ACCESS  read-only    
      STATUS  mandatory
      DESCRIPTION
		"This attribute counts the total number of frames (data and
		management) that have been received successfully from the 
		Wireless LAN."
      ::= { brzRxWlanCnt 1 }


brzRxMSDUFromWlan OBJECT-TYPE
      SYNTAX  Counter					                      
      ACCESS  read-only    
      STATUS  mandatory
      DESCRIPTION
		"This attribute counts the total number of MSDUs (data frames)
		that have been received successfully from the Wireless LAN."
      ::= { brzRxWlanCnt 2 }


brzRxFragFromWlan OBJECT-TYPE  -- Equals to the dot11 aReceivedFrameCount.
      SYNTAX  Counter					                      
      ACCESS  read-only    
      STATUS  mandatory
      DESCRIPTION
		"This attribute counts the number of fragments (data and 
		management), that have been received successfully from the 
		Wireless LAN."
      ::= { brzRxWlanCnt 3 }


brzRxBadFragFromWlan OBJECT-TYPE
      SYNTAX  Counter					                      
      ACCESS  read-only    
      STATUS  mandatory
      DESCRIPTION
		"This counter is incremented when an error is detected in a fragment,
		received from the Wireless LAN." 
      ::= { brzRxWlanCnt 4 }


brzRxDuplicateFragFromWlan OBJECT-TYPE  -- Equals to the dot11 aFrameDuplicateCount 
      SYNTAX  Counter					                      
      ACCESS  read-only    
      STATUS  mandatory
      DESCRIPTION
		"This counter is incremented when a duplicated fragment is received
		from the Wireless LAN." 
      ::= { brzRxWlanCnt 5 }


freqStatisticsTable OBJECT-TYPE
      SYNTAX  SEQUENCE OF FreqStatisticsEntry
      ACCESS  not-accessible
      STATUS  mandatory
      DESCRIPTION
    	"A table for the traffic statistics of each frequency."
      ::= {  brzRxWlanCnt 6 }


freqStatisticsEntry OBJECT-TYPE
    SYNTAX  FreqStatisticsEntry
    ACCESS  not-accessible
    STATUS  mandatory
    DESCRIPTION
    	"An entry in the Frequencies Statistics table."
    INDEX  { freqStatisticsIndex }
    ::= { freqStatisticsTable 1 }

FreqStatisticsEntry ::=
    SEQUENCE {
    freqStatisticsIndex INTEGER,
    freqNo				INTEGER,
    freqTotalReceived   Counter
    }

freqStatisticsIndex OBJECT-TYPE
    SYNTAX  INTEGER	 -- (1..79)
    ACCESS  read-only
    STATUS  mandatory
    DESCRIPTION
    "A unique value, representing the index of the frequency in the 
    hopping sequence table" 
    ::= { freqStatisticsEntry 1 }


freqNo OBJECT-TYPE
    SYNTAX  INTEGER -- (2..101)
    ACCESS  read-only
    STATUS  mandatory
    DESCRIPTION
    "This attributes specifies the channel number of the frequency, 
    for which this entry accumulates the statistics." 
    ::= { freqStatisticsEntry 2 }

freqTotalReceived OBJECT-TYPE
    SYNTAX  Counter    
    ACCESS  read-only
    STATUS  mandatory
    DESCRIPTION
	"This attribute counts the total number of frames (data and
	management) that have been received successfully from the 
	Wireless LAN, in that specific frequency."
    ::= { freqStatisticsEntry 3 }


brzRoamCnt OBJECT IDENTIFIER ::= { brzCnt 3 }

brzNumOfReassocRequests OBJECT-TYPE
      SYNTAX  Counter 
      ACCESS  read-only    
      STATUS  mandatory
      DESCRIPTION
      "For an AP: The number of Associations and ReAssociations requests, 
         received since the last reset of the AP. This counter is useful 
         for getting information about mobility activity on the BSS.
      For a Station: The number of Associations and ReAssociation requests 
         issued by the station since the last reset."
      ::= { brzRoamCnt 1 }

brzMngCnt OBJECT IDENTIFIER ::= { brzCnt 4 }

brzMngAP OBJECT IDENTIFIER ::= { brzMngCnt 1 }

probeResponseSent OBJECT-TYPE
      SYNTAX  Counter 
      ACCESS  read-only    
      STATUS  mandatory
      DESCRIPTION
	  "For an AP: Number of Probe response that sent."
      ::= { brzMngAP 1 }

probeResponseLost OBJECT-TYPE
      SYNTAX  Counter 
      ACCESS  read-only    
      STATUS  mandatory
      DESCRIPTION
	  "For an AP: Number of Probe response that got lost."
      ::= { brzMngAP 2 }

probeResponseSentRetx OBJECT-TYPE
      SYNTAX  Counter 
      ACCESS  read-only    
      STATUS  mandatory
      DESCRIPTION
	  "For an AP: Number of retransmitted Probe response frames that sent."
      ::= { brzMngAP 3 }

probeRequestRecive OBJECT-TYPE
      SYNTAX  Counter 
      ACCESS  read-only    
      STATUS  mandatory
      DESCRIPTION
	  "For an AP: Number of Probe request frames that has received."
      ::= { brzMngAP 4 }

assocResponseSent OBJECT-TYPE
      SYNTAX  Counter 
      ACCESS  read-only    
      STATUS  mandatory
      DESCRIPTION
	  "For an AP: Number of Association response frames that sent."
      ::= { brzMngAP 5 }

assocResponseLost OBJECT-TYPE
      SYNTAX  Counter 
      ACCESS  read-only    
      STATUS  mandatory
      DESCRIPTION
	  "For an AP: Number of Association response frames 
	  that got lost."
      ::= { brzMngAP 6 }
	  
assocResponseSentRetx OBJECT-TYPE
      SYNTAX  Counter 
      ACCESS  read-only    
      STATUS  mandatory
      DESCRIPTION
	  "For an AP: Number of retransmitted Association response
	  frames that sent."
      ::= { brzMngAP 7 }
	  
assocRequestRecive OBJECT-TYPE
      SYNTAX  Counter 
      ACCESS  read-only    
      STATUS  mandatory
      DESCRIPTION
	  "For an AP: Number of Association request frames that has received."
      ::= { brzMngAP 8 }
	  
reAssocRequestRecive OBJECT-TYPE
      SYNTAX  Counter 
      ACCESS  read-only    
      STATUS  mandatory
      DESCRIPTION
	  "For an AP: Number of ReAssociation request frames that has received."
      ::= { brzMngAP 9 }

brzMngSAWB OBJECT IDENTIFIER ::= { brzMngCnt 2 }

probRequestSent OBJECT-TYPE
      SYNTAX  Counter 
      ACCESS  read-only    
      STATUS  mandatory
      DESCRIPTION
	  "For WB or SA: Number of Probe request frames that sent." 
      ::= { brzMngSAWB 1 }

probResponceRecive OBJECT-TYPE
      SYNTAX  Counter 
      ACCESS  read-only    
      STATUS  mandatory
      DESCRIPTION
	  "For WB or SA: Number of received Probe response frames." 
      ::= { brzMngSAWB 2 }

authRequestSent OBJECT-TYPE
      SYNTAX  Counter 
      ACCESS  read-only    
      STATUS  mandatory
      DESCRIPTION
	  "For WB or SA: Number of Authentication request frames that sent."
      ::= { brzMngSAWB 3 }

authRequestSentRetx OBJECT-TYPE
      SYNTAX  Counter 
      ACCESS  read-only    
      STATUS  mandatory
      DESCRIPTION
	  "For WB or SA: Number of Retransmitted Authentication request frames that sent."
      ::= { brzMngSAWB 4 }

authResponceRecive OBJECT-TYPE
      SYNTAX  Counter 
      ACCESS  read-only    
      STATUS  mandatory
      DESCRIPTION
	  "For WB or SA: Number of received Authentication response frames."
      ::= { brzMngSAWB 5 }

assocRequestSent OBJECT-TYPE
      SYNTAX  Counter 
      ACCESS  read-only    
      STATUS  mandatory
      DESCRIPTION
	  "For WB or SA: Number of Association request frames that sent."
      ::= { brzMngSAWB 6 }

assocRequestSentRetx OBJECT-TYPE
      SYNTAX  Counter 
      ACCESS  read-only    
      STATUS  mandatory
      DESCRIPTION
	  "For WB or SA: Number of Retransmitted Association request frames that sent."
      ::= { brzMngSAWB 7 }

assocResponceRecive OBJECT-TYPE
      SYNTAX  Counter 
      ACCESS  read-only    
      STATUS  mandatory
      DESCRIPTION
	  "For WB or SA: Number of received Association response frames."
      ::= { brzMngSAWB 8 }


brzPSCnt OBJECT IDENTIFIER ::= { brzCnt 5 }

pSFreeEntries OBJECT-TYPE
      SYNTAX  Counter 
      ACCESS  read-only    
      STATUS  mandatory
      DESCRIPTION
	  "For an AP: Number of station free entries."
      ::= { brzPSCnt 1 }

pSInternallydiscarded OBJECT-TYPE
      SYNTAX  Counter 
      ACCESS  read-only    
      STATUS  mandatory
      DESCRIPTION
	  "For an AP: Number of Internally Discarded frames."
      ::= { brzPSCnt 2 }

pSstations OBJECT-TYPE
      SYNTAX  Counter 
      ACCESS  read-only    
      STATUS  mandatory
      DESCRIPTION
	  "For an AP: Number of power saved station connected to 
	  this AP."
      ::= { brzPSCnt 3 }

pSPowerSavingAged OBJECT-TYPE
      SYNTAX  Counter 
      ACCESS  read-only    
      STATUS  mandatory
      DESCRIPTION
	  "For an AP: Number of frames that were not transmitted 
	  due to the end of aging time."
      ::= { brzPSCnt 4 }

powreStationsTable OBJECT-TYPE
    SYNTAX  SEQUENCE OF PowreStationsEntry
    ACCESS  not-accessible
    STATUS  mandatory
    DESCRIPTION
    "A list of trap-hosts entries."
    ::= { brzPSCnt 5 }
  
powreStationsEntry OBJECT-TYPE
    SYNTAX  PowreStationsEntry
    ACCESS  not-accessible
    STATUS  mandatory
    DESCRIPTION
    "A trap-receiving host entry, containing
     trap-host objects for a particular host."
    INDEX  { powerSaveIndex }
    ::= { powreStationsTable 1 }

PowreStationsEntry ::=
    SEQUENCE {
	powerSaveIndex     INTEGER,
    powerSaveStationID INTEGER,
    powerSaveBuffered  INTEGER,
    powerSaveAged      INTEGER,
	powerSaveSent	   INTEGER,
	powerSaveQueueFull INTEGER
    }

powerSaveIndex OBJECT-TYPE
    SYNTAX  INTEGER
    ACCESS  read-only
    STATUS  mandatory
    DESCRIPTION
    "A unique value, representing the index of the frequency in the 
    hopping sequence table"
    ::= { powreStationsEntry 1 }

powerSaveStationID OBJECT-TYPE
    SYNTAX  INTEGER
    ACCESS  read-only
    STATUS  mandatory
    DESCRIPTION
    "The identifier numerator of the Station in the AP.
    Note : ID zero is Broadcast."
    ::= { powreStationsEntry 2 }

powerSaveBuffered OBJECT-TYPE
    SYNTAX  INTEGER
    ACCESS  read-only
    STATUS  mandatory
    DESCRIPTION
    "This attributes specifies how many messages are waiting 
    to that Station in the AP buffers"
    ::= { powreStationsEntry 3 }

powerSaveAged OBJECT-TYPE
    SYNTAX  INTEGER
    ACCESS  read-only
    STATUS  mandatory
    DESCRIPTION
    "This attributes specifies how many Stations were deleted
     after long time of waiting"
    ::= { powreStationsEntry 4 }

powerSaveSent OBJECT-TYPE
    SYNTAX  INTEGER
    ACCESS  read-only
    STATUS  mandatory
    DESCRIPTION
    "This attributes specifies how many messages were sent to that station"
    ::= { powreStationsEntry 5 }

powerSaveQueueFull OBJECT-TYPE
    SYNTAX  INTEGER
    ACCESS  read-only
    STATUS  mandatory
    DESCRIPTION
    "This attributes specifies how many messages were discarded 
    because the queue to that station was full"
    ::= { powreStationsEntry 6 }

brzTraps OBJECT IDENTIFIER ::= { brznetmib 5 }

brzTrapAPMacAddr	OBJECT-TYPE
   	SYNTAX	MacAddress
    ACCESS  read-only 
    STATUS  mandatory
    DESCRIPTION
	"The MAC address of an AP"
    ::= { brzTraps 1 }

brzTrapSTAMacAddr	OBJECT-TYPE
   	SYNTAX	MacAddress
    ACCESS  read-only  
    STATUS mandatory
    DESCRIPTION
	"The MAC address of a station device"
    ::= { brzTraps 2 }

brzTrapMacAddress	OBJECT-TYPE
   	SYNTAX	MacAddress
    ACCESS  read-only  
    STATUS mandatory
    DESCRIPTION
	"A STA or AP MAC address"
    ::= { brzTraps 3 }

brzTrapRssiQuality	OBJECT-TYPE
   	SYNTAX INTEGER
    ACCESS read-only  
    STATUS mandatory
    DESCRIPTION
	"The RSSI level of the signal received from the Access Point"
    ::= { brzTraps 4 }

brzTrapLastRssiQuality	OBJECT-TYPE
   	SYNTAX INTEGER
    ACCESS read-only  
    STATUS mandatory
    DESCRIPTION
	"The RSSI level of the signal received from the previous Access Point"
    ::= { brzTraps 5 }

brzTrapIndex	OBJECT-TYPE			   
   	SYNTAX INTEGER					   
    ACCESS read-only
    STATUS mandatory
    DESCRIPTION
	"Index number for future trap implementation "
    ::= { brzTraps 6 }

brzTrapText	OBJECT-TYPE
   	SYNTAX DisplayString
    ACCESS read-only
    STATUS mandatory
    DESCRIPTION
	"Textual string for future trap implementation "
    ::= { brzTraps 7 }

brzTrapToggle	OBJECT-TYPE
   	SYNTAX INTEGER{
		on  (1),
		off (2)
		}
    ACCESS read-only
    STATUS mandatory
    DESCRIPTION
	"A general ON/OFF toggle value, for the traps." 
    ::= { brzTraps 8 }

brzTrapSTAType	OBJECT-TYPE
	SYNTAX INTEGER {
      	sa10    (1),
      	wb10    (2),
		sa40    (3),
		sa-pc	(4),
		breeze-new (5),
		unknown    (6)
		} 
	ACCESS read-only
	STATUS mandatory
	DESCRIPTION
	"This attribute identifies the device type of the station." 
	::= { brzTraps 9 }

-- *********************    A P    T R A P S   ********************

brzAProamingIn TRAP-TYPE
	ENTERPRISE  breezecomAP10
    VARIABLES {
     	brzTrapSTAMacAddr, 	-- Station MAC address
     	brzTrapSTAType  	-- Station device type
        }
    DESCRIPTION
	  "A trap indicating that a station has roamed into this AP.
	   It contains the MAC address of the associated station
	   and the device type of that station."
	::= 1

brzAPassociated TRAP-TYPE
	ENTERPRISE  breezecomAP10
    VARIABLES {
     	brzTrapSTAMacAddr  	-- Station MAC address
        }
    DESCRIPTION
	  "An AP trap indicating that a new station was associated with
	  this AP. It contains the MAC address of the associated
	  station."
	::= 2

brzAPdisassociated TRAP-TYPE
	ENTERPRISE  breezecomAP10
    VARIABLES {
     	brzTrapSTAMacAddr  	-- Station MAC address
        }
    DESCRIPTION
	  "An AP trap indicating that the station dis-associated itself from 
	  the AP. The trap contains the MAC address of the disassociated 
	  station."
	::= 3

brzAPaging TRAP-TYPE
	ENTERPRISE  breezecomAP10
    VARIABLES {
     	brzTrapSTAMacAddr  	-- Station MAC address
        }
    DESCRIPTION
	  "An AP trap indicating that the station association was aged out,
	  and removed from that AP. The trap contains the MAC address
	  of the aging station"
	::= 4

brzAProamedOut TRAP-TYPE
	ENTERPRISE  breezecomAP10
    VARIABLES {
		brzTrapSTAMacAddr	-- Station MAC address
        }
    DESCRIPTION
	  "An AP trap indicating that a given station has roamed out from
	  this AP. The trap contains the MAC address of the roamed out station"
	::= 5

brzAPWlanStatusap TRAP-TYPE
	ENTERPRISE  breezecomAP10
    VARIABLES {
		brzTrapToggle,
		brzTrapMacAddress
        }
    DESCRIPTION
	  "An AP trap, indicating a change in the Wireless media  
	   conditions. An ON value is sent when the Wireless LAN 
	   quality drops below the brzWlanTrapThreashold value. 
	   A trap with an OFF value is sent if the quality improves,
	   exceeding the brzWlanTrapThreashold value.
	   The Wireless LAN quality value is also being sent."
	::= 7

brzWlanStatusOfStation TRAP-TYPE
	ENTERPRISE  breezecomAP10
    VARIABLES {
		brzTrapToggle,
		brzTrapMacAddress
        }
    DESCRIPTION
	  "An AP trap, indicating a change in the quality of the
	   Wireless connection, with a specific (associated) station.
	   An ON value indicates a specially bad connection, and an
	   OFF value is sent if the quality improves, exceeding a 
	   predetermined threshold value.
	   The brzTrapMacAddress contains the MAC address of the 
	   applicable station."  
	::= 8

brzGeneralAP TRAP-TYPE
	ENTERPRISE  breezecomAP10
    VARIABLES {
		brzTrapIndex,
        brzTrapText
        }
    DESCRIPTION
	  "An AP general purpose trap, 	
	   for future trap implementation."
	::= 9

-- ********************* T R A P S   W B ********************

brzWBassociated TRAP-TYPE
	ENTERPRISE  breezecomWB10
    VARIABLES {
	    brzLastAPMacAddress,		-- Old AP mac address
		brzTrapAPMacAddr,			-- New AP mac address
		brzTrapLastRssiQuality,		-- Average RSSI with old AP
		brzTrapRssiQuality			-- Average RSSI with new AP
    }
    DESCRIPTION
	  " A WB trap, indicating that the station became associated-with,
	   or has roamed-to, another AP. The trap contains the MAC address and 
	   the average RSSI level of the new AP. If the station was roaming, 
	   the MAC address of the old AP, and the RSSI level prior to roaming,
	   is also provided (for an association, the second address will 
	   appear as all-zeros)." 
	::= 6


brzWBWlanStatus TRAP-TYPE
	ENTERPRISE  breezecomWB10
    VARIABLES {
		brzTrapToggle,
		brzTrapMacAddress
        }
    DESCRIPTION
	  "A WB trap, indicating a change in the Wireless media  
	   conditions. An ON value is sent when the Wireless LAN 
	   quality drops below the brzWlanTrapThreashold value. 
	   A trap with an OFF value is sent if the quality improves,
	   exceeding the brzWlanTrapThreashold value.
	   The Wireless LAN quality value is also being sent."
	::= 7

brzGeneralWB TRAP-TYPE
	ENTERPRISE  breezecomWB10
    VARIABLES {
		brzTrapIndex,
        brzTrapText
        }
    DESCRIPTION
	  "A WB general purpose trap, 	
	   for future trap implementation."
	::= 9

-- ************************* T R A P S    S T A  ********************

brzSTAassociated TRAP-TYPE
	ENTERPRISE  breezecomSA10
    VARIABLES {
	    brzLastAPMacAddress,		-- Old AP mac address
		brzTrapAPMacAddr,			-- New AP mac address
		brzTrapLastRssiQuality,		-- Average RSSI with old AP
		brzTrapRssiQuality			-- Average RSSI with new AP
    }
    DESCRIPTION
	  " A station trap, indicating that the station became associated-with,
	   or has roamed-to, another AP. The trap contains the MAC address and 
	   the average RSSI level of the new AP. If the station was roaming, 
	   the MAC address of the old AP, and the RSSI level prior to roaming,
	   is also provided (for an association, the second address will 
	   appear as all-zeros)." 
	::= 6

brzSTAWlanStatus TRAP-TYPE
	ENTERPRISE  breezecomSA10
    VARIABLES {
		brzTrapToggle,
		brzTrapMacAddress
        }
    DESCRIPTION
	  "A STA trap, indicating a change in the Wireless media  
	   conditions. An ON value is sent when the Wireless LAN 
	   quality drops below the brzWlanTrapThreashold value. 
	   A trap with an OFF value is sent if the quality improves,
	   exceeding the brzWlanTrapThreashold value.
	   The Wireless LAN quality value is also being sent."
	::= 7

brzGeneralSTA TRAP-TYPE
	ENTERPRISE  breezecomSA10
    VARIABLES {
		brzTrapIndex,
        brzTrapText
        }
    DESCRIPTION
	  "A STA general purpose trap, 	
	   for future trap implementation."
	::= 9

-- *************************  T R A P S    S A 4 0   ********************

brzSA40associated TRAP-TYPE
	ENTERPRISE  breezecomSA40
    VARIABLES {
	    brzLastAPMacAddress,		-- Old AP mac address
		brzTrapAPMacAddr,			-- New AP mac address
		brzTrapLastRssiQuality,		-- Average RSSI with old AP
		brzTrapRssiQuality			-- Average RSSI with new AP
    }
    DESCRIPTION
	  " A SA-40 trap, indicating that the station became associated-with,
	   or has roamed-to, another AP. The trap contains the MAC address and 
	   the average RSSI level of the new AP. If the station was roaming, 
	   the MAC address of the old AP, and the RSSI level prior to roaming,
	   is also provided (for an association, the second address will 
	   appear as all-zeros)." 
	::= 6


brzSA40WlanStatus TRAP-TYPE
	ENTERPRISE  breezecomSA40
    VARIABLES {
		brzTrapToggle,
		brzTrapMacAddress
        }
    DESCRIPTION
	  "SA-40 trap, indicating a change in the Wireless media  
	   conditions. An ON value is sent when the Wireless LAN 
	   quality drops below the brzWlanTrapThreashold value. 
	   A trap with an OFF value is sent if the quality improves,
	   exceeding the brzWlanTrapThreashold value.
	   The Wireless LAN quality value is also being sent."
	::= 7

brzGeneralSA40 TRAP-TYPE
	ENTERPRISE  breezecomSA40
    VARIABLES {
		brzTrapIndex,
        brzTrapText
        }
    DESCRIPTION
	  "SA-40 general purpose trap, 	
	   for future trap implementation."
	::= 9

-- ******************** E N D   O F    T R A P S ********************

   brzdot11 OBJECT IDENTIFIER ::= { brznetmib 6 }

-- ******************************************************************
--	rev1dot11 - 801.11 Standard MIB elements 
-- ******************************************************************

-- Station Management Attributes
   dot11smt   		   OBJECT IDENTIFIER ::= { brzdot11 1 }

   dot11DefaultWEPKeys OBJECT IDENTIFIER ::= { dot11smt 3 }

dot11DefaultWEPKey1 OBJECT-TYPE
		SYNTAX DisplayString  
		ACCESS read-write
		STATUS mandatory
		DESCRIPTION	 
		"This attribute indicates the WEP secret key
		value corresponding to KeyID 1.
		The WEP secret key is logically WRITE-ONLY.
		Attempts to read this attribute shall return a string 
		of asterisks (enter exactly 10 Hex-Decimal digits)."
		::= {dot11DefaultWEPKeys 1 }

dot11DefaultWEPKey2 OBJECT-TYPE
		SYNTAX DisplayString  
		ACCESS read-write
		STATUS mandatory
		DESCRIPTION	 
		"This attribute indicates the WEP secret key
		value corresponding to KeyID 2.
		The WEP secret key is logically WRITE-ONLY.
		Attempts to read this attribute shall return a string 
		of asterisks (enter exactly 10 Hex-Decimal digits)."
		::= {dot11DefaultWEPKeys 2 }

dot11DefaultWEPKey3 OBJECT-TYPE
		SYNTAX DisplayString  
		ACCESS read-write
		STATUS mandatory
		DESCRIPTION	 
		"This attribute indicates the WEP secret key
		value corresponding to KeyID 3.
		The WEP secret key is logically WRITE-ONLY.
		Attempts to read this attribute shall return a string 
		of asterisks (enter exactly 10 Hex-Decimal digits)."
		::= {dot11DefaultWEPKeys 3 }

dot11DefaultWEPKey4 OBJECT-TYPE
		SYNTAX DisplayString  
		ACCESS read-write
		STATUS mandatory
		DESCRIPTION	 
		"This attribute indicates the WEP secret key
		value corresponding to KeyID 4.
		The WEP secret key is logically WRITE-ONLY.
		Attempts to read this attribute shall return a string 
		of asterisks (enter exactly 10 Hex-Decimal digits)."
		::= {dot11DefaultWEPKeys 4 }


   dot11PrivacyGrp	   OBJECT IDENTIFIER ::= { dot11smt 6 }

dot11Preauthentication OBJECT-TYPE
		SYNTAX INTEGER {  
			disable (0),   
			enable (1)
			}
		ACCESS read-write
		STATUS mandatory
		DESCRIPTION	 
		"This attribute, when true, enables Preauthentication algorithm."
		::= {dot11PrivacyGrp 1}

dot11PrivacyOptionImplemented OBJECT-TYPE
		SYNTAX INTEGER {  
			true (1),   
			false (2)
			}
		ACCESS read-only
		STATUS mandatory
		DESCRIPTION	 
		"This attribute, when true, shall indicate that 
		the 802.11 WEP option is implemented."
		::= {dot11PrivacyGrp 2}

dot11PrivacyInvoke OBJECT-TYPE
		SYNTAX	INTEGER  
		ACCESS read-only
		STATUS mandatory
		DESCRIPTION	 
		"This attribute indicates if a special mechanism is invoked,
		to protect the Wireless LAN transmissions.
		The value is one of the following:
		1 - Standard WEP,
		2 - No Encryption,
		20 - Special Encryption (#0),
		21 - Special Encryption (#1),
		22 - Special Encryption (#2)"
	::= {dot11PrivacyGrp 3 }

dot11WEPDefaultKeyID  OBJECT-TYPE
		SYNTAX INTEGER   -- (1..4)
		ACCESS read-write
		STATUS mandatory
		DESCRIPTION
		"This attribute shall indicate the use of the first,
		second, third or fourth DefaultWEPKey when set to values
		of one, two, three or four."
		::= {dot11PrivacyGrp 4}


-- MAC Attributes
   dot11mac   		OBJECT IDENTIFIER ::= { brzdot11 2 }
   
   dot11OperationGrp	OBJECT IDENTIFIER ::= { dot11mac 1 }

dot11MaxMulticastRate OBJECT-TYPE
		SYNTAX	INTEGER  
		ACCESS read-write
		STATUS mandatory
		DESCRIPTION	 
		"This attribute indicates the basic rate for multicast frames."
	::= {dot11OperationGrp 1 }

dot11DwellTime OBJECT-TYPE
		SYNTAX	INTEGER  
		ACCESS read-write
		STATUS mandatory
		DESCRIPTION	 
		"This attribute indicates the dwell time in Kilo-microsecond
		Allowed Values for version 5.x.x and higher are between 19..390.
		For older versions values are between 1 - 3.
		This attribute is available only in AP's."
	::= {dot11OperationGrp 2 }

dot11RTSThreshold OBJECT-TYPE
		SYNTAX	INTEGER  
		ACCESS read-write
		STATUS mandatory
		DESCRIPTION	 
		"This attribute indicates the number of bytes in an 
		MPDU (frame), above which an RTS/CTS handshake will be
		performed. Setting this attribute to be larger than the
		maximum frame size, will prevent the RTS/CTS handshake 
		for frames transmitted by this station."
	::= {dot11OperationGrp 3 }

dot11ShortRetryLimit OBJECT-TYPE
		SYNTAX	INTEGER  
		ACCESS read-write
		STATUS mandatory
		DESCRIPTION	 
		"This attribute indicates the number of retransmission
		attempts made, before a failure condition is indicated.
		Values between 0..20 ."
	::= {dot11OperationGrp 4 }
 
dot11DwellRetryLimit OBJECT-TYPE
		SYNTAX	INTEGER  
		ACCESS read-write
		STATUS mandatory
		DESCRIPTION	 
		"This attribute indicates the number of retransmission
		attempts made in several Dwells, before a failure condition 
		is indicated. Values between 0..9 ."
	::= {dot11OperationGrp 5 }
 
dot11FragmentationThreshold OBJECT-TYPE
		SYNTAX	INTEGER  
		ACCESS read-write
		STATUS mandatory
		DESCRIPTION	 
		"This attribute specifies the current maximum size, in octets,
		of the MPDU that will be delivered to the PHY. A frame will be 
		broken into fragments if its size exceeds the value of this 
		attribute, after adding MAC header and tailors.
		The value is one of the following:
		   1 -  560 octets, 
		   2 -  800 octets,
		   3 - 1518 octets."
	::= {dot11OperationGrp 6 }

dot11ShortRetryLimitForVoice OBJECT-TYPE
		SYNTAX	INTEGER  
		ACCESS read-write
		STATUS mandatory
		DESCRIPTION	 
		"This attribute indicates the number of retransmission for voice
		attempts made, before a failure condition is indicated.
		Values between 0..9 . This option is only for AP's."
	::= {dot11OperationGrp 7 }
 
dot11DwellRetryLimitForVoice OBJECT-TYPE
		SYNTAX	INTEGER  
		ACCESS read-write
		STATUS mandatory
		DESCRIPTION	 
		"This attribute indicates the number of retransmission for voice
		attempts made in several Dwells, before a failure condition 
		is indicated. Values between 0..5 . This option is only for AP's."
	::= {dot11OperationGrp 8 }
 
-- Resource Type ID
   dot11res			OBJECT IDENTIFIER ::= { brzdot11 3 }

   dot11resAttribute	OBJECT IDENTIFIER ::= { dot11res 8 }
   dot11ResourceInfo    OBJECT IDENTIFIER ::= {	dot11resAttribute 2}

dot11CurrentStationStatus OBJECT-TYPE
   	SYNTAX DisplayString (SIZE(30))
    ACCESS read-only
    STATUS mandatory
    DESCRIPTION
	"This attribute identifies the current Station Wlan status.
	This attribute is not available in AP's."
     ::= {dot11ResourceInfo 1 }

dot11TotalNumberOfAssocSinceLastReset OBJECT-TYPE
   	SYNTAX Counter
    ACCESS read-only
    STATUS mandatory
    DESCRIPTION
	"This attribute identifies how many time the device Associated
	 since startup."
     ::= {dot11ResourceInfo 2 } 
 								 
dot11manufacturerName OBJECT-TYPE
   	SYNTAX DisplayString (SIZE(20))
    ACCESS read-only
    STATUS mandatory
    DESCRIPTION
	"This attribute identifies the manufacturer of the resource."
     ::= { dot11ResourceInfo 3 }

dot11manufacturerProductName OBJECT-TYPE
   	SYNTAX DisplayString (SIZE(30))
    ACCESS read-only
    STATUS mandatory
    DESCRIPTION
	"This attribute identifies the manufacturer product name of 
	the resource."
     ::= {dot11ResourceInfo 4 }

dot11manufacturerProductVersion OBJECT-TYPE
   	SYNTAX DisplayString (SIZE(20))
    ACCESS read-only
    STATUS mandatory
    DESCRIPTION
	"This attribute identifies the manufacturer's product version 
	of the resource." 
     ::= {dot11ResourceInfo 5 }

-- PHY group
   dot11phy   		OBJECT IDENTIFIER ::= { brzdot11 4 }

   dot11PhyOperationGrp	OBJECT IDENTIFIER ::= { dot11phy 1 }

dot11CurrentRegDomain OBJECT-TYPE
		SYNTAX	INTEGER {
		    ethairnet  	(0),
			usa         (16),   
			canada      (32),   
			europe      (48),   
			spain       (49),   
			france      (50),   
			europe-dd   (55),   
			netherlands (56),   
			japan       (64),   
			korea       (65),   
			israel      (72),   
			australia   (73),   
			proprietary (96)   
		}
		ACCESS read-write
		STATUS mandatory
		DESCRIPTION	 
		"This attribute specifies the regularity domain, for the 
		radio operation of this device. 
		This integer contains an 8 bit value, as defined below:
		 00h - EthAirNet, 10h - USA, 20h - Canada, 30h - Europe, 31h - Spain,
		 32h - France, 37h - Europe Double Deviation, 38h - Netherlands, 
		 40h - Japan, 41h - Korea, 48h - Israel, 49h - Australia,
		 60h - Proprietary. "
	::= {dot11PhyOperationGrp 3 }


   dot11PhyAntennaGrp 	OBJECT IDENTIFIER ::= { dot11phy 3 }

dot11CurrentTxAntenna OBJECT-TYPE  
		SYNTAX	INTEGER    
		ACCESS read-write
		STATUS mandatory
		DESCRIPTION	 
		"This attribute specifies the current antenna being used 
		to transmit. The value is one of the following:
		 0 - Intelligent antennas selection, 
		 1 - Transmitting only with antenna 1,
		 2 - Transmitting always with antenna 2."
	::= {dot11PhyAntennaGrp 2 }


    dot11PhyTxPwrGrp	OBJECT IDENTIFIER ::= { dot11phy 4 }

dot11CurrentTxPwrLvl OBJECT-TYPE  
		SYNTAX	INTEGER{
			low(0),
			high(1)
			}    
		ACCESS read-write
		STATUS mandatory
		DESCRIPTION	 
		"This attribute specifies the power level, currently being
		used to transmit data. The value is one of the following:
		 0 - Low, or 1 - High. "
	::= {dot11PhyTxPwrGrp 11 }


   dot11PhyFHSSGrp 	OBJECT IDENTIFIER ::= { dot11phy 5 }


dot11CurrentDwellTime OBJECT-TYPE  
		SYNTAX	INTEGER   
		ACCESS read-write
		STATUS mandatory
		DESCRIPTION	 
		"This attribute specifies the current time, in Kilo-microseconds,
		that the radio operates on a single channel.
		The value is from 19 - 390. 
		The same Dwell Time value should be assigned to all the
		devices within the same Wireless LAN network."
	::= {dot11PhyFHSSGrp 5 }


dot11CurrentSet OBJECT-TYPE  
		SYNTAX	INTEGER    
		ACCESS read-write
		STATUS mandatory
		DESCRIPTION	 
		"This attribute represents the current set of patterns that 
		the device is using to determine the hop sequence.
		The range of values is 1 to 3, and the default is 1."
	::= {dot11PhyFHSSGrp 6 }


dot11CurrentPattern OBJECT-TYPE
		SYNTAX	INTEGER  
		ACCESS read-write
		STATUS mandatory
		DESCRIPTION	 
		"This attribute represents the current pattern that the  
		device is using to determine the hop sequence."
	::= { dot11PhyFHSSGrp 7 }
																		
dot11MultySupport			OBJECT IDENTIFIER ::= { brzdot11 5 }

dot11MultyRateSupport OBJECT-TYPE	
		SYNTAX	INTEGER{
			disabled (0),
			enabled (1)
			}  
		ACCESS read-write
		STATUS mandatory
		DESCRIPTION	 
		"This attribute indicates the multi cast rate support."
	::= {dot11MultySupport 1 }

dot11MultyRateDecisionWindow OBJECT-TYPE	
		SYNTAX	INTEGER  
		ACCESS read-write
		STATUS mandatory
		DESCRIPTION	 
		"This attribute indicates the multi cast rate decision 
		window size."
	::= {dot11MultySupport 2 }

dot11Maintenance			OBJECT IDENTIFIER ::= { brzdot11 6 }

dot11WaitforAssociationAddress OBJECT-TYPE	
		SYNTAX INTEGER{
			use-mine (0),
			get-from-ethernet (1)
			}
		ACCESS read-write
		STATUS mandatory
		DESCRIPTION	 
		"This attribute indicates the station mac-address.
		0 - Use mine
		1 - Wait for update via Ethernet
		Available only for Stations."
	::= {dot11Maintenance 1 }

dot11JapanCallSign OBJECT-TYPE	
		SYNTAX DisplayString (SIZE(17))  
		ACCESS read-write
		STATUS mandatory
		DESCRIPTION	 
		"This attribute indicates the Japan call sign string.
		Available only for Japan Standard."
	::= {dot11Maintenance 2 }

END
