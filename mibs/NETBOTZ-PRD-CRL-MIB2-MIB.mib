NETBOTZ-PRD-CRL-MIB2-MIB DEFINITIONS ::= BEGIN

IMPORTS
   OBJECT-TYPE FROM RFC-1212
	DisplayString FROM RFC1213-MIB
	TimeTicks FROM RFC1155-SMI
	netBotz-prd-crawlers FROM NETBOTZ-PRODUCTS-MIB;

netbotz-crawlers OBJECT IDENTIFIER
                     ::= { netBotz-prd-crawlers 5528 }
netBotz-prd-crl-mib2 OBJECT IDENTIFIER
                     ::= { netbotz-crawlers 1 }
netBotz-prd-crl-mib2if OBJECT IDENTIFIER
                     ::= { netbotz-crawlers 2 }

netBotz-prd-crl-mib2-ping OBJECT-TYPE
	SYNTAX		INTEGER
	ACCESS		read-only
	STATUS		mandatory
	DESCRIPTION	"Netbotz device ping. This object indicates the status of a ping
	on a device monitored by a Netbotz device."
	REFERENCE 	"Netbotz Device Ping"
	::= { netBotz-prd-crl-mib2 3 }

netBotz-prd-crl-mib2-uptime OBJECT-TYPE
	SYNTAX		TimeTicks
	ACCESS		read-only
	STATUS		mandatory
	DESCRIPTION	"The uptime of a device monitored by a Netbotz device."
	REFERENCE 	"Netbotz Uptime"
	::= { netBotz-prd-crl-mib2 8 }

netBotz-prd-crl-mib2-snmpstatus OBJECT-TYPE
	SYNTAX		DisplayString
	ACCESS		read-only
	STATUS		mandatory
	DESCRIPTION	"The SNMP status of a device monitored by a Netbotz device."
	REFERENCE 	"Netbotz SNMP Status"
	::= { netBotz-prd-crl-mib2 9 }

netBotz-prd-crl-mib2if-opstatus OBJECT-TYPE
	SYNTAX		INTEGER
	ACCESS		read-only
	STATUS		mandatory
	DESCRIPTION	"The operational status of a device monitored by a Netbotz device."
	REFERENCE 	"Netbotz Operational Status"
	::= { netBotz-prd-crl-mib2if 6 }

END
