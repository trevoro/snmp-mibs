-- *********************************************************************
-- ciscoEntitySensorCapability MIB
--
-- AGENT-CAPABILITIES MIB for CISCO-ENTITY-SENSOR-MIB 
--
-- March 2003, Feng Luo
--
-- Copyright(c) 2003, 2004, 2005, 2006 by Cisco Systems,Inc.
--
-- *********************************************************************

CISCO-ENTITY-SENSOR-CAPABILITY DEFINITIONS ::= BEGIN
IMPORTS
        MODULE-IDENTITY
                FROM SNMPv2-SMI
        AGENT-CAPABILITIES
                FROM SNMPv2-CONF
        ciscoAgentCapability
                FROM CISCO-SMI;   

ciscoEntitySensorCapability MODULE-IDENTITY
        LAST-UPDATED        "200606290000Z"
        ORGANIZATION        "Cisco Systems, Inc."
        CONTACT-INFO
                "       Cisco Systems
                        Customer Service

                Postal: 170 W Tasman Drive
                        San Jose, CA  95134
                        USA

                        Tel: +1 800 553-NETS

                E-mail: cs-wanatm@cisco.com
                        cs-lan-switch-snmp@cisco.com"
        DESCRIPTION
                "The Agent capabilities for CISCO-ENTITY-SENSOR-MIB."

        REVISION        "200606290000Z"
        DESCRIPTION
                "Added capability statement
                 cEntitySensorCapCatOSV08R0601."
        REVISION        "200509150000Z"
        DESCRIPTION
                "entSensorThresholdSeverity, entSensorThresholdRelation
                 , entSensorThresholdValue are read-only objects for
                 cEntitySensorCapV12R0119ECat6K,
                 cEntitySensorCapV12R0214SXCat6K,
                 cEntitySensorCapCatOSV08R0101."
        REVISION        "200504220000Z"
        DESCRIPTION
                "Added capability statement
                 cEntitySensorCapMDS3R0."
        REVISION        "200409090000Z"
        DESCRIPTION
                "Added cEntitySensorCapabilityV5R015 for 
                 MGX8850 release 5.0.15."

        REVISION        "200308120000Z"
        DESCRIPTION
                "- Added cEntitySensorCapV12R0119ECat6K for IOS
                   12.1(19)E on Catalyst 6000/6500 and Cisco
                   7600 series devices.
                 - Added cEntitySensorCapV12R0214SXCat6K for IOS
                   12.2(14)SX on Catalyst 6000/6500 and Cisco
                   7600 series devices.
                 - Added ciscoEsCapabilityCatOSV81R1 for
                   Cisco CatOS 8.1(1)."

        REVISION        "200303130000Z"
        DESCRIPTION
                "Initial version of this MIB module."
        ::= { ciscoAgentCapability 350 }

ciscoEntitySensorCapabilityV5R000 AGENT-CAPABILITIES

    PRODUCT-RELEASE     "MGX8850 Release 5.0."
    STATUS              current
    DESCRIPTION         "Agent capabilities for CISCO-ENTITY-SENSOR-MIB 
                         of Voice Switch Service Module(VXSM) in 
                         Release 5.0.0."

    SUPPORTS            CISCO-ENTITY-SENSOR-MIB
        INCLUDES        { entitySensorValueGroup, 
                          entitySensorThresholdGroup }

        VARIATION       entSensorType
            SYNTAX      INTEGER {
                            voltsDC(4),
                            celsius(8)   
                        }
            DESCRIPTION "Information limited on VXSM."

        VARIATION       entSensorScale
            SYNTAX      INTEGER {
                            milli (8),
                            units (9)   
                        }
            DESCRIPTION "Information limited on VXSM."

        VARIATION       entSensorPrecision
            ACCESS      not-implemented
            DESCRIPTION "Not supported."
    
        VARIATION       entSensorValueTimeStamp
            ACCESS      not-implemented
            DESCRIPTION "Not supported."

        VARIATION       entSensorValueUpdateRate
            ACCESS      not-implemented
            DESCRIPTION "Not supported." 

    ::= { ciscoEntitySensorCapability 1 }

cEntitySensorCapV12R0119ECat6K AGENT-CAPABILITIES
    PRODUCT-RELEASE     "Cisco IOS 12.1(19)E on Catalyst 6000/6500
                         and Cisco 7600 series devices."
    STATUS              current
    DESCRIPTION         "CISCO-ENTITY-SENSOR-MIB capabilities."

    SUPPORTS            CISCO-ENTITY-SENSOR-MIB
        INCLUDES        {
                            entitySensorValueGroup,
                            entitySensorThresholdGroup,
                            entitySensorThresholdNotificationGroup
                        }
        VARIATION       entSensorThresholdSeverity
            ACCESS      read-only
            DESCRIPTION "write access is not supported."

        VARIATION       entSensorThresholdRelation
            ACCESS      read-only
            DESCRIPTION "write access is not supported."

        VARIATION       entSensorThresholdValue
            ACCESS      read-only
            DESCRIPTION "write access is not supported."

    ::= { ciscoEntitySensorCapability 2 }

cEntitySensorCapV12R0214SXCat6K AGENT-CAPABILITIES
    PRODUCT-RELEASE     "Cisco IOS 12.2(14)SX on Catalyst 6000/6500
                         and Cisco 7600 series devices."
    STATUS              current
    DESCRIPTION         "CISCO-ENTITY-SENSOR-MIB capabilities."

    SUPPORTS            CISCO-ENTITY-SENSOR-MIB
        INCLUDES        {
                            entitySensorValueGroup,
                            entitySensorThresholdGroup,
                            entitySensorThresholdNotificationGroup
                        }

        VARIATION       entSensorThresholdSeverity
            ACCESS      read-only
            DESCRIPTION "write access is not supported."

        VARIATION       entSensorThresholdRelation
            ACCESS      read-only
            DESCRIPTION "write access is not supported."

        VARIATION       entSensorThresholdValue
            ACCESS      read-only
            DESCRIPTION "write access is not supported."

    ::= { ciscoEntitySensorCapability 3 }

cEntitySensorCapCatOSV08R0101 AGENT-CAPABILITIES
    PRODUCT-RELEASE     "Cisco CatOS 8.1(1) on Catalyst 6000/6500
                         and Cisco 7600 series devices."
    STATUS              current
    DESCRIPTION         "CISCO-ENTITY-SENSOR-MIB capabilities."

    SUPPORTS            CISCO-ENTITY-SENSOR-MIB
        INCLUDES        {
                            entitySensorValueGroup,
                            entitySensorThresholdGroup,
                            entitySensorThresholdNotificationGroup
                        }

        VARIATION       entSensorThresholdSeverity
            ACCESS      read-only
            DESCRIPTION "write access is not supported."

        VARIATION       entSensorThresholdRelation
            ACCESS      read-only
            DESCRIPTION "write access is not supported."

        VARIATION       entSensorThresholdValue
            ACCESS      read-only
            DESCRIPTION "write access is not supported."

    ::= { ciscoEntitySensorCapability 4 }

cEntitySensorCapabilityV5R015 AGENT-CAPABILITIES

    PRODUCT-RELEASE     "MGX8850 Release 5.0.15"
    STATUS              current
    DESCRIPTION         "Agent capabilities for CISCO-ENTITY-SENSOR-MIB 
                         of Voice Switch Service Module(VXSM) in 
                         Release 5.0.15."

    SUPPORTS            CISCO-ENTITY-SENSOR-MIB
        INCLUDES        { entitySensorValueGroup, 
                          entitySensorThresholdGroup 
                        }

        VARIATION       entSensorValueTimeStamp
            ACCESS      not-implemented
            DESCRIPTION "Not supported."

        VARIATION       entSensorValueUpdateRate
            ACCESS      not-implemented
            DESCRIPTION "Not supported." 

        VARIATION       entSensorThresholdValue
            SYNTAX      INTEGER (-55..3000)
            DESCRIPTION "Limited data range supported by VXSM."

    ::= { ciscoEntitySensorCapability 5 }

cEntitySensorCapMDS3R0 AGENT-CAPABILITIES

    PRODUCT-RELEASE     "Cisco MDS 3.0(1)."
    STATUS              current
    DESCRIPTION         "CISCO-ENTITY-SENSOR-MIB capabilities."
                     
    SUPPORTS            CISCO-ENTITY-SENSOR-MIB
        INCLUDES        { entitySensorValueGroup, 
                          entitySensorThresholdGroup,
                          entitySensorThresholdNotificationGroup
                        }

    ::= { ciscoEntitySensorCapability 6 }

cEntitySensorCapCatOSV08R0601 AGENT-CAPABILITIES
    PRODUCT-RELEASE     "Cisco CatOS 8.6(1)."
    STATUS              current
    DESCRIPTION         "CISCO-ENTITY-SENSOR-MIB capabilities."

    SUPPORTS            CISCO-ENTITY-SENSOR-MIB
        INCLUDES        {
                            entitySensorValueGroup,
                            entitySensorThresholdGroup,
                            entitySensorThresholdNotificationGroup
                        }

        VARIATION       entSensorThresholdSeverity
            ACCESS      read-only
            DESCRIPTION "Unable to set this on CatOS."

        VARIATION       entSensorThresholdRelation
            ACCESS      read-only
            DESCRIPTION "Unable to set this on CatOS."

        VARIATION       entSensorThresholdValue
            ACCESS      read-write
            DESCRIPTION "Write access is supported only if the
                        corresponding entPhysicalIndex represents
                        an optical transceiver sensor.

                        The valid range is based on the value of
                        the corresponding instance of entSensorType.

                        entSensorType           Valid Range
                        ------------------------------------------------
                        dBm                     -400 to 82
                        amperes                 0 to 10000
                        celsius                 -500 to 850
                        voltsDC                 0 to 6550
                        "

    ::= { ciscoEntitySensorCapability 7 }

END
