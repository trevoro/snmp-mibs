CPQHSV110V3-MIB DEFINITIONS ::= BEGIN
 
-- This MIB built using parse file: HSV110_event_CC0135_3010.txt 6

-- ****************************************************************************
--
--         StorageWorks cpqHSV Management Information Base (MIB)
--         Management Information Base for SNMP Network Management
--
--
--      Copyright 1999, Compaq Computer Corporation.
--      Copyright 2002, Hewlett-Packard Company.
--      All Rights Reserved.
--
--      The information in this document is subject to change without notice.
--
--      COMPAQ COMPUTER CORPORATION SHALL NOT BE LIABLE FOR TECHNICAL
--      OR EDITORIAL ERRORS OR OMISSIONS CONTAINED HEREIN; NOR FOR INCIDENTAL
--      OR CONSEQUENTIAL DAMAGES RESULTING FROM THE FURNISHING, PERFORMANCE,
--      OR USE OF THIS MATERIAL.
--
--      The HP StorageWorks maHSV1x0 MIB provides HSV Controller information,
--      and HSV Management Agent information.
--
--      The Compaq Enterprise number is 232.
--      The ASN.1 prefix to, and including the Compaq Enterprise is:
--           1.3.6.1.4.1.232
--      iso(1) org(3) dod(6) internet(1) private(4) enterprises(1) compaq(232)
-- ****************************************************************************



	 IMPORTS
		 enterprises             FROM RFC1155-SMI
		 OBJECT-TYPE		 FROM RFC-1212
		 DisplayString           FROM RFC1213-MIB
                 TRAP-TYPE           FROM RFC-1215;

	compaq             OBJECT IDENTIFIER ::= { enterprises 232 } 
	cpqElementManager  OBJECT IDENTIFIER ::= { compaq 136 }
    cpqHSV             OBJECT IDENTIFIER ::= { cpqElementManager 1 }

--  CPQELEMMNGR MIB
	cpqHSVAgent        OBJECT IDENTIFIER ::= { cpqHSV 1 }
	cpqHSVServer       OBJECT IDENTIFIER ::= { cpqHSV 2 }
	hsvObject          OBJECT IDENTIFIER ::= { cpqHSV 3 }  
    maHSVMibRev        OBJECT IDENTIFIER ::= { cpqHSV 4 }


-- HSV SAN OBJECTS 
	scell		 OBJECT IDENTIFIER ::= { hsvObject 1 }
	agent		 OBJECT IDENTIFIER ::= { hsvObject 2 }
	host		 OBJECT IDENTIFIER ::= { hsvObject 3 }
	nsc		     OBJECT IDENTIFIER ::= { hsvObject 4 }
	shelf        OBJECT IDENTIFIER ::= { hsvObject 8 }

-- ********************************************************************	
--      Agent Information Group          1.3.6.1.4.1.232.136.1.1

--                                       1.3.6.1.4.1.232.136.1.1.1
	agManufacturer OBJECT-TYPE
	     SYNTAX  DisplayString
	     ACCESS  read-only
	     STATUS  mandatory
	     DESCRIPTION
		     "The name of the StorageWorks HSV Agent manufacturer."
	     ::= { cpqHSVAgent 1 }

--                                       1.3.6.1.4.1.232.136.1.1.2	
	agMajVersion OBJECT-TYPE
	     SYNTAX  INTEGER
	     ACCESS  read-only
	     STATUS  mandatory
	     DESCRIPTION
		     "StorageWorks HSV Agent Major Version Number (e.g., 3 
		     for 3.0)."	      
	     ::= { cpqHSVAgent 2 }

--                                       1.3.6.1.4.1.232.136.1.1.3
	agMinVersion OBJECT-TYPE
	     SYNTAX  INTEGER
	     ACCESS  read-only
	     STATUS  mandatory
	     DESCRIPTION
		     "StorageWorks HSV Agent Minor Version Number (e.g., 0 
		     for 3.0)."		      
	     ::= { cpqHSVAgent 3 }

--                                       1.3.6.1.4.1.232.136.1.1.4
	agHostName OBJECT-TYPE
	     SYNTAX  DisplayString
	     ACCESS  read-only
	     STATUS  mandatory
	     DESCRIPTION
		     "The Host System Network Name where the agent resides."		      
	     ::= { cpqHSVAgent 4 }

--                                       1.3.6.1.4.1.232.136.1.1.5
	agEnterprise OBJECT-TYPE
	     SYNTAX  OBJECT IDENTIFIER
	     ACCESS  read-only
	     STATUS  mandatory
	     DESCRIPTION
		     "The Enterprise ID subtree for StorageWorks HSV Agent MIB 
		      is registered."
		      
	     ::= { cpqHSVAgent 5 }

--                                       1.3.6.1.4.1.232.136.1.1.6
	agDescription OBJECT-TYPE
	     SYNTAX  DisplayString
	     ACCESS  read-only
	     STATUS  mandatory
	     DESCRIPTION
		     "The StorageWorks HSV Agent description."
		      
	     ::= { cpqHSVAgent 6 }

--                                       1.3.6.1.4.1.232.136.1.1.7
	agStatusTable OBJECT-TYPE                                  
	     SYNTAX  SEQUENCE OF AgentEntry
	     ACCESS  not-accessible
	     STATUS  mandatory
	     DESCRIPTION
		     "This table holds the status information for
		      each HSV Management Agent."
		      
	     ::= { cpqHSVAgent 7 }

--                                       1.3.6.1.4.1.232.136.1.1.7.1
	agentEntry OBJECT-TYPE
	     SYNTAX  AgentEntry
	     ACCESS  not-accessible
	     STATUS  mandatory
	     DESCRIPTION
	     "The Agent information entry."
	     INDEX   { agentEntryIndex }
		      
	     ::= { agStatusTable 1 }

	AgentEntry ::=                                              
	  SEQUENCE{
		agentEntryIndex
			INTEGER,
		agentStatus         
			INTEGER,
		agentEventCode
			INTEGER,
		agentEventLevel
			INTEGER,
        agentEventTimeDate
            DisplayString,
		agentEventDescription
			DisplayString
	  }

--                                       1.3.6.1.4.1.232.136.1.1.7.1.1
	agentEntryIndex OBJECT-TYPE
	     SYNTAX  INTEGER
	     ACCESS  read-only
	     STATUS  mandatory
	     DESCRIPTION
		     "The index into agentStatusTable ."
	     ::= { agentEntry 1 }

--                                       1.3.6.1.4.1.232.136.1.1.7.1.2
	agentStatus OBJECT-TYPE
             SYNTAX  INTEGER  {
                          other(1),
                          ok(2),
                          degraded(3),
                          failed(4)
                      }
 	     ACCESS  read-only
	     STATUS  mandatory
	     DESCRIPTION
		      "This variable reports the overall status of the
		       Agent. 
		       INFORMATIONAL: Normal Operating Condition
		       MINOR: Warning Condition
		       MAJOR: Failure or Failure Immanent
                   CRITICAL: Agent condition is critical or unknown"
	     ::= { agentEntry 2 }

--                                       1.3.6.1.4.1.232.136.1.1.7.1.3
	agentEventCode OBJECT-TYPE
	     SYNTAX  INTEGER
	     ACCESS  read-only
	     STATUS  mandatory
	     DESCRIPTION
		     "The management agent event code."
	     ::= { agentEntry 3 }

--                                       1.3.6.1.4.1.232.136.1.1.7.1.4
	agentEventLevel OBJECT-TYPE
	     SYNTAX  INTEGER
	     ACCESS  read-only
	     STATUS  mandatory
	     DESCRIPTION
		     "The management event level."
	     ::= { agentEntry 4 }

--                                       1.3.6.1.4.1.232.136.1.1.7.1.5
      agentEventTimeDate OBJECT-TYPE
	     SYNTAX  DisplayString
	     ACCESS  read-only
	     STATUS  mandatory
	     DESCRIPTION
		     "The date and time the event occurred dd-mm-yyyy/hr:min:sec." 
	     ::= { agentEntry 5 }
--                                       1.3.6.1.4.1.232.136.1.1.7.1.6
	agentEventDescription OBJECT-TYPE
	     SYNTAX  DisplayString
	     ACCESS  read-only
	     STATUS  mandatory
	     DESCRIPTION
		     "The Description of the management agent event." 
	     ::= { agentEntry 6 }


-- Workstation Group *****************************************************

	srvCPU OBJECT-TYPE
	     SYNTAX  DisplayString
	     ACCESS  read-only
	     STATUS  mandatory
	     DESCRIPTION
		     "The server CPU type (e.g., 80486)."
		      
	     ::= { cpqHSVServer 1 }

	srvComputerType OBJECT-TYPE
	     SYNTAX  DisplayString
	     ACCESS  read-only
	     STATUS  mandatory
	     DESCRIPTION
		     "The server Computer type (e.g., PC/AT)."
		      
	     ::= { cpqHSVServer 2 }

	srvModel OBJECT-TYPE
	     SYNTAX  INTEGER
	     ACCESS  read-only
	     STATUS  mandatory
	     DESCRIPTION
		     "The server model number."
		      
	     ::= { cpqHSVServer 3 }

	srvSubModel OBJECT-TYPE
	     SYNTAX  INTEGER
	     ACCESS  read-only
	     STATUS  mandatory
	     DESCRIPTION
		     "The server submodel number."
		      
	     ::= { cpqHSVServer 4 }

	srvBiosVersion OBJECT-TYPE
	     SYNTAX  DisplayString
	     ACCESS  read-only
	     STATUS  mandatory
	     DESCRIPTION
		     "The server BIOS Version."
		      
	     ::= { cpqHSVServer 5 }

	srvOS OBJECT-TYPE
	     SYNTAX  DisplayString
	     ACCESS  read-only
	     STATUS  mandatory
	     DESCRIPTION
		     "The server operating system name (e.g., WINNT)."
		      
	     ::= { cpqHSVServer 6 }

	srvOSMajVersion OBJECT-TYPE
	     SYNTAX  INTEGER
	     ACCESS  read-only
	     STATUS  mandatory
	     DESCRIPTION
		     "The server OS major version number 
		     (e.g., 3 for WINNT 3.51)."
		      
	     ::= { cpqHSVServer 7 }

	srvOSMinVersion OBJECT-TYPE
	     SYNTAX  INTEGER
	     ACCESS  read-only
	     STATUS  mandatory
	     DESCRIPTION
		     "The server OS minor version number (e.g., 51 for
		     WINNT 3.51)."
		      
	     ::= { cpqHSVServer 8 }

-- maHSVMibRev Group       1.3.6.1.4.1.232.136.1.4

--                         1.3.6.1.4.1.232.136.1.4.1
      maHSVMibRevMajor OBJECT-TYPE
           SYNTAX  INTEGER
           ACCESS  read-only
           STATUS  mandatory
           DESCRIPTION
            "The Major Revision level.
             A change in the major revision level represents a major change
             in the architecture of the MIB.  A change in the major revision
             level may indicate a significant change in the information
             supported and/or the meaning of the supported information,
             correct interpretation of data may require a MIB document with
             the same major revision level."

           ::= { maHSVMibRev 1 }

--                         1.3.6.1.4.1.232.136.1.4.2
     maHSVMibRevMinor OBJECT-TYPE	
           SYNTAX  INTEGER
           ACCESS  read-only
           STATUS  mandatory
           DESCRIPTION
            "The Minor Revision level.
             A change in the minor revision level may represent some minor
             additional support, no changes to any pre-existing information
             has occurred."

           ::= { maHSVMibRev 2 }

-- Object Groups          1.3.6.1.4.1.232.136.1.3

-- *********************************************************************
-- StorageCell  Group         1.3.6.1.4.1.232.136.1.3.1  = scell

--                                  1.3.6.1.4.1.232.136.1.3.1.1
	scellTotal OBJECT-TYPE
	     SYNTAX  INTEGER 
	     ACCESS  read-only
	     STATUS  mandatory
	     DESCRIPTION
		     "The total number of StorageCells (storage pools) present 
                  in the Fusion System."	      
	     ::= { scell 1 }

--                                  1.3.6.1.4.1.232.136.1.3.1.2
	scellStatusTable OBJECT-TYPE                                  
	     SYNTAX  SEQUENCE OF ScellEntry
	     ACCESS  not-accessible
	     STATUS  mandatory
	     DESCRIPTION
		     "This table holds the status information for
		      each StorageCell."   
	     ::= { scell 2 }

--                                 1.3.6.1.4.1.232.136.1.3.1.2.1
	scellEntry OBJECT-TYPE
	     SYNTAX  ScellEntry
	     ACCESS  not-accessible
	     STATUS  mandatory
	     DESCRIPTION
	     "The StorageCell information entry."
	     INDEX   { scellEntryIndex }
	     ::= { scellStatusTable 1 }


	ScellEntry ::=                                              
	  SEQUENCE{
		scellEntryIndex
			INTEGER,
		scellName           
			DisplayString,
		scellUUID           
			DisplayString,
		scellStatus         
			INTEGER,
            scellEventDescription
                  DisplayString,
            scellEventTimeDate
                  DisplayString,
            scellEventCode
                  DisplayString,
		scellSWComponent
                  INTEGER,
            scellECode
			INTEGER,
            scellCAC
			INTEGER,
		scellEIP
			INTEGER,
            scellNameDateTime
                  DisplayString
	  }

--		1.3.6.1.4.1.232.136.1.3.1.2.1.1
	scellEntryIndex OBJECT-TYPE
	     SYNTAX  INTEGER
	     ACCESS  read-only
	     STATUS  mandatory
	     DESCRIPTION
		     "The index into scellStatusTable ."		      
	     ::= { scellEntry 1 }

--		1.3.6.1.4.1.232.136.1.3.1.2.1.2
	scellName OBJECT-TYPE
	     SYNTAX  DisplayString
	     ACCESS  read-only
	     STATUS  mandatory
	     DESCRIPTION
		     "The StorageCell Name."
	     ::= { scellEntry 2 }

--		1.3.6.1.4.1.232.136.1.3.1.2.1.3
	scellUUID OBJECT-TYPE
	     SYNTAX  DisplayString
	     ACCESS  read-only
	     STATUS  mandatory
	     DESCRIPTION
		     "The StorageCell unique ID."		      
	     ::= { scellEntry 3 }

--		1.3.6.1.4.1.232.136.1.3.1.2.1.4
	scellStatus OBJECT-TYPE
             SYNTAX  INTEGER  {
                          informational(1),
                          minor(2),
                          major(3),
                          failed(4)
                      }
 	     ACCESS  read-only
	     STATUS  mandatory
	     DESCRIPTION
		      "This variable reports the overall status of the
		       StorageCell. 
		       INFORMATIONAL: Normal Operating Condition
		       MINOR: Warning Condition
		       MAJOR: Failure or Failure Immanent
                   CRITICAL: Condition is critical or unknown"
	     ::= { scellEntry 4 }

--		1.3.6.1.4.1.232.136.1.3.1.2.1.5
	scellEventDescription OBJECT-TYPE
	     SYNTAX  DisplayString
	     ACCESS  read-only
	     STATUS  mandatory
	     DESCRIPTION
		     "The StorageCell Event Description."		      
	     ::= { scellEntry 5 }

--		1.3.6.1.4.1.232.136.1.3.1.2.1.6
      scellEventTimeDate OBJECT-TYPE
	     SYNTAX  DisplayString
	     ACCESS  read-only
	     STATUS  mandatory
	     DESCRIPTION
		     "The StorageCell Event Time and Date."		      
	     ::= { scellEntry 6 }

--		1.3.6.1.4.1.232.136.1.3.1.2.1.7
      scellEventCode OBJECT-TYPE
	     SYNTAX  DisplayString
	     ACCESS  read-only
	     STATUS  mandatory
	     DESCRIPTION
		     "The StorageCell Event Code."		      
	     ::= { scellEntry 7 }

--		1.3.6.1.4.1.232.136.1.3.1.2.1.8
	scellSWComponent OBJECT-TYPE
	     SYNTAX  INTEGER
	     ACCESS  read-only
	     STATUS  mandatory
	     DESCRIPTION
		     "The Event Code Software Component ID."
	     ::= { scellEntry 8 }

--		1.3.6.1.4.1.232.136.1.3.1.2.1.9
	scellECode OBJECT-TYPE
	     SYNTAX  INTEGER
	     ACCESS  read-only
	     STATUS  mandatory
	     DESCRIPTION
		     "The StorageCell Event Code event number."	      
	     ::= { scellEntry 9 }

--		1.3.6.1.4.1.232.136.1.3.1.2.1.10
	scellCAC OBJECT-TYPE
	     SYNTAX  INTEGER
	     ACCESS  read-only
	     STATUS  mandatory
	     DESCRIPTION
		     "The event code Corrective Action Code."	      
	     ::= { scellEntry 10 }

--		1.3.6.1.4.1.232.136.1.3.1.2.1.11
	scellEIP OBJECT-TYPE
	     SYNTAX  INTEGER
	     ACCESS  read-only
	     STATUS  mandatory
	     DESCRIPTION
		     "The Event Code EIP Type." 
	     ::= { scellEntry 11 }

--		1.3.6.1.4.1.232.136.1.3.1.2.1.12
	scellNameDateTime OBJECT-TYPE
	     SYNTAX  DisplayString
	     ACCESS  read-only
	     STATUS  mandatory
	     DESCRIPTION
		     "The StorageCell Name: Date & Time of Event."
	     ::= { scellEntry 12 }		

-- /*****************************************************************/


-- Host Group		1.3.6.1.4.1.232.136.1.3.3

	hostTotal OBJECT-TYPE
	     SYNTAX  INTEGER 
	     ACCESS  read-only
	     STATUS  mandatory
	     DESCRIPTION
		     "The total number of hosts attached the Fusion System."
--                              1.3.6.1.4.1.232.136.1.3.3.3.1
	     ::= { host 1 }

	hostStatusTable OBJECT-TYPE                                  
	     SYNTAX  SEQUENCE OF HostEntry
	     ACCESS  not-accessible
	     STATUS  mandatory
	     DESCRIPTION
		     "This table holds the status information for
		      each Host."
--                              1.3.6.1.4.1.232.136.1.3.3.3.2		      
	     ::= { host 2 }

	hostEntry OBJECT-TYPE
	     SYNTAX  HostEntry
	     ACCESS  not-accessible
	     STATUS  mandatory
	     DESCRIPTION
	     "The Host information entry."
	     INDEX   { hostEntryIndex }
--                              1.3.6.1.4.1.232.136.1.3.3.3.2.1
	     ::= { hostStatusTable 1 }

	HostEntry ::=                                              
	  SEQUENCE{
		hostEntryIndex
			INTEGER,
		hostName           
			DisplayString,
		hostUUID           
			DisplayString,
		hostStatus         
			INTEGER
	  }



	hostEntryIndex OBJECT-TYPE
	     SYNTAX  INTEGER
	     ACCESS  read-only
	     STATUS  mandatory
	     DESCRIPTION
		     "The index into hostStatusTable ."
--                              1.3.6.1.4.1.232.136.1.3.3.3.2.1.1
	     ::= { hostEntry 1 }

	hostName OBJECT-TYPE
	     SYNTAX  DisplayString
	     ACCESS  read-only
	     STATUS  mandatory
	     DESCRIPTION
		     "The Host Name."
--                              1.3.6.1.4.1.232.136.1.3.3.3.2.1.2
	     ::= { hostEntry 2 }

	hostUUID OBJECT-TYPE
	     SYNTAX  DisplayString
	     ACCESS  read-only
	     STATUS  mandatory
	     DESCRIPTION
		     "The Host unique ID."
--                              1.3.6.1.4.1.232.136.1.3.3.3.2.1.3		      
	     ::= { hostEntry 3 }

	hostStatus OBJECT-TYPE
             SYNTAX  INTEGER  {
                          informational(0),
                          minor(1),
                          major(2),
                          critical(3)
                      }
 	     ACCESS  read-only
	     STATUS  mandatory
	     DESCRIPTION
		      "This variable reports the overall status of the Host. 
		       INFORMATIONAL: Normal Operating Condition
		       MINOR: Warning Condition
		       MAJOR: Failure or Failure Immanent
                   CRITICAL: Condition is critical or unknown"
--                              1.3.6.1.4.1.232.136.1.3.3.3.2.1.4
	     ::= { hostEntry 4 }


-- Network Storage Controller Group   1.3.6.1.4.1.232.136.1.3.3.4

	nscTotal OBJECT-TYPE
	     SYNTAX  INTEGER 
	     ACCESS  read-only
	     STATUS  mandatory
	     DESCRIPTION
		     "The total number of Network Storage Controllers present in the Fusion System."
--                              1.3.6.1.4.1.232.136.1.3.3.4.1
	     ::= { nsc 1 }

	nscStatusTable OBJECT-TYPE                                  
	     SYNTAX  SEQUENCE OF NscEntry
	     ACCESS  not-accessible
	     STATUS  mandatory
	     DESCRIPTION
		     "This table holds the status information for
		      each Network Storage Controller."
--                              1.3.6.1.4.1.232.136.1.3.3.4.2
	     ::= { nsc 2 }

	nscEntry OBJECT-TYPE
	     SYNTAX  NscEntry
	     ACCESS  not-accessible
	     STATUS  mandatory
	     DESCRIPTION
	     "The NSC information entry."
	     INDEX   { nscEntryIndex }
--                              1.3.6.1.4.1.232.136.1.3.3.4.2.1
	     ::= { nscStatusTable 1 }

	NscEntry ::=                                              
	  SEQUENCE{
		nscEntryIndex
			INTEGER,
		nscName           
			DisplayString,
		nscUUID           
			DisplayString,
		nscStatus         
			INTEGER
	  }



	nscEntryIndex OBJECT-TYPE
	     SYNTAX  INTEGER
	     ACCESS  read-only
	     STATUS  mandatory
	     DESCRIPTION
		     "The index into nscStatusTable ."
--                              1.3.6.1.4.1.232.136.1.3.3.4.2.1.1
	     ::= { nscEntry 1 }

	nscName OBJECT-TYPE
	     SYNTAX  DisplayString
	     ACCESS  read-only
	     STATUS  mandatory
	     DESCRIPTION
		     "The Network Storage Controller Name."
--                              1.3.6.1.4.1.232.136.1.3.3.4.2.1.2
	     ::= { nscEntry 2 }

	nscUUID OBJECT-TYPE
	     SYNTAX  DisplayString
	     ACCESS  read-only
	     STATUS  mandatory
	     DESCRIPTION
		     "The NSC unique ID."
--                              1.3.6.1.4.1.232.136.1.3.3.4.2.1.3
	     ::= { nscEntry 3 }

	nscStatus OBJECT-TYPE
             SYNTAX  INTEGER  {
                          informational(0),
                          minor(1),
                          major(2),
                          critical(3)
                      }
 	     ACCESS  read-only
	     STATUS  mandatory
	     DESCRIPTION
		      "This variable reports the overall status of the
		       Network Storage Controller. 
		       INFORMATIONAL: Normal Operating Condition
		       MINOR: Warning Condition
		       MAJOR: Failure or Failure Immanent
                   CRITICAL: Condition is critical or unknown"
--                              1.3.6.1.4.1.232.136.1.3.3.4.2.1.4      
	     ::= { nscEntry 4 }

-- Shelf Group                      1.3.6.1.4.1.232.136.1.3.8
--                                  1.3.6.1.4.1.232.136.1.3.8.1
	shelfTotal OBJECT-TYPE
	     SYNTAX  INTEGER 
	     ACCESS  read-only
	     STATUS  mandatory
	     DESCRIPTION
		     "The total number of disk shelves present in the HSV system."
	     ::= { shelf 1 }

--                                  1.3.6.1.4.1.232.136.1.3.8.2
	shelfStatusTable OBJECT-TYPE                                  
	     SYNTAX  SEQUENCE OF ShelfEntry
	     ACCESS  not-accessible
	     STATUS  mandatory
	     DESCRIPTION
		     "This table holds the status information for
		      each Shelf."
	     ::= { shelf 2 }

--                                  1.3.6.1.4.1.232.136.1.3.8.2.1
	shelfEntry OBJECT-TYPE
	     SYNTAX  ShelfEntry
	     ACCESS  not-accessible
	     STATUS  mandatory
	     DESCRIPTION
	     "The Shelf information entry."
	     INDEX   { shelfEntryIndex }
	     ::= { shelfStatusTable 1 }

	ShelfEntry ::=
	  SEQUENCE{
		shelfEntryIndex
			INTEGER,
		shelfStatus
			INTEGER,
		shelfId	
			INTEGER,
		shelfElementType
			INTEGER,
		shelfElementNum
			INTEGER,
		shelfErrorCode
			INTEGER
	  }

--                                  1.3.6.1.4.1.232.136.1.3.8.2.1.1
	shelfEntryIndex OBJECT-TYPE
	     SYNTAX  INTEGER
	     ACCESS  read-only
	     STATUS  mandatory
	     DESCRIPTION
		     "The index into shelfStatusTable ."		      
	     ::= { shelfEntry 1 }

--                                  1.3.6.1.4.1.232.136.1.3.8.2.1.2
	shelfStatus OBJECT-TYPE
             SYNTAX  INTEGER  {
                          other(1),
                          ok(2),
                          degraded(3),
                          failed(4)
                      }
 	     ACCESS  read-only
	     STATUS  mandatory
	     DESCRIPTION
		      "This variable reports the overall status of the
		       Shelf. 
                   OTHER: unknown or undeterminable
		       OK: Normal Operating Condition
		       DEGRADED: Warning Condition
		       FAILED: Failure"		      
	     ::= { shelfEntry 2 }

--                                  1.3.6.1.4.1.232.136.1.3.8.2.1.3
	shelfId OBJECT-TYPE
	     SYNTAX  INTEGER
	     ACCESS  read-only
	     STATUS  mandatory
	     DESCRIPTION
		     "The Shelf Id (shelf number)."		      
	     ::= { shelfEntry 3 }

--                                  1.3.6.1.4.1.232.136.1.3.8.2.1.4
	shelfElementType OBJECT-TYPE
	     SYNTAX  INTEGER
	     ACCESS  read-only
	     STATUS  mandatory
	     DESCRIPTION
		     "The Shelf Element type.
			01: Disk
			02: Power Supply
			03: Fan
			04: Temp Sensor
			06: Alarm Horn
			07: EMU
			12: LCD
			15: GBIC
			16: Language
			17: Comm Port
			18: Volt Sensor
			19: Amp Sensor
			128:Enclosure
			130:Back plane
			255:Host"
	     ::= { shelfEntry 4 }

--                                  1.3.6.1.4.1.232.136.1.3.8.2.1.5
	shelfElementNum OBJECT-TYPE
	     SYNTAX  INTEGER
	     ACCESS  read-only
	     STATUS  mandatory
	     DESCRIPTION
		     "Which particular Element of that type."
	     ::= { shelfEntry 5 }

--                                  1.3.6.1.4.1.232.136.1.3.8.2.1.6
	shelfErrorCode OBJECT-TYPE
	     SYNTAX  INTEGER
	     ACCESS  read-only
	     STATUS  mandatory
	     DESCRIPTION
		     "The Element Type's Error Code."
	     ::= { shelfEntry 6 }


-- Traps
   emuEventTrapInformative TRAP-TYPE
        ENTERPRISE compaq
        VARIABLES  { scellNameDateTime,
                     shelfId,
                     shelfElementType,
                     shelfElementNum,
                     shelfErrorCode }
        DESCRIPTION
           "An EMU Informational event has occurred
              scellNameDateTime: StorageCell name, and date/time
		  emuShelfId: disk shelf number in the cabinet
		  emuElementType: the element type
		    01: Disk      
		    02: Pwr Supply      
		    03: Fan      
		    04: Temp Sensor      
		    06: Alarm Horn      
		    07: EMU      
		    12: LCD      
		    15: Xcvr      
		    16: Lang      
		    17: Comm Port      
  		    18: Volt Sensor      
		    19: Amp Sensor      
		    128:Encl      
		    130:Back plane      
		  emuErrorCode: error number "

	       --#TYPE      "EMU Informational Event"
             --#SUMMARY   "scellNameDateTime %s : emuShelfId %d : emuElementType %d : emuElementNum %d : emuErrorCode %d"
             --#ARGUMENTS {0,1,2,3,4}
             --#SEVERITY  INFORMATIONAL
             --#TIMEINDEX 136
             --#STATE     OK

        ::= 136001

   emuEventTrapNoncritical TRAP-TYPE
        ENTERPRISE compaq
        VARIABLES  { scellNameDateTime,
                     shelfId,
                     shelfElementType,
                     shelfElementNum,
                     shelfErrorCode }
        DESCRIPTION
           "An EMU Non-critical event has occurred
              scellNameDateTime: StorageCell name, and date/time
		  emuShelfId: disk shelf number in the cabinet
		  emuElementType: the element type
		    01: Disk      
		    02: Pwr Supply      
		    03: Fan      
		    04: Temp Sensor      
		    06: Alarm Horn      
		    07: EMU      
		    12: LCD      
		    15: Xcvr      
		    16: Lang      
		    17: Comm Port      
  		    18: Volt Sensor      
		    19: Amp Sensor      
		    128:Encl      
		    130:Back plane      
		  emuErrorCode: error number "

	       --#TYPE      "EMU Non Critical Event"
             --#SUMMARY   "scellNameDateTime %s : emuShelfId %d : emuElementType %d : emuElementNum %d : emuErrorCode %d"
             --#ARGUMENTS {0,1,2,3,4}
             --#SEVERITY  MINOR
             --#TIMEINDEX 136
             --#STATE     WARNING

        ::= 136002

   emuEventTrapCritical TRAP-TYPE
        ENTERPRISE compaq
        VARIABLES  { scellNameDateTime,
                     shelfId,
                     shelfElementType,
                     shelfElementNum,
                     shelfErrorCode }
        DESCRIPTION
           "An EMU Critical event has occurred
              scellNameDateTime: StorageCell name, and date/time
		  emuShelfId: disk shelf number in the cabinet
		  emuElementType: the element type
		    01: Disk      
		    02: Pwr Supply      
		    03: Fan      
		    04: Temp Sensor      
		    06: Alarm Horn      
		    07: EMU      
		    12: LCD      
		    15: Xcvr      
		    16: Lang      
		    17: Comm Port      
  		    18: Volt Sensor      
		    19: Amp Sensor      
		    128:Encl      
		    130:Back plane      
		  emuErrorCode: error number "

	       --#TYPE      "EMU Critical Event"
             --#SUMMARY   "scellNameDateTime %s : emuShelfId %d : emuElementType %d : emuElementNum %d : emuErrorCode %d"
             --#ARGUMENTS {0,1,2,3,4}
             --#SEVERITY  CRITICAL
             --#TIMEINDEX 136
             --#STATE     CRITICAL

        ::= 136003

   emuEventTrapUnrecoverable TRAP-TYPE
        ENTERPRISE compaq
        VARIABLES  { scellNameDateTime,
                     shelfId,
                     shelfElementType,
                     shelfElementNum,
                     shelfErrorCode }
        DESCRIPTION
           "An EMU Unrecoverable event has occurred
              scellNameDateTime: StorageCell name, and date/time
		  emuShelfId: disk shelf number in the cabinet
		  emuElementType: the element type
		    01: Disk      
		    02: Pwr Supply      
		    03: Fan      
		    04: Temp Sensor      
		    06: Alarm Horn      
		    07: EMU      
		    12: LCD      
		    15: Xcvr      
		    16: Lang      
		    17: Comm Port      
  		    18: Volt Sensor      
		    19: Amp Sensor      
		    128:Encl      
		    130:Back plane      
		  emuErrorCode: error number "

	       --#TYPE      "EMU Unrecoverable Event"
             --#SUMMARY   "scellNameDateTime %s : emuShelfId %d : emuElementType %d : emuElementNum %d : emuErrorCode %d"
             --#ARGUMENTS {0,1,2,3,4}
             --#SEVERITY  CRITICAL
             --#TIMEINDEX 136
             --#STATE     FAILED

        ::= 136004
 
-- Following are the traps defined for StorageCell Events
-- The trap name is constructed from 2 of the 4 numbers that uniquely Identify
-- a SC Event: Software Component ID, and the Event Number.
-- These numbers are represented as hex numbers in the controller event parse file.
-- For example: sCellEventTrap_9_66  has: 
--   Software Component ID: 9 (hex)
--   Event Number: 66 (hex) { = 102 base 10 }
--   
--  
 
-- The Trap number is calculated by using the complete number space
-- of the Software Component & Event numbers.  There are a possible
-- 256 s/w components, each with a possible 256 events giving an
-- address space of 65536 events.  To ensure that trap numbers do not
-- change when additional SC Events are defined the following formula
-- is used:  Base + (SWCID * 256) + Event Number
-- The large base was used to avoid collisions with the management trap
-- numbers who share the same address space of 0-65536
-- In our example above: sCellEventTrap_9_66 the trap number is -
-- Base = 13600000  (which preserves our unique OID sub-identifier of 136) +
--        ( 9 * 256 )  +   102 (66hex)   =  13602406
 
 
   sCellEventTrap-1-0 TRAP-TYPE  -- CAC Code: 0
        ENTERPRISE compaq
        VARIABLES  { scellNameDateTime,
                     scellSWComponent,
                     scellECode,
                     scellCAC,
                     scellEIP}
        DESCRIPTION
             "Severity: Normal -- informational in nature. During Executive Services initialization the system time value was set to the value contained in the time field. The action field contains one of the following codes which describes the condition that caused the time value to be chosen: <UL><LI>0 = TOY clock unavailable; time reset to default date and time. <LI>1 = TOY clock time value was less than or equal to the last known time value previously stored in nonvolatile memory; time reset to default date and time. <LI>2 = EDC was bad for last known time value previously stored in nonvolatile memory; time reset to default date and time. <LI>3 = TOY clock not running; time reset to default date and time. <LI>4 = TOY clock time value believed to be accurate; time set to TOY clock time value. </UL>"
           --#TYPE      "StorageCell Event"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13600256
 
   sCellEventTrap-1-1 TRAP-TYPE  -- CAC Code: 0
        ENTERPRISE compaq
        VARIABLES  { scellNameDateTime,
                     scellSWComponent,
                     scellECode,
                     scellCAC,
                     scellEIP}
        DESCRIPTION
             "Severity: Normal -- informational in nature. The system time value was set to the value contained in the time field by a call to the EXEC$SET-TIME service. As part of setting the time in a dual HSV110 controller configuration, the times are synchronized. The action field contains one of the following codes which describes the action taken: <UL><LI>0 = The time was set to the time value on this HSV110 controller. <LI>1 = The master HSV110 controller requested the slave HSV110 controller to set its time to the time value. <LI>2 = The slave HSV110 controller set the local time to the time value. <LI>3 = The HSV110 controller's TOY clock was set to the time value. </UL>"
           --#TYPE      "StorageCell Event"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13600257
 
   sCellEventTrap-3-0 TRAP-TYPE  -- CAC Code: 0
        ENTERPRISE compaq
        VARIABLES  { scellNameDateTime,
                     scellSWComponent,
                     scellECode,
                     scellCAC,
                     scellEIP}
        DESCRIPTION
             "Severity: Normal -- informational in nature. The HSV110 controller identified in the node-name field has failed in communicating with the Cabinet (Rack) Bus Interface Controller."
           --#TYPE      "StorageCell Event"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13600768
 
   sCellEventTrap-3-1 TRAP-TYPE  -- CAC Code: 40
        ENTERPRISE compaq
        VARIABLES  { scellNameDateTime,
                     scellSWComponent,
                     scellECode,
                     scellCAC,
                     scellEIP}
        DESCRIPTION
             "Severity: Critical -- failure or failure imminent. The physical disk drive identified by the device field has been rendered inoperable. <UL><LI>If the flags.quorum-disk flag is nonzero, the physical disk drive is the Storage System Quorum disk identified in the quorum-sequence field. <LI>If the flags.inq-state flag is nonzero, the content of the inq-data and capacity fields is valid. <LI>If the rss-flags.member-abnormal flag is nonzero, the content of the member-state field is valid. </UL>The rack-num field will not be valid until a future release. <P> The reason-code field contains a code giving the reason the physical disk drive has been rendered inoperable: <UL><LI>0x001 = CS IO failure <LI>0x002 = Scrubber IO failure <LI>0x003 = Attempt to set CBIT on normal drive <LI>0x004 = Attempt to set CBIT on merging drive <LI>0x100 = The Target Discovery Service Descriptor retry count has been exceeded <LI>0x101 = Inoperable for Bad Block Replacement <LI>0x102 = The soft error count has been exceeded <LI>0x103 = The number of exchange timeouts permitted was exceeded <LI>0x104 = Communication with drive has failed an excessive number of times <LI>0x105 = The number of retries has been exceeded <LI>0x106 = Medium/Hardware Errors encountered on this physical disk drive <LI>0x107 = The number of Directed LIP's has surpassed the threshold <LI>0x200 = Smart event from a physical disk drive not in Storage System <LI>0x201 = Smart event from a physical disk drive not a Volume <LI>0x202 = Smart event from a physical disk drive not a RSS <LI>0x203 = Failure predicted from physical disk drive <LI>0x204 = Can't read from physical disk drive from the poll <LI>0x205 = Failure predicted from physical disk drive while deleting Disk Group <LI>0x206 = physical disk drive forced inoperative from maintenance command for temporary POID <LI>0x207 = physical disk drive forced inoperative from maintenance command for POID <LI>0x208 = Bad block recovery failed or can't read FPAB <LI>0x209 = Failure to remove volume from Storage System <LI>0x20A = Failure to update metadata </UL>"
           --#TYPE      "StorageCell Event"
           --#SUMMARY   "SCellName-TimeDate %s : SWCID %d : ECode: %d : CAC %d : EIP %d."
           --#ARGUMENTS {0,1,2,3,4,}
           --#SEVERITY  CRITICAL
           --#TIMEINDEX 136
           --#STATE     WARNING
        ::= 13600769
 
   sCellEventTrap-3-2 TRAP-TYPE  -- CAC Code: 4f
        ENTERPRISE compaq
        VARIABLES  { scellNameDateTime,
                     scellSWComponent,
                     scellECode,
                     scellCAC,
                     scellEIP}
        DESCRIPTION
             "Severity: Warning -- not failed but attention recommended or required. A physical disk drive will not be used because the maximum number of physical disk drives already exist in the current Storage System. The affected physical disk drive is identified in the device field. The Fibre Channel port used to communicate with the physical disk drive is contained in the cerp-id field. The HSV110 controller internal Fibre Channel port number used to communicate with the physical disk drive is contained in the port field. The location of the physical disk drive is contained in the rack-num, dencl-num, and bay fields. Note that the content of the rack-num field will not be valid until a future release. Note also that in this case the content of the reason-code, flags, rss-flags, inq-data, quorum-sequence, capacity, and member-state fields is undefined."
           --#TYPE      "StorageCell Event"
           --#SUMMARY   "SCellName-TimeDate %s : SWCID %d : ECode: %d : CAC %d : EIP %d."
           --#ARGUMENTS {0,1,2,3,4,}
           --#SEVERITY  MINOR
           --#TIMEINDEX 136
           --#STATE     WARNING
        ::= 13600770
 
   sCellEventTrap-3-3 TRAP-TYPE  -- CAC Code: 0
        ENTERPRISE compaq
        VARIABLES  { scellNameDateTime,
                     scellSWComponent,
                     scellECode,
                     scellCAC,
                     scellEIP}
        DESCRIPTION
             "Severity: Normal -- informational in nature. A HSV110 controller has begun booting. That controller is identified in the node-name field. Note that in this case the content of the scell-tag field is undefined."
           --#TYPE      "StorageCell Event"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13600771
 
   sCellEventTrap-3-4 TRAP-TYPE  -- CAC Code: 0
        ENTERPRISE compaq
        VARIABLES  { scellNameDateTime,
                     scellSWComponent,
                     scellECode,
                     scellCAC,
                     scellEIP}
        DESCRIPTION
             "Severity: Normal -- informational in nature. The HSV110 controller identified in the node-name field has finished the process of bringing the Storage System, identified in the scell-tag field, online."
           --#TYPE      "StorageCell Event"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13600772
 
   sCellEventTrap-3-5 TRAP-TYPE  -- CAC Code: 0
        ENTERPRISE compaq
        VARIABLES  { scellNameDateTime,
                     scellSWComponent,
                     scellECode,
                     scellCAC,
                     scellEIP}
        DESCRIPTION
             "Severity: Normal -- informational in nature. The HSV110 controller identified in the node-name field has been joined into the Storage System."
           --#TYPE      "StorageCell Event"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13600773
 
   sCellEventTrap-3-6 TRAP-TYPE  -- CAC Code: 0
        ENTERPRISE compaq
        VARIABLES  { scellNameDateTime,
                     scellSWComponent,
                     scellECode,
                     scellCAC,
                     scellEIP}
        DESCRIPTION
             "Severity: Normal -- informational in nature. The HSV110 controller identified in the node-name field has been ousted from the Storage System identified in the scell-tag field."
           --#TYPE      "StorageCell Event"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13600774
 
   sCellEventTrap-3-7 TRAP-TYPE  -- CAC Code: 0
        ENTERPRISE compaq
        VARIABLES  { scellNameDateTime,
                     scellSWComponent,
                     scellECode,
                     scellCAC,
                     scellEIP}
        DESCRIPTION
             "Severity: Normal -- informational in nature. The HSV110 controller identified in the node-name field is now the Storage System, identified in the scell-tag field, master."
           --#TYPE      "StorageCell Event"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13600775
 
   sCellEventTrap-3-8 TRAP-TYPE  -- CAC Code: 0
        ENTERPRISE compaq
        VARIABLES  { scellNameDateTime,
                     scellSWComponent,
                     scellECode,
                     scellCAC,
                     scellEIP}
        DESCRIPTION
             "Severity: Normal -- informational in nature. The HSV110 controller identified in the node-name field has been brought into the Storage System identified in the scell-tag field."
           --#TYPE      "StorageCell Event"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13600776
 
   sCellEventTrap-4-0 TRAP-TYPE  -- CAC Code: 3
        ENTERPRISE compaq
        VARIABLES  { scellNameDateTime,
                     scellSWComponent,
                     scellECode,
                     scellCAC,
                     scellEIP}
        DESCRIPTION
             "Severity: Undetermined -- more information needed to determine severity. HSV110 controller operation was terminated due to an unrecoverable event detected by either software or hardware or due to an action initiated via the Storage System Management Interface."
           --#TYPE      "StorageCell Event"
           --#SUMMARY   "SCellName-TimeDate %s : SWCID %d : ECode: %d : CAC %d : EIP %d."
           --#ARGUMENTS {0,1,2,3,4,}
           --#SEVERITY  CRITICAL
           --#TIMEINDEX 136
           --#STATE     WARNING
        ::= 13601024
 
   sCellEventTrap-4-1 TRAP-TYPE  -- CAC Code: 3
        ENTERPRISE compaq
        VARIABLES  { scellNameDateTime,
                     scellSWComponent,
                     scellECode,
                     scellCAC,
                     scellEIP}
        DESCRIPTION
             "Severity: Undetermined -- more information needed to determine severity. An HSV110 controller has sent a last gasp message prior to terminating operation. The terminated HSV110 controller is identified in the lter.terminating-ctrlr field. The lter.termination-event.u.value field contains the termination cause (i.e., termination code). The lter.termination-event.termination-location field contains the termination location. The lter.termination-time field contains the termination date and time. The lter.seq field contains the index of the HSV110 controller's Last Termination Event Array element assigned to the termination event. The lter.sw-version, lter.baselevel-id, and lter.ctrlr-model-id fields identify the software level and controller model information. The lter.uptime field contains a value that represents the number of seconds the HSV110 controller has executed functional code since its first power up. Note that the reporting-ctrlr header field identifies the HSV110 controller that received the last gasp message. All other header fields reflect information supplied by the terminating controller."
           --#TYPE      "StorageCell Event"
           --#SUMMARY   "SCellName-TimeDate %s : SWCID %d : ECode: %d : CAC %d : EIP %d."
           --#ARGUMENTS {0,1,2,3,4,}
           --#SEVERITY  CRITICAL
           --#TIMEINDEX 136
           --#STATE     WARNING
        ::= 13601025
 
   sCellEventTrap-4-2 TRAP-TYPE  -- CAC Code: 1
        ENTERPRISE compaq
        VARIABLES  { scellNameDateTime,
                     scellSWComponent,
                     scellECode,
                     scellCAC,
                     scellEIP}
        DESCRIPTION
             "Severity: Critical -- failure or failure imminent. A machine check occurred while a termination event was being processed. The post-termination operation being performed at the time the event occurred can be derived from the lter.reuea-index field. Note: The lteihd and lter fields may not describe the event that caused the HSV110 controller to terminate operation depending on how far termination processing got before the machine check occurred."
           --#TYPE      "StorageCell Event"
           --#SUMMARY   "SCellName-TimeDate %s : SWCID %d : ECode: %d : CAC %d : EIP %d."
           --#ARGUMENTS {0,1,2,3,4,}
           --#SEVERITY  CRITICAL
           --#TIMEINDEX 136
           --#STATE     WARNING
        ::= 13601026
 
   sCellEventTrap-4-3 TRAP-TYPE  -- CAC Code: 1
        ENTERPRISE compaq
        VARIABLES  { scellNameDateTime,
                     scellSWComponent,
                     scellECode,
                     scellCAC,
                     scellEIP}
        DESCRIPTION
             "Severity: Critical -- failure or failure imminent. An unexpected event occurred while a termination event was being processed. The value contained in the uei.type field describes the event as follows: <UL><LI>0 = Unrecognized Unexpected Event code. <LI>1 = Power failure before initialization could complete. <LI>2 = Recursive termination before initialization could complete. <LI>3 = Terminated during the first part post-termination preparation. <LI>4 = Terminated during the load of the G3 Glue registers. <LI>5 = Terminated during the second part post-termination preparation. <LI>6 = Terminated during event report block load. <LI>7 = Terminated during initialization of all hardware components and software data structures in preparation for restart. <LI>8 = Terminated during execution of an unrecognized post-termination operation (premature). <LI>9 = Power failure during execution of a post-termination operation. <LI>A = No good entries found in Termination Event Array. (Note that this condition is expected following the first boot of a newly manufactured HSV110 controller. In that case this event can be safely ignored; no action is necessary.) <LI>B = The EDC of one or more Termination Event Array entries is bad. <LI>C = Termination Event Array entry control block revision is different. <LI>D = Termination Event Array entry information block revision is different. <LI>E = Termination Event Array entry up time value is greater than the system's up time value. <LI>F = Termination Event Array entry up time value is less than the previous entry's up time value. <LI>10= Termination Event Array entry sequence number value is less than the previous entry's sequence number value. <LI>11= Detected an unrecognized dump/restart control code. <LI>12= Failed to terminate the entity dump loop. <LI>13= Unexpected dump entity size. <LI>14= Unexpected Event Log Packet processing stage code. <LI>15= Number of Termination Parameters supplied not equal to maximum allowed as required. </UL><P> The post-termination operation being performed at the time the unexpected event occurred is contained in the uei.pto field. Note: The lteihd and lter fields may not describe the event that caused the HSV110 controller to terminate operation depending on how far termination processing got before the unexpected event occurred."
           --#TYPE      "StorageCell Event"
           --#SUMMARY   "SCellName-TimeDate %s : SWCID %d : ECode: %d : CAC %d : EIP %d."
           --#ARGUMENTS {0,1,2,3,4,}
           --#SEVERITY  CRITICAL
           --#TIMEINDEX 136
           --#STATE     WARNING
        ::= 13601027
 
   sCellEventTrap-4-4 TRAP-TYPE  -- CAC Code: 0
        ENTERPRISE compaq
        VARIABLES  { scellNameDateTime,
                     scellSWComponent,
                     scellECode,
                     scellCAC,
                     scellEIP}
        DESCRIPTION
             "Severity: Normal -- informational in nature. The Storage System Event Log validation completed successfully. The content of the cinfo.scelcbi.status field, the cinfo.scelcbi structure, and the minfo.scelmi structure show the validated state of the Storage System Event Log. The meaning of the status value contained in the cinfo.scelcbi.status field is as follows: <UL><LI>0 = No problems found. </UL><P> Note: The content of the ainfo fields, cinfo.sctelcbi structure, and minfo.sctelmi structure is undefined."
           --#TYPE      "StorageCell Event"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13601028
 
   sCellEventTrap-4-5 TRAP-TYPE  -- CAC Code: 0
        ENTERPRISE compaq
        VARIABLES  { scellNameDateTime,
                     scellSWComponent,
                     scellECode,
                     scellCAC,
                     scellEIP}
        DESCRIPTION
             "Severity: Normal -- informational in nature. The Storage System Event Log validation failed. The content of the cinfo.scelcbi.status field, the cinfo.scelcbi structure, and the minfo.scelmi structure show the state of the Storage System Event Log at the time of the failure. The content and state of the Storage System Event Log have been initialized to their initial operational settings. The meaning of the status value contained in the cinfo.scelcbi.status field is as follows: <UL><LI>1 = Cookie value is not as expected. <LI>2 = Event data overflows the buffer. <LI>3 = Event data size is not a multiple of 4 bytes, is less than the minimum, or is greater than the maximum. <LI>4 = Event Information Packet type is greater than the maximum. <LI>5 = Event information size is not a multiple of 4 bytes, is less than the minimum, is greater than the maximum, doesn't match the Event Information Packet type size, or when combined with the entry header size doesn't equal the entry size. <LI>6 = Event code is zero. <LI>7 = Event is out of sequence. <LI>8 = Dead space area at the end of a partially packed buffer contains a nonzero value. <LI>9 = An event data block containing a nonzero value was found after end of event data was detected. <LI>A = Sequence number reset flag not set as expected. <LI>B = The event log contains no entries. <LI>C = Event data block read failed during maintenance verification. <LI>D = Event data block read failed during maintenance completion. <LI>E = Event data block erase failed during maintenance completion. <LI>F = Control block read failed during maintenance verification. <LI>17= The event log was destroyed and prepared for re-initialization. </UL><P> Note: The content of the ainfo fields, cinfo.sctelcbi structure, and minfo.sctelmi structure is undefined."
           --#TYPE      "StorageCell Event"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13601029
 
   sCellEventTrap-4-6 TRAP-TYPE  -- CAC Code: 1
        ENTERPRISE compaq
        VARIABLES  { scellNameDateTime,
                     scellSWComponent,
                     scellECode,
                     scellCAC,
                     scellEIP}
        DESCRIPTION
             "Severity: Critical -- failure or failure imminent. Event reports were lost due to an insufficient supply of Event Log Packets on the HSV110 controller that is the Storage System Master. The ainfo.events-not-reported field shows the number of event reports lost. Note: The content of the ainfo.quiesce-type field, ainfo.remote-event field cinfo.sctelcbi structure, and minfo.sctelmi structure is undefined."
           --#TYPE      "StorageCell Event"
           --#SUMMARY   "SCellName-TimeDate %s : SWCID %d : ECode: %d : CAC %d : EIP %d."
           --#ARGUMENTS {0,1,2,3,4,}
           --#SEVERITY  CRITICAL
           --#TIMEINDEX 136
           --#STATE     WARNING
        ::= 13601030
 
   sCellEventTrap-4-7 TRAP-TYPE  -- CAC Code: 1
        ENTERPRISE compaq
        VARIABLES  { scellNameDateTime,
                     scellSWComponent,
                     scellECode,
                     scellCAC,
                     scellEIP}
        DESCRIPTION
             "Severity: Critical -- failure or failure imminent. Event reports were lost due to an insufficient supply of Event Log Packets on the HSV110 controller that is not the Storage System Master. The ainfo.events-not-reported field shows the number of event reports lost. Note: The content of the ainfo.quiesce-type field, ainfo.remote-event field cinfo.sctelcbi structure, and minfo.sctelmi structure is undefined."
           --#TYPE      "StorageCell Event"
           --#SUMMARY   "SCellName-TimeDate %s : SWCID %d : ECode: %d : CAC %d : EIP %d."
           --#ARGUMENTS {0,1,2,3,4,}
           --#SEVERITY  CRITICAL
           --#TIMEINDEX 136
           --#STATE     WARNING
        ::= 13601031
 
   sCellEventTrap-4-8 TRAP-TYPE  -- CAC Code: 0
        ENTERPRISE compaq
        VARIABLES  { scellNameDateTime,
                     scellSWComponent,
                     scellECode,
                     scellCAC,
                     scellEIP}
        DESCRIPTION
             "Severity: Normal -- informational in nature. The Storage System Termination Event Log has become inaccessible. The content of the cinfo.sctelcbi.status field, the cinfo.sctelcbi structure, and the minfo.sctelmi structure show the current state of the Storage System Termination Event Log. The meaning of the status value contained in the cinfo.sctelcbi.status field is as follows: <UL><LI>F = Control block read failed during maintenance verification. <LI>10= Control block write failed during maintenance verification. <LI>11= Event data block write failed during maintenance update. <LI>12= Control block write failed during maintenance completion. <LI>13= Storage System Termination Event Log related send was unsuccessful or the master found that the Storage System Termination Event Log is inaccessible. <LI>16= Event data block read failed during retrieval request. </UL><P> Note: The content of the ainfo fields, cinfo.scelcbi structure, and minfo.scelmi structure is undefined."
           --#TYPE      "StorageCell Event"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13601032
 
   sCellEventTrap-4-9 TRAP-TYPE  -- CAC Code: 0
        ENTERPRISE compaq
        VARIABLES  { scellNameDateTime,
                     scellSWComponent,
                     scellECode,
                     scellCAC,
                     scellEIP}
        DESCRIPTION
             "Severity: Normal -- informational in nature. The Storage System Termination Event Log validation completed successfully. The content of the cinfo.sctelcbi.status field, the cinfo.sctelcbi structure, and the minfo.sctelmi structure show the validated state of the Storage System Termination Event Log. The meaning of the status value contained in the cinfo.sctelcbi.status field is as follows: <UL><LI>0 = No problems found. </UL><P> Note: The content of the ainfo fields, cinfo.scelcbi structure, and minfo.scelmi structure is undefined."
           --#TYPE      "StorageCell Event"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13601033
 
   sCellEventTrap-4-a TRAP-TYPE  -- CAC Code: 0
        ENTERPRISE compaq
        VARIABLES  { scellNameDateTime,
                     scellSWComponent,
                     scellECode,
                     scellCAC,
                     scellEIP}
        DESCRIPTION
             "Severity: Normal -- informational in nature. The Storage System Termination Event Log validation failed. The content of the cinfo.sctelcbi.status field, the cinfo.sctelcbi structure, and the minfo.sctelmi structure show the state of the Storage System Termination Event Log at the time of the failure. The meaning of the status value contained in the cinfo.sctelcbi.status field is as follows: <UL><LI>F = Control block read failed during maintenance verification. <LI>10= Control block write failed during maintenance verification. <LI>11= Event data block write failed during maintenance update. <LI>12= Control block write failed during maintenance completion. <LI>13= Storage System Termination Event Log related send was unsuccessful or the master found that the Storage System Termination Event Log is inaccessible. <LI>16= Event data block read failed during retrieval request. <LI>17= The log was destroyed and prepared for re-initialization. </UL><P> Note: The content of the ainfo fields, cinfo.scelcbi structure, and minfo.scelmi structure is undefined."
           --#TYPE      "StorageCell Event"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13601034
 
   sCellEventTrap-4-b TRAP-TYPE  -- CAC Code: 0
        ENTERPRISE compaq
        VARIABLES  { scellNameDateTime,
                     scellSWComponent,
                     scellECode,
                     scellCAC,
                     scellEIP}
        DESCRIPTION
             "Severity: Normal -- informational in nature. The Storage System Termination Event Log has been updated with the termination event information obtained from the HSV110 controller that is not the Storage System Master. The content of the cinfo.sctelcbi.status field, the cinfo.sctelcbi structure, and the minfo.sctelmi structure show the updated state of the Storage System Termination Event Log. The meaning of the status value contained in the cinfo.sctelcbi.status field is as follows: <UL><LI>0 = No problems found. </UL><P> Note: The content of the ainfo fields, cinfo.scelcbi structure, and minfo.scelmi structure is undefined."
           --#TYPE      "StorageCell Event"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13601035
 
   sCellEventTrap-4-c TRAP-TYPE  -- CAC Code: 1
        ENTERPRISE compaq
        VARIABLES  { scellNameDateTime,
                     scellSWComponent,
                     scellECode,
                     scellCAC,
                     scellEIP}
        DESCRIPTION
             "Severity: Critical -- failure or failure imminent. The Fault Manager on the Storage System Master received an invalid Event Information Packet from the remote Fault Manager. The header information from the invalid Event Information Packet is contained in the ainfo.remote-event field. Note: The content of the ainfo.quiesce-type field, ainfo.events-not-reported field, cinfo.scelcbi structure, cinfo.sctelcbi structure, minfo.scelmi structure, and minfo.sctelmi structure is undefined."
           --#TYPE      "StorageCell Event"
           --#SUMMARY   "SCellName-TimeDate %s : SWCID %d : ECode: %d : CAC %d : EIP %d."
           --#ARGUMENTS {0,1,2,3,4,}
           --#SEVERITY  CRITICAL
           --#TIMEINDEX 136
           --#STATE     WARNING
        ::= 13601036
 
   sCellEventTrap-4-d TRAP-TYPE  -- CAC Code: 0
        ENTERPRISE compaq
        VARIABLES  { scellNameDateTime,
                     scellSWComponent,
                     scellECode,
                     scellCAC,
                     scellEIP}
        DESCRIPTION
             "Severity: Normal -- informational in nature. The Fault Manager operation was made quiescent. If the ainfo.quiesce-type field is equal to 0, the operation was performed on both HSV110 controllers. If the ainfo.quiesce-type field is equal to 1, the operation was performed only on the HSV110 controller that is not the Storage System Master. Note: The content of the ainfo.events-not-reported field, cinfo.scelcbi structure, cinfo.sctelcbi structure, minfo.scelmi structure, and minfo.sctelmi structure is undefined."
           --#TYPE      "StorageCell Event"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13601037
 
   sCellEventTrap-4-e TRAP-TYPE  -- CAC Code: 3
        ENTERPRISE compaq
        VARIABLES  { scellNameDateTime,
                     scellSWComponent,
                     scellECode,
                     scellCAC,
                     scellEIP}
        DESCRIPTION
             "Severity: Undetermined -- more information needed to determine severity. An HSV110 controller sent a last gasp message prior to terminating operation with an indication that the HSV110 controller identified in the lter.terminating-ctrlr field should also terminate operation."
           --#TYPE      "StorageCell Event"
           --#SUMMARY   "SCellName-TimeDate %s : SWCID %d : ECode: %d : CAC %d : EIP %d."
           --#ARGUMENTS {0,1,2,3,4,}
           --#SEVERITY  CRITICAL
           --#TIMEINDEX 136
           --#STATE     WARNING
        ::= 13601038
 
   sCellEventTrap-4-f TRAP-TYPE  -- CAC Code: 0
        ENTERPRISE compaq
        VARIABLES  { scellNameDateTime,
                     scellSWComponent,
                     scellECode,
                     scellCAC,
                     scellEIP}
        DESCRIPTION
             "Severity: Normal -- informational in nature. This HSV110 controller sent its termination event information to the HSV110 controller that is the Storage System Master. The content of the cinfo.sctelcbi.status field, the cinfo.sctelcbi structure, and the minfo.sctelmi structure show the updated state of the Storage System Termination Event Log. The meaning of the status value contained in the cinfo.sctelcbi.status field is as follows: <UL><LI>0 = No problems found. </UL><P> Note: The content of the ainfo fields, cinfo.scelcbi structure, and minfo.scelmi structure is undefined."
           --#TYPE      "StorageCell Event"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13601039
 
   sCellEventTrap-4-10 TRAP-TYPE  -- CAC Code: 1
        ENTERPRISE compaq
        VARIABLES  { scellNameDateTime,
                     scellSWComponent,
                     scellECode,
                     scellCAC,
                     scellEIP}
        DESCRIPTION
             "Severity: Critical -- failure or failure imminent. Event reports were lost due to an insufficient supply of ISR Event Log Packets on the HSV110 controller that is the Storage System Master. The ainfo.events-not-reported field shows the number of event reports lost. Note: The content of the ainfo.quiesce-type field, ainfo.remote-event field cinfo.sctelcbi structure, and minfo.sctelmi structure is undefined."
           --#TYPE      "StorageCell Event"
           --#SUMMARY   "SCellName-TimeDate %s : SWCID %d : ECode: %d : CAC %d : EIP %d."
           --#ARGUMENTS {0,1,2,3,4,}
           --#SEVERITY  CRITICAL
           --#TIMEINDEX 136
           --#STATE     WARNING
        ::= 13601040
 
   sCellEventTrap-4-11 TRAP-TYPE  -- CAC Code: 1
        ENTERPRISE compaq
        VARIABLES  { scellNameDateTime,
                     scellSWComponent,
                     scellECode,
                     scellCAC,
                     scellEIP}
        DESCRIPTION
             "Severity: Critical -- failure or failure imminent. Event reports were lost due to an insufficient supply of ISR Event Log Packets on the HSV110 controller that is not the Storage System Master. The ainfo.events-not-reported field shows the number of event reports lost. Note: The content of the ainfo.quiesce-type field, ainfo.remote-event field cinfo.sctelcbi structure, and minfo.sctelmi structure is undefined."
           --#TYPE      "StorageCell Event"
           --#SUMMARY   "SCellName-TimeDate %s : SWCID %d : ECode: %d : CAC %d : EIP %d."
           --#ARGUMENTS {0,1,2,3,4,}
           --#SEVERITY  CRITICAL
           --#TIMEINDEX 136
           --#STATE     WARNING
        ::= 13601041
 
   sCellEventTrap-6-0 TRAP-TYPE  -- CAC Code: 40
        ENTERPRISE compaq
        VARIABLES  { scellNameDateTime,
                     scellSWComponent,
                     scellECode,
                     scellCAC,
                     scellEIP}
        DESCRIPTION
             "Severity: Critical -- failure or failure imminent. A physical disk drive has reported that it has exceeded its failure prediction threshold. The identity of the physical disk drive is contained in the device field. The Fibre Channel port used to communicate with the physical disk drive is contained in the cerp-id field. The HSV110 controller internal Fibre Channel port number used to communicate with the physical disk drive is contained in the port field. The arbitrated loop physical address of the physical disk drive is contained in the al-pa field. The location of the physical disk drive is determined by the content of the dencl-num field as follows: <UL><LI>If dencl-num is less than 99, the location is as indicated by the content of the rack-num, dencl-num, and bay fields. <LI>If dencl-num is equal to 99, the location is unknown. Note that the content of the rack-num and bay fields is undefined in this case. <LI>If dencl-num is greater than 99, the HSV110 controller does not have proof of the current location but the last known location is indicated by the content of the rack-num, dencl-num, and bay fields. Subtract 100 from the content of those fields to determine the actual last known location. If there have been no configuration changes, the last known location values will be accurate. The identity contained in the device field should be used to confirm the last known location values. </UL>Note that the content of the rack-num field will not be valid until a future release. The Fibre Channel Exchange Descriptor class is contained in the fed-class field. The command issued to the physical disk drive is contained in the cmd field. The sense data obtained from the physical disk drive as a result of the failure prediction threshold exceeded error is contained in the error field. The enclosures array shows the drive enclosures available on the Fibre Channel port identified in the cerp-id field. The location of an available drive enclosure is determined by the content of the enclosures.dencl-num field as follows: <UL><LI>If enclosures.dencl-num is less than 99, the location is as indicated by the content of the enclosures.rack-num and enclosures.dencl-num fields. <LI>If enclosures.dencl-num is equal to 99, the enclosures array entry is not used. Note that the content of the enclosures.rack-num field is undefined in this case. <LI>If enclosures.dencl-num is greater than 99, the HSV110 controller does not have proof of the current location but the last known location is indicated by the content of the enclosures.rack-num and enclosures.dencl-num fields. Subtract 100 from the content of those fields to determine the actual last known location. If there have been no configuration changes, the last known location values will be accurate. </UL>Note that the content of the enclosures.rack-num field will not be valid until a future release."
           --#TYPE      "StorageCell Event"
           --#SUMMARY   "SCellName-TimeDate %s : SWCID %d : ECode: %d : CAC %d : EIP %d."
           --#ARGUMENTS {0,1,2,3,4,}
           --#SEVERITY  CRITICAL
           --#TIMEINDEX 136
           --#STATE     WARNING
        ::= 13601536
 
   sCellEventTrap-6-1 TRAP-TYPE  -- CAC Code: 4a
        ENTERPRISE compaq
        VARIABLES  { scellNameDateTime,
                     scellSWComponent,
                     scellECode,
                     scellCAC,
                     scellEIP}
        DESCRIPTION
             "Severity: Warning -- not failed but attention recommended or required. A Fibre Channel port on the HSV110 controller has failed to respond. The identity of the affected Fibre Channel port is contained in the cerp-id field. The HSV110 controller internal Fibre Channel port number of the affected Fibre Channel port is contained in the port field. The peb array contains the port event block information. The peq-frz-prod-index field contains the index to the port event block in use when the Tachyon chip entered the frozen state. The peq-prod-index field contains the index to the next port event block. The peq-cons-index field contains the index to the next port event block to be acted upon. The failure-cause field contains the internal routing value as follows: <UL><LI>1 - Excessive exchange timeouts on loop <LI>2 - Excessive link errors on loop <LI>3 - Exhausted Link Down retries on loop with signal <LI>4 - Exhausted Link Down retries on loop with loss of signal <LI>5 - Excessive link inits on loop without completing device discovery </UL>"
           --#TYPE      "StorageCell Event"
           --#SUMMARY   "SCellName-TimeDate %s : SWCID %d : ECode: %d : CAC %d : EIP %d."
           --#ARGUMENTS {0,1,2,3,4,}
           --#SEVERITY  MINOR
           --#TIMEINDEX 136
           --#STATE     WARNING
        ::= 13601537
 
   sCellEventTrap-6-2 TRAP-TYPE  -- CAC Code: 0
        ENTERPRISE compaq
        VARIABLES  { scellNameDateTime,
                     scellSWComponent,
                     scellECode,
                     scellCAC,
                     scellEIP}
        DESCRIPTION
             "Severity: Normal -- informational in nature. A physical disk drive has reported a check condition error. The identity of the physical disk drive is contained in the device field. The Fibre Channel port used to communicate with the physical disk drive is contained in the cerp-id field. The HSV110 controller internal Fibre Channel port number used to communicate with the physical disk drive is contained in the port field. The arbitrated loop physical address of the physical disk drive is contained in the al-pa field. The location of the physical disk drive is determined by the content of the dencl-num field as follows: <UL><LI>If dencl-num is less than 99, the location is as indicated by the content of the rack-num, dencl-num, and bay fields. <LI>If dencl-num is equal to 99, the location is unknown. Note that the content of the rack-num and bay fields is undefined in this case. <LI>If dencl-num is greater than 99, the HSV110 controller does not have proof of the current location but the last known location is indicated by the content of the rack-num, dencl-num, and bay fields. Subtract 100 from the content of those fields to determine the actual last known location. If there have been no configuration changes, the last known location values will be accurate. The identity contained in the device field should be used to confirm the last known location values. </UL>Note that the content of the rack-num field will not be valid until a future release. The Fibre Channel Exchange Descriptor class is contained in the fed-class field. The command issued to the physical disk drive is contained in the cmd field. The sense data obtained from the physical disk drive as a result of the check condition error is contained in the error field. The enclosures array shows the drive enclosures available on the Fibre Channel port identified in the cerp-id field. The location of an available drive enclosure is determined by the content of the enclosures.dencl-num field as follows: <UL><LI>If enclosures.dencl-num is less than 99, the location is as indicated by the content of the enclosures.rack-num and enclosures.dencl-num fields. <LI>If enclosures.dencl-num is equal to 99, the enclosures array entry is not used. Note that the content of the enclosures.rack-num field is undefined in this case. <LI>If enclosures.dencl-num is greater than 99, the HSV110 controller does not have proof of the current location but the last known location is indicated by the content of the enclosures.rack-num and enclosures.dencl-num fields. Subtract 100 from the content of those fields to determine the actual last known location. If there have been no configuration changes, the last known location values will be accurate. </UL>Note that the content of the enclosures.rack-num field will not be valid until a future release."
           --#TYPE      "StorageCell Event"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13601538
 
   sCellEventTrap-6-3 TRAP-TYPE  -- CAC Code: 47
        ENTERPRISE compaq
        VARIABLES  { scellNameDateTime,
                     scellSWComponent,
                     scellECode,
                     scellCAC,
                     scellEIP}
        DESCRIPTION
             "Severity: Warning -- not failed but attention recommended or required. An exchange sent to a physical disk drive or another HSV110 controller via the mirror port or a Fibre Channel port has timed out. The identity of the intended recipient is contained in the device field. The Fibre Channel port over which the frame was sent is identified in the cerp-id field. The HSV110 controller internal Fibre Channel port number over which the frame was sent is contained in the port field. The arbitrated loop physical address of the intended recipient is contained in the al-pa field. The missing-port and missing-cerp-id fields are unused. The location of the intended recipient is determined by the content of the dencl-num field as follows: <UL><LI>If dencl-num is less than 99, the location is as indicated by the content of the rack-num, dencl-num, and bay fields. <LI>If dencl-num is equal to 99, the location is unknown. Note that the content of the rack-num and bay fields is undefined in this case. <LI>If dencl-num is greater than 99, the HSV110 controller does not have proof of the current location but the last known location is indicated by the content of the rack-num, dencl-num, and bay fields. Subtract 100 from the content of those fields to determine the actual last known location. If there have been no configuration changes, the last known location values will be accurate. The identity contained in the device field should be used to confirm the last known location values. </UL>Note that the content of the rack-num field will not be valid until a future release. The number of timeouts detected is contained in the num-times field. The enclosures array shows the drive enclosures available on the Fibre Channel port identified in the cerp-id field. The location of an available drive enclosure is determined by the content of the enclosures.dencl-num field as follows: <UL><LI>If enclosures.dencl-num is less than 99, the location is as indicated by the content of the enclosures.rack-num and enclosures.dencl-num fields. <LI>If enclosures.dencl-num is equal to 99, the enclosures array entry is not used. Note that the content of the enclosures.rack-num field is undefined in this case. <LI>If enclosures.dencl-num is greater than 99, the HSV110 controller does not have proof of the current location but the last known location is indicated by the content of the enclosures.rack-num and enclosures.dencl-num fields. Subtract 100 from the content of those fields to determine the actual last known location. If there have been no configuration changes, the last known location values will be accurate. </UL>Note that the content of the enclosures.rack-num field will not be valid until a future release."
           --#TYPE      "StorageCell Event"
           --#SUMMARY   "SCellName-TimeDate %s : SWCID %d : ECode: %d : CAC %d : EIP %d."
           --#ARGUMENTS {0,1,2,3,4,}
           --#SEVERITY  MINOR
           --#TIMEINDEX 136
           --#STATE     WARNING
        ::= 13601539
 
   sCellEventTrap-6-4 TRAP-TYPE  -- CAC Code: 48
        ENTERPRISE compaq
        VARIABLES  { scellNameDateTime,
                     scellSWComponent,
                     scellECode,
                     scellCAC,
                     scellEIP}
        DESCRIPTION
             "Severity: Warning -- not failed but attention recommended or required. Work was unexpectedly sent to this HSV110 controller by a physical disk drive or another HSV110 controller. This HSV110 controller did not originate the work. The identity of the sender is contained in the device field. The Fibre Channel port over which the unexpected work was received is identified in the cerp-id field. The HSV110 controller internal Fibre Channel port number over which the unexpected work was received is contained in the port field. The arbitrated loop physical address of the sender is contained in the al-pa field. The location of the sender is determined by the content of the dencl-num field as follows: <UL><LI>If dencl-num is less than 99, the location is as indicated by the content of the rack-num, dencl-num, and bay fields. <LI>If dencl-num is equal to 99, the location is unknown. Note that the content of the rack-num and bay fields is undefined in this case. <LI>If dencl-num is greater than 99, the HSV110 controller does not have proof of the current location but the last known location is indicated by the content of the rack-num, dencl-num, and bay fields. Subtract 100 from the content of those fields to determine the actual last known location. If there have been no configuration changes, the last known location values will be accurate. The identity contained in the device field should be used to confirm the last known location values. </UL>Note that the content of the rack-num field will not be valid until a future release. The hdr-cdb field contains the command descriptor block and Fibre Channel header information associated with the unexpected work."
           --#TYPE      "StorageCell Event"
           --#SUMMARY   "SCellName-TimeDate %s : SWCID %d : ECode: %d : CAC %d : EIP %d."
           --#ARGUMENTS {0,1,2,3,4,}
           --#SEVERITY  MINOR
           --#TIMEINDEX 136
           --#STATE     WARNING
        ::= 13601540
 
   sCellEventTrap-6-5 TRAP-TYPE  -- CAC Code: 49
        ENTERPRISE compaq
        VARIABLES  { scellNameDateTime,
                     scellSWComponent,
                     scellECode,
                     scellCAC,
                     scellEIP}
        DESCRIPTION
             "Severity: Warning -- not failed but attention recommended or required. Work has been sent to a physical disk drive or another HSV110 controller via the mirror port but it did not respond. The identity of the intended target is contained in the device field. The Fibre Channel port over which the work was sent is identified in the cerp-id field. The HSV110 controller internal Fibre Channel port over which the work was sent is contained in the port field. The arbitrated loop physical address of the intended target is contained in the al-pa field. The location of the intended target is determined by the content of the dencl-num field as follows: <UL><LI>If dencl-num is less than 99, the location is as indicated by the content of the rack-num, dencl-num, and bay fields. <LI>If dencl-num is equal to 99, the location is unknown. Note that the content of the rack-num and bay fields is undefined in this case. <LI>If dencl-num is greater than 99, the HSV110 controller does not have proof of the current location but the last known location is indicated by the content of the rack-num, dencl-num, and bay fields. Subtract 100 from the content of those fields to determine the actual last known location. If there have been no configuration changes, the last known location values will be accurate. The identity contained in the device field should be used to confirm the last known location values. </UL>Note that the content of the rack-num field will not be valid until a future release. The Fibre Channel Exchange Descriptor class is contained in the fed-class field. The command issued to the intended target is contained in the cmd field. Note that in this case the content of the error field is undefined. The enclosures array shows the drive enclosures available on the Fibre Channel port identified in the cerp-id field. The location of an available drive enclosure is determined by the content of the enclosures.dencl-num field as follows: <UL><LI>If enclosures.dencl-num is less than 99, the location is as indicated by the content of the enclosures.rack-num and enclosures.dencl-num fields. <LI>If enclosures.dencl-num is equal to 99, the enclosures array entry is not used. Note that the content of the enclosures.rack-num field is undefined in this case. <LI>If enclosures.dencl-num is greater than 99, the HSV110 controller does not have proof of the current location but the last known location is indicated by the content of the enclosures.rack-num and enclosures.dencl-num fields. Subtract 100 from the content of those fields to determine the actual last known location. If there have been no configuration changes, the last known location values will be accurate. </UL>Note that the content of the enclosures.rack-num field will not be valid until a future release."
           --#TYPE      "StorageCell Event"
           --#SUMMARY   "SCellName-TimeDate %s : SWCID %d : ECode: %d : CAC %d : EIP %d."
           --#ARGUMENTS {0,1,2,3,4,}
           --#SEVERITY  MINOR
           --#TIMEINDEX 136
           --#STATE     WARNING
        ::= 13601541
 
   sCellEventTrap-6-7 TRAP-TYPE  -- CAC Code: 47
        ENTERPRISE compaq
        VARIABLES  { scellNameDateTime,
                     scellSWComponent,
                     scellECode,
                     scellCAC,
                     scellEIP}
        DESCRIPTION
             "Severity: Warning -- not failed but attention recommended or required. A Target Discovery Service Descriptor exchange sent to a physical disk drive has timed out. The identity of the physical disk drive is contained in the device field. The Fibre Channel port used to communicate with the physical disk drive is contained in the cerp-id field. The HSV110 controller internal Fibre Channel port number used to communicate with the physical disk drive is contained in the port field. The arbitrated loop physical address of the physical disk drive is contained in the al-pa field. The location of the physical disk drive is determined by the content of the dencl-num field as follows: <UL><LI>If dencl-num is less than 99, the location is as indicated by the content of the rack-num, dencl-num, and bay fields. <LI>If dencl-num is equal to 99, the location is unknown. Note that the content of the rack-num and bay fields is undefined in this case. <LI>If dencl-num is greater than 99, the HSV110 controller does not have proof of the current location but the last known location is indicated by the content of the rack-num, dencl-num, and bay fields. Subtract 100 from the content of those fields to determine the actual last known location. If there have been no configuration changes, the last known location values will be accurate. The identity contained in the device field should be used to confirm the last known location values. </UL>Note that the content of the rack-num field will not be valid until a future release. The Fibre Channel Exchange Descriptor class is contained in the fed-class field. The command issued to the physical disk drive is contained in the cmd field. Note that in this case the content of the error field is undefined. The enclosures array shows the drive enclosures available on the Fibre Channel port identified in the cerp-id field. The location of an available drive enclosure is determined by the content of the enclosures.dencl-num field as follows: <UL><LI>If enclosures.dencl-num is less than 99, the location is as indicated by the content of the enclosures.rack-num and enclosures.dencl-num fields. <LI>If enclosures.dencl-num is equal to 99, the enclosures array entry is not used. Note that the content of the enclosures.rack-num field is undefined in this case. <LI>If enclosures.dencl-num is greater than 99, the HSV110 controller does not have proof of the current location but the last known location is indicated by the content of the enclosures.rack-num and enclosures.dencl-num fields. Subtract 100 from the content of those fields to determine the actual last known location. If there have been no configuration changes, the last known location values will be accurate. </UL>Note that the content of the enclosures.rack-num field will not be valid until a future release."
           --#TYPE      "StorageCell Event"
           --#SUMMARY   "SCellName-TimeDate %s : SWCID %d : ECode: %d : CAC %d : EIP %d."
           --#ARGUMENTS {0,1,2,3,4,}
           --#SEVERITY  MINOR
           --#TIMEINDEX 136
           --#STATE     WARNING
        ::= 13601543
 
   sCellEventTrap-6-8 TRAP-TYPE  -- CAC Code: 0
        ENTERPRISE compaq
        VARIABLES  { scellNameDateTime,
                     scellSWComponent,
                     scellECode,
                     scellCAC,
                     scellEIP}
        DESCRIPTION
             "Severity: Normal -- informational in nature. An excessive number of link errors were detected on a HSV110 controller's Fibre Channel port. The identity of the affected Fibre Channel port is contained in the cerp-id field. The HSV110 controller internal Fibre Channel port number of the affected Fibre Channel port is contained in the port field. This is an informational event triggered by the occurrence of an excessive number of Tachyon chip link status errors detected within a particular link status error type. The number of occurrences of each link status error type is contained in a separate type-specific field (e.g., loss-of-signal, bad-rx-char, etc.). The HSV110 controller checks each of its Fibre Channel port's for excessive link status errors periodically."
           --#TYPE      "StorageCell Event"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13601544
 
   sCellEventTrap-6-9 TRAP-TYPE  -- CAC Code: 40
        ENTERPRISE compaq
        VARIABLES  { scellNameDateTime,
                     scellSWComponent,
                     scellECode,
                     scellCAC,
                     scellEIP}
        DESCRIPTION
             "Severity: Critical -- failure or failure imminent. A physical disk drive has reported numerous failure prediction threshold exceeded errors. The identity of the physical disk drive is contained in the device field. The Fibre Channel port used to communicate with the physical disk drive is contained in the cerp-id field. The HSV110 controller internal Fibre Channel port number used to communicate with the physical disk drive is contained in the port field. The arbitrated loop physical address of the physical disk drive is contained in the al-pa field. The missing-port and missing-cerp-id fields are unused. The location of the physical disk drive is determined by the content of the dencl-num field as follows: <UL><LI>If dencl-num is less than 99, the location is as indicated by the content of the rack-num, dencl-num, and bay fields. <LI>If dencl-num is equal to 99, the location is unknown. Note that the content of the rack-num and bay fields is undefined in this case. <LI>If dencl-num is greater than 99, the HSV110 controller does not have proof of the current location but the last known location is indicated by the content of the rack-num, dencl-num, and bay fields. Subtract 100 from the content of those fields to determine the actual last known location. If there have been no configuration changes, the last known location values will be accurate. The identity contained in the device field should be used to confirm the last known location values. </UL>Note that the content of the rack-num field will not be valid until a future release. The Fibre Channel Exchange Descriptor class is contained in the fed-class field. The num-times field is the number of failure prediction threshold exceeded errors reported by the physical disk drive in the previous minute. The enclosures array shows the drive enclosures available on the Fibre Channel port identified in the cerp-id field. The location of an available drive enclosure is determined by the content of the enclosures.dencl-num field as follows: <UL><LI>If enclosures.dencl-num is less than 99, the location is as indicated by the content of the enclosures.rack-num and enclosures.dencl-num fields. <LI>If enclosures.dencl-num is equal to 99, the enclosures array entry is not used. Note that the content of the enclosures.rack-num field is undefined in this case. <LI>If enclosures.dencl-num is greater than 99, the HSV110 controller does not have proof of the current location but the last known location is indicated by the content of the enclosures.rack-num and enclosures.dencl-num fields. Subtract 100 from the content of those fields to determine the actual last known location. If there have been no configuration changes, the last known location values will be accurate. </UL>Note that the content of the enclosures.rack-num field will not be valid until a future release."
           --#TYPE      "StorageCell Event"
           --#SUMMARY   "SCellName-TimeDate %s : SWCID %d : ECode: %d : CAC %d : EIP %d."
           --#ARGUMENTS {0,1,2,3,4,}
           --#SEVERITY  CRITICAL
           --#TIMEINDEX 136
           --#STATE     WARNING
        ::= 13601545
 
   sCellEventTrap-6-a TRAP-TYPE  -- CAC Code: 0
        ENTERPRISE compaq
        VARIABLES  { scellNameDateTime,
                     scellSWComponent,
                     scellECode,
                     scellCAC,
                     scellEIP}
        DESCRIPTION
             "Severity: Normal -- informational in nature. A physical disk drive has reported numerous check condition errors. The identity of the physical disk drive is contained in the device field. The Fibre Channel port used to communicate with the physical disk drive is contained in the cerp-id field. The HSV110 controller internal Fibre Channel port number used to communicate with the physical disk drive is contained in the port field. The arbitrated loop physical address of the physical disk drive is contained in the al-pa field. The missing-port and missing-cerp-id fields are unused. The location of the physical disk drive is determined by the content of the dencl-num field as follows: <UL><LI>If dencl-num is less than 99, the location is as indicated by the content of the rack-num, dencl-num, and bay fields. <LI>If dencl-num is equal to 99, the location is unknown. Note that the content of the rack-num and bay fields is undefined in this case. <LI>If dencl-num is greater than 99, the HSV110 controller does not have proof of the current location but the last known location is indicated by the content of the rack-num, dencl-num, and bay fields. Subtract 100 from the content of those fields to determine the actual last known location. If there have been no configuration changes, the last known location values will be accurate. The identity contained in the device field should be used to confirm the last known location values. </UL>Note that the content of the rack-num field will not be valid until a future release. The Fibre Channel Exchange Descriptor class is contained in the fed-class field. The num-times field is the number of check condition errors reported by the physical disk drive in the previous minute. The enclosures array shows the drive enclosures available on the Fibre Channel port identified in the cerp-id field. The location of an available drive enclosure is determined by the content of the enclosures.dencl-num field as follows: <UL><LI>If enclosures.dencl-num is less than 99, the location is as indicated by the content of the enclosures.rack-num and enclosures.dencl-num fields. <LI>If enclosures.dencl-num is equal to 99, the enclosures array entry is not used. Note that the content of the enclosures.rack-num field is undefined in this case. <LI>If enclosures.dencl-num is greater than 99, the HSV110 controller does not have proof of the current location but the last known location is indicated by the content of the enclosures.rack-num and enclosures.dencl-num fields. Subtract 100 from the content of those fields to determine the actual last known location. If there have been no configuration changes, the last known location values will be accurate. </UL>Note that the content of the enclosures.rack-num field will not be valid until a future release."
           --#TYPE      "StorageCell Event"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13601546
 
   sCellEventTrap-6-b TRAP-TYPE  -- CAC Code: 47
        ENTERPRISE compaq
        VARIABLES  { scellNameDateTime,
                     scellSWComponent,
                     scellECode,
                     scellCAC,
                     scellEIP}
        DESCRIPTION
             "Severity: Warning -- not failed but attention recommended or required. A non-data exchange sent to a physical disk drive has timed out. The identity of the physical disk drive is contained in the device field. The Fibre Channel port used to communicate with the physical disk drive is contained in the cerp-id field. The HSV110 controller internal Fibre Channel port number used to communicate with the physical disk drive is contained in the port field. The arbitrated loop physical address of the physical disk drive is contained in the al-pa field. The location of the physical disk drive is determined by the content of the dencl-num field as follows: <UL><LI>If dencl-num is less than 99, the location is as indicated by the content of the rack-num, dencl-num, and bay fields. <LI>If dencl-num is equal to 99, the location is unknown. Note that the content of the rack-num and bay fields is undefined in this case. <LI>If dencl-num is greater than 99, the HSV110 controller does not have proof of the current location but the last known location is indicated by the content of the rack-num, dencl-num, and bay fields. Subtract 100 from the content of those fields to determine the actual last known location. If there have been no configuration changes, the last known location values will be accurate. The identity contained in the device field should be used to confirm the last known location values. </UL>Note that the content of the rack-num field will not be valid until a future release. The Fibre Channel Exchange Descriptor class is contained in the fed-class field. The command issued to the physical disk drive is contained in the cmd field. Note that in this case the content of the error field is undefined. The enclosures array shows the drive enclosures available on the Fibre Channel port identified in the cerp-id field. The location of an available drive enclosure is determined by the content of the enclosures.dencl-num field as follows: <UL><LI>If enclosures.dencl-num is less than 99, the location is as indicated by the content of the enclosures.rack-num and enclosures.dencl-num fields. <LI>If enclosures.dencl-num is equal to 99, the enclosures array entry is not used. Note that the content of the enclosures.rack-num field is undefined in this case. <LI>If enclosures.dencl-num is greater than 99, the HSV110 controller does not have proof of the current location but the last known location is indicated by the content of the enclosures.rack-num and enclosures.dencl-num fields. Subtract 100 from the content of those fields to determine the actual last known location. If there have been no configuration changes, the last known location values will be accurate. </UL>Note that the content of the enclosures.rack-num field will not be valid until a future release."
           --#TYPE      "StorageCell Event"
           --#SUMMARY   "SCellName-TimeDate %s : SWCID %d : ECode: %d : CAC %d : EIP %d."
           --#ARGUMENTS {0,1,2,3,4,}
           --#SEVERITY  MINOR
           --#TIMEINDEX 136
           --#STATE     WARNING
        ::= 13601547
 
   sCellEventTrap-6-c TRAP-TYPE  -- CAC Code: 0
        ENTERPRISE compaq
        VARIABLES  { scellNameDateTime,
                     scellSWComponent,
                     scellECode,
                     scellCAC,
                     scellEIP}
        DESCRIPTION
             "Severity: Normal -- informational in nature. A loop switch has been detected on a Fibre Channel port. The identity of the Fibre Channel port is contained in the cerp-id field. The HSV110 controller internal Fibre Channel port number is contained in the port field. Note that in this case the content of the device, al-pa, rack-num, dencl-num, bay, fed-class and num-times fields is undefined. The enclosures array shows the drive enclosures available on the Fibre Channel port identified in the cerp-id field. The missing-port and missing-cerp-id fields are unused. The location of an available drive enclosure is determined by the content of the enclosures.dencl-num field as follows: <UL><LI>If enclosures.dencl-num is less than 99, the location is as indicated by the content of the enclosures.rack-num and enclosures.dencl-num fields. <LI>If enclosures.dencl-num is equal to 99, the enclosures array entry is not used. Note that the content of the enclosures.rack-num field is undefined in this case. <LI>If enclosures.dencl-num is greater than 99, the HSV110 controller does not have proof of the current location but the last known location is indicated by the content of the enclosures.rack-num and enclosures.dencl-num fields. Subtract 100 from the content of those fields to determine the actual last known location. If there have been no configuration changes, the last known location values will be accurate. </UL>Note that the content of the enclosures.rack-num field will not be valid until a future release."
           --#TYPE      "StorageCell Event"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13601548
 
   sCellEventTrap-6-d TRAP-TYPE  -- CAC Code: 0
        ENTERPRISE compaq
        VARIABLES  { scellNameDateTime,
                     scellSWComponent,
                     scellECode,
                     scellCAC,
                     scellEIP}
        DESCRIPTION
             "Severity: Normal -- informational in nature. The location of a physical disk drive previously reported as unknown is now known. The identity of the physical disk drive is contained in the device field. The Fibre Channel port used to communicate with the physical disk drive is contained in the cerp-id field. The HSV110 controller internal Fibre Channel port number used to communicate with the physical disk drive is contained in the port field. The arbitrated loop physical address of the physical disk drive is contained in the al-pa field. The missing-port and missing-cerp-id fields are unused. The location of the physical disk drive is contained in the rack-num, dencl-num, and bay fields. Note that the content of the rack-num field will not be valid until a future release. Note also that in this case the content of fed-class, al-pa and num-times fields are undefined. The enclosures array shows the drive enclosures available on the Fibre Channel port identified in the cerp-id field. The location of an available drive enclosure is determined by the content of the enclosures.dencl-num field as follows: <UL><LI>If enclosures.dencl-num is less than 99, the location is as indicated by the content of the enclosures.rack-num and enclosures.dencl-num fields. <LI>If enclosures.dencl-num is equal to 99, the enclosures array entry is not used. Note that the content of the enclosures.rack-num field is undefined in this case. <LI>If enclosures.dencl-num is greater than 99, the HSV110 controller does not have proof of the current location but the last known location is indicated by the content of the enclosures.rack-num and enclosures.dencl-num fields. Subtract 100 from the content of those fields to determine the actual last known location. If there have been no configuration changes, the last known location values will be accurate. </UL>Note that the content of the enclosures.rack-num field will not be valid until a future release."
           --#TYPE      "StorageCell Event"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13601549
 
   sCellEventTrap-6-e TRAP-TYPE  -- CAC Code: 96
        ENTERPRISE compaq
        VARIABLES  { scellNameDateTime,
                     scellSWComponent,
                     scellECode,
                     scellCAC,
                     scellEIP}
        DESCRIPTION
             "Severity: Critical -- failure or failure imminent. A Drive Enclosure Environmental Monitoring Unit requested a code update but the code update could not be found, so the update was not performed. The identity of the affected Drive Enclosure Environmental Monitoring Unit is contained in the device field. The Fibre Channel port used to communicate with the Drive Enclosure Environmental Monitoring Unit is contained in the cerp-id field. The HSV110 controller internal Fibre Channel port number used to communicate with the Drive Enclosure Environmental Monitoring Unit is contained in the port field. The missing-port and missing-cerp-id fields are unused. The location of the Drive Enclosure Environmental Monitoring Unit is contained in the rack-num and dencl-num fields. Note that the content of the rack-num field will not be valid until a future release. Note also that in this case the content of the al-pa, bay, fed-class and num-times field is undefined. The enclosures array shows the drive enclosures available on the Fibre Channel port identified in the cerp-id field. The location of an available drive enclosure is determined by the content of the enclosures.dencl-num field as follows: <UL><LI>If enclosures.dencl-num is less than 99, the location is as indicated by the content of the enclosures.rack-num and enclosures.dencl-num fields. <LI>If enclosures.dencl-num is equal to 99, the enclosures array entry is not used. Note that the content of the enclosures.rack-num field is undefined in this case. <LI>If enclosures.dencl-num is greater than 99, the HSV110 controller does not have proof of the current location but the last known location is indicated by the content of the enclosures.rack-num and enclosures.dencl-num fields. Subtract 100 from the content of those fields to determine the actual last known location. If there have been no configuration changes, the last known location values will be accurate. </UL>Note that the content of the enclosures.rack-num field will not be valid until a future release."
           --#TYPE      "StorageCell Event"
           --#SUMMARY   "SCellName-TimeDate %s : SWCID %d : ECode: %d : CAC %d : EIP %d."
           --#ARGUMENTS {0,1,2,3,4,}
           --#SEVERITY  CRITICAL
           --#TIMEINDEX 136
           --#STATE     WARNING
        ::= 13601550
 
   sCellEventTrap-6-f TRAP-TYPE  -- CAC Code: 40
        ENTERPRISE compaq
        VARIABLES  { scellNameDateTime,
                     scellSWComponent,
                     scellECode,
                     scellCAC,
                     scellEIP}
        DESCRIPTION
             "Severity: Critical -- failure or failure imminent. The Drive Enclosure Environmental Monitoring Unit is able to communicate with a physical disk drive but this HSV110 controller is unable to communicate with that physical disk drive on the Fibre Channel bus. The identity of the Drive Enclosure Environmental Monitoring Unit is contained in the device field. The Fibre Channel port used to communicate with the physical disk drive is contained in the cerp-id field. The HSV110 controller internal Fibre Channel port number used to communicate with the physical disk drive is contained in the port field. The missing-port and missing-cerp-id fields are unused. The location of the physical disk drive is contained in the rack-num, dencl-num, and bay fields. Note that the content of the rack-num field will not be valid until a future release. Note also that in this case the content of the al-pa, fed-class and num-times fields is undefined. The enclosures array shows the drive enclosures available on the Fibre Channel port identified in the cerp-id field. The location of an available drive enclosure is determined by the content of the enclosures.dencl-num field as follows: <UL><LI>If enclosures.dencl-num is less than 99, the location is as indicated by the content of the enclosures.rack-num and enclosures.dencl-num fields. <LI>If enclosures.dencl-num is equal to 99, the enclosures array entry is not used. Note that the content of the enclosures.rack-num field is undefined in this case. <LI>If enclosures.dencl-num is greater than 99, the HSV110 controller does not have proof of the current location but the last known location is indicated by the content of the enclosures.rack-num and enclosures.dencl-num fields. Subtract 100 from the content of those fields to determine the actual last known location. If there have been no configuration changes, the last known location values will be accurate. </UL>Note that the content of the enclosures.rack-num field will not be valid until a future release."
           --#TYPE      "StorageCell Event"
           --#SUMMARY   "SCellName-TimeDate %s : SWCID %d : ECode: %d : CAC %d : EIP %d."
           --#ARGUMENTS {0,1,2,3,4,}
           --#SEVERITY  CRITICAL
           --#TIMEINDEX 136
           --#STATE     WARNING
        ::= 13601551
 
   sCellEventTrap-6-10 TRAP-TYPE  -- CAC Code: 9b
        ENTERPRISE compaq
        VARIABLES  { scellNameDateTime,
                     scellSWComponent,
                     scellECode,
                     scellCAC,
                     scellEIP}
        DESCRIPTION
             "Severity: Undetermined -- more information needed to determine severity. A HSV110 controller is unable to communicate with this Drive Enclosure Environmental Monitoring Unit. The Drive Enclosure Environmental Monitoring Unit identified in the device field has stopped communicating with the HSV110 controller. The Fibre Channel port used to communicate with the Drive Enclosure Environmental Monitoring Unit is contained in the cerp-id field. The HSV110 controller internal Fibre Channel port number used to communicate with the Drive Enclosure Environmental Monitoring Unit is contained in the port field. The missing-port and missing-cerp-id fields are unused. The location of the Drive Enclosure Environmental Monitoring Unit is contained in the rack-num and dencl-num fields. Note that the content of the rack-num field will not be valid until a future release. Note also that in this case the content of the bay, al-pa, fed-class and num-times fields is undefined. The enclosures array shows the drive enclosures available on the Fibre Channel port identified in the cerp-id field. The location of an available drive enclosure is determined by the content of the enclosures.dencl-num field as follows: <UL><LI>If enclosures.dencl-num is less than 99, the location is as indicated by the content of the enclosures.rack-num and enclosures.dencl-num fields. <LI>If enclosures.dencl-num is equal to 99, the enclosures array entry is not used. Note that the content of the enclosures.rack-num field is undefined in this case. <LI>If enclosures.dencl-num is greater than 99, the HSV110 controller does not have proof of the current location but the last known location is indicated by the content of the enclosures.rack-num and enclosures.dencl-num fields. Subtract 100 from the content of those fields to determine the actual last known location. If there have been no configuration changes, the last known location values will be accurate. </UL>Note that the content of the enclosures.rack-num field will not be valid until a future release."
           --#TYPE      "StorageCell Event"
           --#SUMMARY   "SCellName-TimeDate %s : SWCID %d : ECode: %d : CAC %d : EIP %d."
           --#ARGUMENTS {0,1,2,3,4,}
           --#SEVERITY  CRITICAL
           --#TIMEINDEX 136
           --#STATE     WARNING
        ::= 13601552
 
   sCellEventTrap-6-12 TRAP-TYPE  -- CAC Code: 0
        ENTERPRISE compaq
        VARIABLES  { scellNameDateTime,
                     scellSWComponent,
                     scellECode,
                     scellCAC,
                     scellEIP}
        DESCRIPTION
             "Severity: Normal -- informational in nature. The retry count for a task assigned to a Drive Enclosure Environmental Monitoring Unit has been exhausted. The Fibre Channel port used to communicate with the physical disk drive is contained in the cerp-id field. The HSV110 controller internal Fibre Channel port number used to communicate with the physical disk drive is contained in the port field. The peb array contains the task list that was intended to be sent to the Drive Enclosure Environmental Monitoring Unit. The peq-frz-prod-index field contains the task that was being retried. The peq-prod-index field contains the drive enclosure where the physical disk drive used to communicate with the Drive Enclosure Environmental Monitoring Unit is located. The peq-cons-index field identifies the Fibre Channel loop pair (0 = Loop A, 1 = Loop B) used to communicate with the physical disk drive that was used to communicate with the Drive Enclosure Environmental Monitoring Unit. The failure-cause field contains the bay where the physical disk drive used to communicate with the Drive Enclosure Environmental Monitoring Unit."
           --#TYPE      "StorageCell Event"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13601554
 
   sCellEventTrap-6-13 TRAP-TYPE  -- CAC Code: 0
        ENTERPRISE compaq
        VARIABLES  { scellNameDateTime,
                     scellSWComponent,
                     scellECode,
                     scellCAC,
                     scellEIP}
        DESCRIPTION
             "Severity: Normal -- informational in nature. A Drive Enclosure Environmental Monitoring Unit is able to communicate with this HSV110 controller. The identity of the Drive Enclosure Environmental Monitoring Unit is contained in the device field. The Fibre Channel port used to communicate with the Drive Enclosure Environmental Monitoring Unit is contained in the cerp-id field. The HSV110 controller internal Fibre Channel port number used to communicate with the Drive Enclosure Environmental Monitoring Unit is contained in the port field. The missing-port and missing-cerp-id fields are unused. The location of the Drive Enclosure Environmental Monitoring Unit is contained in the rack-num and dencl-num fields. Note that the content of the rack-num field will not be valid until a future release. Note also that in this case the content of the bay, fed-class and num-times fields is undefined. The enclosures array shows the drive enclosures available on the Fibre Channel port identified in the cerp-id field. The location of an available drive enclosure is determined by the content of the enclosures.dencl-num field as follows: <UL><LI>If enclosures.dencl-num is less than 99, the location is as indicated by the content of the enclosures.rack-num and enclosures.dencl-num fields. <LI>If enclosures.dencl-num is equal to 99, the enclosures array entry is not used. Note that the content of the enclosures.rack-num field is undefined in this case. <LI>If enclosures.dencl-num is greater than 99, the HSV110 controller does not have proof of the current location but the last known location is indicated by the content of the enclosures.rack-num and enclosures.dencl-num fields. Subtract 100 from the content of those fields to determine the actual last known location. If there have been no configuration changes, the last known location values will be accurate. </UL>Note that the content of the enclosures.rack-num field will not be valid until a future release."
           --#TYPE      "StorageCell Event"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13601555
 
   sCellEventTrap-6-14 TRAP-TYPE  -- CAC Code: 98
        ENTERPRISE compaq
        VARIABLES  { scellNameDateTime,
                     scellSWComponent,
                     scellECode,
                     scellCAC,
                     scellEIP}
        DESCRIPTION
             "Severity: Critical -- failure or failure imminent. There are too many drive enclosures attached to a Fibre Channel port. The Fibre Channel port with too many drive enclosures attached to the HSV110 controller is contained in the cerp-id field. Note that in this case the content of the bay, fed-class, rack-num, dencl-num and num-times fields is undefined. The enclosures array shows the drive enclosures available on the Fibre Channel port identified in the cerp-id field. The missing-port and missing-cerp-id fields are unused. The location of the identified in the cerp-id field. The device, missing-port and missing-cerp-id fields are unused. The location of the physical disk drive is determined by the content of the dencl-num field as follows: <UL><LI>If enclosures.dencl-num is less than 99, the location is as indicated by the content of the enclosures.rack-num and enclosures.dencl-num fields. <LI>If enclosures.dencl-num is equal to 99, the enclosures array entry is not used. Note that the content of the enclosures.rack-num field is undefined in this case. <LI>If enclosures.dencl-num is greater than 99, the HSV110 controller does not have proof of the current location but the last known location is indicated by the content of the enclosures.rack-num and enclosures.dencl-num fields. Subtract 100 from the content of those fields to determine the actual last known location. If there have been no configuration changes, the last known location values will be accurate. </UL>Note that the content of the enclosures.rack-num field will not be valid until a future release."
           --#TYPE      "StorageCell Event"
           --#SUMMARY   "SCellName-TimeDate %s : SWCID %d : ECode: %d : CAC %d : EIP %d."
           --#ARGUMENTS {0,1,2,3,4,}
           --#SEVERITY  CRITICAL
           --#TIMEINDEX 136
           --#STATE     WARNING
        ::= 13601556
 
   sCellEventTrap-6-15 TRAP-TYPE  -- CAC Code: 99
        ENTERPRISE compaq
        VARIABLES  { scellNameDateTime,
                     scellSWComponent,
                     scellECode,
                     scellCAC,
                     scellEIP}
        DESCRIPTION
             "Severity: Critical -- failure or failure imminent. The cable connected to the I/O module is attached to the wrong Fibre Channel port. The Fibre Channel port incorrectly attached to the HSV110 controller is contained in the cerp-id field. Note that in this case the content of the device, missing-port, missing-cerp-id, bay, fed-class, rack-num, dencl-num and num-times fields is undefined. The enclosures array shows the drive enclosures available on the Fibre Channel port identified in the cerp-id field. The location of an available drive enclosure is determined by the content of the enclosures.dencl-num field as follows: <UL><LI>If enclosures.dencl-num is less than 99, the location is as indicated by the content of the enclosures.rack-num and enclosures.dencl-num fields. <LI>If enclosures.dencl-num is equal to 99, the enclosures array entry is not used. Note that the content of the enclosures.rack-num field is undefined in this case. <LI>If enclosures.dencl-num is greater than 99, the HSV110 controller does not have proof of the current location but the last known location is indicated by the content of the enclosures.rack-num and enclosures.dencl-num fields. Subtract 100 from the content of those fields to determine the actual last known location. If there have been no configuration changes, the last known location values will be accurate. </UL>Note that the content of the enclosures.rack-num field will not be valid until a future release."
           --#TYPE      "StorageCell Event"
           --#SUMMARY   "SCellName-TimeDate %s : SWCID %d : ECode: %d : CAC %d : EIP %d."
           --#ARGUMENTS {0,1,2,3,4,}
           --#SEVERITY  CRITICAL
           --#TIMEINDEX 136
           --#STATE     WARNING
        ::= 13601557
 
   sCellEventTrap-6-16 TRAP-TYPE  -- CAC Code: 97
        ENTERPRISE compaq
        VARIABLES  { scellNameDateTime,
                     scellSWComponent,
                     scellECode,
                     scellCAC,
                     scellEIP}
        DESCRIPTION
             "Severity: Critical -- failure or failure imminent. A HSV110 controller does not have an address on the enclosure address bus. The HSV110 controller location cannot be identified. Note that in this case the content of the missing-port, missing-cerp-id, bay, fed-class, rack-num, dencl-num, al-pa, device, cerp-id, port, enclosures array and num-times fields is undefined."
           --#TYPE      "StorageCell Event"
           --#SUMMARY   "SCellName-TimeDate %s : SWCID %d : ECode: %d : CAC %d : EIP %d."
           --#ARGUMENTS {0,1,2,3,4,}
           --#SEVERITY  CRITICAL
           --#TIMEINDEX 136
           --#STATE     WARNING
        ::= 13601558
 
   sCellEventTrap-6-18 TRAP-TYPE  -- CAC Code: 0
        ENTERPRISE compaq
        VARIABLES  { scellNameDateTime,
                     scellSWComponent,
                     scellECode,
                     scellCAC,
                     scellEIP}
        DESCRIPTION
             "Severity: Normal -- informational in nature. A Drive Enclosure Environmental Monitoring Unit has begun updating its code. Do not power down this drive enclosure until the code update has completed. The identity of the Drive Enclosure Environmental Monitoring Unit is contained in the device field. The Fibre Channel port used to communicate with the Drive Enclosure Environmental Monitoring Unit is contained in the cerp-id field. The HSV110 controller internal Fibre Channel port number used to communicate with the Drive Enclosure Environmental Monitoring Unit is contained in the port field. The missing-port and missing-cerp-id fields are unused. The location of the Drive Enclosure Environmental Monitoring Unit is determined by the content of the dencl-num field as follows: <UL><LI>If dencl-num is less than 99, the location is as indicated by the content of the rack-num and dencl-num fields. <LI>If dencl-num is equal to 99, the location is unknown. Note that the content of the rack-num field is undefined in this case. In addition, the device field may contain all zeroes. <LI>If dencl-num is greater than 99, the HSV110 controller does not have proof of the current location but the last known location is indicated by the content of the rack-num and dencl-num fields. Subtract 100 from the content of those fields to determine the actual last known location. If there have been no configuration changes, the last known location values will be accurate. The identity contained in the device field should be used to confirm the last known location values. </UL>Note that the content of the rack-num field will not be valid until a future release. Note also that the content of the fed-class, al-pa, and num-times fields is undefined. The enclosures array shows the drive enclosures available on the Fibre Channel port identified in the cerp-id field. The location of an available drive enclosure is determined by the content of the enclosures.dencl-num field as follows: <UL><LI>If enclosures.dencl-num is less than 99, the location is as indicated by the content of the enclosures.rack-num and enclosures.dencl-num fields. <LI>If enclosures.dencl-num is equal to 99, the enclosures array entry is not used. Note that the content of the enclosures.rack-num field is undefined in this case. <LI>If enclosures.dencl-num is greater than 99, the HSV110 controller does not have proof of the current location but the last known location is indicated by the content of the enclosures.rack-num and enclosures.dencl-num fields. Subtract 100 from the content of those fields to determine the actual last known location. If there have been no configuration changes, the last known location values will be accurate. </UL>Note that the content of the enclosures.rack-num field will not be valid until a future release."
           --#TYPE      "StorageCell Event"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13601560
 
   sCellEventTrap-6-19 TRAP-TYPE  -- CAC Code: 0
        ENTERPRISE compaq
        VARIABLES  { scellNameDateTime,
                     scellSWComponent,
                     scellECode,
                     scellCAC,
                     scellEIP}
        DESCRIPTION
             "Severity: Normal -- informational in nature. A Drive Enclosure Environmental Monitoring Unit has completed updating its code. It is now safe to power down this drive enclosure. The identity of the Drive Enclosure Environmental Monitoring Unit is contained in the device field. The Fibre Channel port used to communicate with the Drive Enclosure Environmental Monitoring Unit is contained in the cerp-id field. The HSV110 controller internal Fibre Channel port number used to communicate with the Drive Enclosure Environmental Monitoring Unit is contained in the port field. The missing-port and missing-cerp-id fields are unused. The location of the Drive Enclosure Environmental Monitoring Unit is contained in the rack-num and dencl-num fields. Note that the content of the rack-num field will not be valid until a future release. Note also that in this case the content of the fed-class, al-pa, and num-times fields is undefined. The enclosures array shows the drive enclosures available on the Fibre Channel port identified in the cerp-id field. The location of an available drive enclosure is determined by the content of the enclosures.dencl-num field as follows: <UL><LI>If enclosures.dencl-num is less than 99, the location is as indicated by the content of the enclosures.rack-num and enclosures.dencl-num fields. <LI>If enclosures.dencl-num is equal to 99, the enclosures array entry is not used. Note that the content of the enclosures.rack-num field is undefined in this case. <LI>If enclosures.dencl-num is greater than 99, the HSV110 controller does not have proof of the current location but the last known location is indicated by the content of the enclosures.rack-num and enclosures.dencl-num fields. Subtract 100 from the content of those fields to determine the actual last known location. If there have been no configuration changes, the last known location values will be accurate. </UL>Note that the content of the enclosures.rack-num field will not be valid until a future release."
           --#TYPE      "StorageCell Event"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13601561
 
   sCellEventTrap-6-1a TRAP-TYPE  -- CAC Code: 40
        ENTERPRISE compaq
        VARIABLES  { scellNameDateTime,
                     scellSWComponent,
                     scellECode,
                     scellCAC,
                     scellEIP}
        DESCRIPTION
             "Severity: Critical -- failure or failure imminent. A physical disk drive has exceeded its soft error threshold. The identity of the physical disk drive is contained in the device field. The Fibre Channel port used to communicate with the physical disk drive is contained in the cerp-id field. The HSV110 controller internal Fibre Channel port number used to communicate with the physical disk drive is contained in the port field. The arbitrated loop physical address of the physical disk drive is contained in the al-pa field. The location of the physical disk drive is determined by the content of the dencl-num field as follows: <UL><LI>If dencl-num is less than 99, the location is as indicated by the content of the rack-num, dencl-num, and bay fields. <LI>If dencl-num is equal to 99, the location is unknown. Note that the content of the rack-num and bay fields is undefined in this case. <LI>If dencl-num is greater than 99, the HSV110 controller does not have proof of the current location but the last known location is indicated by the content of the rack-num, dencl-num, and bay fields. Subtract 100 from the content of those fields to determine the actual last known location. If there have been no configuration changes, the last known location values will be accurate. The identity contained in the device field should be used to confirm the last known location values. </UL>Note that the content of the rack-num field will not be valid until a future release. Note also that in this case the content of the fed-class, cdb, and sense-data fields is undefined. The enclosures array shows the drive enclosures available on the Fibre Channel port identified in the cerp-id field. The location of an available drive enclosure is determined by the content of the enclosures.dencl-num field as follows: <UL><LI>If enclosures.dencl-num is less than 99, the location is as indicated by the content of the enclosures.rack-num and enclosures.dencl-num fields. <LI>If enclosures.dencl-num is equal to 99, the enclosures array entry is not used. Note that the content of the enclosures.rack-num field is undefined in this case. <LI>If enclosures.dencl-num is greater than 99, the HSV110 controller does not have proof of the current location but the last known location is indicated by the content of the enclosures.rack-num and enclosures.dencl-num fields. Subtract 100 from the content of those fields to determine the actual last known location. If there have been no configuration changes, the last known location values will be accurate. </UL>Note that the content of the enclosures.rack-num field will not be valid until a future release."
           --#TYPE      "StorageCell Event"
           --#SUMMARY   "SCellName-TimeDate %s : SWCID %d : ECode: %d : CAC %d : EIP %d."
           --#ARGUMENTS {0,1,2,3,4,}
           --#SEVERITY  CRITICAL
           --#TIMEINDEX 136
           --#STATE     WARNING
        ::= 13601562
 
   sCellEventTrap-6-1b TRAP-TYPE  -- CAC Code: 0
        ENTERPRISE compaq
        VARIABLES  { scellNameDateTime,
                     scellSWComponent,
                     scellECode,
                     scellCAC,
                     scellEIP}
        DESCRIPTION
             "Severity: Normal -- informational in nature. A HSV110 controller now has an address on the enclosure address bus. The HSV110 controller location has been identified. The location of the HSV110 controller is contained in the rack-num and dencl-num fields. Note that the content of the rack-num field will not be valid until a future release. Note also that in this case the content of the bay, fed-class, al-pa, cerp-id, port, and num-times fields is undefined. The enclosures array shows the drive enclosures available on the Fibre Channel port identified in the cerp-id field. The missing-port and missing-cerp-id fields are unused. The location of an available drive enclosure is determined by the content of the enclosures.dencl-num field as follows: <UL><LI>If enclosures.dencl-num is less than 99, the location is as indicated by the content of the enclosures.rack-num and enclosures.dencl-num fields. <LI>If enclosures.dencl-num is equal to 99, the enclosures array entry is not used. Note that the content of the enclosures.rack-num field is undefined in this case. <LI>If enclosures.dencl-num is greater than 99, the HSV110 controller does not have proof of the current location but the last known location is indicated by the content of the enclosures.rack-num and enclosures.dencl-num fields. Subtract 100 from the content of those fields to determine the actual last known location. If there have been no configuration changes, the last known location values will be accurate. </UL>Note that the content of the enclosures.rack-num field will not be valid until a future release."
           --#TYPE      "StorageCell Event"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13601563
 
   sCellEventTrap-6-1c TRAP-TYPE  -- CAC Code: 47
        ENTERPRISE compaq
        VARIABLES  { scellNameDateTime,
                     scellSWComponent,
                     scellECode,
                     scellCAC,
                     scellEIP}
        DESCRIPTION
             "Severity: Warning -- not failed but attention recommended or required. An outbound frame targeted to a physical disk drive has timed out. The identity of the physical disk drive is contained in the device field. The Fibre Channel port used to communicate with the physical disk drive is contained in the cerp-id field. The HSV110 controller internal Fibre Channel port number used to communicate with the physical disk drive is contained in the port field. The arbitrated loop physical address of the physical disk drive is contained in the al-pa field. The location of the physical disk drive is determined by the content of the dencl-num field as follows: <UL><LI>If dencl-num is less than 99, the location is as indicated by the content of the rack-num, dencl-num, and bay fields. <LI>If dencl-num is equal to 99, the location is unknown. Note that the content of the rack-num and bay fields is undefined in this case. <LI>If dencl-num is greater than 99, the HSV110 controller does not have proof of the current location but the last known location is indicated by the content of the rack-num, dencl-num, and bay fields. Subtract 100 from the content of those fields to determine the actual last known location. If there have been no configuration changes, the last known location values will be accurate. The identity contained in the device field should be used to confirm the last known location values. </UL>Note that the content of the rack-num field will not be valid until a future release. The Fibre Channel Exchange Descriptor class is contained in the fed-class field. The command issued to the physical disk drive is contained in the cmd field. Note that in this case the content of the error field is undefined. The enclosures array shows the drive enclosures available on the Fibre Channel port identified in the cerp-id field. The location of an available drive enclosure is determined by the content of the enclosures.dencl-num field as follows: <UL><LI>If enclosures.dencl-num is less than 99, the location is as indicated by the content of the enclosures.rack-num and enclosures.dencl-num fields. <LI>If enclosures.dencl-num is equal to 99, the enclosures array entry is not used. Note that the content of the enclosures.rack-num field is undefined in this case. <LI>If enclosures.dencl-num is greater than 99, the HSV110 controller does not have proof of the current location but the last known location is indicated by the content of the enclosures.rack-num and enclosures.dencl-num fields. Subtract 100 from the content of those fields to determine the actual last known location. If there have been no configuration changes, the last known location values will be accurate. </UL>Note that the content of the enclosures.rack-num field will not be valid until a future release."
           --#TYPE      "StorageCell Event"
           --#SUMMARY   "SCellName-TimeDate %s : SWCID %d : ECode: %d : CAC %d : EIP %d."
           --#ARGUMENTS {0,1,2,3,4,}
           --#SEVERITY  MINOR
           --#TIMEINDEX 136
           --#STATE     WARNING
        ::= 13601564
 
   sCellEventTrap-6-1d TRAP-TYPE  -- CAC Code: 47
        ENTERPRISE compaq
        VARIABLES  { scellNameDateTime,
                     scellSWComponent,
                     scellECode,
                     scellCAC,
                     scellEIP}
        DESCRIPTION
             "Severity: Warning -- not failed but attention recommended or required. A Fibre Channel exchange to a physical disk drive has completed but is missing data. The identity of the physical disk drive is contained in the device field. The Fibre Channel port used to communicate with the physical disk drive is contained in the cerp-id field. The HSV110 controller internal Fibre Channel port number used to communicate with the physical disk drive is contained in the port field. The arbitrated loop physical address of the physical disk drive is contained in the al-pa field. The location of the physical disk drive is determined by the content of the dencl-num field as follows: <UL><LI>If dencl-num is less than 99, the location is as indicated by the content of the rack-num, dencl-num, and bay fields. <LI>If dencl-num is equal to 99, the location is unknown. Note that the content of the rack-num and bay fields is undefined in this case. <LI>If dencl-num is greater than 99, the HSV110 controller does not have proof of the current location but the last known location is indicated by the content of the rack-num, dencl-num, and bay fields. Subtract 100 from the content of those fields to determine the actual last known location. If there have been no configuration changes, the last known location values will be accurate. The identity contained in the device field should be used to confirm the last known location values. </UL>Note that the content of the rack-num field will not be valid until a future release. The Fibre Channel Exchange Descriptor class is contained in the fed-class field. The command issued to the physical disk drive is contained in the cmd field. Note that in this case the content of the error field is undefined. The enclosures array shows the drive enclosures available on the Fibre Channel port identified in the cerp-id field. The location of an available drive enclosure is determined by the content of the enclosures.dencl-num field as follows: <UL><LI>If enclosures.dencl-num is less than 99, the location is as indicated by the content of the enclosures.rack-num and enclosures.dencl-num fields. <LI>If enclosures.dencl-num is equal to 99, the enclosures array entry is not used. Note that the content of the enclosures.rack-num field is undefined in this case. <LI>If enclosures.dencl-num is greater than 99, the HSV110 controller does not have proof of the current location but the last known location is indicated by the content of the enclosures.rack-num and enclosures.dencl-num fields. Subtract 100 from the content of those fields to determine the actual last known location. If there have been no configuration changes, the last known location values will be accurate. </UL>Note that the content of the enclosures.rack-num field will not be valid until a future release."
           --#TYPE      "StorageCell Event"
           --#SUMMARY   "SCellName-TimeDate %s : SWCID %d : ECode: %d : CAC %d : EIP %d."
           --#ARGUMENTS {0,1,2,3,4,}
           --#SEVERITY  MINOR
           --#TIMEINDEX 136
           --#STATE     WARNING
        ::= 13601565
 
   sCellEventTrap-6-1e TRAP-TYPE  -- CAC Code: 4c
        ENTERPRISE compaq
        VARIABLES  { scellNameDateTime,
                     scellSWComponent,
                     scellECode,
                     scellCAC,
                     scellEIP}
        DESCRIPTION
             "Severity: Critical -- failure or failure imminent. A HSV110 controller has detected only one port of a Fibre Channel device. This Fibre Channel device has entered the Single Port on Fibre state which should be corrected as soon as possible. The identity of the Fibre Channel device is contained in the device field. The Fibre Channel port still able to communicate with the Fibre Channel device is contained in the cerp-id field. The HSV110 controller internal Fibre Channel port number able to communicate with the Fibre Channel device is contained in the port field. The Fibre Channel port unable to communicate with the Fibre Channel device is contained in the missing-cerp-id field. The HSV110 controller internal Fibre Channel port number unable to communicate with the Fibre Channel device is contained in the missing-port field. The arbitrated loop physical address of the Fibre Channel device is contained in the al-pa field. The location of the Fibre Channel device is determined by the content of the dencl-num field as follows: <UL><LI>If dencl-num is less than 99, the location is as indicated by the content of the rack-num, dencl-num, and bay fields. <LI>If dencl-num is equal to 99, the location is unknown. Note that the content of the rack-num and bay fields is undefined in this case. <LI>If dencl-num is greater than 99, the HSV110 controller does not have proof of the current location but the last known location is indicated by the content of the rack-num, dencl-num, and bay fields. Subtract 100 from the content of those fields to determine the actual last known location. If there have been no configuration changes, the last known location values will be accurate. The identity contained in the device field should be used to confirm the last known location values. </UL>Note that the content of the rack-num field will not be valid until a future release. Note also that in this case the content of the fed-class, and num-times fields is undefined. The enclosures array shows the drive enclosures available on the Fibre Channel port identified in the cerp-id field. The location of an available drive enclosure is determined by the content of the enclosures.dencl-num field as follows: <UL><LI>If enclosures.dencl-num is less than 99, the location is as indicated by the content of the enclosures.rack-num and enclosures.dencl-num fields. <LI>If enclosures.dencl-num is equal to 99, the enclosures array entry is not used. Note that the content of the enclosures.rack-num field is undefined in this case. <LI>If enclosures.dencl-num is greater than 99, the HSV110 controller does not have proof of the current location but the last known location is indicated by the content of the enclosures.rack-num and enclosures.dencl-num fields. Subtract 100 from the content of those fields to determine the actual last known location. If there have been no configuration changes, the last known location values will be accurate. </UL>Note that the content of the enclosures.rack-num field will not be valid until a future release."
           --#TYPE      "StorageCell Event"
           --#SUMMARY   "SCellName-TimeDate %s : SWCID %d : ECode: %d : CAC %d : EIP %d."
           --#ARGUMENTS {0,1,2,3,4,}
           --#SEVERITY  CRITICAL
           --#TIMEINDEX 136
           --#STATE     WARNING
        ::= 13601566
 
   sCellEventTrap-6-1f TRAP-TYPE  -- CAC Code: 0
        ENTERPRISE compaq
        VARIABLES  { scellNameDateTime,
                     scellSWComponent,
                     scellECode,
                     scellCAC,
                     scellEIP}
        DESCRIPTION
             "Severity: Normal -- informational in nature. A previously reported Fibre Channel device with only one port has been corrected and redundancy has been restored. The device is no longer in the Single Port on Fibre state. The identity of the Fibre Channel device is contained in the device field. The Fibre Channel port used to communicate with the Fibre Channel device is contained in the cerp-id field. The HSV110 controller internal Fibre Channel port number used to communicate with the Fibre Channel device is contained in the port field. The missing-port and missing-cerp-id fields are unused. The arbitrated loop physical address of the Fibre Channel device is contained in the al-pa field. The location of the Fibre Channel device is determined by the content of the dencl-num field as follows: <UL><LI>If dencl-num is less than 99, the location is as indicated by the content of the rack-num, dencl-num, and bay fields. <LI>If dencl-num is equal to 99, the location is unknown. Note that the content of the rack-num and bay fields is undefined in this case. <LI>If dencl-num is greater than 99, the HSV110 controller does not have proof of the current location but the last known location is indicated by the content of the rack-num, dencl-num, and bay fields. Subtract 100 from the content of those fields to determine the actual last known location. If there have been no configuration changes, the last known location values will be accurate. The identity contained in the device field should be used to confirm the last known location values. </UL>Note that the content of the rack-num field will not be valid until a future release. Note also that in this case the content of the fed-class, and num-times fields is undefined. The enclosures array shows the drive enclosures available on the Fibre Channel port identified in the cerp-id field. The location of an available drive enclosure is determined by the content of the enclosures.dencl-num field as follows: <UL><LI>If enclosures.dencl-num is less than 99, the location is as indicated by the content of the enclosures.rack-num and enclosures.dencl-num fields. <LI>If enclosures.dencl-num is equal to 99, the enclosures array entry is not used. Note that the content of the enclosures.rack-num field is undefined in this case. <LI>If enclosures.dencl-num is greater than 99, the HSV110 controller does not have proof of the current location but the last known location is indicated by the content of the enclosures.rack-num and enclosures.dencl-num fields. Subtract 100 from the content of those fields to determine the actual last known location. If there have been no configuration changes, the last known location values will be accurate. </UL>Note that the content of the enclosures.rack-num field will not be valid until a future release."
           --#TYPE      "StorageCell Event"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13601567
 
   sCellEventTrap-6-20 TRAP-TYPE  -- CAC Code: 40
        ENTERPRISE compaq
        VARIABLES  { scellNameDateTime,
                     scellSWComponent,
                     scellECode,
                     scellCAC,
                     scellEIP}
        DESCRIPTION
             "Severity: Critical -- failure or failure imminent. An unsupported Fibre Channel device has been detected. The drive has been failed to prevent possible data corruption or system instability. The identity of the Fibre Channel device is contained in the device field. The Fibre Channel port used to communicate with the Fibre Channel device is contained in the cerp-id field. The HSV110 controller internal Fibre Channel port number used to communicate with the Fibre Channel device is contained in the port field. The arbitrated loop physical address of the Fibre Channel device is contained in the al-pa field. The missing-port and missing-cerp-id fields are unused. The location of the Fibre Channel device is determined by the content of the dencl-num field as follows: <UL><LI>If dencl-num is less than 99, the location is as indicated by the content of the rack-num, dencl-num, and bay fields. <LI>If dencl-num is equal to 99, the location is unknown. Note that the content of the rack-num and bay fields is undefined in this case. <LI>If dencl-num is greater than 99, the HSV110 controller does not have proof of the current location but the last known location is indicated by the content of the rack-num, dencl-num, and bay fields. Subtract 100 from the content of those fields to determine the actual last known location. If there have been no configuration changes, the last known location values will be accurate. The identity contained in the device field should be used to confirm the last known location values. </UL>Note that the content of the rack-num field will not be valid until a future release. Note also that in this case the content of the fed-class and num-times fields is undefined. The enclosures array shows the drive enclosures available on the Fibre Channel port identified in the cerp-id field. The location of an available drive enclosure is determined by the content of the enclosures.dencl-num field as follows: <UL><LI>If enclosures.dencl-num is less than 99, the location is as indicated by the content of the enclosures.rack-num and enclosures.dencl-num fields. <LI>If enclosures.dencl-num is equal to 99, the enclosures array entry is not used. Note that the content of the enclosures.rack-num field is undefined in this case. <LI>If enclosures.dencl-num is greater than 99, the HSV110 controller does not have proof of the current location but the last known location is indicated by the content of the enclosures.rack-num and enclosures.dencl-num fields. Subtract 100 from the content of those fields to determine the actual last known location. If there have been no configuration changes, the last known location values will be accurate. </UL>Note that the content of the enclosures.rack-num field will not be valid until a future release."
           --#TYPE      "StorageCell Event"
           --#SUMMARY   "SCellName-TimeDate %s : SWCID %d : ECode: %d : CAC %d : EIP %d."
           --#ARGUMENTS {0,1,2,3,4,}
           --#SEVERITY  CRITICAL
           --#TIMEINDEX 136
           --#STATE     WARNING
        ::= 13601568
 
   sCellEventTrap-6-21 TRAP-TYPE  -- CAC Code: 0
        ENTERPRISE compaq
        VARIABLES  { scellNameDateTime,
                     scellSWComponent,
                     scellECode,
                     scellCAC,
                     scellEIP}
        DESCRIPTION
             "Severity: Normal -- informational in nature. A Fibre Channel device with the incorrect block size has been detected. The identity of the Fibre Channel device is contained in the device field. The Fibre Channel port used to communicate with the Fibre Channel device is contained in the cerp-id field. The HSV110 controller internal Fibre Channel port number used to communicate with the Fibre Channel device is contained in the port field. The arbitrated loop physical address of the Fibre Channel device is contained in the al-pa field. The missing-port and missing-cerp-id fields are unused. The location of the Fibre Channel device is determined by the content of the dencl-num field as follows: <UL><LI>If dencl-num is less than 99, the location is as indicated by the content of the rack-num, dencl-num, and bay fields. <LI>If dencl-num is equal to 99, the location is unknown. Note that the content of the rack-num and bay fields is undefined in this case. <LI>If dencl-num is greater than 99, the HSV110 controller does not have proof of the current location but the last known location is indicated by the content of the rack-num, dencl-num, and bay fields. Subtract 100 from the content of those fields to determine the actual last known location. If there have been no configuration changes, the last known location values will be accurate. The identity contained in the device field should be used to confirm the last known location values. </UL>Note that the content of the rack-num field will not be valid until a future release. Note also that in this case the content of the fed-class and num-times fields is undefined. The enclosures array shows the drive enclosures available on the Fibre Channel port identified in the cerp-id field. The location of an available drive enclosure is determined by the content of the enclosures.dencl-num field as follows: <UL><LI>If enclosures.dencl-num is less than 99, the location is as indicated by the content of the enclosures.rack-num and enclosures.dencl-num fields. <LI>If enclosures.dencl-num is equal to 99, the enclosures array entry is not used. Note that the content of the enclosures.rack-num field is undefined in this case. <LI>If enclosures.dencl-num is greater than 99, the HSV110 controller does not have proof of the current location but the last known location is indicated by the content of the enclosures.rack-num and enclosures.dencl-num fields. Subtract 100 from the content of those fields to determine the actual last known location. If there have been no configuration changes, the last known location values will be accurate. </UL>Note that the content of the enclosures.rack-num field will not be valid until a future release."
           --#TYPE      "StorageCell Event"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13601569
 
   sCellEventTrap-6-23 TRAP-TYPE  -- CAC Code: 0
        ENTERPRISE compaq
        VARIABLES  { scellNameDateTime,
                     scellSWComponent,
                     scellECode,
                     scellCAC,
                     scellEIP}
        DESCRIPTION
             "Severity: Normal -- informational in nature. A HSV110 controller is about to retry a failed port. The Fibre Channel port that is about to be retried is contained in the cerp-id field. The HSV110 controller internal Fibre Channel port number about to be retried is contained in the port field. Note that in this case the content of the bay, rack-num, fed-class, al-pa, dencl-num, device, and num-times fields is undefined. The enclosures array shows the drive enclosures available on the Fibre Channel port identified in the cerp-id field. The missing-port and missing-cerp-id fields are unused. The location of an available drive enclosure is determined by the content of the enclosures.dencl-num field as follows: <UL><LI>If enclosures.dencl-num is less than 99, the location is as indicated by the content of the enclosures.rack-num and enclosures.dencl-num fields. <LI>If enclosures.dencl-num is equal to 99, the enclosures array entry is not used. Note that the content of the enclosures.rack-num field is undefined in this case. <LI>If enclosures.dencl-num is greater than 99, the HSV110 controller does not have proof of the current location but the last known location is indicated by the content of the enclosures.rack-num and enclosures.dencl-num fields. Subtract 100 from the content of those fields to determine the actual last known location. If there have been no configuration changes, the last known location values will be accurate. </UL>Note that the content of the enclosures.rack-num field will not be valid until a future release."
           --#TYPE      "StorageCell Event"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13601571
 
   sCellEventTrap-6-24 TRAP-TYPE  -- CAC Code: 0
        ENTERPRISE compaq
        VARIABLES  { scellNameDateTime,
                     scellSWComponent,
                     scellECode,
                     scellCAC,
                     scellEIP}
        DESCRIPTION
             "Severity: Normal -- informational in nature. A HSV110 controller has successfully retried a failed port. The Fibre Channel port that has been restarted is contained in the cerp-id field. The HSV110 controller internal Fibre Channel port number that has been restarted is contained in the port field. Note that in this case the content of the bay, rack-num, fed-class, al-pa, dencl-num, device, and num-times fields is undefined. The enclosures array shows the drive enclosures available on the Fibre Channel port identified in the cerp-id field. The missing-port and missing-cerp-id fields are unused. The location of an available drive enclosure is determined by the content of the enclosures.dencl-num field as follows: <UL><LI>If enclosures.dencl-num is less than 99, the location is as indicated by the content of the enclosures.rack-num and enclosures.dencl-num fields. <LI>If enclosures.dencl-num is equal to 99, the enclosures array entry is not used. Note that the content of the enclosures.rack-num field is undefined in this case. <LI>If enclosures.dencl-num is greater than 99, the HSV110 controller does not have proof of the current location but the last known location is indicated by the content of the enclosures.rack-num and enclosures.dencl-num fields. Subtract 100 from the content of those fields to determine the actual last known location. If there have been no configuration changes, the last known location values will be accurate. </UL>Note that the content of the enclosures.rack-num field will not be valid until a future release."
           --#TYPE      "StorageCell Event"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13601572
 
   sCellEventTrap-6-25 TRAP-TYPE  -- CAC Code: 43
        ENTERPRISE compaq
        VARIABLES  { scellNameDateTime,
                     scellSWComponent,
                     scellECode,
                     scellCAC,
                     scellEIP}
        DESCRIPTION
             "Severity: Critical -- failure or failure imminent. A Drive Enclosure Environmental Monitoring Unit has failed to assign a hard address to a physical disk drive on the loop. The device field contains the identity of the enclosure. The Fibre Channel port used to communicate with the physical disk drive is contained in the cerp-id field. The HSV110 controller internal Fibre Channel port number used to communicate with the physical disk drive is contained in the port field. The al-pa field contains the expected AL-PA, and the num-times field contains the actual AL-PA. The missing-port and missing-cerp-id fields are unused. The location of the physical disk drive is determined by the content of the dencl-num field as follows: <UL><LI>If dencl-num is less than 99, the location is as indicated by the content of the rack-num, dencl-num, and bay fields. <LI>If dencl-num is equal to 99, the location is unknown. Note that the content of the rack-num and bay fields is undefined in this case. <LI>If dencl-num is greater than 99, the HSV110 controller does not have proof of the current location but the last known location is indicated by the content of the rack-num, dencl-num, and bay fields. Subtract 100 from the content of those fields to determine the actual last known location. If there have been no configuration changes, the last known location values will be accurate. The identity contained in the device field should be used to confirm the last known location values. </UL>Note that the content of the rack-num field will not be valid until a future release. Note that in this case the content of the fed-class is undefined. The enclosures array shows the drive enclosures available on the Fibre Channel port identified in the cerp-id field. The location of an available drive enclosure is determined by the content of the enclosures.dencl-num field as follows: <UL><LI>If enclosures.dencl-num is less than 99, the location is as indicated by the content of the enclosures.rack-num and enclosures.dencl-num fields. <LI>If enclosures.dencl-num is equal to 99, the enclosures array entry is not used. Note that the content of the enclosures.rack-num field is undefined in this case. <LI>If enclosures.dencl-num is greater than 99, the HSV110 controller does not have proof of the current location but the last known location is indicated by the content of the enclosures.rack-num and enclosures.dencl-num fields. Subtract 100 from the content of those fields to determine the actual last known location. If there have been no configuration changes, the last known location values will be accurate. </UL>Note that the content of the enclosures.rack-num field will not be valid until a future release."
           --#TYPE      "StorageCell Event"
           --#SUMMARY   "SCellName-TimeDate %s : SWCID %d : ECode: %d : CAC %d : EIP %d."
           --#ARGUMENTS {0,1,2,3,4,}
           --#SEVERITY  CRITICAL
           --#TIMEINDEX 136
           --#STATE     WARNING
        ::= 13601573
 
   sCellEventTrap-6-26 TRAP-TYPE  -- CAC Code: 89
        ENTERPRISE compaq
        VARIABLES  { scellNameDateTime,
                     scellSWComponent,
                     scellECode,
                     scellCAC,
                     scellEIP}
        DESCRIPTION
             "Severity: Critical -- failure or failure imminent. A Drive Enclosure Environmental Monitoring Unit has failed to assign an address to a physical disk drive on the loop. This has occurred because another physical disk drive has already obtained this AL-PA. The device field contains the identity of the enclosure. The Fibre Channel port used to communicate with the physical disk drive is contained in the cerp-id field. The HSV110 controller internal Fibre Channel port number used to communicate with the physical disk drive is contained in the port field. The al-pa field contains the AL-PA that was stolen. The missing-port and missing-cerp-id fields are unused. The location of the physical disk drive is determined by the content of the dencl-num field as follows: <UL><LI>If dencl-num is less than 99, the location is as indicated by the content of the rack-num, dencl-num, and bay fields. <LI>If dencl-num is equal to 99, the location is unknown. Note that the content of the rack-num and bay fields is undefined in this case. <LI>If dencl-num is greater than 99, the HSV110 controller does not have proof of the current location but the last known location is indicated by the content of the rack-num, dencl-num, and bay fields. Subtract 100 from the content of those fields to determine the actual last known location. If there have been no configuration changes, the last known location values will be accurate. The identity contained in the device field should be used to confirm the last known location values. </UL>Note that the content of the rack-num field will not be valid until a future release. Note also that in this case the content of the fed-class and num-times fields is undefined. The enclosures array shows the drive enclosures available on the Fibre Channel port identified in the cerp-id field. The location of an available drive enclosure is determined by the content of the enclosures.dencl-num field as follows: <UL><LI>If enclosures.dencl-num is less than 99, the location is as indicated by the content of the enclosures.rack-num and enclosures.dencl-num fields. <LI>If enclosures.dencl-num is equal to 99, the enclosures array entry is not used. Note that the content of the enclosures.rack-num field is undefined in this case. <LI>If enclosures.dencl-num is greater than 99, the HSV110 controller does not have proof of the current location but the last known location is indicated by the content of the enclosures.rack-num and enclosures.dencl-num fields. Subtract 100 from the content of those fields to determine the actual last known location. If there have been no configuration changes, the last known location values will be accurate. </UL>Note that the content of the enclosures.rack-num field will not be valid until a future release."
           --#TYPE      "StorageCell Event"
           --#SUMMARY   "SCellName-TimeDate %s : SWCID %d : ECode: %d : CAC %d : EIP %d."
           --#ARGUMENTS {0,1,2,3,4,}
           --#SEVERITY  CRITICAL
           --#TIMEINDEX 136
           --#STATE     WARNING
        ::= 13601574
 
   sCellEventTrap-6-27 TRAP-TYPE  -- CAC Code: 1
        ENTERPRISE compaq
        VARIABLES  { scellNameDateTime,
                     scellSWComponent,
                     scellECode,
                     scellCAC,
                     scellEIP}
        DESCRIPTION
             "Severity: Critical -- failure or failure imminent. A Drive Enclosure Environmental Monitoring Unit has failed to assign address(s) to a physical disk drive on the loop. Soft addressing was detected for this enclosure. The device field contains the identity of the enclosure. The Fibre Channel port used to communicate with the physical disk drive is contained in the cerp-id field. The HSV110 controller internal Fibre Channel port number used to communicate with the physical disk drive is contained in the port field. The missing-port and missing-cerp-id fields are unused. The location of the physical disk drive is determined by the content of the dencl-num field as follows: <UL><LI>If dencl-num is less than 99, the location is as indicated by the content of the rack-num, dencl-num, and bay fields. <LI>If dencl-num is equal to 99, the location is unknown. Note that the content of the rack-num and bay fields is undefined in this case. <LI>If dencl-num is greater than 99, the HSV110 controller does not have proof of the current location but the last known location is indicated by the content of the rack-num, dencl-num, and bay fields. Subtract 100 from the content of those fields to determine the actual last known location. If there have been no configuration changes, the last known location values will be accurate. The identity contained in the device field should be used to confirm the last known location values. </UL>Note that the content of the rack-num field will not be valid until a future release. Note also that in this case the content of the fed-class, al-pa, and num-times fields is undefined. The enclosures array shows the drive enclosures available on the Fibre Channel port identified in the cerp-id field. The location of an available drive enclosure is determined by the content of the enclosures.dencl-num field as follows: <UL><LI>If enclosures.dencl-num is less than 99, the location is as indicated by the content of the enclosures.rack-num and enclosures.dencl-num fields. <LI>If enclosures.dencl-num is equal to 99, the enclosures array entry is not used. Note that the content of the enclosures.rack-num field is undefined in this case. <LI>If enclosures.dencl-num is greater than 99, the HSV110 controller does not have proof of the current location but the last known location is indicated by the content of the enclosures.rack-num and enclosures.dencl-num fields. Subtract 100 from the content of those fields to determine the actual last known location. If there have been no configuration changes, the last known location values will be accurate. </UL>Note that the content of the enclosures.rack-num field will not be valid until a future release."
           --#TYPE      "StorageCell Event"
           --#SUMMARY   "SCellName-TimeDate %s : SWCID %d : ECode: %d : CAC %d : EIP %d."
           --#ARGUMENTS {0,1,2,3,4,}
           --#SEVERITY  CRITICAL
           --#TIMEINDEX 136
           --#STATE     WARNING
        ::= 13601575
 
   sCellEventTrap-6-28 TRAP-TYPE  -- CAC Code: 0
        ENTERPRISE compaq
        VARIABLES  { scellNameDateTime,
                     scellSWComponent,
                     scellECode,
                     scellCAC,
                     scellEIP}
        DESCRIPTION
             "Severity: Normal -- informational in nature. The retry count for an OB task assigned to a Drive Enclosure Environmental Monitoring Unit has been exhausted. The Fibre Channel port used to communicate with the physical disk drive is contained in the cerp-id field. The HSV110 controller internal Fibre Channel port number used to communicate with the physical disk drive is contained in the port field. The peb array contains the task list that was intended to be sent to the Drive Enclosure Environmental Monitoring Unit. The peq-frz-prod-index field contains the task that was being retried. The peq-prod-index field contains the drive enclosure where the physical disk drive used to communicate with the Drive Enclosure Environmental Monitoring Unit is located. The peq-cons-index field identifies the Fibre Channel loop pair (0 = Loop A, 1 = Loop B) used to communicate with the physical disk drive that was used to communicate with the Drive Enclosure Environmental Monitoring Unit. The failure-cause field contains the bay where the physical disk drive used to communicate with the Drive Enclosure Environmental Monitoring Unit."
           --#TYPE      "StorageCell Event"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13601576
 
   sCellEventTrap-6-29 TRAP-TYPE  -- CAC Code: 0
        ENTERPRISE compaq
        VARIABLES  { scellNameDateTime,
                     scellSWComponent,
                     scellECode,
                     scellCAC,
                     scellEIP}
        DESCRIPTION
             "Severity: Normal -- informational in nature. The HSV110 controller has sent a Basic Link Service command Abort Sequence Frame. The original work is described in this event. The identity of the intended target is contained in the device field. The Fibre Channel port over which the work was sent is identified in the cerp-id field. The HSV110 controller internal Fibre Channel port over which the work was sent is contained in the port field. The arbitrated loop physical address of the intended target is contained in the al-pa field. The location of the intended target is determined by the content of the dencl-num field as follows: <UL><LI>If dencl-num is less than 99, the location is as indicated by the content of the rack-num, dencl-num, and bay fields. <LI>If dencl-num is equal to 99, the location is unknown. Note that the content of the rack-num and bay fields is undefined in this case. <LI>If dencl-num is greater than 99, the HSV110 controller does not have proof of the current location but the last known location is indicated by the content of the rack-num, dencl-num, and bay fields. Subtract 100 from the content of those fields to determine the actual last known location. If there have been no configuration changes, the last known location values will be accurate. The identity contained in the device field should be used to confirm the last known location values. </UL>Note that the content of the rack-num field will not be valid until a future release. The Fibre Channel Exchange Descriptor class is contained in the fed-class field. The command issued to the intended target is contained in the cmd field. Note that in this case the content of the error field is undefined. The enclosures array shows the drive enclosures available on the Fibre Channel port identified in the cerp-id field. The location of an available drive enclosure is determined by the content of the enclosures.dencl-num field as follows: <UL><LI>If enclosures.dencl-num is less than 99, the location is as indicated by the content of the enclosures.rack-num and enclosures.dencl-num fields. <LI>If enclosures.dencl-num is equal to 99, the enclosures array entry is not used. Note that the content of the enclosures.rack-num field is undefined in this case. <LI>If enclosures.dencl-num is greater than 99, the HSV110 controller does not have proof of the current location but the last known location is indicated by the content of the enclosures.rack-num and enclosures.dencl-num fields. Subtract 100 from the content of those fields to determine the actual last known location. If there have been no configuration changes, the last known location values will be accurate. </UL>Note that the content of the enclosures.rack-num field will not be valid until a future release."
           --#TYPE      "StorageCell Event"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13601577
 
   sCellEventTrap-6-2a TRAP-TYPE  -- CAC Code: 0
        ENTERPRISE compaq
        VARIABLES  { scellNameDateTime,
                     scellSWComponent,
                     scellECode,
                     scellCAC,
                     scellEIP}
        DESCRIPTION
             "Severity: Normal -- informational in nature. The HSV110 controller has sent an Extended Link Service command Reinstate Recovery Qualifier. The original work is described in this event. The identity of the intended target is contained in the device field. The Fibre Channel port over which the work was sent is identified in the cerp-id field. The HSV110 controller internal Fibre Channel port over which the work was sent is contained in the port field. The arbitrated loop physical address of the intended target is contained in the al-pa field. The location of the intended target is determined by the content of the dencl-num field as follows: <UL><LI>If dencl-num is less than 99, the location is as indicated by the content of the rack-num, dencl-num, and bay fields. <LI>If dencl-num is equal to 99, the location is unknown. Note that the content of the rack-num and bay fields is undefined in this case. <LI>If dencl-num is greater than 99, the HSV110 controller does not have proof of the current location but the last known location is indicated by the content of the rack-num, dencl-num, and bay fields. Subtract 100 from the content of those fields to determine the actual last known location. If there have been no configuration changes, the last known location values will be accurate. The identity contained in the device field should be used to confirm the last known location values. </UL>Note that the content of the rack-num field will not be valid until a future release. The Fibre Channel Exchange Descriptor class is contained in the fed-class field. The command issued to the intended target is contained in the cmd field. Note that in this case the content of the error field is undefined. The enclosures array shows the drive enclosures available on the Fibre Channel port identified in the cerp-id field. The location of an available drive enclosure is determined by the content of the enclosures.dencl-num field as follows: <UL><LI>If enclosures.dencl-num is less than 99, the location is as indicated by the content of the enclosures.rack-num and enclosures.dencl-num fields. <LI>If enclosures.dencl-num is equal to 99, the enclosures array entry is not used. Note that the content of the enclosures.rack-num field is undefined in this case. <LI>If enclosures.dencl-num is greater than 99, the HSV110 controller does not have proof of the current location but the last known location is indicated by the content of the enclosures.rack-num and enclosures.dencl-num fields. Subtract 100 from the content of those fields to determine the actual last known location. If there have been no configuration changes, the last known location values will be accurate. </UL>Note that the content of the enclosures.rack-num field will not be valid until a future release."
           --#TYPE      "StorageCell Event"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13601578
 
   sCellEventTrap-6-2b TRAP-TYPE  -- CAC Code: 40
        ENTERPRISE compaq
        VARIABLES  { scellNameDateTime,
                     scellSWComponent,
                     scellECode,
                     scellCAC,
                     scellEIP}
        DESCRIPTION
             "Severity: Critical -- failure or failure imminent. A physical disk drive was bypassed rendering it unusable. The physical disk drive is unusable because a Drive Enclosure Environmental Monitoring Unit bypassed a drive bay or the physical disk drive left itself bypassed. The physical disk drive is not available to the HSV110 controllers and will not be displayed by the HSV element manager GUI. The physical disk drive fault led will be lit to indicate that it is unusable. The Fibre Channel port over which this condition was detected is identified in the cerp-id field. The HSV110 controller internal Fibre Channel port over which this condition was detected is contained in the port field. The al-pa field is invalid. The location of the physical disk drive is as indicated by the content of the rack-num, dencl-num, and bay fields. Note that the content of the rack-num field will not be valid until a future release. The bypass-reason field is used to indicate how the physical disk drive was bypassed: <UL><LI>1 = The physical disk drive left itself bypassed <LI>2 = The Drive Enclosure Environmental Monitoring Unit bypassed the drive bay </UL>The Drive Enclosure Environmental Monitoring Unit is identified in the device field. Additionally, the content of the pid, rev, and enclosures array fields is undefined in this case."
           --#TYPE      "StorageCell Event"
           --#SUMMARY   "SCellName-TimeDate %s : SWCID %d : ECode: %d : CAC %d : EIP %d."
           --#ARGUMENTS {0,1,2,3,4,}
           --#SEVERITY  CRITICAL
           --#TIMEINDEX 136
           --#STATE     WARNING
        ::= 13601579
 
   sCellEventTrap-6-2c TRAP-TYPE  -- CAC Code: 0
        ENTERPRISE compaq
        VARIABLES  { scellNameDateTime,
                     scellSWComponent,
                     scellECode,
                     scellCAC,
                     scellEIP}
        DESCRIPTION
             "Severity: Normal -- informational in nature. One or more media defects were detected on a physical disk drive. The affected physical disk drive is identified in the device field. The Fibre Channel port over which the media defect(s) was detected is identified in the cerp-id field. The HSV110 controller internal Fibre Channel port number over which the media defect(s) was detected is contained in the port field. The arbitrated loop physical address of the physical disk drive is contained in the al-pa field. The Logical Block Address of each media defect is contained in a separate entry of the hdr-cdb array. Only nonzero values in the hdr-cdb array entries are valid. The location of the physical disk drive is determined by the content of the dencl-num field as follows: <UL><LI>If dencl-num is less than 99, the location is as indicated by the content of the rack-num, dencl-num, and bay fields. <LI>If dencl-num is equal to 99, the location is unknown. Note that the content of the rack-num and bay fields is undefined in this case. <LI>If dencl-num is greater than 99, the HSV110 controller does not have proof of the current location but the last known location is indicated by the content of the rack-num, dencl-num, and bay fields. Subtract 100 from the content of those fields to determine the actual last known location. If there have been no configuration changes, the last known location values will be accurate. The identity contained in the device field should be used to confirm the last known location values. </UL>Note that the content of the rack-num field will not be valid until a future release."
           --#TYPE      "StorageCell Event"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13601580
 
   sCellEventTrap-6-2d TRAP-TYPE  -- CAC Code: 0
        ENTERPRISE compaq
        VARIABLES  { scellNameDateTime,
                     scellSWComponent,
                     scellECode,
                     scellCAC,
                     scellEIP}
        DESCRIPTION
             "Severity: Normal -- informational in nature. An HSV110 controller issued a directed LIP to an arbitrated loop physical address. The Fibre Channel port over which the directed LIP was issued is identified in the cerp-id field. The HSV110 controller internal Fibre Channel port number over which the directed LIP was issued is contained in the port field. The arbitrated loop physical address of the physical disk drive is contained in the al-pa field."
           --#TYPE      "StorageCell Event"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13601581
 
   sCellEventTrap-6-2e TRAP-TYPE  -- CAC Code: 0
        ENTERPRISE compaq
        VARIABLES  { scellNameDateTime,
                     scellSWComponent,
                     scellECode,
                     scellCAC,
                     scellEIP}
        DESCRIPTION
             "Severity: Normal -- informational in nature. An HSV110 controller has detected Loop Receiver Failures. The Fibre Channel port over which the Loop Receiver Failures were detected is identified in the cerp-id field. The HSV110 controller internal Fibre Channel port number over which the Loop Receiver Failures were detected is contained in the port field. The counts and the AL-PAs of the Loop Receiver Failures are contained in a separate entry of the hdr-cdb array. Only nonzero values in the hdr-cdb array entries are valid. The affected HSV110 controller is identified in the device field. Note that in this case the content of the al-pa, dencl-num, bay, and rack-num fields are undefined."
           --#TYPE      "StorageCell Event"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13601582
 
   sCellEventTrap-6-30 TRAP-TYPE  -- CAC Code: 4e
        ENTERPRISE compaq
        VARIABLES  { scellNameDateTime,
                     scellSWComponent,
                     scellECode,
                     scellCAC,
                     scellEIP}
        DESCRIPTION
             "Severity: Critical -- failure or failure imminent. A HSV110 controller has detected only one port of all Fibre Channel devices in an enclosure. These Fibre Channel devices have entered the Single Port on Fibre state which should be corrected as soon as possible. The identity of the Fibre Channel device enclosure is contained in the device field. The Fibre Channel port still able to communicate with the Fibre Channel device is contained in the cerp-id field. The HSV110 controller internal Fibre Channel port number able to communicate with the Fibre Channel device is contained in the port field. The Fibre Channel port unable to communicate with the Fibre Channel device is contained in the missing-cerp-id field. The HSV110 controller internal Fibre Channel port number unable to communicate with the Fibre Channel device is contained in the missing-port field. The al-pa and bay fields are invalid. The location of the Fibre Channel enclosure is determined by the content of the dencl-num field as follows: <UL><LI>If dencl-num is less than 99, the location is as indicated by the content of the rack-num and dencl-num fields. <LI>If dencl-num is equal to 99, the location is unknown. Note that the content of the rack-num field is undefined in this case. <LI>If dencl-num is greater than 99, the HSV110 controller does not have proof of the current location but the last known location is indicated by the content of the rack-num and dencl-num fields. Subtract 100 from the content of those fields to determine the actual last known location. If there have been no configuration changes, the last known location values will be accurate. The identity contained in the device field should be used to confirm the last known location values. </UL>Note that the content of the rack-num field will not be valid until a future release. Note also that in this case the content of the fed-class, and num-times fields is undefined. The enclosures array shows the drive enclosures available on the Fibre Channel port identified in the cerp-id field. The location of an available drive enclosure is determined by the content of the enclosures.dencl-num field as follows: <UL><LI>If enclosures.dencl-num is less than 99, the location is as indicated by the content of the enclosures.rack-num and enclosures.dencl-num fields. <LI>If enclosures.dencl-num is equal to 99, the enclosures array entry is not used. Note that the content of the enclosures.rack-num field is undefined in this case. <LI>If enclosures.dencl-num is greater than 99, the HSV110 controller does not have proof of the current location but the last known location is indicated by the content of the enclosures.rack-num and enclosures.dencl-num fields. Subtract 100 from the content of those fields to determine the actual last known location. If there have been no configuration changes, the last known location values will be accurate. </UL>Note that the content of the enclosures.rack-num field will not be valid until a future release."
           --#TYPE      "StorageCell Event"
           --#SUMMARY   "SCellName-TimeDate %s : SWCID %d : ECode: %d : CAC %d : EIP %d."
           --#ARGUMENTS {0,1,2,3,4,}
           --#SEVERITY  CRITICAL
           --#TIMEINDEX 136
           --#STATE     WARNING
        ::= 13601584
 
   sCellEventTrap-6-31 TRAP-TYPE  -- CAC Code: 0
        ENTERPRISE compaq
        VARIABLES  { scellNameDateTime,
                     scellSWComponent,
                     scellECode,
                     scellCAC,
                     scellEIP}
        DESCRIPTION
             "Severity: Normal -- informational in nature. A previously reported Fibre Channel device enclosure with only one port has been corrected and redundancy has been restored. The devices in the enclosure are no longer in the Single Port on Fibre state. The identity of the Fibre Channel device enclosure is contained in the device field. The Fibre Channel port used to communicate with the Fibre Channel device enclosure is contained in the cerp-id field. The HSV110 controller internal Fibre Channel port number used to communicate with the Fibre Channel device is contained in the port field. The al-pa, bay, missing-port, and missing-cerp-id fields are invalid. The location of the Fibre Channel device is determined by the content of the dencl-num field as follows: <UL><LI>If dencl-num is less than 99, the location is as indicated by the content of the rack-num and dencl-num fields. <LI>If dencl-num is equal to 99, the location is unknown. Note that the content of the rack-num field is undefined in this case. <LI>If dencl-num is greater than 99, the HSV110 controller does not have proof of the current location but the last known location is indicated by the content of the rack-num and dencl-num fields. Subtract 100 from the content of those fields to determine the actual last known location. If there have been no configuration changes, the last known location values will be accurate. The identity contained in the device field should be used to confirm the last known location values. </UL>Note that the content of the rack-num field will not be valid until a future release. Note also that in this case the content of the fed-class, and num-times fields is undefined. The enclosures array shows the drive enclosures available on the Fibre Channel port identified in the cerp-id field. The location of an available drive enclosure is determined by the content of the enclosures.dencl-num field as follows: <UL><LI>If enclosures.dencl-num is less than 99, the location is as indicated by the content of the enclosures.rack-num and enclosures.dencl-num fields. <LI>If enclosures.dencl-num is equal to 99, the enclosures array entry is not used. Note that the content of the enclosures.rack-num field is undefined in this case. <LI>If enclosures.dencl-num is greater than 99, the HSV110 controller does not have proof of the current location but the last known location is indicated by the content of the enclosures.rack-num and enclosures.dencl-num fields. Subtract 100 from the content of those fields to determine the actual last known location. If there have been no configuration changes, the last known location values will be accurate. </UL>Note that the content of the enclosures.rack-num field will not be valid until a future release."
           --#TYPE      "StorageCell Event"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13601585
 
   sCellEventTrap-6-32 TRAP-TYPE  -- CAC Code: 4e
        ENTERPRISE compaq
        VARIABLES  { scellNameDateTime,
                     scellSWComponent,
                     scellECode,
                     scellCAC,
                     scellEIP}
        DESCRIPTION
             "Severity: Critical -- failure or failure imminent. A HSV110 controller has detected only one port of all Fibre Channel devices on a loop. These Fibre Channel devices have entered the Single Port on Fibre state which should be corrected as soon as possible. The device, al-pa, dencl-num, and bay fields are all invalid. The Fibre Channel port still able to communicate with the Fibre Channel device is contained in the cerp-id field. The HSV110 controller internal Fibre Channel port number able to communicate with the Fibre Channel device is contained in the port field. The Fibre Channel port unable to communicate with the Fibre Channel device is contained in the missing-cerp-id field. The HSV110 controller internal Fibre Channel port number unable to communicate with the Fibre Channel device is contained in the missing-port field."
           --#TYPE      "StorageCell Event"
           --#SUMMARY   "SCellName-TimeDate %s : SWCID %d : ECode: %d : CAC %d : EIP %d."
           --#ARGUMENTS {0,1,2,3,4,}
           --#SEVERITY  CRITICAL
           --#TIMEINDEX 136
           --#STATE     WARNING
        ::= 13601586
 
   sCellEventTrap-6-33 TRAP-TYPE  -- CAC Code: 0
        ENTERPRISE compaq
        VARIABLES  { scellNameDateTime,
                     scellSWComponent,
                     scellECode,
                     scellCAC,
                     scellEIP}
        DESCRIPTION
             "Severity: Normal -- informational in nature. A previously reported Fibre Channel loop with only one port has been corrected and redundancy has been restored. The devices on the loop are no longer in the Single Port on Fibre state. The device, al-pa, dencl-num, bay, missing-port, and missing-cerp-id fields are invalid. The Fibre Channel port used to communicate with the Fibre Channel devices is contained in the cerp-id field. The HSV110 controller internal Fibre Channel port number used to communicate with the Fibre Channel devices is contained in the port field."
           --#TYPE      "StorageCell Event"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13601587
 
   sCellEventTrap-6-34 TRAP-TYPE  -- CAC Code: 0
        ENTERPRISE compaq
        VARIABLES  { scellNameDateTime,
                     scellSWComponent,
                     scellECode,
                     scellCAC,
                     scellEIP}
        DESCRIPTION
             "Severity: Normal -- informational in nature. A HSV110 controller has been told to enable a device port, and that device port was not disabled during boot diagnostics. The Fibre Channel port that was enabled is contained in the cerp-id field. The HSV110 controller internal Fibre Channel port number enabled is contained in the port field. Note that in this case the contents of the bay, rack-num, fed-class, al-pa, dencl-num, device, enclosure array, and num-times fields are undefined. The missing-port and missing-cerp-id fields are unused."
           --#TYPE      "StorageCell Event"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13601588
 
   sCellEventTrap-6-35 TRAP-TYPE  -- CAC Code: 4d
        ENTERPRISE compaq
        VARIABLES  { scellNameDateTime,
                     scellSWComponent,
                     scellECode,
                     scellCAC,
                     scellEIP}
        DESCRIPTION
             "Severity: Critical -- failure or failure imminent. An unrecognized Fibre Channel physical disk drive firmware revision has been detected by the physical disk drive firmware load process. The identity of the physical disk drive is contained in the device field. The Fibre Channel port used to communicate with the physical disk drive is contained in the cerp-id field. The HSV110 controller internal Fibre Channel port number used to communicate with the physical disk drive is contained in the port field. The arbitrated loop physical address of the physical disk drive is contained in the al-pa field. The bypass-reason field is invalid. The location of the physical disk drive is determined by the content of the dencl-num field as follows: <UL><LI>If dencl-num is less than 99, the location is as indicated by the content of the rack-num, dencl-num, and bay fields. <LI>If dencl-num is equal to 99, the location is unknown. Note that the content of the rack-num, al-pa and bay fields is undefined in this case. <LI>If dencl-num is greater than 99, the HSV110 controller does not have proof of the current location but the last known location is indicated by the content of the rack-num, dencl-num, and bay fields. Subtract 100 from the content of those fields to determine the actual last known location. If there have been no configuration changes, the last known location values will be accurate. The identity contained in the device field should be used to confirm the last known location values. </UL>Note that the content of the rack-num field will not be valid until a future release. The pid field contains the SCSI Inquiry Product Identification obtained from the physical disk drive. The rev field contains the current firmware revision obtained from the physical disk drive. The new-rev field contains the latest firmware version known to the controller, or blanks if the isn't a known version. The enclosures array shows the drive enclosures available on the Fibre Channel port identified in the cerp-id field. The location of an available drive enclosure is determined by the content of the enclosures.dencl-num field as follows: <UL><LI>If enclosures.dencl-num is less than 99, the location is as indicated by the content of the enclosures.rack-num and enclosures.dencl-num fields. <LI>If enclosures.dencl-num is equal to 99, the enclosures array entry is not used. Note that the content of the enclosures.rack-num field is undefined in this case. <LI>If enclosures.dencl-num is greater than 99, the HSV110 controller does not have proof of the current location but the last known location is indicated by the content of the enclosures.rack-num and enclosures.dencl-num fields. Subtract 100 from the content of those fields to determine the actual last known location. If there have been no configuration changes, the last known location values will be accurate. </UL>Note that the content of the enclosures.rack-num field will not be valid until a future release."
           --#TYPE      "StorageCell Event"
           --#SUMMARY   "SCellName-TimeDate %s : SWCID %d : ECode: %d : CAC %d : EIP %d."
           --#ARGUMENTS {0,1,2,3,4,}
           --#SEVERITY  CRITICAL
           --#TIMEINDEX 136
           --#STATE     WARNING
        ::= 13601589
 
   sCellEventTrap-6-36 TRAP-TYPE  -- CAC Code: 4d
        ENTERPRISE compaq
        VARIABLES  { scellNameDateTime,
                     scellSWComponent,
                     scellECode,
                     scellCAC,
                     scellEIP}
        DESCRIPTION
             "Severity: Critical -- failure or failure imminent. An unsupported Fibre Channel physical disk drive firmware revision has been detected by the physical disk drive firmware load process. The identity of the physical disk drive is contained in the device field. The Fibre Channel port used to communicate with the physical disk drive is contained in the cerp-id field. The HSV110 controller internal Fibre Channel port number used to communicate with the physical disk drive is contained in the port field. The arbitrated loop physical address of the physical disk drive is contained in the al-pa field. The bypass-reason field is invalid. The location of the physical disk drive is determined by the content of the dencl-num field as follows: <UL><LI>If dencl-num is less than 99, the location is as indicated by the content of the rack-num, dencl-num, and bay fields. <LI>If dencl-num is equal to 99, the location is unknown. Note that the content of the rack-num, al-pa and bay fields is undefined in this case. <LI>If dencl-num is greater than 99, the HSV110 controller does not have proof of the current location but the last known location is indicated by the content of the rack-num, dencl-num, and bay fields. Subtract 100 from the content of those fields to determine the actual last known location. If there have been no configuration changes, the last known location values will be accurate. The identity contained in the device field should be used to confirm the last known location values. </UL>Note that the content of the rack-num field will not be valid until a future release. The pid field contains the SCSI Inquiry Product Identification obtained from the physical disk drive. The rev field contains the current firmware revision obtained from the physical disk drive. The new-rev field contains the latest firmware version known to the controller, or blanks if the isn't a known version. The enclosures array shows the drive enclosures available on the Fibre Channel port identified in the cerp-id field. The location of an available drive enclosure is determined by the content of the enclosures.dencl-num field as follows: <UL><LI>If enclosures.dencl-num is less than 99, the location is as indicated by the content of the enclosures.rack-num and enclosures.dencl-num fields. <LI>If enclosures.dencl-num is equal to 99, the enclosures array entry is not used. Note that the content of the enclosures.rack-num field is undefined in this case. <LI>If enclosures.dencl-num is greater than 99, the HSV110 controller does not have proof of the current location but the last known location is indicated by the content of the enclosures.rack-num and enclosures.dencl-num fields. Subtract 100 from the content of those fields to determine the actual last known location. If there have been no configuration changes, the last known location values will be accurate. </UL>Note that the content of the enclosures.rack-num field will not be valid until a future release."
           --#TYPE      "StorageCell Event"
           --#SUMMARY   "SCellName-TimeDate %s : SWCID %d : ECode: %d : CAC %d : EIP %d."
           --#ARGUMENTS {0,1,2,3,4,}
           --#SEVERITY  CRITICAL
           --#TIMEINDEX 136
           --#STATE     WARNING
        ::= 13601590
 
   sCellEventTrap-6-37 TRAP-TYPE  -- CAC Code: c4
        ENTERPRISE compaq
        VARIABLES  { scellNameDateTime,
                     scellSWComponent,
                     scellECode,
                     scellCAC,
                     scellEIP}
        DESCRIPTION
             "Severity: Normal -- informational in nature. A Fibre Channel physical disk drive firmware revision has been detected by the physical disk drive firmware load process that is later than the latest known supported revision. If the location information is 0, it indicates the type of drive, not a specific drive. The identity of the physical disk drive is contained in the device field. The Fibre Channel port used to communicate with the physical disk drive is contained in the cerp-id field. The HSV110 controller internal Fibre Channel port number used to communicate with the physical disk drive is contained in the port field. The arbitrated loop physical address of the physical disk drive is contained in the al-pa field. The bypass-reason field is invalid. The location of the physical disk drive is determined by the content of the dencl-num field as follows: <UL><LI>If dencl-num is less than 99, the location is as indicated by the content of the rack-num, dencl-num, and bay fields. <LI>If dencl-num is equal to 99, the location is unknown. Note that the content of the rack-num, al-pa and bay fields is undefined in this case. <LI>If dencl-num is greater than 99, the HSV110 controller does not have proof of the current location but the last known location is indicated by the content of the rack-num, dencl-num, and bay fields. Subtract 100 from the content of those fields to determine the actual last known location. If there have been no configuration changes, the last known location values will be accurate. The identity contained in the device field should be used to confirm the last known location values. </UL>Note that the content of the rack-num field will not be valid until a future release. The pid field contains the SCSI Inquiry Product Identification obtained from the physical disk drive. The rev field contains the current firmware revision obtained from the physical disk drive. The new-rev field contains the latest firmware version known to the controller, or blanks if the isn't a known version. The enclosures array shows the drive enclosures available on the Fibre Channel port identified in the cerp-id field. The location of an available drive enclosure is determined by the content of the enclosures.dencl-num field as follows: <UL><LI>If enclosures.dencl-num is less than 99, the location is as indicated by the content of the enclosures.rack-num and enclosures.dencl-num fields. <LI>If enclosures.dencl-num is equal to 99, the enclosures array entry is not used. Note that the content of the enclosures.rack-num field is undefined in this case. <LI>If enclosures.dencl-num is greater than 99, the HSV110 controller does not have proof of the current location but the last known location is indicated by the content of the enclosures.rack-num and enclosures.dencl-num fields. Subtract 100 from the content of those fields to determine the actual last known location. If there have been no configuration changes, the last known location values will be accurate. </UL>Note that the content of the enclosures.rack-num field will not be valid until a future release."
           --#TYPE      "StorageCell Event"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13601591
 
   sCellEventTrap-6-38 TRAP-TYPE  -- CAC Code: c4
        ENTERPRISE compaq
        VARIABLES  { scellNameDateTime,
                     scellSWComponent,
                     scellECode,
                     scellCAC,
                     scellEIP}
        DESCRIPTION
             "Severity: Normal -- informational in nature. A Fibre Channel physical disk drive firmware revision has been detected by the physical disk drive firmware load process that has a newer supported revision available. If the location information is 0, it indicates the type of drive, not a specific drive. The identity of the physical disk drive is contained in the device field. The Fibre Channel port used to communicate with the physical disk drive is contained in the cerp-id field. The HSV110 controller internal Fibre Channel port number used to communicate with the physical disk drive is contained in the port field. The arbitrated loop physical address of the physical disk drive is contained in the al-pa field. The bypass-reason field is invalid. The location of the physical disk drive is determined by the content of the dencl-num field as follows: <UL><LI>If dencl-num is less than 99, the location is as indicated by the content of the rack-num, dencl-num, and bay fields. <LI>If dencl-num is equal to 99, the location is unknown. Note that the content of the rack-num, al-pa and bay fields is undefined in this case. <LI>If dencl-num is greater than 99, the HSV110 controller does not have proof of the current location but the last known location is indicated by the content of the rack-num, dencl-num, and bay fields. Subtract 100 from the content of those fields to determine the actual last known location. If there have been no configuration changes, the last known location values will be accurate. The identity contained in the device field should be used to confirm the last known location values. </UL>Note that the content of the rack-num field will not be valid until a future release. The pid field contains the SCSI Inquiry Product Identification obtained from the physical disk drive. The rev field contains the current firmware revision obtained from the physical disk drive. The new-rev field contains the latest firmware version known to the controller, or blanks if the isn't a known version. The enclosures array shows the drive enclosures available on the Fibre Channel port identified in the cerp-id field. The location of an available drive enclosure is determined by the content of the enclosures.dencl-num field as follows: <UL><LI>If enclosures.dencl-num is less than 99, the location is as indicated by the content of the enclosures.rack-num and enclosures.dencl-num fields. <LI>If enclosures.dencl-num is equal to 99, the enclosures array entry is not used. Note that the content of the enclosures.rack-num field is undefined in this case. <LI>If enclosures.dencl-num is greater than 99, the HSV110 controller does not have proof of the current location but the last known location is indicated by the content of the enclosures.rack-num and enclosures.dencl-num fields. Subtract 100 from the content of those fields to determine the actual last known location. If there have been no configuration changes, the last known location values will be accurate. </UL>Note that the content of the enclosures.rack-num field will not be valid until a future release."
           --#TYPE      "StorageCell Event"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13601592
 
   sCellEventTrap-6-39 TRAP-TYPE  -- CAC Code: 0
        ENTERPRISE compaq
        VARIABLES  { scellNameDateTime,
                     scellSWComponent,
                     scellECode,
                     scellCAC,
                     scellEIP}
        DESCRIPTION
             "Severity: Normal -- informational in nature. The HSV110 controller bypassed a device bay in an attempt to restore operability. The identity of the bay is indicated by the rack-num, dencl-num, and bay fields. All other fields are invalid."
           --#TYPE      "StorageCell Event"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13601593
 
   sCellEventTrap-6-3a TRAP-TYPE  -- CAC Code: 0
        ENTERPRISE compaq
        VARIABLES  { scellNameDateTime,
                     scellSWComponent,
                     scellECode,
                     scellCAC,
                     scellEIP}
        DESCRIPTION
             "Severity: Normal -- informational in nature. The HSV110 controller is attempting to recovery devices on the indicated port. All other fields are invalid."
           --#TYPE      "StorageCell Event"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13601594
 
   sCellEventTrap-6-3b TRAP-TYPE  -- CAC Code: 0
        ENTERPRISE compaq
        VARIABLES  { scellNameDateTime,
                     scellSWComponent,
                     scellECode,
                     scellCAC,
                     scellEIP}
        DESCRIPTION
             "Severity: Normal -- informational in nature. The HSV110 controller has finished error recovery attempts on the indicated port. All other fields are invalid."
           --#TYPE      "StorageCell Event"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13601595
 
   sCellEventTrap-6-3c TRAP-TYPE  -- CAC Code: 0
        ENTERPRISE compaq
        VARIABLES  { scellNameDateTime,
                     scellSWComponent,
                     scellECode,
                     scellCAC,
                     scellEIP}
        DESCRIPTION
             "Severity: Normal -- informational in nature. The HSV110 controller been requested to unbypass device bays on the indicated port. All other fields are invalid."
           --#TYPE      "StorageCell Event"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13601596
 
   sCellEventTrap-6-3d TRAP-TYPE  -- CAC Code: 9b
        ENTERPRISE compaq
        VARIABLES  { scellNameDateTime,
                     scellSWComponent,
                     scellECode,
                     scellCAC,
                     scellEIP}
        DESCRIPTION
             "Severity: Undetermined -- more information needed to determine severity. The HSV110 controller has detected a enclosure on the CAB bus that does not have a Fibre Channel connection. All fields except port and rack are invalid. other fields are invalid."
           --#TYPE      "StorageCell Event"
           --#SUMMARY   "SCellName-TimeDate %s : SWCID %d : ECode: %d : CAC %d : EIP %d."
           --#ARGUMENTS {0,1,2,3,4,}
           --#SEVERITY  CRITICAL
           --#TIMEINDEX 136
           --#STATE     WARNING
        ::= 13601597
 
   sCellEventTrap-6-3e TRAP-TYPE  -- CAC Code: c5
        ENTERPRISE compaq
        VARIABLES  { scellNameDateTime,
                     scellSWComponent,
                     scellECode,
                     scellCAC,
                     scellEIP}
        DESCRIPTION
             "Severity: Critical -- failure or failure imminent. The HSV110 controller has detected an enclosure on the Fibre Channel but is unable to communicate with the EMU on the CAB bus or the EMU is reporting an invalid enclosure number. All fields except port and rack are invalid. other fields are invalid."
           --#TYPE      "StorageCell Event"
           --#SUMMARY   "SCellName-TimeDate %s : SWCID %d : ECode: %d : CAC %d : EIP %d."
           --#ARGUMENTS {0,1,2,3,4,}
           --#SEVERITY  CRITICAL
           --#TIMEINDEX 136
           --#STATE     WARNING
        ::= 13601598
 
   sCellEventTrap-7-0 TRAP-TYPE  -- CAC Code: b5
        ENTERPRISE compaq
        VARIABLES  { scellNameDateTime,
                     scellSWComponent,
                     scellECode,
                     scellCAC,
                     scellEIP}
        DESCRIPTION
             "Severity: Warning -- not failed but attention recommended or required. Allocation of a Virtual Disk has stalled due to insufficient space in the Disk Group caused by the failure or pulling of a physical disk drive. The tag1 field contains the identity of the Virtual Disk. The tag2 field contains the identity of the Disk Group. The values that may be found in the state field are as follows: <UL><LI>0 = Attempting to retry the allocation <LI>1 = Awaiting a leveling event (a drive needs to be inserted) </UL>"
           --#TYPE      "StorageCell Event"
           --#SUMMARY   "SCellName-TimeDate %s : SWCID %d : ECode: %d : CAC %d : EIP %d."
           --#ARGUMENTS {0,1,2,3,4,}
           --#SEVERITY  MINOR
           --#TIMEINDEX 136
           --#STATE     WARNING
        ::= 13601792
 
   sCellEventTrap-7-1 TRAP-TYPE  -- CAC Code: b5
        ENTERPRISE compaq
        VARIABLES  { scellNameDateTime,
                     scellSWComponent,
                     scellECode,
                     scellCAC,
                     scellEIP}
        DESCRIPTION
             "Severity: Warning -- not failed but attention recommended or required. Expansion of a Virtual Disk has stalled due to insufficient space in the Disk Group caused by the failure or pulling of a physical disk drive. The tag1 field contains the identity of the Virtual Disk. The tag2 field contains the identity of the Disk Group. The values that may be found in the state field are as follows: <UL><LI>0 = Attempting to retry the expansion <LI>1 = Awaiting a leveling event (a drive needs to be inserted) </UL>"
           --#TYPE      "StorageCell Event"
           --#SUMMARY   "SCellName-TimeDate %s : SWCID %d : ECode: %d : CAC %d : EIP %d."
           --#ARGUMENTS {0,1,2,3,4,}
           --#SEVERITY  MINOR
           --#TIMEINDEX 136
           --#STATE     WARNING
        ::= 13601793
 
   sCellEventTrap-7-2 TRAP-TYPE  -- CAC Code: 0
        ENTERPRISE compaq
        VARIABLES  { scellNameDateTime,
                     scellSWComponent,
                     scellECode,
                     scellCAC,
                     scellEIP}
        DESCRIPTION
             "Severity: Normal -- informational in nature. Leveling of capacity in a Disk Group has started. The identity of the Disk Group is contained in the tag1 field."
           --#TYPE      "StorageCell Event"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13601794
 
   sCellEventTrap-7-3 TRAP-TYPE  -- CAC Code: 0
        ENTERPRISE compaq
        VARIABLES  { scellNameDateTime,
                     scellSWComponent,
                     scellECode,
                     scellCAC,
                     scellEIP}
        DESCRIPTION
             "Severity: Normal -- informational in nature. Leveling of capacity in a Disk Group has finished. The identity of the Disk Group is contained in the tag1 field."
           --#TYPE      "StorageCell Event"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13601795
 
   sCellEventTrap-7-4 TRAP-TYPE  -- CAC Code: 0
        ENTERPRISE compaq
        VARIABLES  { scellNameDateTime,
                     scellSWComponent,
                     scellECode,
                     scellCAC,
                     scellEIP}
        DESCRIPTION
             "Severity: Normal -- informational in nature. A member management operation has started due to the appearance or disappearance of a physical disk drive. If available, the tag1 field contains the identity of the physical disk drive. The tag2 field contains the disk unit block in which physical disk drive resides. The values that may be found in the state field are as follows: <UL><LI>2 = Reconstructing <LI>4 = Migrating <LI>6 = Reverting </UL>"
           --#TYPE      "StorageCell Event"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13601796
 
   sCellEventTrap-7-5 TRAP-TYPE  -- CAC Code: 0
        ENTERPRISE compaq
        VARIABLES  { scellNameDateTime,
                     scellSWComponent,
                     scellECode,
                     scellCAC,
                     scellEIP}
        DESCRIPTION
             "Severity: Normal -- informational in nature. A member management operation has finished. If available, the tag1 field contains the identity of the physical disk drive. The tag2 field contains the disk unit block in which the physical disk drive resides. The values that may be found in the state field are as follows: <UL><LI>2 = Reconstructing <LI>4 = Migrating <LI>6 = Reverting </UL>The status field contains one of the following values: <UL><LI>1 = PSEGS NONE ( Reconstruction of data was successful ) <LI>2 = PSEGS RAID0 ( Could not reconstruct RAID0 data ) <LI>4 = PSEGS RAID5 ( Could not reconstruct RAID5 data ) <LI>8 = PSEGS RAID1 ( Could not reconstruct RAID1 data ) </UL>"
           --#TYPE      "StorageCell Event"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13601797
 
   sCellEventTrap-7-6 TRAP-TYPE  -- CAC Code: 0
        ENTERPRISE compaq
        VARIABLES  { scellNameDateTime,
                     scellSWComponent,
                     scellECode,
                     scellCAC,
                     scellEIP}
        DESCRIPTION
             "Severity: Normal -- informational in nature. A Disk Group has started changing its internal structure due to the appearance or disappearance of a Volume. The identity of the Disk Group is contained in the tag1 field. The values that may be found in the state field are as follows: <UL><LI>4 = Merge began <LI>8 = Split began </UL>"
           --#TYPE      "StorageCell Event"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13601798
 
   sCellEventTrap-7-7 TRAP-TYPE  -- CAC Code: 0
        ENTERPRISE compaq
        VARIABLES  { scellNameDateTime,
                     scellSWComponent,
                     scellECode,
                     scellCAC,
                     scellEIP}
        DESCRIPTION
             "Severity: Normal -- informational in nature. A Disk Group has finished changing its internal structure due to the appearance or disappearance of a volume. The identity of the Disk Group is contained in the tag1 field. The values that may be found in the state field are as follows: <UL><LI>4 = Merge completed <LI>8 = Split completed </UL>"
           --#TYPE      "StorageCell Event"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13601799
 
   sCellEventTrap-7-8 TRAP-TYPE  -- CAC Code: 0
        ENTERPRISE compaq
        VARIABLES  { scellNameDateTime,
                     scellSWComponent,
                     scellECode,
                     scellCAC,
                     scellEIP}
        DESCRIPTION
             "Severity: Normal -- informational in nature. Deallocation of a Virtual Disk has failed after three attempts due to unknown circumstances. This will more than likely be caused by failing physical drives. The deletion will be restarted when a resync/reboot occurs. The tag1 field contains the identity of the Virtual Disk. The tag2 field contains the identity of the Disk Group. The values that may be found in the status field indicate the returned status from the delete operation."
           --#TYPE      "StorageCell Event"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13601800
 
   sCellEventTrap-9-1 TRAP-TYPE  -- CAC Code: 0
        ENTERPRISE compaq
        VARIABLES  { scellNameDateTime,
                     scellSWComponent,
                     scellECode,
                     scellCAC,
                     scellEIP}
        DESCRIPTION
             "Severity: Normal -- informational in nature. The state of the Physical Disk Drive identified in the handle field has transitioned to the NORMAL state. The value.ul1 field contains the new state: 1 (NORMAL). The value.ul2 field contains the old state. The state values that may be in the value.ul2 field are as follows: <UL><LI>2 = Degraded <LI>3 = Failed <LI>4 = Not present <LI>5 = Single Port on Fibre </UL>The enclosure number, bay number, and rack number where the Physical Disk Drive is located are contained in the attribute.value.u32[0], attribute.value.u32[1], attribute.value.u32[2] fields, respectively. The attribute.type field contains value 1. The rack number in the attribute.value.u32[2] field will not contain a valid value until a future release."
           --#TYPE      "StorageCell Event"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13602305
 
   sCellEventTrap-9-2 TRAP-TYPE  -- CAC Code: 0
        ENTERPRISE compaq
        VARIABLES  { scellNameDateTime,
                     scellSWComponent,
                     scellECode,
                     scellCAC,
                     scellEIP}
        DESCRIPTION
             "Severity: Normal -- informational in nature. The state of a Volume has changed. The identity of the affected Volume is contained in the handle field. The add-handle field contains the identity of the Physical Disk Drive that is associated with that Volume. The enclosure number, bay number, and rack number where the associated Physical Disk Drive is located are contained in the attribute.value.u32[0], attribute.value.u32[1], and attribute.value.u32[2] fields, respectively. The internal identification of that Volume's Redundant Storage Set is contained in the attribute.value.u32[3] field. The attribute.type field contains the value of 1. The value.ul1 field contains the new state. The value.ul2 field contains the old state. The state values that may be found in the value.ul1 and value.ul2 fields are as follows: <UL><LI>1 = Normal - Volume is present and operating normally <LI>2 = Migrating - Data from this volume is being moved to other storage in this Disk Group <LI>3 = Missing - Volume is inaccessible <LI>4 = Reconstructing - Volume is inaccessible; redundant data is being regenerated and moved to other storage in this Disk Group <LI>5 = Completing - This previously inaccessible volume has become accessible; data migration is being completed <LI>6 = Reverting - This previously inaccessible volume has become accessible; data is being regenerated <LI>7 = Failed - Volume is not being used in the Disk Group; disk errors are preventing normal usage </UL>"
           --#TYPE      "StorageCell Event"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13602306
 
   sCellEventTrap-9-3 TRAP-TYPE  -- CAC Code: 0
        ENTERPRISE compaq
        VARIABLES  { scellNameDateTime,
                     scellSWComponent,
                     scellECode,
                     scellCAC,
                     scellEIP}
        DESCRIPTION
             "Severity: Normal -- informational in nature. The state of the internal Logical Disk associated with the Virtual Disk identified in the handle field has changed. The value.ul1 field contains the new state. The value.ul2 field contains the old state. The state values that may be found in the value.ul1 and value.ul2 fields are as follows: <UL><LI>1 = Normal <LI>2 = Replacement delay in progress <LI>3 = Redundancy lost, restore in progress <LI>4 = Redundancy lost, restore stalled <LI>5 = Failed <LI>6 = Creation in progress <LI>7 = Snapshot is inoperative due to lack of snapshot space <LI>8 = Deletion in progress <LI>9 = Capacity change in progress <LI>10 = Inoperative due to data lost <LI>11 = Capacity reservation in progress <LI>12 = Capacity unreservation in progress </UL>"
           --#TYPE      "StorageCell Event"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13602307
 
   sCellEventTrap-9-4 TRAP-TYPE  -- CAC Code: 0
        ENTERPRISE compaq
        VARIABLES  { scellNameDateTime,
                     scellSWComponent,
                     scellECode,
                     scellCAC,
                     scellEIP}
        DESCRIPTION
             "Severity: Normal -- informational in nature. The state of the HSV110 controller identified in the handle field has transitioned to the NORMAL state. The value.ul1 field contains the new state: 1 (NORMAL). The value.ul2 field contains the old state: 3 (FAILED)."
           --#TYPE      "StorageCell Event"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13602308
 
   sCellEventTrap-9-5 TRAP-TYPE  -- CAC Code: 0
        ENTERPRISE compaq
        VARIABLES  { scellNameDateTime,
                     scellSWComponent,
                     scellECode,
                     scellCAC,
                     scellEIP}
        DESCRIPTION
             "Severity: Normal -- informational in nature. The state of a battery assembly within the HSV110 controller identified in the handle field has changed. The value.ul1 field contains the new state. The value.ul2 field contains the old state. The state values that may be found in the value.ul1 and value.ul2 fields are as follows: <UL><LI>1 = Battery System Hold-up Time is greater than 96 hours <LI>3 = Battery System Hold-up Time is greater than 0 and less than 96 hours <LI>5 = Battery System Hold-up Time is zero hours </UL>"
           --#TYPE      "StorageCell Event"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13602309
 
   sCellEventTrap-9-6 TRAP-TYPE  -- CAC Code: bf
        ENTERPRISE compaq
        VARIABLES  { scellNameDateTime,
                     scellSWComponent,
                     scellECode,
                     scellCAC,
                     scellEIP}
        DESCRIPTION
             "Severity: Undetermined -- more information needed to determine severity. A Volume has transitioned to the MISSING state. The affected Volume is identified in the handle field. The add-handle field contains the identity of the Physical Disk Drive that is associated with that Volume. The enclosure number, bay number, and rack number where the associated Physical Disk Drive is located are contained in the attribute.value.u32[0], attribute.value.u32[1], and attribute.value.u32[2] fields, respectively. The internal identification of that Volume's Redundant Storage Set is contained in the attribute.value.u32[3] field. The attribute.type field contains the value of 1. The value.ul1 field contains the new state. The value.ul2 field contains the old state. The state values that may be found in the value.ul1 and value.ul2 fields are as follows: <UL><LI>1 = Normal - Volume is present and operating normally <LI>2 = Migrating - Data from this volume is being moved to other storage in this Disk Group <LI>4 = Reconstructing - Volume is inaccessible; redundant data is being regenerated and moved to other storage in this Disk Group <LI>5 = Completing - This previously inaccessible volume has become accessible; data migration is being completed <LI>6 = Reverting - This previously inaccessible volume has become accessible; data is being regenerated <LI>7 = Failed - Volume is not being used in the Disk Group; disk errors are preventing normal usage </UL>"
           --#TYPE      "StorageCell Event"
           --#SUMMARY   "SCellName-TimeDate %s : SWCID %d : ECode: %d : CAC %d : EIP %d."
           --#ARGUMENTS {0,1,2,3,4,}
           --#SEVERITY  CRITICAL
           --#TIMEINDEX 136
           --#STATE     WARNING
        ::= 13602310
 
   sCellEventTrap-9-7 TRAP-TYPE  -- CAC Code: 0
        ENTERPRISE compaq
        VARIABLES  { scellNameDateTime,
                     scellSWComponent,
                     scellECode,
                     scellCAC,
                     scellEIP}
        DESCRIPTION
             "Severity: Normal -- informational in nature. The state of the Fibre Channel port identified in the attribute.value.str field and located on the rear panel of the HSV110 controller identified in the handle field has transitioned to the NORMAL state. The attribute.type field contains the value 4. The value.ul1 field contains the new state: 1 (NORMAL). The value.ul2 field contains the old state: 2 (FAILED). <P> Note that the HSV110 controller's internal identity of the affected Fibre Channel port is contained in the secondary-id field."
           --#TYPE      "StorageCell Event"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13602311
 
   sCellEventTrap-9-8 TRAP-TYPE  -- CAC Code: b4
        ENTERPRISE compaq
        VARIABLES  { scellNameDateTime,
                     scellSWComponent,
                     scellECode,
                     scellCAC,
                     scellEIP}
        DESCRIPTION
             "Severity: Warning -- not failed but attention recommended or required. The Occupancy Alarm Level threshold has been reached for the Disk Group identified in the handle field."
           --#TYPE      "StorageCell Event"
           --#SUMMARY   "SCellName-TimeDate %s : SWCID %d : ECode: %d : CAC %d : EIP %d."
           --#ARGUMENTS {0,1,2,3,4,}
           --#SEVERITY  MINOR
           --#TIMEINDEX 136
           --#STATE     WARNING
        ::= 13602312
 
   sCellEventTrap-9-9 TRAP-TYPE  -- CAC Code: 0
        ENTERPRISE compaq
        VARIABLES  { scellNameDateTime,
                     scellSWComponent,
                     scellECode,
                     scellCAC,
                     scellEIP}
        DESCRIPTION
             "Severity: Normal -- informational in nature. The Resource Availability state of a Volume has transitioned to the SUFFICIENT state. The affected Volume is identified in the handle field. The add-handle field contains the identity of the Physical Disk Drive that is associated with that Volume. The enclosure number, bay number, and rack number where the associated Physical Disk Drive is located are contained in the attribute.value.u32[0], attribute.value.u32[1], and attribute.value.u32[2] fields, respectively. The internal identification of that Volume's Redundant Storage Set is contained in the attribute.value.u32[3] field. The attribute.type field contains the value of 1. The value.ul1 field contains the new state: 0 (SUFFICIENT). The value.ul2 field contains the old state: 1 (INSUFFICIENT)."
           --#TYPE      "StorageCell Event"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13602313
 
   sCellEventTrap-9-a TRAP-TYPE  -- CAC Code: 0
        ENTERPRISE compaq
        VARIABLES  { scellNameDateTime,
                     scellSWComponent,
                     scellECode,
                     scellCAC,
                     scellEIP}
        DESCRIPTION
             "Severity: Normal -- informational in nature. The Data Availability state of the internal Logical Disk associated with the Virtual Disk identified in the handle field has transitioned to the NORMAL state. The value.ul1 field contains the new state: 0 (NORMAL). The value.ul2 field contains the old state: 1 (DATA LOST)."
           --#TYPE      "StorageCell Event"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13602314
 
   sCellEventTrap-9-c TRAP-TYPE  -- CAC Code: 0
        ENTERPRISE compaq
        VARIABLES  { scellNameDateTime,
                     scellSWComponent,
                     scellECode,
                     scellCAC,
                     scellEIP}
        DESCRIPTION
             "Severity: Normal -- informational in nature. The Snapclone Logical Disk identified in the handle field has completed the unsharing operation. The secondary-id field contains the noid of the associated successor internal Logical Disk."
           --#TYPE      "StorageCell Event"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13602316
 
   sCellEventTrap-9-d TRAP-TYPE  -- CAC Code: 0
        ENTERPRISE compaq
        VARIABLES  { scellNameDateTime,
                     scellSWComponent,
                     scellECode,
                     scellCAC,
                     scellEIP}
        DESCRIPTION
             "Severity: Normal -- informational in nature. The state of the Quorum Disk flag of a Volume has changed. The affected Volume is identified in the handle field. The value.ul1 field contains the new state of the Quorum Disk flag. The value.ul2 field contains the old state of the Quorum Disk flag. The state values that may be found in the value.ul1 and value.ul2 fields are as follows: <UL><LI>0 = Not quorum disk <LI>1 = Quorum disk </UL>"
           --#TYPE      "StorageCell Event"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13602317
 
   sCellEventTrap-9-e TRAP-TYPE  -- CAC Code: 36
        ENTERPRISE compaq
        VARIABLES  { scellNameDateTime,
                     scellSWComponent,
                     scellECode,
                     scellCAC,
                     scellEIP}
        DESCRIPTION
             "Severity: Critical -- failure or failure imminent. The temperature trip point for a temperature sensor located within an HSV110 controller has been reached. The HSV110 controller is identified in the handle field. The value.ul1 field contains the current temperature reading from I2C sensor 1 in degrees celsius while the value.ul2 field contains the adjusted reading from I2C sensor 2. The set temperature trip point is contained in the secondary-id field."
           --#TYPE      "StorageCell Event"
           --#SUMMARY   "SCellName-TimeDate %s : SWCID %d : ECode: %d : CAC %d : EIP %d."
           --#ARGUMENTS {0,1,2,3,4,}
           --#SEVERITY  CRITICAL
           --#TIMEINDEX 136
           --#STATE     WARNING
        ::= 13602318
 
   sCellEventTrap-9-f TRAP-TYPE  -- CAC Code: 2e
        ENTERPRISE compaq
        VARIABLES  { scellNameDateTime,
                     scellSWComponent,
                     scellECode,
                     scellCAC,
                     scellEIP}
        DESCRIPTION
             "Severity: Warning -- not failed but attention recommended or required. The temperature within the HSV110 controller identified in the handle field is approaching its trip point. The value.ul1 field contains the current temperature reading from I2C sensor 1 in degrees celsius while the value.ul2 field contains the adjusted reading from I2C sensor 2. The secondary-id field contains the set temperature trip point in Celsius."
           --#TYPE      "StorageCell Event"
           --#SUMMARY   "SCellName-TimeDate %s : SWCID %d : ECode: %d : CAC %d : EIP %d."
           --#ARGUMENTS {0,1,2,3,4,}
           --#SEVERITY  MINOR
           --#TIMEINDEX 136
           --#STATE     WARNING
        ::= 13602319
 
   sCellEventTrap-9-11 TRAP-TYPE  -- CAC Code: 0
        ENTERPRISE compaq
        VARIABLES  { scellNameDateTime,
                     scellSWComponent,
                     scellECode,
                     scellCAC,
                     scellEIP}
        DESCRIPTION
             "Severity: Normal -- informational in nature. The Blower Present flag for the '1' blower assembly located within the HSV110 controller identified in the handle field has transitioned from the NOT PRESENT to PRESENT state indicating that the blower has been reinstalled. The secondary-id field contains the '1' blower assembly internal identifier value: 1. The value.ul1 field contains the new state of the Blower Present flag: 1 (PRESENT). The value.ul2 field contains the old state of the Blower Present flag: 0 (NOT PRESENT)."
           --#TYPE      "StorageCell Event"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13602321
 
   sCellEventTrap-9-12 TRAP-TYPE  -- CAC Code: 24
        ENTERPRISE compaq
        VARIABLES  { scellNameDateTime,
                     scellSWComponent,
                     scellECode,
                     scellCAC,
                     scellEIP}
        DESCRIPTION
             "Severity: Critical -- failure or failure imminent. The '1' blower located within the HSV110 controller identified in the handle field is running slower than the lowest acceptable speed. The secondary-id field contains the '1' blower assembly internal identifier value: 1. The value.ul1 field contains the current speed of the '1' blower. The value.ul2 field contains the lowest acceptable speed for the '1' blower."
           --#TYPE      "StorageCell Event"
           --#SUMMARY   "SCellName-TimeDate %s : SWCID %d : ECode: %d : CAC %d : EIP %d."
           --#ARGUMENTS {0,1,2,3,4,}
           --#SEVERITY  CRITICAL
           --#TIMEINDEX 136
           --#STATE     WARNING
        ::= 13602322
 
   sCellEventTrap-9-13 TRAP-TYPE  -- CAC Code: 0
        ENTERPRISE compaq
        VARIABLES  { scellNameDateTime,
                     scellSWComponent,
                     scellECode,
                     scellCAC,
                     scellEIP}
        DESCRIPTION
             "Severity: Normal -- informational in nature. One of the voltage sensors located within the HSV110 controller identified in the handle field has reported a voltage that is out of range. The value.ul1 field contains the out of range voltage value. The secondary-id field contains the specific voltage threshold value (i.e., 12V, 5V, 3.3V, 2.5V or 2V). Note that the voltages are expressed in millivolts--e.g.,12.5V is expressed as 12500."
           --#TYPE      "StorageCell Event"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13602323
 
   sCellEventTrap-9-14 TRAP-TYPE  -- CAC Code: bf
        ENTERPRISE compaq
        VARIABLES  { scellNameDateTime,
                     scellSWComponent,
                     scellECode,
                     scellCAC,
                     scellEIP}
        DESCRIPTION
             "Severity: Undetermined -- more information needed to determine severity. The state of a Volume has transitioned to the FAILED state. The affected Volume is identified in the handle field. The add-handle field contains the identity of the Physical Disk Drive that is associated with that Volume. The enclosure number, bay number, and rack number where the associated Physical Disk Drive is located are contained in the attribute.value.u32[0], attribute.value.u32[1], and attribute.value.u32[2] fields, respectively. The internal identification of that Volume's Redundant Storage Set is contained in the attribute.value.u32[3] field. The attribute.type field contains the value of 1. The value.ul1 field contains the new state: 7 (FAILED). The value.ul2 field contains the old state. The state values that may be found in the value.ul2 fields are as follows: <UL><LI>1 = Normal - Volume is present and operating normally <LI>2 = Migrating - Data from this volume is being moved to other storage in this Disk Group <LI>3 = Missing - Volume is inaccessible <LI>4 = Reconstructing - Volume is inaccessible; redundant data is being regenerated and moved to other storage in this Disk Group <LI>5 = Completing - This previously inaccessible volume has become accessible; data migration is being completed <LI>6 = Reverting - This previously inaccessible volume has become accessible; data is being regenerated </UL>"
           --#TYPE      "StorageCell Event"
           --#SUMMARY   "SCellName-TimeDate %s : SWCID %d : ECode: %d : CAC %d : EIP %d."
           --#ARGUMENTS {0,1,2,3,4,}
           --#SEVERITY  CRITICAL
           --#TIMEINDEX 136
           --#STATE     WARNING
        ::= 13602324
 
   sCellEventTrap-9-15 TRAP-TYPE  -- CAC Code: b9
        ENTERPRISE compaq
        VARIABLES  { scellNameDateTime,
                     scellSWComponent,
                     scellECode,
                     scellCAC,
                     scellEIP}
        DESCRIPTION
             "Severity: Undetermined -- more information needed to determine severity. An HSV110 controller has failed. The state of the HSV110 controller identified in the handle field has transitioned to the FAILED state. The value.ul1 field contains the new state: 3 (FAILED). The value.ul2 field contains the old state: 1 (NORMAL)."
           --#TYPE      "StorageCell Event"
           --#SUMMARY   "SCellName-TimeDate %s : SWCID %d : ECode: %d : CAC %d : EIP %d."
           --#ARGUMENTS {0,1,2,3,4,}
           --#SEVERITY  CRITICAL
           --#TIMEINDEX 136
           --#STATE     WARNING
        ::= 13602325
 
   sCellEventTrap-9-16 TRAP-TYPE  -- CAC Code: 0
        ENTERPRISE compaq
        VARIABLES  { scellNameDateTime,
                     scellSWComponent,
                     scellECode,
                     scellCAC,
                     scellEIP}
        DESCRIPTION
             "Severity: Normal -- informational in nature. The temperature within the HSV110 controller identified in the handle field has returned to its normal operating range. The value.ul1 field contains the current temperature reading in celsius from I2C sensor 1, while the value.ul2 field contains the adjusted reading from I2C sensor 2."
           --#TYPE      "StorageCell Event"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13602326
 
   sCellEventTrap-9-17 TRAP-TYPE  -- CAC Code: 28
        ENTERPRISE compaq
        VARIABLES  { scellNameDateTime,
                     scellSWComponent,
                     scellECode,
                     scellCAC,
                     scellEIP}
        DESCRIPTION
             "Severity: Critical -- failure or failure imminent. An HSV110 controller's battery assembly has been removed. The Battery Present flag for battery assembly '1' located within the HSV110 controller identified in the handle field has changed from PRESENT to NOT PRESENT indicating that the battery assembly was removed. The secondary-id field contains the battery assembly '1' internal identifier value: 1. The value.ul1 field contains the new state of the Battery Present flag: 0 (NOT PRESENT). The value.ul2 field contains the old state of the Battery Present flag: 1 (PRESENT)."
           --#TYPE      "StorageCell Event"
           --#SUMMARY   "SCellName-TimeDate %s : SWCID %d : ECode: %d : CAC %d : EIP %d."
           --#ARGUMENTS {0,1,2,3,4,}
           --#SEVERITY  CRITICAL
           --#TIMEINDEX 136
           --#STATE     WARNING
        ::= 13602327
 
   sCellEventTrap-9-18 TRAP-TYPE  -- CAC Code: 0
        ENTERPRISE compaq
        VARIABLES  { scellNameDateTime,
                     scellSWComponent,
                     scellECode,
                     scellCAC,
                     scellEIP}
        DESCRIPTION
             "Severity: Normal -- informational in nature. The Battery In Use flag for battery assembly '1' located within the HSV110 controller identified in the handle field has transitioned from the NOT IN USE to IN USE state indicating that the battery assembly is functioning properly. The secondary-id field contains the battery assembly '1' internal identifier value: 1. The value.ul1 field contains the new state of the Battery In Use flag: 1 (IN USE). The value.ul2 field contains the old state of the Battery In Use flag: 0 (NOT IN USE)."
           --#TYPE      "StorageCell Event"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13602328
 
   sCellEventTrap-9-19 TRAP-TYPE  -- CAC Code: 0
        ENTERPRISE compaq
        VARIABLES  { scellNameDateTime,
                     scellSWComponent,
                     scellECode,
                     scellCAC,
                     scellEIP}
        DESCRIPTION
             "Severity: Normal -- informational in nature. One of the voltage sensors located within the HSV110 controller identified in the handle field has reported a voltage that indicates that a voltage that was previously out of range has returned to the normal range. The value.ul1 field contains the normal range voltage value. The secondary-id field contains the voltage threshold value (i.e., 12V, 5V, 3.3V, 2.5V or 2V). Note that the voltages are expressed in thousands--e.g., 12.5V is expressed as 12500."
           --#TYPE      "StorageCell Event"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13602329
 
   sCellEventTrap-9-1a TRAP-TYPE  -- CAC Code: 2f
        ENTERPRISE compaq
        VARIABLES  { scellNameDateTime,
                     scellSWComponent,
                     scellECode,
                     scellCAC,
                     scellEIP}
        DESCRIPTION
             "Severity: Warning -- not failed but attention recommended or required. The battery assembly voltage regulator located within the HSV110 controller identified in the handle field is offline."
           --#TYPE      "StorageCell Event"
           --#SUMMARY   "SCellName-TimeDate %s : SWCID %d : ECode: %d : CAC %d : EIP %d."
           --#ARGUMENTS {0,1,2,3,4,}
           --#SEVERITY  MINOR
           --#TIMEINDEX 136
           --#STATE     WARNING
        ::= 13602330
 
   sCellEventTrap-9-1b TRAP-TYPE  -- CAC Code: 0
        ENTERPRISE compaq
        VARIABLES  { scellNameDateTime,
                     scellSWComponent,
                     scellECode,
                     scellCAC,
                     scellEIP}
        DESCRIPTION
             "Severity: Normal -- informational in nature. The state of the Disk Group identified in the handle field has transitioned to the NORMAL state. The value.ul1 field contains the new Disk Group state: 1 (NORMAL). The value.ul2 field contains the old Disk Group state. The state values that may be found in the value.ul2 field are as follows: <UL><LI>2 = Disk Group with no redundancy is inoperative <LI>3 = Disk Group with parity redundancy is inoperative <LI>4 = Disk Group with mirrored redundancy is inoperative <LI>5 = Disk Group with no redundancy is inoperative, marked for re-use <LI>6 = Disk Group with parity redundancy is inoperative, marked for re-use <LI>7 = Disk Group with mirrored redundancy is inoperative, marked for re-use </UL>"
           --#TYPE      "StorageCell Event"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13602331
 
   sCellEventTrap-9-1c TRAP-TYPE  -- CAC Code: 0
        ENTERPRISE compaq
        VARIABLES  { scellNameDateTime,
                     scellSWComponent,
                     scellECode,
                     scellCAC,
                     scellEIP}
        DESCRIPTION
             "Severity: Normal -- informational in nature. The Occupancy Alarm Level for the Disk Group identified in the handle field has returned to the normal range."
           --#TYPE      "StorageCell Event"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13602332
 
   sCellEventTrap-9-1d TRAP-TYPE  -- CAC Code: 22
        ENTERPRISE compaq
        VARIABLES  { scellNameDateTime,
                     scellSWComponent,
                     scellECode,
                     scellCAC,
                     scellEIP}
        DESCRIPTION
             "Severity: Critical -- failure or failure imminent. An HSV110 controller's battery assembly has malfunctioned. The Battery In Use flag for battery assembly '1' located within the HSV110 controller identified in the handle field has transitioned from the IN USE to NOT IN USE state indicating that the battery assembly has malfunctioned. The secondary-id field contains the battery assembly '1' internal identifier value: 1. The value.ul1 field contains the new state of the Battery In Use flag: 0 (NOT IN USE). The value.ul2 field contains the old state of the Battery In Use flag: 1 (IN USE)."
           --#TYPE      "StorageCell Event"
           --#SUMMARY   "SCellName-TimeDate %s : SWCID %d : ECode: %d : CAC %d : EIP %d."
           --#ARGUMENTS {0,1,2,3,4,}
           --#SEVERITY  CRITICAL
           --#TIMEINDEX 136
           --#STATE     WARNING
        ::= 13602333
 
   sCellEventTrap-9-1e TRAP-TYPE  -- CAC Code: 0
        ENTERPRISE compaq
        VARIABLES  { scellNameDateTime,
                     scellSWComponent,
                     scellECode,
                     scellCAC,
                     scellEIP}
        DESCRIPTION
             "Severity: Normal -- informational in nature. The Battery Present flag for battery assembly '1' located within the HSV110 controller identified in the handle field has changed from NOT PRESENT to PRESENT indicating that the battery assembly was reinstalled. The secondary-id field contains the battery assembly '1' internal identifier value: 1. The value.ul1 field contains the new state of the Battery Present flag: 1 (PRESENT). The value.ul2 field contains the old state of the Battery Present flag: 0 (NOT PRESENT)."
           --#TYPE      "StorageCell Event"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13602334
 
   sCellEventTrap-9-1f TRAP-TYPE  -- CAC Code: 29
        ENTERPRISE compaq
        VARIABLES  { scellNameDateTime,
                     scellSWComponent,
                     scellECode,
                     scellCAC,
                     scellEIP}
        DESCRIPTION
             "Severity: Critical -- failure or failure imminent. An HSV110 controller's battery assembly has been removed. The Battery Present flag for battery assembly '2' located within the HSV110 controller identified in the handle field has changed from PRESENT to NOT PRESENT indicating that the battery assembly was removed. The secondary-id field contains the battery assembly '2' internal identifier value: 2. The value.ul1 field contains the new state of the Battery Present flag: 0 (NOT PRESENT). The value.ul2 field contains the old state of the Battery Present flag: 1 (PRESENT)."
           --#TYPE      "StorageCell Event"
           --#SUMMARY   "SCellName-TimeDate %s : SWCID %d : ECode: %d : CAC %d : EIP %d."
           --#ARGUMENTS {0,1,2,3,4,}
           --#SEVERITY  CRITICAL
           --#TIMEINDEX 136
           --#STATE     WARNING
        ::= 13602335
 
   sCellEventTrap-9-20 TRAP-TYPE  -- CAC Code: 0
        ENTERPRISE compaq
        VARIABLES  { scellNameDateTime,
                     scellSWComponent,
                     scellECode,
                     scellCAC,
                     scellEIP}
        DESCRIPTION
             "Severity: Normal -- informational in nature. The Battery Present flag for battery assembly '2' located within the HSV110 controller identified in the handle field has changed from NOT PRESENT to PRESENT indicating that the battery assembly was reinstalled. The secondary-id field contains the battery assembly '2' internal identifier value: 2. The value.ul1 field contains the new state of the Battery Present flag: 1 (PRESENT). The value.ul2 field contains the old state of the Battery Present flag: 0 (NOT PRESENT)."
           --#TYPE      "StorageCell Event"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13602336
 
   sCellEventTrap-9-21 TRAP-TYPE  -- CAC Code: 0
        ENTERPRISE compaq
        VARIABLES  { scellNameDateTime,
                     scellSWComponent,
                     scellECode,
                     scellCAC,
                     scellEIP}
        DESCRIPTION
             "Severity: Normal -- informational in nature. The Battery In Use flag for battery assembly '2' located within the HSV110 controller identified in the handle field has transitioned from the NOT IN USE to IN USE state indicating that the battery assembly is functioning properly. The secondary-id field contains the battery assembly '2' internal identifier value: 2. The value.ul1 field contains the new state of the Battery In Use flag: 1 (IN USE). The value.ul2 field contains the old state of the Battery In Use flag: 0 (NOT IN USE)."
           --#TYPE      "StorageCell Event"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13602337
 
   sCellEventTrap-9-22 TRAP-TYPE  -- CAC Code: 23
        ENTERPRISE compaq
        VARIABLES  { scellNameDateTime,
                     scellSWComponent,
                     scellECode,
                     scellCAC,
                     scellEIP}
        DESCRIPTION
             "Severity: Critical -- failure or failure imminent. An HSV110 controller's battery assembly has malfunctioned. The Battery In Use flag for battery assembly '2' located within the HSV110 controller identified in the handle field has transitioned from the IN USE to NOT IN USE state indicating that the battery assembly has malfunctioned. The secondary-id field contains the battery assembly '2' internal identifier value: 2. The value.ul1 field contains the new state of the Battery In Use flag: 0 (NOT IN USE). The value.ul2 field contains the old state of the Battery In Use flag: 1 (IN USE)."
           --#TYPE      "StorageCell Event"
           --#SUMMARY   "SCellName-TimeDate %s : SWCID %d : ECode: %d : CAC %d : EIP %d."
           --#ARGUMENTS {0,1,2,3,4,}
           --#SEVERITY  CRITICAL
           --#TIMEINDEX 136
           --#STATE     WARNING
        ::= 13602338
 
   sCellEventTrap-9-23 TRAP-TYPE  -- CAC Code: 2b
        ENTERPRISE compaq
        VARIABLES  { scellNameDateTime,
                     scellSWComponent,
                     scellECode,
                     scellCAC,
                     scellEIP}
        DESCRIPTION
             "Severity: Critical -- failure or failure imminent. The Blower Present flag for the '2' blower assembly located within the HSV110 controller identified in the handle field has transitioned from the PRESENT to NOT PRESENT state indicating that the blower has been removed. The secondary-id field contains the '2' blower assembly internal identifier value: 2. The value.ul1 field contains the new state of the Blower Present flag: 0 (NOT PRESENT). The value.ul2 field contains the old state of the Blower Present flag: 1 (PRESENT)."
           --#TYPE      "StorageCell Event"
           --#SUMMARY   "SCellName-TimeDate %s : SWCID %d : ECode: %d : CAC %d : EIP %d."
           --#ARGUMENTS {0,1,2,3,4,}
           --#SEVERITY  CRITICAL
           --#TIMEINDEX 136
           --#STATE     WARNING
        ::= 13602339
 
   sCellEventTrap-9-24 TRAP-TYPE  -- CAC Code: 0
        ENTERPRISE compaq
        VARIABLES  { scellNameDateTime,
                     scellSWComponent,
                     scellECode,
                     scellCAC,
                     scellEIP}
        DESCRIPTION
             "Severity: Normal -- informational in nature. The Blower Present flag for the '2' blower assembly located within the HSV110 controller identified in the handle field has transitioned from the NOT PRESENT to PRESENT state indicating that the blower has been reinstalled. The secondary-id field contains the '2' blower assembly internal identifier value: 2. The value.ul1 field contains the new state of the Blower Present flag: 1 (PRESENT). The value.ul2 field contains the old state of the Blower Present flag: 0 (NOT PRESENT)."
           --#TYPE      "StorageCell Event"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13602340
 
   sCellEventTrap-9-25 TRAP-TYPE  -- CAC Code: 25
        ENTERPRISE compaq
        VARIABLES  { scellNameDateTime,
                     scellSWComponent,
                     scellECode,
                     scellCAC,
                     scellEIP}
        DESCRIPTION
             "Severity: Critical -- failure or failure imminent. The '2' blower located within the HSV110 controller identified in the handle field is running slower than the lowest acceptable speed. The secondary-id field contains the '2' blower assembly internal identifier value: 2. The value.ul1 field contains the current speed of the '2' blower. The value.ul2 field contains the lowest acceptable speed for the '2' blower."
           --#TYPE      "StorageCell Event"
           --#SUMMARY   "SCellName-TimeDate %s : SWCID %d : ECode: %d : CAC %d : EIP %d."
           --#ARGUMENTS {0,1,2,3,4,}
           --#SEVERITY  CRITICAL
           --#TIMEINDEX 136
           --#STATE     WARNING
        ::= 13602341
 
   sCellEventTrap-9-26 TRAP-TYPE  -- CAC Code: 2c
        ENTERPRISE compaq
        VARIABLES  { scellNameDateTime,
                     scellSWComponent,
                     scellECode,
                     scellCAC,
                     scellEIP}
        DESCRIPTION
             "Severity: Critical -- failure or failure imminent. An HSV110 controller's '1' blower/power supply assembly has been removed or AC power has been removed from the power supply. The HSV110 controller is identified in the handle field. The secondary-id field contains the '1' blower/power supply assembly internal identifier value: 1. The value.ul1 field contains the new state of the Blower/Power Supply Present flag: 0 (NOT PRESENT). The value.ul2 field contains the old state of the Blower/Power Supply Present flag: 1 (PRESENT)."
           --#TYPE      "StorageCell Event"
           --#SUMMARY   "SCellName-TimeDate %s : SWCID %d : ECode: %d : CAC %d : EIP %d."
           --#ARGUMENTS {0,1,2,3,4,}
           --#SEVERITY  CRITICAL
           --#TIMEINDEX 136
           --#STATE     WARNING
        ::= 13602342
 
   sCellEventTrap-9-27 TRAP-TYPE  -- CAC Code: 0
        ENTERPRISE compaq
        VARIABLES  { scellNameDateTime,
                     scellSWComponent,
                     scellECode,
                     scellCAC,
                     scellEIP}
        DESCRIPTION
             "Severity: Normal -- informational in nature. An HSV110 controller's '1' blower/power supply assembly has been reinstalled or AC power has been restored to the power supply. The HSV110 controller is identified in the handle field. The secondary-id field contains the '1' blower/power supply assembly internal identifier value: 1. The value.ul1 field contains the new state of the Blower/Power Supply Present flag: 1 (PRESENT). The value.ul2 field contains the old state of the Blower/Power Supply Present flag: 0 (NOT PRESENT)."
           --#TYPE      "StorageCell Event"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13602343
 
   sCellEventTrap-9-28 TRAP-TYPE  -- CAC Code: 2d
        ENTERPRISE compaq
        VARIABLES  { scellNameDateTime,
                     scellSWComponent,
                     scellECode,
                     scellCAC,
                     scellEIP}
        DESCRIPTION
             "Severity: Critical -- failure or failure imminent. An HSV110 controller's '2' blower/power supply assembly has been removed or AC power has been removed from the power supply. The HSV110 controller is identified in the handle field. The secondary-id field contains the '2' blower/power supply assembly internal identifier value: 2. The value.ul1 field contains the new state of the Blower/Power Supply Present flag: 0 (NOT PRESENT). The value.ul2 field contains the old state of the Blower/Power Supply Present flag: 1 (PRESENT)."
           --#TYPE      "StorageCell Event"
           --#SUMMARY   "SCellName-TimeDate %s : SWCID %d : ECode: %d : CAC %d : EIP %d."
           --#ARGUMENTS {0,1,2,3,4,}
           --#SEVERITY  CRITICAL
           --#TIMEINDEX 136
           --#STATE     WARNING
        ::= 13602344
 
   sCellEventTrap-9-29 TRAP-TYPE  -- CAC Code: 0
        ENTERPRISE compaq
        VARIABLES  { scellNameDateTime,
                     scellSWComponent,
                     scellECode,
                     scellCAC,
                     scellEIP}
        DESCRIPTION
             "Severity: Normal -- informational in nature. An HSV110 controller's '2' blower/power supply assembly has been reinstalled or AC power has been restored to the power supply. The HSV110 controller is identified in the handle field. The secondary-id field contains the '2' blower/power supply assembly internal identifier value: 2. The value.ul1 field contains the new state of the Blower/Power Supply Present flag: 1 (PRESENT). The value.ul2 field contains the old state of the Blower/Power Supply Present flag: 0 (NOT PRESENT)."
           --#TYPE      "StorageCell Event"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13602345
 
   sCellEventTrap-9-2a TRAP-TYPE  -- CAC Code: 26
        ENTERPRISE compaq
        VARIABLES  { scellNameDateTime,
                     scellSWComponent,
                     scellECode,
                     scellCAC,
                     scellEIP}
        DESCRIPTION
             "Severity: Critical -- failure or failure imminent. The '1' blower/power supply located within the HSV110 controller identified in the handle field is running slower than the lowest acceptable speed. The secondary-id field contains the '1' blower/power supply assembly internal identifier value: 1. The value.ul1 field contains the current speed of the '1' blower/power supply. The value.ul2 field contains the lowest acceptable speed for the '1' blower/power supply."
           --#TYPE      "StorageCell Event"
           --#SUMMARY   "SCellName-TimeDate %s : SWCID %d : ECode: %d : CAC %d : EIP %d."
           --#ARGUMENTS {0,1,2,3,4,}
           --#SEVERITY  CRITICAL
           --#TIMEINDEX 136
           --#STATE     WARNING
        ::= 13602346
 
   sCellEventTrap-9-2b TRAP-TYPE  -- CAC Code: 27
        ENTERPRISE compaq
        VARIABLES  { scellNameDateTime,
                     scellSWComponent,
                     scellECode,
                     scellCAC,
                     scellEIP}
        DESCRIPTION
             "Severity: Critical -- failure or failure imminent. The '2' blower/power supply located within the HSV110 controller identified in the handle field is running slower than the lowest acceptable speed. The secondary-id field contains the '2' blower/power supply assembly internal identifier value: 2. The value.ul1 field contains the current speed of the '2' blower/power supply. The value.ul2 field contains the lowest acceptable speed for the '2' blower/power supply."
           --#TYPE      "StorageCell Event"
           --#SUMMARY   "SCellName-TimeDate %s : SWCID %d : ECode: %d : CAC %d : EIP %d."
           --#ARGUMENTS {0,1,2,3,4,}
           --#SEVERITY  CRITICAL
           --#TIMEINDEX 136
           --#STATE     WARNING
        ::= 13602347
 
   sCellEventTrap-9-2c TRAP-TYPE  -- CAC Code: 2f
        ENTERPRISE compaq
        VARIABLES  { scellNameDateTime,
                     scellSWComponent,
                     scellECode,
                     scellCAC,
                     scellEIP}
        DESCRIPTION
             "Severity: Warning -- not failed but attention recommended or required. The state of a battery assembly within the HSV110 controller identified in the handle field has transitioned to the Battery System Hold-up Time is zero hours state. The value.ul1 field contains the new state 5: (Battery System Hold-up Time is zero hours). The value.ul2 field contains the old state. The state values that may be found in the value.ul2 field are as follows: <UL><LI>1 = Battery System Hold-up Time is greater than 96 hours <LI>3 = Battery System Hold-up Time is greater than 0 and less than 96 hours <LI>5 = Battery System Hold-up Time is zero hours </UL>"
           --#TYPE      "StorageCell Event"
           --#SUMMARY   "SCellName-TimeDate %s : SWCID %d : ECode: %d : CAC %d : EIP %d."
           --#ARGUMENTS {0,1,2,3,4,}
           --#SEVERITY  MINOR
           --#TIMEINDEX 136
           --#STATE     WARNING
        ::= 13602348
 
   sCellEventTrap-9-2d TRAP-TYPE  -- CAC Code: bf
        ENTERPRISE compaq
        VARIABLES  { scellNameDateTime,
                     scellSWComponent,
                     scellECode,
                     scellCAC,
                     scellEIP}
        DESCRIPTION
             "Severity: Undetermined -- more information needed to determine severity. The Resource Availability state of a Volume has transitioned to the INSUFFICIENT state. The affected Volume is identified in the handle field. The add-handle field contains the identity of the Physical Disk Drive that is associated with that Volume. The enclosure number, bay number, and rack number where the associated Physical Disk Drive is located are contained in the attribute.value.u32[0], attribute.value.u32[1], and attribute.value.u32[2] fields, respectively. The internal identification of that Volume's Redundant Storage Set is contained in the attribute.value.u32[3] field. The attribute.type field contains the value of 1. The value.ul1 field contains the new state: 1 (INSUFFICIENT). The value.ul2 field contains the old state: 0 (SUFFICIENT)."
           --#TYPE      "StorageCell Event"
           --#SUMMARY   "SCellName-TimeDate %s : SWCID %d : ECode: %d : CAC %d : EIP %d."
           --#ARGUMENTS {0,1,2,3,4,}
           --#SEVERITY  CRITICAL
           --#TIMEINDEX 136
           --#STATE     WARNING
        ::= 13602349
 
   sCellEventTrap-9-2e TRAP-TYPE  -- CAC Code: 0
        ENTERPRISE compaq
        VARIABLES  { scellNameDateTime,
                     scellSWComponent,
                     scellECode,
                     scellCAC,
                     scellEIP}
        DESCRIPTION
             "Severity: Normal -- informational in nature. The HSV110 controller identified in the handle field rejected a login attempt. The value.ul1 and value.ul2 fields contain words [0] and [1], respectively, of the World Wide Name of the host adapter that originated the rejected login attempt. The secondary-id field contains the reason for the rejection as follows: <UL><LI>50 = The host is already logged in <LI>101 = Maximum number of logins is exceeded <LI>102 = Invalid cookie was sent <LI>106 = The password is not set on the HSV110 controller </UL>"
           --#TYPE      "StorageCell Event"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13602350
 
   sCellEventTrap-9-2f TRAP-TYPE  -- CAC Code: 0
        ENTERPRISE compaq
        VARIABLES  { scellNameDateTime,
                     scellSWComponent,
                     scellECode,
                     scellCAC,
                     scellEIP}
        DESCRIPTION
             "Severity: Normal -- informational in nature. The HSV110 controller identified in the handle field processed a Storage System Management Interface command with the result of non-success return code. The value.ul1 field contains internal the command type. The value.ul2 field contains the internal return code. The attribute.value.obj field contains the internal target and internal version of the command."
           --#TYPE      "StorageCell Event"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13602351
 
   sCellEventTrap-9-30 TRAP-TYPE  -- CAC Code: 0
        ENTERPRISE compaq
        VARIABLES  { scellNameDateTime,
                     scellSWComponent,
                     scellECode,
                     scellCAC,
                     scellEIP}
        DESCRIPTION
             "Severity: Normal -- informational in nature. The HSV110 controller identified in the handle field has updated the physical disk drive map for the loop pair identified in the secondary-id field. The value.ul1 field contains the new internal map generation number. The value.ul2 field contains the old internal map generation number."
           --#TYPE      "StorageCell Event"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13602352
 
   sCellEventTrap-9-31 TRAP-TYPE  -- CAC Code: 42
        ENTERPRISE compaq
        VARIABLES  { scellNameDateTime,
                     scellSWComponent,
                     scellECode,
                     scellCAC,
                     scellEIP}
        DESCRIPTION
             "Severity: Critical -- failure or failure imminent. The state of the Physical Disk Drive identified in the handle field has transitioned to the DEGRADED state. The value.ul1 field contains the new state: 2 (DEGRADED). The value.ul2 field contains the old state. The state values that may be in the value.ul2 field are as follows: <UL><LI>1 = Normal <LI>3 = Failed <LI>4 = Not present <LI>5 = Single Port on Fibre </UL>The enclosure number, bay number, and rack number where the Physical Disk Drive is located are contained in the attribute.value.u32[0], attribute.value.u32[1], attribute.value.u32[2] fields, respectively. The attribute.type field contains value 1. The rack number in the attribute.value.u32[2] field will not contain a valid value until a future release."
           --#TYPE      "StorageCell Event"
           --#SUMMARY   "SCellName-TimeDate %s : SWCID %d : ECode: %d : CAC %d : EIP %d."
           --#ARGUMENTS {0,1,2,3,4,}
           --#SEVERITY  CRITICAL
           --#TIMEINDEX 136
           --#STATE     WARNING
        ::= 13602353
 
   sCellEventTrap-9-32 TRAP-TYPE  -- CAC Code: 40
        ENTERPRISE compaq
        VARIABLES  { scellNameDateTime,
                     scellSWComponent,
                     scellECode,
                     scellCAC,
                     scellEIP}
        DESCRIPTION
             "Severity: Critical -- failure or failure imminent. The state of the Physical Disk Drive identified in the handle field has transitioned to the FAILED state. The value.ul1 field contains the new state: 3 (FAILED). The value.ul2 field contains the old state. The state values that may be in the value.ul2 field are as follows: <UL><LI>1 = Normal <LI>2 = Degraded <LI>4 = Not present <LI>5 = Single Port on Fibre </UL>The enclosure number, bay number, and rack number where the Physical Disk Drive is located are contained in the attribute.value.u32[0], attribute.value.u32[1], attribute.value.u32[2] fields, respectively. The attribute.type field contains value 1. The rack number in the attribute.value.u32[2] field will not contain a valid value until a future release."
           --#TYPE      "StorageCell Event"
           --#SUMMARY   "SCellName-TimeDate %s : SWCID %d : ECode: %d : CAC %d : EIP %d."
           --#ARGUMENTS {0,1,2,3,4,}
           --#SEVERITY  CRITICAL
           --#TIMEINDEX 136
           --#STATE     WARNING
        ::= 13602354
 
   sCellEventTrap-9-33 TRAP-TYPE  -- CAC Code: 0
        ENTERPRISE compaq
        VARIABLES  { scellNameDateTime,
                     scellSWComponent,
                     scellECode,
                     scellCAC,
                     scellEIP}
        DESCRIPTION
             "Severity: Normal -- informational in nature. The Derived Unit identified in the handle field was created. The add-handle field contains the identity of the Storage System Virtual Disk that is associated with that Derived Unit. The attribute.value.obj field contains the identity of the Virtual Disk associated with that Derived Unit."
           --#TYPE      "StorageCell Event"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13602355
 
   sCellEventTrap-9-34 TRAP-TYPE  -- CAC Code: 0
        ENTERPRISE compaq
        VARIABLES  { scellNameDateTime,
                     scellSWComponent,
                     scellECode,
                     scellCAC,
                     scellEIP}
        DESCRIPTION
             "Severity: Normal -- informational in nature. The internal Logical Disk associated with the Virtual Disk identified in the handle field was created. The add-handle field contains the identity of the Disk Group where this internal Logical Disk was created. The attribute.value.u64[0] field contains the size (in blocks) of the internal Logical Disk. The attribute.value.u32[2] field contains the redundancy type of the internal Logical Disk. The attribute.type field contains the value 5. The values that may be found in the attribute.value.u32[2] field are as follows: <UL><LI>1 = Vraid0 <LI>2 = Vraid1 <LI>3 = Vraid5 </UL>"
           --#TYPE      "StorageCell Event"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13602356
 
   sCellEventTrap-9-35 TRAP-TYPE  -- CAC Code: 0
        ENTERPRISE compaq
        VARIABLES  { scellNameDateTime,
                     scellSWComponent,
                     scellECode,
                     scellCAC,
                     scellEIP}
        DESCRIPTION
             "Severity: Normal -- informational in nature. The Disk Group identified in the handle field was created. The attribute.value.u32[0] field contains the number of physical disk drives within the Disk Group. The attribute.type field contains the value 1."
           --#TYPE      "StorageCell Event"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13602357
 
   sCellEventTrap-9-36 TRAP-TYPE  -- CAC Code: 0
        ENTERPRISE compaq
        VARIABLES  { scellNameDateTime,
                     scellSWComponent,
                     scellECode,
                     scellCAC,
                     scellEIP}
        DESCRIPTION
             "Severity: Normal -- informational in nature. The Physical Disk Drive identified in the handle field was discovered. The enclosure, bay and rack where the Physical Disk Drive is located are contained in the attribute.value.u32[0], attribute.value.u32[1] and attribute.value.u32[2] fields, respectively. The attribute.type field contains the value 1."
           --#TYPE      "StorageCell Event"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13602358
 
   sCellEventTrap-9-37 TRAP-TYPE  -- CAC Code: 0
        ENTERPRISE compaq
        VARIABLES  { scellNameDateTime,
                     scellSWComponent,
                     scellECode,
                     scellCAC,
                     scellEIP}
        DESCRIPTION
             "Severity: Normal -- informational in nature. The Presented Unit identified in the handle field was created. The add-handle field contains the identity of the Storage System Virtual Disk that is associated with the Presented Unit. This Presented Unit is associated with the Virtual Disk identified in the attribute.value.obj.handle field. The add-handle2 field contains the associated Storage System Host path, and add-data[0] and add-data[1] contains the host LUN number."
           --#TYPE      "StorageCell Event"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13602359
 
   sCellEventTrap-9-38 TRAP-TYPE  -- CAC Code: 0
        ENTERPRISE compaq
        VARIABLES  { scellNameDateTime,
                     scellSWComponent,
                     scellECode,
                     scellCAC,
                     scellEIP}
        DESCRIPTION
             "Severity: Normal -- informational in nature. The Storage System Host path identified in the handle field was created."
           --#TYPE      "StorageCell Event"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13602360
 
   sCellEventTrap-9-39 TRAP-TYPE  -- CAC Code: 0
        ENTERPRISE compaq
        VARIABLES  { scellNameDateTime,
                     scellSWComponent,
                     scellECode,
                     scellCAC,
                     scellEIP}
        DESCRIPTION
             "Severity: Normal -- informational in nature. The Storage System Virtual Disk identified in the handle field was created."
           --#TYPE      "StorageCell Event"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13602361
 
   sCellEventTrap-9-3a TRAP-TYPE  -- CAC Code: 0
        ENTERPRISE compaq
        VARIABLES  { scellNameDateTime,
                     scellSWComponent,
                     scellECode,
                     scellCAC,
                     scellEIP}
        DESCRIPTION
             "Severity: Normal -- informational in nature. A Volume was created. The Volume is identified in the handle field. The add-handle field contains the identity of the Physical Disk Drive that is associated with that Volume. The enclosure number, bay number, and rack number where the associated Physical Disk Drive is located are contained in the attribute.value.u32[0], attribute.value.u32[1], and attribute.value.u32[2] fields, respectively. The attribute.type field contains the value of 1."
           --#TYPE      "StorageCell Event"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13602362
 
   sCellEventTrap-9-3b TRAP-TYPE  -- CAC Code: 0
        ENTERPRISE compaq
        VARIABLES  { scellNameDateTime,
                     scellSWComponent,
                     scellECode,
                     scellCAC,
                     scellEIP}
        DESCRIPTION
             "Severity: Normal -- informational in nature. The Derived Unit identified in the handle field was deleted. The add-handle field contains the identity of the Storage System Virtual Disk that was associated with the Derived Unit. This Derived Unit is associated with the Virtual Disk identified in the attribute.value.obj.handle field."
           --#TYPE      "StorageCell Event"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13602363
 
   sCellEventTrap-9-3c TRAP-TYPE  -- CAC Code: 0
        ENTERPRISE compaq
        VARIABLES  { scellNameDateTime,
                     scellSWComponent,
                     scellECode,
                     scellCAC,
                     scellEIP}
        DESCRIPTION
             "Severity: Normal -- informational in nature. The internal Logical Disk associated with the Virtual Disk identified in the handle field was deleted."
           --#TYPE      "StorageCell Event"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13602364
 
   sCellEventTrap-9-3d TRAP-TYPE  -- CAC Code: 0
        ENTERPRISE compaq
        VARIABLES  { scellNameDateTime,
                     scellSWComponent,
                     scellECode,
                     scellCAC,
                     scellEIP}
        DESCRIPTION
             "Severity: Normal -- informational in nature. The Disk Group identified in the handle field was deleted."
           --#TYPE      "StorageCell Event"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13602365
 
   sCellEventTrap-9-3e TRAP-TYPE  -- CAC Code: 42
        ENTERPRISE compaq
        VARIABLES  { scellNameDateTime,
                     scellSWComponent,
                     scellECode,
                     scellCAC,
                     scellEIP}
        DESCRIPTION
             "Severity: Critical -- failure or failure imminent. The Physical Disk Drive identified in the handle field has disappeared. The enclosure, bay and rack where the Physical Disk Drive is located are contained in the attribute.value.u32[0], attribute.value.u32[1] and attribute.value.u32[2] fields, respectively. The attribute.type field contains the value 1."
           --#TYPE      "StorageCell Event"
           --#SUMMARY   "SCellName-TimeDate %s : SWCID %d : ECode: %d : CAC %d : EIP %d."
           --#ARGUMENTS {0,1,2,3,4,}
           --#SEVERITY  CRITICAL
           --#TIMEINDEX 136
           --#STATE     WARNING
        ::= 13602366
 
   sCellEventTrap-9-3f TRAP-TYPE  -- CAC Code: 0
        ENTERPRISE compaq
        VARIABLES  { scellNameDateTime,
                     scellSWComponent,
                     scellECode,
                     scellCAC,
                     scellEIP}
        DESCRIPTION
             "Severity: Normal -- informational in nature. The Presented Unit identified in the handle field was deleted. The add-handle field contains the identity of the Storage System Virtual Disk that was associated with the Presented Unit. This Presented Unit is associated with the Virtual Disk identified in the attribute.value.obj.handle field."
           --#TYPE      "StorageCell Event"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13602367
 
   sCellEventTrap-9-40 TRAP-TYPE  -- CAC Code: 0
        ENTERPRISE compaq
        VARIABLES  { scellNameDateTime,
                     scellSWComponent,
                     scellECode,
                     scellCAC,
                     scellEIP}
        DESCRIPTION
             "Severity: Normal -- informational in nature. The Storage System Host path identified in the handle field was deleted."
           --#TYPE      "StorageCell Event"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13602368
 
   sCellEventTrap-9-41 TRAP-TYPE  -- CAC Code: 0
        ENTERPRISE compaq
        VARIABLES  { scellNameDateTime,
                     scellSWComponent,
                     scellECode,
                     scellCAC,
                     scellEIP}
        DESCRIPTION
             "Severity: Normal -- informational in nature. The Storage System Virtual Disk identified in the handle field was deleted. The Storage System Virtual Disk is associated with the Virtual Disk identified in the add-handle field."
           --#TYPE      "StorageCell Event"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13602369
 
   sCellEventTrap-9-43 TRAP-TYPE  -- CAC Code: 0
        ENTERPRISE compaq
        VARIABLES  { scellNameDateTime,
                     scellSWComponent,
                     scellECode,
                     scellCAC,
                     scellEIP}
        DESCRIPTION
             "Severity: Normal -- informational in nature. The HSV110 controller identified in the handle field has joined the Storage System. If the handle field is zero, the HSV110 controller identity could not be obtained due to an unexpected state transition."
           --#TYPE      "StorageCell Event"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13602371
 
   sCellEventTrap-9-44 TRAP-TYPE  -- CAC Code: ba
        ENTERPRISE compaq
        VARIABLES  { scellNameDateTime,
                     scellSWComponent,
                     scellECode,
                     scellCAC,
                     scellEIP}
        DESCRIPTION
             "Severity: Undetermined -- more information needed to determine severity. An HSV110 controller has left the Storage System. The HSV110 controller is identified in the handle field. If the handle field is zero, the HSV110 controller identity could not be obtained due to an unexpected state transition."
           --#TYPE      "StorageCell Event"
           --#SUMMARY   "SCellName-TimeDate %s : SWCID %d : ECode: %d : CAC %d : EIP %d."
           --#ARGUMENTS {0,1,2,3,4,}
           --#SEVERITY  CRITICAL
           --#TIMEINDEX 136
           --#STATE     WARNING
        ::= 13602372
 
   sCellEventTrap-9-45 TRAP-TYPE  -- CAC Code: 0
        ENTERPRISE compaq
        VARIABLES  { scellNameDateTime,
                     scellSWComponent,
                     scellECode,
                     scellCAC,
                     scellEIP}
        DESCRIPTION
             "Severity: Normal -- informational in nature. A Storage System has been deleted by an HSV110 controller. The Storage System is identified in the handle field. The HSV110 controller is identified in the add-handle field. If the handle field or add-handle field is zero, the corresponding identity could not be obtained due to an unexpected state transition."
           --#TYPE      "StorageCell Event"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13602373
 
   sCellEventTrap-9-46 TRAP-TYPE  -- CAC Code: 0
        ENTERPRISE compaq
        VARIABLES  { scellNameDateTime,
                     scellSWComponent,
                     scellECode,
                     scellCAC,
                     scellEIP}
        DESCRIPTION
             "Severity: Normal -- informational in nature. The Data Replication Group identified in the handle field was created."
           --#TYPE      "StorageCell Event"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13602374
 
   sCellEventTrap-9-47 TRAP-TYPE  -- CAC Code: 0
        ENTERPRISE compaq
        VARIABLES  { scellNameDateTime,
                     scellSWComponent,
                     scellECode,
                     scellCAC,
                     scellEIP}
        DESCRIPTION
             "Severity: Normal -- informational in nature. The Data Replication Group identified in the handle field was deleted."
           --#TYPE      "StorageCell Event"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13602375
 
   sCellEventTrap-9-48 TRAP-TYPE  -- CAC Code: 0
        ENTERPRISE compaq
        VARIABLES  { scellNameDateTime,
                     scellSWComponent,
                     scellECode,
                     scellCAC,
                     scellEIP}
        DESCRIPTION
             "Severity: Normal -- informational in nature. The internal Logical Disk associated with the Snapshot Virtual Disk identified in the handle field was created. The add-handle field contains the identity of the Disk Group where this internal Logical Disk was created. The attribute.value.u64[0] field contains the size (in blocks) of the reserved capacity of the internal Logical Disk. The attribute.value.u32[2] field contains the redundancy type of the internal Logical Disk. The attribute.value.u32[3] field contains the noid of the associated successor internal Logical Disk. The attribute.type field contains the value 6. The values that may be found in the attribute.value.u32[2] field are as follows: <UL><LI>1 = Vraid0 <LI>2 = Vraid1 <LI>3 = Vraid5 </UL>"
           --#TYPE      "StorageCell Event"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13602376
 
   sCellEventTrap-9-49 TRAP-TYPE  -- CAC Code: 0
        ENTERPRISE compaq
        VARIABLES  { scellNameDateTime,
                     scellSWComponent,
                     scellECode,
                     scellCAC,
                     scellEIP}
        DESCRIPTION
             "Severity: Normal -- informational in nature. The internal Logical Disk associated with the Copy of the Virtual Disk identified in the handle field was created. The add-handle field contains the identity of the Disk Group where this internal Logical Disk was created. The attribute.value.u64[0] field contains the size (in blocks) of the reserved capacity of the target Virtual Disk. The attribute.value.u32[2] field contains the redundancy type of the internal Logical Disk. The attribute.value.u32[3] field contains the noid of the associated successor internal Logical Disk. The attribute.type field contains the value 6. The values that may be found in the attribute.value.u32[2] field are as follows: <UL><LI>1 = Vraid0 <LI>2 = Vraid1 <LI>3 = Vraid5 </UL>"
           --#TYPE      "StorageCell Event"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13602377
 
   sCellEventTrap-9-65 TRAP-TYPE  -- CAC Code: 0
        ENTERPRISE compaq
        VARIABLES  { scellNameDateTime,
                     scellSWComponent,
                     scellECode,
                     scellCAC,
                     scellEIP}
        DESCRIPTION
             "Severity: Normal -- informational in nature. The Host Operating System mode of the Storage System Host identified in the handle field has changed. The old-attr.type and new-attr.type fields contain the value 1. The old-attr.value.u32[0] field contains the old Host Operating System mode. The new-attr.value.u32[0] field contains the new Host Operating System mode. The values that may be found in the old-attr.value.u32[0] and new-attr.value.u32[0] fields are as follows: <UL><LI>0 = Unknown <LI>1 = User defined <LI>2 = Unused <LI>3 = WINNT with SecurePath <LI>4 = VMS <LI>5 = TRU64 UNIX <LI>6 = Sun UNIX <LI>7 = NetWare <LI>8 = HP <LI>9 = IBM <LI>10 = LINUX <LI>11 = SCO UNIX </UL>"
           --#TYPE      "StorageCell Event"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13602405
 
   sCellEventTrap-9-66 TRAP-TYPE  -- CAC Code: 0
        ENTERPRISE compaq
        VARIABLES  { scellNameDateTime,
                     scellSWComponent,
                     scellECode,
                     scellCAC,
                     scellEIP}
        DESCRIPTION
             "Severity: Normal -- informational in nature. Time was set on the Storage System identified in the handle field."
           --#TYPE      "StorageCell Event"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13602406
 
   sCellEventTrap-9-67 TRAP-TYPE  -- CAC Code: 0
        ENTERPRISE compaq
        VARIABLES  { scellNameDateTime,
                     scellSWComponent,
                     scellECode,
                     scellCAC,
                     scellEIP}
        DESCRIPTION
             "Severity: Normal -- informational in nature. The LUN of the Presented Unit identified in the handle field has changed. The old-attr.type field and the new-attr.type fields contain the value 1. The old-attr.value.u32[0..1] fields contain the value of the old LUN. The new-attr.value.u32[0..1] fields contain the value of the new LUN. The secondary-id field contains the noid portion of the handle for the Storage System Virtual Disk associated with the Presented Unit. This Presented Unit is associated with the Virtual Disk identified in the add-handle field."
           --#TYPE      "StorageCell Event"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13602407
 
   sCellEventTrap-9-68 TRAP-TYPE  -- CAC Code: 0
        ENTERPRISE compaq
        VARIABLES  { scellNameDateTime,
                     scellSWComponent,
                     scellECode,
                     scellCAC,
                     scellEIP}
        DESCRIPTION
             "Severity: Normal -- informational in nature. The Device Addition Policy of the Storage System identified in the handle field has changed. The old-attr.type field and the new-attr.type fields contain the value 1. The old-attr.value.u32[0] field contains the old Device Addition Policy. The new-attr.value.u32[0] field contains the new Device Addition Policy. The policy values that may be found in the old-attr.value.u32[0] and new-attr.value.u32[0] fields are as follows: <UL><LI>1 = Manual policy <LI>2 = Automatic policy </UL>"
           --#TYPE      "StorageCell Event"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13602408
 
   sCellEventTrap-9-69 TRAP-TYPE  -- CAC Code: 0
        ENTERPRISE compaq
        VARIABLES  { scellNameDateTime,
                     scellSWComponent,
                     scellECode,
                     scellCAC,
                     scellEIP}
        DESCRIPTION
             "Severity: Normal -- informational in nature. The Quiescent state of the Storage System Virtual Disk identified in the handle field has changed. The old-attr.type field and the new-attr.type fields contain the value 1. The old-attr.value.u32[0] field contains the old Quiescent state. The new-attr.value.u32[0] field contains the new Quiescent state. The state values that may be found in the old-attr.value.u32[0] and new-attr.value.u32[0] fields are as follows: <UL><LI>0 = Not quiescent <LI>1 = Quiescent </UL>This Storage System Virtual Disk is associated with the Virtual Disk identified in the add-handle field."
           --#TYPE      "StorageCell Event"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13602409
 
   sCellEventTrap-9-6a TRAP-TYPE  -- CAC Code: 0
        ENTERPRISE compaq
        VARIABLES  { scellNameDateTime,
                     scellSWComponent,
                     scellECode,
                     scellCAC,
                     scellEIP}
        DESCRIPTION
             "Severity: Normal -- informational in nature. The Enabled/Disabled state of the Storage System Virtual Disk identified in the handle field has changed. The old-attr.type field and the new-attr.type fields contain the value 1. The old-attr.value.u32[0] field contains the old Enabled/Disabled state. The new-attr.value.u32[0] field contains the new Enabled/Disabled state. The state values that may be found in the old-attr.value.u32[0] and new-attr.value.u32[0] fields are as follows: <UL><LI>1 = Disabled <LI>2 = Enabled </UL>This Storage System Virtual Disk is associated with the Virtual Disk identified in the add-handle field."
           --#TYPE      "StorageCell Event"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13602410
 
   sCellEventTrap-9-6b TRAP-TYPE  -- CAC Code: 0
        ENTERPRISE compaq
        VARIABLES  { scellNameDateTime,
                     scellSWComponent,
                     scellECode,
                     scellCAC,
                     scellEIP}
        DESCRIPTION
             "Severity: Normal -- informational in nature. The Cache Policy of the Storage System Virtual Disk identified in the handle field has changed. <P> The old-attr.type field and the new-attr.type fields contain the value 1. The old-attr.value.u32[0] field contains the old Write Cache Policy. The new-attr.value.u32[0] field contains the new Write Cache Policy. The policy values that may be found in the old-attr.value.u32[0] and new-attr.value.u32[0] fields are as follows: <UL><LI>1 = Writethrough <LI>2 = Writeback </UL><P> The old-attr.value.u32[1] field contains the old Read Cache Policy. The new-attr.value.u32[1] field contains the new Read Cache Policy. The policy values that may be found in the old-attr.value.u32[1] and new-attr.value.u32[1] fields are as follows: <UL><LI>1 = Read cache on <LI>2 = Read cache off </UL><P> The old-attr.value.u32[2] field contains the old Cache Mirroring Policy. The new-attr.value.u32[2] field contains the new Cache Mirroring Policy. The policy values that may be found in the old-attr.value.u32[2] and new-attr.value.u32[2] fields are as follows: <UL><LI>1 = Mirror <LI>2 = No mirror </UL>This Storage System Virtual Disk is associated with the Virtual Disk identified in the add-handle field."
           --#TYPE      "StorageCell Event"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13602411
 
   sCellEventTrap-9-6c TRAP-TYPE  -- CAC Code: 0
        ENTERPRISE compaq
        VARIABLES  { scellNameDateTime,
                     scellSWComponent,
                     scellECode,
                     scellCAC,
                     scellEIP}
        DESCRIPTION
             "Severity: Normal -- informational in nature. The Usage state of a Volume changed. The affected Volume is identified in the handle field. The old-attr.value.u32[0] field contains the old Usage state. The new-attr.value.u32[0] field contains the new Usage state. The Usage state values that may be found in the old-attr.value.u32[0] and new-attr.value.u32[0] fields are as follows: <UL><LI>1 = Disk Group <LI>2 = Reserved <LI>4 - 20 = temporary usage reserved for drive code load </UL>This Volume is associated with the Disk Group identified in the add-handle field, if either the old Usage state or the new Usage state is 1. The secondary-id field contains the internal identification of that Volume's Redundant Storage Set."
           --#TYPE      "StorageCell Event"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13602412
 
   sCellEventTrap-9-6d TRAP-TYPE  -- CAC Code: 0
        ENTERPRISE compaq
        VARIABLES  { scellNameDateTime,
                     scellSWComponent,
                     scellECode,
                     scellCAC,
                     scellEIP}
        DESCRIPTION
             "Severity: Normal -- informational in nature. The Disk Failure Protection Level of the Disk Group identified in the handle field has changed. The old-attr.type and new-attr.type fields contain the value 1. The old-attr.value.u32[0] field contains the old number of physical disk drives available for use. The new-attr.value.u32[0] field contains the new number of physical disk drives available for use."
           --#TYPE      "StorageCell Event"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13602413
 
   sCellEventTrap-9-6e TRAP-TYPE  -- CAC Code: 0
        ENTERPRISE compaq
        VARIABLES  { scellNameDateTime,
                     scellSWComponent,
                     scellECode,
                     scellCAC,
                     scellEIP}
        DESCRIPTION
             "Severity: Normal -- informational in nature. The Write Protected state of the Derived Unit identified in the handle field has changed. This Derived Unit is associated with the Virtual Disk identified in the add-handle field. The secondary-id field contains the noid portion of the handle for the Storage System Virtual Disk associated with the Derived Unit. The old-attr.type field and the new-attr.type fields contain the value 1. The old-attr.value.u32[0] field contains the old Write Protected state. The new-attr.value.u32[0] field contains the new Write Protected state. The Write Protected state values that may be found in the old-attr.value.u32[0] and new-attr.value.u32[0] fields are as follows: <UL><LI>0 = Write protect off <LI>1 = Write protect on </UL>This Derived Unit is associated with the Virtual Disk identified in the add-handle field."
           --#TYPE      "StorageCell Event"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13602414
 
   sCellEventTrap-9-70 TRAP-TYPE  -- CAC Code: 46
        ENTERPRISE compaq
        VARIABLES  { scellNameDateTime,
                     scellSWComponent,
                     scellECode,
                     scellCAC,
                     scellEIP}
        DESCRIPTION
             "Severity: Warning -- not failed but attention recommended or required. The Physical Disk Drive identified in the handle field has experienced numerous communication failures on a particular Fibre Channel port identified in the new-attr.value.str field. The old-attr.value.u32[0] field contains the internal port ID. The enclosure number, bay number, and rack number where the Physical Disk Drive is located are contained in the old-attr.value.u32[1], old-attr.value.u32[2], old-attr.value.u32[3] fields, respectively. The old-attr.type field contains value 1. The new-attr.value.str field contains the cerp-id of the Fibre Channel port. The new-attr.type field contains value 4."
           --#TYPE      "StorageCell Event"
           --#SUMMARY   "SCellName-TimeDate %s : SWCID %d : ECode: %d : CAC %d : EIP %d."
           --#ARGUMENTS {0,1,2,3,4,}
           --#SEVERITY  MINOR
           --#TIMEINDEX 136
           --#STATE     WARNING
        ::= 13602416
 
   sCellEventTrap-9-71 TRAP-TYPE  -- CAC Code: 0
        ENTERPRISE compaq
        VARIABLES  { scellNameDateTime,
                     scellSWComponent,
                     scellECode,
                     scellCAC,
                     scellEIP}
        DESCRIPTION
             "Severity: Normal -- informational in nature. The HSV110 controller identified in the handle field received a request to shutdown. <P> The old-attr.type field and field contain the value 1. The old-attr.value.u32[0] field indicates the type of restart that was requested as follows: <UL><LI>0 = None -- no restart <LI>1 = Regular -- full restart, host system connectivity is lost until the controller returns to normal operation <LI>2 = Fast -- resynchronization, restart of the controller in a manner that has little or no impact on host system connectivity </UL><P> The old-attr.value.u32[1] field indicates whether the other HSV110 controller of the pair was requested to remain operational or to also shutdown as follows: <UL><LI>0 = Remain operational <LI>1 = Coupled shutdown </UL><P> The old-attr.value.u32[2] field indicates whether the HSV110 controller was requested to remain in the power on state or power itself off as follows: <UL><LI>0 = Remain in the power on state <LI>1 = Power itself off </UL><P> The old-attr.value.u32[3] field value indicates whether the Physical Disk Drive enclosure(s) was requested to remain in the power on state or to be powered off as follows: <UL><LI>0 = Remain in the power on state <LI>1 = Powered off </UL><P> The old-attr.value.u32[4] field value indicates whether the battery assemblies located within the HSV110 controller were requested to be enabled or disabled as follows: <UL><LI>0 = Enabled <LI>1 = Disabled </UL><P> The old-attr.value.u32[5] field contains the number of seconds the shutdown operation was requested to be delayed."
           --#TYPE      "StorageCell Event"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13602417
 
   sCellEventTrap-9-72 TRAP-TYPE  -- CAC Code: 0
        ENTERPRISE compaq
        VARIABLES  { scellNameDateTime,
                     scellSWComponent,
                     scellECode,
                     scellCAC,
                     scellEIP}
        DESCRIPTION
             "Severity: Normal -- informational in nature. The HSV110 controller identified in the handle field has completed its shutdown preparations. <P> The old-attr.type field contain the value 1. The old-attr.value.u32[0] field value indicates the result of the HSV110 controller Cache Memory shutdown operation as follows: <UL><LI>1 = Success <LI>2 = Failure <LI>3 = Not applicable </UL><P> The old-attr.value.u32[1] field contains the internal Storage System Management Interface cache shutdown status code. <P> The old-attr.value.u32[2] field value indicates the result of the Physical Disk Drive enclosure(s) power off operation as follows: <UL><LI>1 = Success <LI>2 = Failure <LI>3 = Not applicable </UL><P> The old-attr.value.u32[3] field contains the internal Storage System Management Interface Physical Disk Drive enclosure(s) power off status code. <P> The old-attr.value.u32[4] field value indicates the result of the battery assemblies disable operation as follows: <UL><LI>1 = Success <LI>2 = Failure <LI>3 = Not applicable </UL><P> The old-attr.value.u32[5] field value indicates the battery assemblies disable operation failure mode as follows: <UL><LI>0 = No failure indicated. <LI>1 = Failed only on the HSV110 controller identified in the handle field. <LI>2 = Failed only on the other HSV110 controller of the pair. <LI>3 = Failed on both HSV110 controllers. </UL>"
           --#TYPE      "StorageCell Event"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13602418
 
   sCellEventTrap-9-73 TRAP-TYPE  -- CAC Code: 0
        ENTERPRISE compaq
        VARIABLES  { scellNameDateTime,
                     scellSWComponent,
                     scellECode,
                     scellCAC,
                     scellEIP}
        DESCRIPTION
             "Severity: Normal -- informational in nature. The Failsafe state of the Data Replication Group identified in the handle field has changed. The old-attr.value.u32[0] field contains the old Failsafe state. The new-attr.value.u32[0] field contains the new Failsafe state. The Failsafe state values that may be found in the old-attr.value.u32[0] and new-attr.value.u32[0] fields are as follows: <UL><LI>1 = Failsafe Disabled <LI>2 = Failsafe Enabled </UL>"
           --#TYPE      "StorageCell Event"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13602419
 
   sCellEventTrap-9-74 TRAP-TYPE  -- CAC Code: 0
        ENTERPRISE compaq
        VARIABLES  { scellNameDateTime,
                     scellSWComponent,
                     scellECode,
                     scellCAC,
                     scellEIP}
        DESCRIPTION
             "Severity: Normal -- informational in nature. The Mode of the Data Replication Group identified in the handle field has changed. The old-attr.value.u32[0] field contains the old Mode. The new-attr.value.u32[0] field contains the new Mode. The Mode values that may be found in the old-attr.value.u32[0] and new-attr.value.u32[0] fields are as follows: <UL><LI>0 = Normal Active Source <LI>1 = Normal Active Destination <LI>2 = Active/Active (Master) <LI>3 = Active/Active (Non-Master) </UL>"
           --#TYPE      "StorageCell Event"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13602420
 
   sCellEventTrap-9-75 TRAP-TYPE  -- CAC Code: 0
        ENTERPRISE compaq
        VARIABLES  { scellNameDateTime,
                     scellSWComponent,
                     scellECode,
                     scellCAC,
                     scellEIP}
        DESCRIPTION
             "Severity: Normal -- informational in nature. The Operational state of a Data Replication Group has changed to Synchronous or Asynchronous. The old-attr.value.u32[0] field contains the old Operation state. The new-attr.value.u32[0] field contains the new Operation state. The Operation state values that may be found in the old-attr.value.u32[0] and new-attr.value.u32[0] fields are as follows: <UL><LI>1 = Synchronous <LI>2 = Asynchronous </UL>"
           --#TYPE      "StorageCell Event"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13602421
 
   sCellEventTrap-9-76 TRAP-TYPE  -- CAC Code: 0
        ENTERPRISE compaq
        VARIABLES  { scellNameDateTime,
                     scellSWComponent,
                     scellECode,
                     scellCAC,
                     scellEIP}
        DESCRIPTION
             "Severity: Normal -- informational in nature. The Read Only attribute of the Data Replication Group identified in the handle field has changed. The old-attr.value.u32[0] field contains the old Read Only attribute. The new-attr.value.u32[0] field contains the new Read Only attribute. The Read Only attribute values that may be found in the old-attr.value.u32[0] and new-attr.value.u32[0] fields are as follows: <UL><LI>0 = Data Replication Destination Storage System Virtual Disk disabled for read access. <LI>1 = Data Replication Destination Storage System Virtual Disk enabled for read access. </UL>"
           --#TYPE      "StorageCell Event"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13602422
 
   sCellEventTrap-9-77 TRAP-TYPE  -- CAC Code: 0
        ENTERPRISE compaq
        VARIABLES  { scellNameDateTime,
                     scellSWComponent,
                     scellECode,
                     scellCAC,
                     scellEIP}
        DESCRIPTION
             "Severity: Normal -- informational in nature. A Data Replication Group failover has occurred. The handle field contains the identity of the Data Replication Group. The old-attr.value.u32[0] field contains the old Role. The new-attr.value.u32[0] field contains the new Role. <UL><LI>0 = Normal Active Source <LI>1 = Normal Active Destination <LI>2 = Active/Active (Master) <LI>3 = Active/Active (Non-Master) </UL>"
           --#TYPE      "StorageCell Event"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13602423
 
   sCellEventTrap-9-78 TRAP-TYPE  -- CAC Code: 0
        ENTERPRISE compaq
        VARIABLES  { scellNameDateTime,
                     scellSWComponent,
                     scellECode,
                     scellCAC,
                     scellEIP}
        DESCRIPTION
             "Severity: Normal -- informational in nature. A Data Replication Group has been suspended or resumed. The handle field contains the identity of the Data Replication Group. The old-attr.value.u32[0] field contains the old Suspend state. The new-attr.value.u32[0] field contains the new Suspend state. The Suspend state values that may be found in the old-attr.value.u32[0] and new-attr.value.u32[0] fields are as follows: <UL><LI>1 = Connection between the Data Replication Source and Data Replication Destination is active. <LI>2 = Connection between the Data Replication Source and Data Replication Destination is inactive. </UL>"
           --#TYPE      "StorageCell Event"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13602424
 
   sCellEventTrap-9-79 TRAP-TYPE  -- CAC Code: 0
        ENTERPRISE compaq
        VARIABLES  { scellNameDateTime,
                     scellSWComponent,
                     scellECode,
                     scellCAC,
                     scellEIP}
        DESCRIPTION
             "Severity: Normal -- informational in nature. A Storage System Virtual Disk was added to a Data Replication Group. The Storage System Virtual Disk is identified in the add-handle field. The Data Replication Group is identified in the handle field."
           --#TYPE      "StorageCell Event"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13602425
 
   sCellEventTrap-9-7a TRAP-TYPE  -- CAC Code: 0
        ENTERPRISE compaq
        VARIABLES  { scellNameDateTime,
                     scellSWComponent,
                     scellECode,
                     scellCAC,
                     scellEIP}
        DESCRIPTION
             "Severity: Normal -- informational in nature. A Storage System Virtual Disk was removed from a Data Replication Group. The Storage System Virtual Disk is identified in the add-handle field. The Data Replication Group is identified in the handle field."
           --#TYPE      "StorageCell Event"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13602426
 
   sCellEventTrap-9-c8 TRAP-TYPE  -- CAC Code: 51
        ENTERPRISE compaq
        VARIABLES  { scellNameDateTime,
                     scellSWComponent,
                     scellECode,
                     scellCAC,
                     scellEIP}
        DESCRIPTION
             "Severity: Undetermined -- more information needed to determine severity. The Data Availability state of the internal Logical Disk associated with the Virtual Disk identified in the handle field has transitioned to the DATA LOST state. The value.ul1 field contains the new state: 1 (DATA LOST). The value.ul2 field contains the old state: 0 (NORMAL)."
           --#TYPE      "StorageCell Event"
           --#SUMMARY   "SCellName-TimeDate %s : SWCID %d : ECode: %d : CAC %d : EIP %d."
           --#ARGUMENTS {0,1,2,3,4,}
           --#SEVERITY  CRITICAL
           --#TIMEINDEX 136
           --#STATE     WARNING
        ::= 13602504
 
   sCellEventTrap-9-c9 TRAP-TYPE  -- CAC Code: 51
        ENTERPRISE compaq
        VARIABLES  { scellNameDateTime,
                     scellSWComponent,
                     scellECode,
                     scellCAC,
                     scellEIP}
        DESCRIPTION
             "Severity: Undetermined -- more information needed to determine severity. The state of the Disk Group identified in the handle field has transitioned to an INOPERATIVE state. The value.ul1 field contains the new Disk Group state. The value.ul2 field contains the old Disk Group state. The state values that may be found in the value.ul1 and value.ul2 fields are as follows: <UL><LI>1 = Normal <LI>2 = Disk Group with no redundancy is inoperative <LI>3 = Disk Group with parity redundancy is inoperative <LI>4 = Disk Group with mirrored redundancy is inoperative <LI>5 = Disk Group with no redundancy is inoperative, marked for re-use <LI>6 = Disk Group with parity redundancy is inoperative, marked for re-use <LI>7 = Disk Group with mirrored redundancy is inoperative, marked for re-use </UL>"
           --#TYPE      "StorageCell Event"
           --#SUMMARY   "SCellName-TimeDate %s : SWCID %d : ECode: %d : CAC %d : EIP %d."
           --#ARGUMENTS {0,1,2,3,4,}
           --#SEVERITY  CRITICAL
           --#TIMEINDEX 136
           --#STATE     WARNING
        ::= 13602505
 
   sCellEventTrap-9-ca TRAP-TYPE  -- CAC Code: 51
        ENTERPRISE compaq
        VARIABLES  { scellNameDateTime,
                     scellSWComponent,
                     scellECode,
                     scellCAC,
                     scellEIP}
        DESCRIPTION
             "Severity: Undetermined -- more information needed to determine severity. The state of the internal Logical Disk associated with the Virtual Disk identified in the handle field has transitioned to the FAILED state. The value.ul1 field contains the new state: 5 (FAILED). The value.ul2 field contains the old state. The state values that may be found in the value.ul2 field are as follows: <UL><LI>1 = Normal <LI>2 = Replacement delay in progress <LI>3 = Redundancy lost, restore in progress <LI>4 = Redundancy lost, restore stalled <LI>6 = Creation in progress <LI>7 = Snapshot is inoperative due to lack of snapshot space <LI>8 = Deletion in progress <LI>9 = Capacity change in progress <LI>10 = Inoperative due to data lost <LI>11 = Capacity reservation in progress <LI>12 = Capacity unreservation in progress </UL>"
           --#TYPE      "StorageCell Event"
           --#SUMMARY   "SCellName-TimeDate %s : SWCID %d : ECode: %d : CAC %d : EIP %d."
           --#ARGUMENTS {0,1,2,3,4,}
           --#SEVERITY  CRITICAL
           --#TIMEINDEX 136
           --#STATE     WARNING
        ::= 13602506
 
   sCellEventTrap-9-cb TRAP-TYPE  -- CAC Code: 50
        ENTERPRISE compaq
        VARIABLES  { scellNameDateTime,
                     scellSWComponent,
                     scellECode,
                     scellCAC,
                     scellEIP}
        DESCRIPTION
             "Severity: Critical -- failure or failure imminent. The state of the internal Logical Disk associated with the Virtual Disk identified in the handle field has transitioned to the SNAPSHOT OVERCOMMIT state. The value.ul1 field contains the new state: 7 (SNAPSHOT OVERCOMMIT). The value.ul2 field contains the old state. The state values that may be found in the value.ul2 field are as follows: <UL><LI>1 = Normal <LI>2 = Replacement delay in progress <LI>3 = Redundancy lost, restore in progress <LI>4 = Redundancy lost, restore stalled <LI>5 = Failed <LI>6 = Creation in progress <LI>8 = Deletion in progress <LI>9 = Capacity change in progress <LI>10 = Inoperative due to device data lost <LI>11 = Capacity reservation in progress <LI>12 = Capacity unreservation in progress </UL>"
           --#TYPE      "StorageCell Event"
           --#SUMMARY   "SCellName-TimeDate %s : SWCID %d : ECode: %d : CAC %d : EIP %d."
           --#ARGUMENTS {0,1,2,3,4,}
           --#SEVERITY  CRITICAL
           --#TIMEINDEX 136
           --#STATE     WARNING
        ::= 13602507
 
   sCellEventTrap-9-cc TRAP-TYPE  -- CAC Code: 51
        ENTERPRISE compaq
        VARIABLES  { scellNameDateTime,
                     scellSWComponent,
                     scellECode,
                     scellCAC,
                     scellEIP}
        DESCRIPTION
             "Severity: Undetermined -- more information needed to determine severity. The state of the internal Logical Disk associated with the Virtual Disk identified in the handle field has transitioned to the DEVICE DATA LOST state. The value.ul1 field contains the new state: 10 (DEVICE DATA LOST). The value.ul2 field contains the old state. The state values that may be found in the value.ul2 field are as follows: <UL><LI>1 = Normal <LI>2 = Replacement delay in progress <LI>3 = Redundancy lost restore, in progress <LI>4 = Redundancy lost restore, stalled <LI>5 = Failed <LI>6 = Creation in progress <LI>7 = Snapshot is inoperative due to lack of snapshot space <LI>8 = Deletion in progress <LI>9 = Capacity change in progress <LI>11 = Capacity reservation in progress <LI>12 = Capacity unreservation in progress </UL>"
           --#TYPE      "StorageCell Event"
           --#SUMMARY   "SCellName-TimeDate %s : SWCID %d : ECode: %d : CAC %d : EIP %d."
           --#ARGUMENTS {0,1,2,3,4,}
           --#SEVERITY  CRITICAL
           --#TIMEINDEX 136
           --#STATE     WARNING
        ::= 13602508
 
   sCellEventTrap-9-cd TRAP-TYPE  -- CAC Code: c3
        ENTERPRISE compaq
        VARIABLES  { scellNameDateTime,
                     scellSWComponent,
                     scellECode,
                     scellCAC,
                     scellEIP}
        DESCRIPTION
             "Severity: Undetermined -- more information needed to determine severity. The state of the Fibre Channel port identified in the attribute.value.str field and located on the rear panel of the HSV110 controller identified in the handle field has transitioned to the FAILED state. The attribute.type field contains the value 4. The value.ul1 field contains the new state: 2 (FAILED). The value.ul2 field contains the old state: 1 (NORMAL). <P> Note that the HSV110 controller's internal identity of the affected Fibre Channel port is contained in the secondary-id field."
           --#TYPE      "StorageCell Event"
           --#SUMMARY   "SCellName-TimeDate %s : SWCID %d : ECode: %d : CAC %d : EIP %d."
           --#ARGUMENTS {0,1,2,3,4,}
           --#SEVERITY  CRITICAL
           --#TIMEINDEX 136
           --#STATE     WARNING
        ::= 13602509
 
   sCellEventTrap-9-ce TRAP-TYPE  -- CAC Code: 0
        ENTERPRISE compaq
        VARIABLES  { scellNameDateTime,
                     scellSWComponent,
                     scellECode,
                     scellCAC,
                     scellEIP}
        DESCRIPTION
             "Severity: Normal -- informational in nature. The state of the Disk Group identified in the handle field has transitioned to an INOPERATIVE MARKED state. The value.ul1 field contains the new Disk Group state. The value.ul2 field contains the old Disk Group state. The state values that may be found in the value.ul1 and value.ul2 fields are as follows: <UL><LI>1 = Normal <LI>2 = Disk Group with no redundancy is inoperative <LI>3 = Disk Group with parity redundancy is inoperative <LI>4 = Disk Group with mirrored redundancy is inoperative <LI>5 = Disk Group with no redundancy is inoperative, marked for re-use <LI>6 = Disk Group with parity redundancy is inoperative, marked for re-use <LI>7 = Disk Group with mirrored redundancy is inoperative, marked for re-use </UL>"
           --#TYPE      "StorageCell Event"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13602510
 
   sCellEventTrap-9-cf TRAP-TYPE  -- CAC Code: 41
        ENTERPRISE compaq
        VARIABLES  { scellNameDateTime,
                     scellSWComponent,
                     scellECode,
                     scellCAC,
                     scellEIP}
        DESCRIPTION
             "Severity: Warning -- not failed but attention recommended or required. The state of the Physical Disk Drive identified in the handle field has transitioned to the NOT PRESENT state. The value.ul1 field contains the new state: 4 (NOT PRESENT). The value.ul2 field contains the old state. The state values that may be in the value.ul2 field are as follows: <UL><LI>1 = Normal <LI>2 = Degraded <LI>3 = Failed <LI>5 = Single Port on Fibre </UL>The enclosure number, bay number, and rack number where the Physical Disk Drive is located are contained in the attribute.value.u32[0], attribute.value.u32[1], attribute.value.u32[2] fields, respectively. The attribute.type field contains value 1. The rack number in the attribute.value.u32[2] field will not contain a valid value until a future release."
           --#TYPE      "StorageCell Event"
           --#SUMMARY   "SCellName-TimeDate %s : SWCID %d : ECode: %d : CAC %d : EIP %d."
           --#ARGUMENTS {0,1,2,3,4,}
           --#SEVERITY  MINOR
           --#TIMEINDEX 136
           --#STATE     WARNING
        ::= 13602511
 
   sCellEventTrap-9-d0 TRAP-TYPE  -- CAC Code: 0
        ENTERPRISE compaq
        VARIABLES  { scellNameDateTime,
                     scellSWComponent,
                     scellECode,
                     scellCAC,
                     scellEIP}
        DESCRIPTION
             "Severity: Normal -- informational in nature. The HSV110 controller identified in the handle field no longer needs attention."
           --#TYPE      "StorageCell Event"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13602512
 
   sCellEventTrap-9-d1 TRAP-TYPE  -- CAC Code: b9
        ENTERPRISE compaq
        VARIABLES  { scellNameDateTime,
                     scellSWComponent,
                     scellECode,
                     scellCAC,
                     scellEIP}
        DESCRIPTION
             "Severity: Undetermined -- more information needed to determine severity. The HSV110 controller identified in the handle field needs attention."
           --#TYPE      "StorageCell Event"
           --#SUMMARY   "SCellName-TimeDate %s : SWCID %d : ECode: %d : CAC %d : EIP %d."
           --#ARGUMENTS {0,1,2,3,4,}
           --#SEVERITY  CRITICAL
           --#TIMEINDEX 136
           --#STATE     WARNING
        ::= 13602513
 
   sCellEventTrap-9-d2 TRAP-TYPE  -- CAC Code: 2a
        ENTERPRISE compaq
        VARIABLES  { scellNameDateTime,
                     scellSWComponent,
                     scellECode,
                     scellCAC,
                     scellEIP}
        DESCRIPTION
             "Severity: Critical -- failure or failure imminent. The Blower Present flag for the '1' blower assembly located within the HSV110 controller identified in the handle field has transitioned from the PRESENT to NOT PRESENT state indicating that the blower has been removed. The secondary-id field contains the '1' blower assembly internal identifier value: 1. The value.ul1 field contains the new state of the Blower Present flag: 0 (NOT PRESENT). The value.ul2 field contains the old state of the Blower Present flag: 1 (PRESENT)."
           --#TYPE      "StorageCell Event"
           --#SUMMARY   "SCellName-TimeDate %s : SWCID %d : ECode: %d : CAC %d : EIP %d."
           --#ARGUMENTS {0,1,2,3,4,}
           --#SEVERITY  CRITICAL
           --#TIMEINDEX 136
           --#STATE     WARNING
        ::= 13602514
 
   sCellEventTrap-9-d3 TRAP-TYPE  -- CAC Code: 51
        ENTERPRISE compaq
        VARIABLES  { scellNameDateTime,
                     scellSWComponent,
                     scellECode,
                     scellCAC,
                     scellEIP}
        DESCRIPTION
             "Severity: Undetermined -- more information needed to determine severity. At least one Virtual Disk associated with the Data Replication Group identified in the handle field has transitioned to the INOPERATIVE state. The remaining Virtual Disks associated with this Data Replication Group have been forced INOPERATIVE. The value.ul1 field contains the new Data Replication Group member state: 2 (INOPERATIVE). The value.ul2 field contains the old Data Replication Group member state: 1 (OPERATIVE)."
           --#TYPE      "StorageCell Event"
           --#SUMMARY   "SCellName-TimeDate %s : SWCID %d : ECode: %d : CAC %d : EIP %d."
           --#ARGUMENTS {0,1,2,3,4,}
           --#SEVERITY  CRITICAL
           --#TIMEINDEX 136
           --#STATE     WARNING
        ::= 13602515
 
   sCellEventTrap-9-d4 TRAP-TYPE  -- CAC Code: 0
        ENTERPRISE compaq
        VARIABLES  { scellNameDateTime,
                     scellSWComponent,
                     scellECode,
                     scellCAC,
                     scellEIP}
        DESCRIPTION
             "Severity: Normal -- informational in nature. All the Virtual Disks associated with the Data Replication Group identified in the handle field have transitioned to the OPERATIVE state. The value.ul1 field contains the new Data Replication Group member state: 1 (OPERATIVE). The value.ul2 field contains the old Data Replication Group member state: 2 (INOPERATIVE)."
           --#TYPE      "StorageCell Event"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13602516
 
   sCellEventTrap-9-d5 TRAP-TYPE  -- CAC Code: 0
        ENTERPRISE compaq
        VARIABLES  { scellNameDateTime,
                     scellSWComponent,
                     scellECode,
                     scellCAC,
                     scellEIP}
        DESCRIPTION
             "Severity: Normal -- informational in nature. The state of the Physical Disk Drive identified in the handle field has transitioned to the Single Port on Fibre state. The value.ul1 field contains the new state: 5 (SINGLE PORT ON FIBRE). The value.ul2 field contains the old state. The state values that may be in the value.ul2 field are as follows: <UL><LI>1 = Normal <LI>2 = Degraded <LI>3 = Failed <LI>4 = Not Present </UL>The enclosure number, bay number, and rack number where the Physical Disk Drive is located are contained in the attribute.value.u32[0], attribute.value.u32[1], attribute.value.u32[2] fields, respectively. The attribute.type field contains value 1. The rack number in the attribute.value.u32[2] field will not contain a valid value until a future release."
           --#TYPE      "StorageCell Event"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13602517
 
   sCellEventTrap-9-d6 TRAP-TYPE  -- CAC Code: 0
        ENTERPRISE compaq
        VARIABLES  { scellNameDateTime,
                     scellSWComponent,
                     scellECode,
                     scellCAC,
                     scellEIP}
        DESCRIPTION
             "Severity: Normal -- informational in nature. The HSV110 controller identified in the handle field has been shutdown because the temperature sensors do not agree and the system temperature can not be accurately determined. The value.ul1 field contains the current temperature reported in celsius from I2C sensor 1, while the value.ul2 field contains the reading from I2C sensor 2."
           --#TYPE      "StorageCell Event"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13602518
 
   sCellEventTrap-9-d7 TRAP-TYPE  -- CAC Code: 0
        ENTERPRISE compaq
        VARIABLES  { scellNameDateTime,
                     scellSWComponent,
                     scellECode,
                     scellCAC,
                     scellEIP}
        DESCRIPTION
             "Severity: Normal -- informational in nature. The HSV110 controller identified in the handle field has been shutdown because the temperature sensors can not be accessed and the system temperature can not be accurately determined. The value.ul1 field contains the status from the attempted I2C access."
           --#TYPE      "StorageCell Event"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13602519
 
   sCellEventTrap-b-0 TRAP-TYPE  -- CAC Code: 0
        ENTERPRISE compaq
        VARIABLES  { scellNameDateTime,
                     scellSWComponent,
                     scellECode,
                     scellCAC,
                     scellEIP}
        DESCRIPTION
             "Severity: Normal -- informational in nature. The HSV110 controller identified by the node-name field has begun a resynchronization operation (i.e., a restart of the controllers in a manner that has little or no impact on host system connectivity). The information.pc field contains the program counter of resynchronization operation initiator. The information.flags field contains reboot flags value. The information.code field contains the resynchronization operation event code value."
           --#TYPE      "StorageCell Event"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13602816
 
   sCellEventTrap-c-0 TRAP-TYPE  -- CAC Code: 0
        ENTERPRISE compaq
        VARIABLES  { scellNameDateTime,
                     scellSWComponent,
                     scellECode,
                     scellCAC,
                     scellEIP}
        DESCRIPTION
             "Severity: Normal -- informational in nature. The specified Destination Virtual Disk has successfully completed a Full Copy. The following fields are not valid: status, blocks, vda."
           --#TYPE      "StorageCell Event"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13603072
 
   sCellEventTrap-c-1 TRAP-TYPE  -- CAC Code: 5f
        ENTERPRISE compaq
        VARIABLES  { scellNameDateTime,
                     scellSWComponent,
                     scellECode,
                     scellCAC,
                     scellEIP}
        DESCRIPTION
             "Severity: Critical -- failure or failure imminent. The specified Source Virtual Disk has transitioned to the Logging state because the alternate Storage System is not accessible or the Data Replication Group is suspended. The following fields are not valid: status, blocks, vda, port, cerp-id, side."
           --#TYPE      "StorageCell Event"
           --#SUMMARY   "SCellName-TimeDate %s : SWCID %d : ECode: %d : CAC %d : EIP %d."
           --#ARGUMENTS {0,1,2,3,4,}
           --#SEVERITY  CRITICAL
           --#TIMEINDEX 136
           --#STATE     WARNING
        ::= 13603073
 
   sCellEventTrap-c-2 TRAP-TYPE  -- CAC Code: 61
        ENTERPRISE compaq
        VARIABLES  { scellNameDateTime,
                     scellSWComponent,
                     scellECode,
                     scellCAC,
                     scellEIP}
        DESCRIPTION
             "Severity: Critical -- failure or failure imminent. The specified Source Virtual Disk has transitioned to the Logging state because the Destination Virtual Disk is not accessible. The following fields are not valid: status, blocks, vda, port, cerp-id, side."
           --#TYPE      "StorageCell Event"
           --#SUMMARY   "SCellName-TimeDate %s : SWCID %d : ECode: %d : CAC %d : EIP %d."
           --#ARGUMENTS {0,1,2,3,4,}
           --#SEVERITY  CRITICAL
           --#TIMEINDEX 136
           --#STATE     WARNING
        ::= 13603074
 
   sCellEventTrap-c-3 TRAP-TYPE  -- CAC Code: 0
        ENTERPRISE compaq
        VARIABLES  { scellNameDateTime,
                     scellSWComponent,
                     scellECode,
                     scellCAC,
                     scellEIP}
        DESCRIPTION
             "Severity: Normal -- informational in nature. The specified Destination Virtual Disk has transitioned to the Merging state, because the alternate Storage System or Destination Virtual Disk is now accessible or resumed. The following fields are not valid: status, blocks, vda."
           --#TYPE      "StorageCell Event"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13603075
 
   sCellEventTrap-c-4 TRAP-TYPE  -- CAC Code: 5f
        ENTERPRISE compaq
        VARIABLES  { scellNameDateTime,
                     scellSWComponent,
                     scellECode,
                     scellCAC,
                     scellEIP}
        DESCRIPTION
             "Severity: Critical -- failure or failure imminent. A Data Replication Group has entered the Failsafe Locked state due to an inaccessible or inoperative destination. Either the Destination Virtual Disk is not accessible or a Virtual Disk in the Data Replication Group is inoperative. The following fields are not valid: status, blocks, vda, port, cerp-id, side."
           --#TYPE      "StorageCell Event"
           --#SUMMARY   "SCellName-TimeDate %s : SWCID %d : ECode: %d : CAC %d : EIP %d."
           --#ARGUMENTS {0,1,2,3,4,}
           --#SEVERITY  CRITICAL
           --#TIMEINDEX 136
           --#STATE     WARNING
        ::= 13603076
 
   sCellEventTrap-c-5 TRAP-TYPE  -- CAC Code: 60
        ENTERPRISE compaq
        VARIABLES  { scellNameDateTime,
                     scellSWComponent,
                     scellECode,
                     scellCAC,
                     scellEIP}
        DESCRIPTION
             "Severity: Critical -- failure or failure imminent. A Data Replication Group has entered the Failsafe Locked state due to an inoperative source. Either the Source Virtual Disk is not accessible or a Virtual Disk in the Data Replication Group is inoperative. The following fields are not valid: status, blocks, vda, port, cerp-id, side."
           --#TYPE      "StorageCell Event"
           --#SUMMARY   "SCellName-TimeDate %s : SWCID %d : ECode: %d : CAC %d : EIP %d."
           --#ARGUMENTS {0,1,2,3,4,}
           --#SEVERITY  CRITICAL
           --#TIMEINDEX 136
           --#STATE     WARNING
        ::= 13603077
 
   sCellEventTrap-c-6 TRAP-TYPE  -- CAC Code: 60
        ENTERPRISE compaq
        VARIABLES  { scellNameDateTime,
                     scellSWComponent,
                     scellECode,
                     scellCAC,
                     scellEIP}
        DESCRIPTION
             "Severity: Critical -- failure or failure imminent. An unrecoverable read error occurred on the specified Source Virtual Disk during the Full Copy. The Virtual Disk address specified in the vda field indicates the first block in error. The Full Copy was terminated."
           --#TYPE      "StorageCell Event"
           --#SUMMARY   "SCellName-TimeDate %s : SWCID %d : ECode: %d : CAC %d : EIP %d."
           --#ARGUMENTS {0,1,2,3,4,}
           --#SEVERITY  CRITICAL
           --#TIMEINDEX 136
           --#STATE     WARNING
        ::= 13603078
 
   sCellEventTrap-c-7 TRAP-TYPE  -- CAC Code: 5f
        ENTERPRISE compaq
        VARIABLES  { scellNameDateTime,
                     scellSWComponent,
                     scellECode,
                     scellCAC,
                     scellEIP}
        DESCRIPTION
             "Severity: Critical -- failure or failure imminent. A Full Copy terminated prior to completion. A remote copy error occurred due to an inaccessible alternate Storage System. The Virtual Disk address specified in the vda field indicates the first block in error. The Full Copy will continue when the Data Replication Destination is restored."
           --#TYPE      "StorageCell Event"
           --#SUMMARY   "SCellName-TimeDate %s : SWCID %d : ECode: %d : CAC %d : EIP %d."
           --#ARGUMENTS {0,1,2,3,4,}
           --#SEVERITY  CRITICAL
           --#TIMEINDEX 136
           --#STATE     WARNING
        ::= 13603079
 
   sCellEventTrap-c-8 TRAP-TYPE  -- CAC Code: 61
        ENTERPRISE compaq
        VARIABLES  { scellNameDateTime,
                     scellSWComponent,
                     scellECode,
                     scellCAC,
                     scellEIP}
        DESCRIPTION
             "Severity: Critical -- failure or failure imminent. A Full Copy terminated prior to completion. A remote copy error occurred due to an inaccessible Destination Virtual Disk. The Virtual Disk address specified in the vda field indicates the first block in error. The Full Copy will continue when the Data Replication Destination is restored."
           --#TYPE      "StorageCell Event"
           --#SUMMARY   "SCellName-TimeDate %s : SWCID %d : ECode: %d : CAC %d : EIP %d."
           --#ARGUMENTS {0,1,2,3,4,}
           --#SEVERITY  CRITICAL
           --#TIMEINDEX 136
           --#STATE     WARNING
        ::= 13603080
 
   sCellEventTrap-c-9 TRAP-TYPE  -- CAC Code: 62
        ENTERPRISE compaq
        VARIABLES  { scellNameDateTime,
                     scellSWComponent,
                     scellECode,
                     scellCAC,
                     scellEIP}
        DESCRIPTION
             "Severity: Warning -- not failed but attention recommended or required. A Data Replication Log has been reset due to insufficient Disk Group capacity. The Data Replication Destination has been marked for a Full Copy. The following fields are not valid: status, blocks, vda, port, cerp-id, side."
           --#TYPE      "StorageCell Event"
           --#SUMMARY   "SCellName-TimeDate %s : SWCID %d : ECode: %d : CAC %d : EIP %d."
           --#ARGUMENTS {0,1,2,3,4,}
           --#SEVERITY  MINOR
           --#TIMEINDEX 136
           --#STATE     WARNING
        ::= 13603081
 
   sCellEventTrap-c-a TRAP-TYPE  -- CAC Code: 0
        ENTERPRISE compaq
        VARIABLES  { scellNameDateTime,
                     scellSWComponent,
                     scellECode,
                     scellCAC,
                     scellEIP}
        DESCRIPTION
             "Severity: Normal -- informational in nature. A Data Replication Log has been reset due to a Data Replication Group failover. The following fields are not valid: status, blocks, vda."
           --#TYPE      "StorageCell Event"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13603082
 
   sCellEventTrap-c-c TRAP-TYPE  -- CAC Code: 0
        ENTERPRISE compaq
        VARIABLES  { scellNameDateTime,
                     scellSWComponent,
                     scellECode,
                     scellCAC,
                     scellEIP}
        DESCRIPTION
             "Severity: Normal -- informational in nature. A Destination Data Replication Group has successfully completed a Merge. The following fields are not valid: status, blocks, vda."
           --#TYPE      "StorageCell Event"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13603084
 
   sCellEventTrap-c-f TRAP-TYPE  -- CAC Code: 0
        ENTERPRISE compaq
        VARIABLES  { scellNameDateTime,
                     scellSWComponent,
                     scellECode,
                     scellCAC,
                     scellEIP}
        DESCRIPTION
             "Severity: Normal -- informational in nature. A Data Replication Group is no longer in a Failsafe Locked state. The following fields are not valid: status, blocks, vda, port, cerp-id, side."
           --#TYPE      "StorageCell Event"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13603087
 
   sCellEventTrap-c-10 TRAP-TYPE  -- CAC Code: 0
        ENTERPRISE compaq
        VARIABLES  { scellNameDateTime,
                     scellSWComponent,
                     scellECode,
                     scellCAC,
                     scellEIP}
        DESCRIPTION
             "Severity: Normal -- informational in nature. A Destination Data Replication Group has been marked for a Full Copy. The following fields are not valid: status, blocks, vda."
           --#TYPE      "StorageCell Event"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13603088
 
   sCellEventTrap-c-11 TRAP-TYPE  -- CAC Code: 0
        ENTERPRISE compaq
        VARIABLES  { scellNameDateTime,
                     scellSWComponent,
                     scellECode,
                     scellCAC,
                     scellEIP}
        DESCRIPTION
             "Severity: Normal -- informational in nature. A Storage System has discovered that a Data Replication Group failover has taken place. This Virtual Disk is transitioning from a Data Replication Source role to a Data Replication Destination role. The following fields are not valid: status, blocks, vda."
           --#TYPE      "StorageCell Event"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13603089
 
   sCellEventTrap-c-12 TRAP-TYPE  -- CAC Code: 0
        ENTERPRISE compaq
        VARIABLES  { scellNameDateTime,
                     scellSWComponent,
                     scellECode,
                     scellCAC,
                     scellEIP}
        DESCRIPTION
             "Severity: Normal -- informational in nature. This Data Replication Group is transitioning from a Data Replication Destination role to a Data Replication Source role. The following fields are not valid: status, blocks, vda."
           --#TYPE      "StorageCell Event"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13603090
 
   sCellEventTrap-c-15 TRAP-TYPE  -- CAC Code: 0
        ENTERPRISE compaq
        VARIABLES  { scellNameDateTime,
                     scellSWComponent,
                     scellECode,
                     scellCAC,
                     scellEIP}
        DESCRIPTION
             "Severity: Normal -- informational in nature. The Data Replication Path between this Site and the Alternate Site has closed, possibly due to a connection failure between the specified host port and the Alternate Site. The following fields are not valid: group-name-uuid, group-uuid, source-scvd-uuid, status, block, vda."
           --#TYPE      "StorageCell Event"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13603093
 
   sCellEventTrap-d-0 TRAP-TYPE  -- CAC Code: 1
        ENTERPRISE compaq
        VARIABLES  { scellNameDateTime,
                     scellSWComponent,
                     scellECode,
                     scellCAC,
                     scellEIP}
        DESCRIPTION
             "Severity: Critical -- failure or failure imminent. Unrecognized event reported by a Drive Enclosure Environmental Monitoring Unit. The handle field contains the WWN of the drive enclosure containing the Drive Enclosure Environmental Monitoring Unit. The event was reported by the Drive Enclosure Environmental Monitoring Unit located in the drive enclosure determined by the content of the dencl-num field as follows: <UL><LI>If dencl-num is less than 99, the location is as indicated by the content of the rack-num and dencl-num fields. <LI>If dencl-num is equal to 99, the location is unknown. Note that the content of the rack-num field is undefined in this case. <LI>If dencl-num is greater than 99, the HSV110 controller does not have proof of the current location but the last known location is indicated by the content of the rack-num and dencl-num fields. Subtract 100 from the content of those fields to determine the actual last known location. If there have been no configuration changes, the last known location values will be accurate. </UL>Note that the content of the rack-num field will not be valid until a future release. The content of the alarm-error-code field could not be translated into a known event. The enclosures array shows the drive enclosures available on the Fibre Channel loop pair (0 = Loop A, 1 = Loop B) identified in the loop field. The location of an available drive enclosure is determined by the content of the enclosures.dencl-num field as follows: <UL><LI>If enclosures.dencl-num is less than 99, the location is as indicated by the content of the enclosures.rack-num and enclosures.dencl-num fields. <LI>If enclosures.dencl-num is equal to 99, the enclosures array entry is not used. Note that the content of the enclosures.rack-num field is undefined in this case. <LI>If enclosures.dencl-num is greater than 99, the HSV110 controller does not have proof of the current location but the last known location is indicated by the content of the enclosures.rack-num and enclosures.dencl-num fields. Subtract 100 from the content of those fields to determine the actual last known location. If there have been no configuration changes, the last known location values will be accurate. </UL>Note that the content of the enclosures.rack-num field will not be valid until a future release."
           --#TYPE      "StorageCell Event"
           --#SUMMARY   "SCellName-TimeDate %s : SWCID %d : ECode: %d : CAC %d : EIP %d."
           --#ARGUMENTS {0,1,2,3,4,}
           --#SEVERITY  CRITICAL
           --#TIMEINDEX 136
           --#STATE     WARNING
        ::= 13603328
 
   sCellEventTrap-d-1 TRAP-TYPE  -- CAC Code: 40
        ENTERPRISE compaq
        VARIABLES  { scellNameDateTime,
                     scellSWComponent,
                     scellECode,
                     scellCAC,
                     scellEIP}
        DESCRIPTION
             "Severity: Critical -- failure or failure imminent. A physical disk drive that is not Fibre Channel compatible or cannot operate at the link rate established by the drive enclosure I/O modules was detected. The handle field contains the WWN of the drive enclosure containing the Drive Enclosure Environmental Monitoring Unit. This problem was detected by the Drive Enclosure Environmental Monitoring Unit located in the drive enclosure determined by the content of the dencl-num field as follows: <UL><LI>If dencl-num is less than 99, the location is as indicated by the content of the rack-num and dencl-num fields. <LI>If dencl-num is equal to 99, the location is unknown. Note that the content of the rack-num field is undefined in this case. <LI>If dencl-num is greater than 99, the HSV110 controller does not have proof of the current location but the last known location is indicated by the content of the rack-num and dencl-num fields. Subtract 100 from the content of those fields to determine the actual last known location. If there have been no configuration changes, the last known location values will be accurate. </UL>Note that the content of the rack-num field will not be valid until a future release. This problem was detected during spin up of the physical disk drive installed in the drive enclosure bay identified in the alarm-error-code.field.en field. The enclosures array shows the drive enclosures available on the Fibre Channel loop pair (0 = Loop A, 1 = Loop B) identified in the loop field. The location of an available drive enclosure is determined by the content of the enclosures.dencl-num field as follows: <UL><LI>If enclosures.dencl-num is less than 99, the location is as indicated by the content of the enclosures.rack-num and enclosures.dencl-num fields. <LI>If enclosures.dencl-num is equal to 99, the enclosures array entry is not used. Note that the content of the enclosures.rack-num field is undefined in this case. <LI>If enclosures.dencl-num is greater than 99, the HSV110 controller does not have proof of the current location but the last known location is indicated by the content of the enclosures.rack-num and enclosures.dencl-num fields. Subtract 100 from the content of those fields to determine the actual last known location. If there have been no configuration changes, the last known location values will be accurate. </UL>Note that the content of the enclosures.rack-num field will not be valid until a future release."
           --#TYPE      "StorageCell Event"
           --#SUMMARY   "SCellName-TimeDate %s : SWCID %d : ECode: %d : CAC %d : EIP %d."
           --#ARGUMENTS {0,1,2,3,4,}
           --#SEVERITY  CRITICAL
           --#TIMEINDEX 136
           --#STATE     WARNING
        ::= 13603329
 
   sCellEventTrap-d-2 TRAP-TYPE  -- CAC Code: 41
        ENTERPRISE compaq
        VARIABLES  { scellNameDateTime,
                     scellSWComponent,
                     scellECode,
                     scellCAC,
                     scellEIP}
        DESCRIPTION
             "Severity: Warning -- not failed but attention recommended or required. A physical disk drive is improperly installed or missing. This could affect the drive enclosure air flow and cause an over temperature condition. The handle field contains the WWN of the drive enclosure containing the Drive Enclosure Environmental Monitoring Unit. This problem was detected by the Drive Enclosure Environmental Monitoring Unit located in the drive enclosure determined by the content of the dencl-num field as follows: <UL><LI>If dencl-num is less than 99, the location is as indicated by the content of the rack-num and dencl-num fields. <LI>If dencl-num is equal to 99, the location is unknown. Note that the content of the rack-num field is undefined in this case. <LI>If dencl-num is greater than 99, the HSV110 controller does not have proof of the current location but the last known location is indicated by the content of the rack-num and dencl-num fields. Subtract 100 from the content of those fields to determine the actual last known location. If there have been no configuration changes, the last known location values will be accurate. </UL>Note that the content of the rack-num field will not be valid until a future release. The affected drive enclosure bay is identified in the alarm-error-code.field.en field. The enclosures array shows the drive enclosures available on the Fibre Channel loop pair (0 = Loop A, 1 = Loop B) identified in the loop field. The location of an available drive enclosure is determined by the content of the enclosures.dencl-num field as follows: <UL><LI>If enclosures.dencl-num is less than 99, the location is as indicated by the content of the enclosures.rack-num and enclosures.dencl-num fields. <LI>If enclosures.dencl-num is equal to 99, the enclosures array entry is not used. Note that the content of the enclosures.rack-num field is undefined in this case. <LI>If enclosures.dencl-num is greater than 99, the HSV110 controller does not have proof of the current location but the last known location is indicated by the content of the enclosures.rack-num and enclosures.dencl-num fields. Subtract 100 from the content of those fields to determine the actual last known location. If there have been no configuration changes, the last known location values will be accurate. </UL>Note that the content of the enclosures.rack-num field will not be valid until a future release."
           --#TYPE      "StorageCell Event"
           --#SUMMARY   "SCellName-TimeDate %s : SWCID %d : ECode: %d : CAC %d : EIP %d."
           --#ARGUMENTS {0,1,2,3,4,}
           --#SEVERITY  MINOR
           --#TIMEINDEX 136
           --#STATE     WARNING
        ::= 13603330
 
   sCellEventTrap-d-3 TRAP-TYPE  -- CAC Code: 41
        ENTERPRISE compaq
        VARIABLES  { scellNameDateTime,
                     scellSWComponent,
                     scellECode,
                     scellCAC,
                     scellEIP}
        DESCRIPTION
             "Severity: Warning -- not failed but attention recommended or required. A physical disk drive was removed while software-activated drive locking was enabled on a drive enclosure that does not support drive locking. The handle field contains the WWN of the drive enclosure containing the Drive Enclosure Environmental Monitoring Unit. This problem was detected by the Drive Enclosure Environmental Monitoring Unit located in the drive enclosure determined by the content of the dencl-num field as follows: <UL><LI>If dencl-num is less than 99, the location is as indicated by the content of the rack-num and dencl-num fields. <LI>If dencl-num is equal to 99, the location is unknown. Note that the content of the rack-num field is undefined in this case. <LI>If dencl-num is greater than 99, the HSV110 controller does not have proof of the current location but the last known location is indicated by the content of the rack-num and dencl-num fields. Subtract 100 from the content of those fields to determine the actual last known location. If there have been no configuration changes, the last known location values will be accurate. </UL>Note that the content of the rack-num field will not be valid until a future release. The affected drive enclosure bay is identified in the alarm-error-code.field.en field. The enclosures array shows the drive enclosures available on the Fibre Channel loop pair (0 = Loop A, 1 = Loop B) identified in the loop field. The location of an available drive enclosure is determined by the content of the enclosures.dencl-num field as follows: <UL><LI>If enclosures.dencl-num is less than 99, the location is as indicated by the content of the enclosures.rack-num and enclosures.dencl-num fields. <LI>If enclosures.dencl-num is equal to 99, the enclosures array entry is not used. Note that the content of the enclosures.rack-num field is undefined in this case. <LI>If enclosures.dencl-num is greater than 99, the HSV110 controller does not have proof of the current location but the last known location is indicated by the content of the enclosures.rack-num and enclosures.dencl-num fields. Subtract 100 from the content of those fields to determine the actual last known location. If there have been no configuration changes, the last known location values will be accurate. </UL>Note that the content of the enclosures.rack-num field will not be valid until a future release."
           --#TYPE      "StorageCell Event"
           --#SUMMARY   "SCellName-TimeDate %s : SWCID %d : ECode: %d : CAC %d : EIP %d."
           --#ARGUMENTS {0,1,2,3,4,}
           --#SEVERITY  MINOR
           --#TIMEINDEX 136
           --#STATE     WARNING
        ::= 13603331
 
   sCellEventTrap-d-4 TRAP-TYPE  -- CAC Code: 42
        ENTERPRISE compaq
        VARIABLES  { scellNameDateTime,
                     scellSWComponent,
                     scellECode,
                     scellCAC,
                     scellEIP}
        DESCRIPTION
             "Severity: Critical -- failure or failure imminent. A physical disk drive that is capable of operating at the loop link rate established by the drive enclosure I/O module was found to be running at a different rate. The handle field contains the WWN of the drive enclosure containing the Drive Enclosure Environmental Monitoring Unit. This problem was detected by the Drive Enclosure Environmental Monitoring Unit located in the drive enclosure determined by the content of the dencl-num field as follows: <UL><LI>If dencl-num is less than 99, the location is as indicated by the content of the rack-num and dencl-num fields. <LI>If dencl-num is equal to 99, the location is unknown. Note that the content of the rack-num field is undefined in this case. <LI>If dencl-num is greater than 99, the HSV110 controller does not have proof of the current location but the last known location is indicated by the content of the rack-num and dencl-num fields. Subtract 100 from the content of those fields to determine the actual last known location. If there have been no configuration changes, the last known location values will be accurate. </UL>Note that the content of the rack-num field will not be valid until a future release. The affected physical disk drive is installed in the drive enclosure bay identified in the alarm-error-code.field.en field. The Fibre Channel loop on which the problem was detected is identified by the content of the alarm-error-code.field.ec field as follows: <UL><LI>4 = loop A <LI>5 = loop B </UL><P> The enclosures array shows the drive enclosures available on the Fibre Channel loop pair (0 = Loop A, 1 = Loop B) identified in the loop field. The location of an available drive enclosure is determined by the content of the enclosures.dencl-num field as follows: <UL><LI>If enclosures.dencl-num is less than 99, the location is as indicated by the content of the enclosures.rack-num and enclosures.dencl-num fields. <LI>If enclosures.dencl-num is equal to 99, the enclosures array entry is not used. Note that the content of the enclosures.rack-num field is undefined in this case. <LI>If enclosures.dencl-num is greater than 99, the HSV110 controller does not have proof of the current location but the last known location is indicated by the content of the enclosures.rack-num and enclosures.dencl-num fields. Subtract 100 from the content of those fields to determine the actual last known location. If there have been no configuration changes, the last known location values will be accurate. </UL>Note that the content of the enclosures.rack-num field will not be valid until a future release."
           --#TYPE      "StorageCell Event"
           --#SUMMARY   "SCellName-TimeDate %s : SWCID %d : ECode: %d : CAC %d : EIP %d."
           --#ARGUMENTS {0,1,2,3,4,}
           --#SEVERITY  CRITICAL
           --#TIMEINDEX 136
           --#STATE     WARNING
        ::= 13603332
 
   sCellEventTrap-d-33 TRAP-TYPE  -- CAC Code: 9
        ENTERPRISE compaq
        VARIABLES  { scellNameDateTime,
                     scellSWComponent,
                     scellECode,
                     scellCAC,
                     scellEIP}
        DESCRIPTION
             "Severity: Warning -- not failed but attention recommended or required. The AC input to a drive enclosure power supply has been lost. This makes the remaining power supply a single point of failure. The handle field contains the WWN of the drive enclosure containing the Drive Enclosure Environmental Monitoring Unit. This problem was detected by the Drive Enclosure Environmental Monitoring Unit located in the drive enclosure determined by the content of the dencl-num field as follows: <UL><LI>If dencl-num is less than 99, the location is as indicated by the content of the rack-num and dencl-num fields. <LI>If dencl-num is equal to 99, the location is unknown. Note that the content of the rack-num field is undefined in this case. <LI>If dencl-num is greater than 99, the HSV110 controller does not have proof of the current location but the last known location is indicated by the content of the rack-num and dencl-num fields. Subtract 100 from the content of those fields to determine the actual last known location. If there have been no configuration changes, the last known location values will be accurate. </UL>Note that the content of the rack-num field will not be valid until a future release. The location of the affected power supply (1 or 2) is identified in the alarm-error-code.field.en field. The enclosures array shows the drive enclosures available on the Fibre Channel loop pair (0 = Loop A, 1 = Loop B) identified in the loop field. The location of an available drive enclosure is determined by the content of the enclosures.dencl-num field as follows: <UL><LI>If enclosures.dencl-num is less than 99, the location is as indicated by the content of the enclosures.rack-num and enclosures.dencl-num fields. <LI>If enclosures.dencl-num is equal to 99, the enclosures array entry is not used. Note that the content of the enclosures.rack-num field is undefined in this case. <LI>If enclosures.dencl-num is greater than 99, the HSV110 controller does not have proof of the current location but the last known location is indicated by the content of the enclosures.rack-num and enclosures.dencl-num fields. Subtract 100 from the content of those fields to determine the actual last known location. If there have been no configuration changes, the last known location values will be accurate. </UL>Note that the content of the enclosures.rack-num field will not be valid until a future release."
           --#TYPE      "StorageCell Event"
           --#SUMMARY   "SCellName-TimeDate %s : SWCID %d : ECode: %d : CAC %d : EIP %d."
           --#ARGUMENTS {0,1,2,3,4,}
           --#SEVERITY  MINOR
           --#TIMEINDEX 136
           --#STATE     WARNING
        ::= 13603379
 
   sCellEventTrap-d-34 TRAP-TYPE  -- CAC Code: 80
        ENTERPRISE compaq
        VARIABLES  { scellNameDateTime,
                     scellSWComponent,
                     scellECode,
                     scellCAC,
                     scellEIP}
        DESCRIPTION
             "Severity: Critical -- failure or failure imminent. A drive enclosure power supply is improperly installed or missing. This could affect the drive enclosure air flow and cause an over temperature condition. The operational power supply will automatically shut down after a short period of time, thereby disabling the drive enclosure. This condition remains active until either the problem is corrected, or the operational power supply shuts down, whichever occurs first. The handle field contains the WWN of the drive enclosure containing the Drive Enclosure Environmental Monitoring Unit. This problem was detected by the Drive Enclosure Environmental Monitoring Unit located in the drive enclosure determined by the content of the dencl-num field as follows: <UL><LI>If dencl-num is less than 99, the location is as indicated by the content of the rack-num and dencl-num fields. <LI>If dencl-num is equal to 99, the location is unknown. Note that the content of the rack-num field is undefined in this case. <LI>If dencl-num is greater than 99, the HSV110 controller does not have proof of the current location but the last known location is indicated by the content of the rack-num and dencl-num fields. Subtract 100 from the content of those fields to determine the actual last known location. If there have been no configuration changes, the last known location values will be accurate. </UL>Note that the content of the rack-num field will not be valid until a future release. The location of the affected power supply (1 or 2) is identified in the alarm-error-code.field.en field. The enclosures array shows the drive enclosures available on the Fibre Channel loop pair (0 = Loop A, 1 = Loop B) identified in the loop field. The location of an available drive enclosure is determined by the content of the enclosures.dencl-num field as follows: <UL><LI>If enclosures.dencl-num is less than 99, the location is as indicated by the content of the enclosures.rack-num and enclosures.dencl-num fields. <LI>If enclosures.dencl-num is equal to 99, the enclosures array entry is not used. Note that the content of the enclosures.rack-num field is undefined in this case. <LI>If enclosures.dencl-num is greater than 99, the HSV110 controller does not have proof of the current location but the last known location is indicated by the content of the enclosures.rack-num and enclosures.dencl-num fields. Subtract 100 from the content of those fields to determine the actual last known location. If there have been no configuration changes, the last known location values will be accurate. </UL>Note that the content of the enclosures.rack-num field will not be valid until a future release."
           --#TYPE      "StorageCell Event"
           --#SUMMARY   "SCellName-TimeDate %s : SWCID %d : ECode: %d : CAC %d : EIP %d."
           --#ARGUMENTS {0,1,2,3,4,}
           --#SEVERITY  CRITICAL
           --#TIMEINDEX 136
           --#STATE     WARNING
        ::= 13603380
 
   sCellEventTrap-d-35 TRAP-TYPE  -- CAC Code: 9a
        ENTERPRISE compaq
        VARIABLES  { scellNameDateTime,
                     scellSWComponent,
                     scellECode,
                     scellCAC,
                     scellEIP}
        DESCRIPTION
             "Severity: Critical -- failure or failure imminent. A drive enclosure power supply component has failed. The handle field contains the WWN of the drive enclosure containing the Drive Enclosure Environmental Monitoring Unit. This problem was detected by the Drive Enclosure Environmental Monitoring Unit located in the drive enclosure determined by the content of the dencl-num field as follows: <UL><LI>If dencl-num is less than 99, the location is as indicated by the content of the rack-num and dencl-num fields. <LI>If dencl-num is equal to 99, the location is unknown. Note that the content of the rack-num field is undefined in this case. <LI>If dencl-num is greater than 99, the HSV110 controller does not have proof of the current location but the last known location is indicated by the content of the rack-num and dencl-num fields. Subtract 100 from the content of those fields to determine the actual last known location. If there have been no configuration changes, the last known location values will be accurate. </UL>Note that the content of the rack-num field will not be valid until a future release. The location of the affected power supply (1 or 2) is identified in the alarm-error-code.field.en field. The enclosures array shows the drive enclosures available on the Fibre Channel loop pair (0 = Loop A, 1 = Loop B) identified in the loop field. The location of an available drive enclosure is determined by the content of the enclosures.dencl-num field as follows: <UL><LI>If enclosures.dencl-num is less than 99, the location is as indicated by the content of the enclosures.rack-num and enclosures.dencl-num fields. <LI>If enclosures.dencl-num is equal to 99, the enclosures array entry is not used. Note that the content of the enclosures.rack-num field is undefined in this case. <LI>If enclosures.dencl-num is greater than 99, the HSV110 controller does not have proof of the current location but the last known location is indicated by the content of the enclosures.rack-num and enclosures.dencl-num fields. Subtract 100 from the content of those fields to determine the actual last known location. If there have been no configuration changes, the last known location values will be accurate. </UL>Note that the content of the enclosures.rack-num field will not be valid until a future release."
           --#TYPE      "StorageCell Event"
           --#SUMMARY   "SCellName-TimeDate %s : SWCID %d : ECode: %d : CAC %d : EIP %d."
           --#ARGUMENTS {0,1,2,3,4,}
           --#SEVERITY  CRITICAL
           --#TIMEINDEX 136
           --#STATE     WARNING
        ::= 13603381
 
   sCellEventTrap-d-47 TRAP-TYPE  -- CAC Code: 83
        ENTERPRISE compaq
        VARIABLES  { scellNameDateTime,
                     scellSWComponent,
                     scellECode,
                     scellCAC,
                     scellEIP}
        DESCRIPTION
             "Severity: Critical -- failure or failure imminent. A drive enclosure blower is not operating properly. This could affect the drive enclosure air flow and cause an over temperature condition. The handle field contains the WWN of the drive enclosure containing the Drive Enclosure Environmental Monitoring Unit. This problem was detected by the Drive Enclosure Environmental Monitoring Unit located in the drive enclosure determined by the content of the dencl-num field as follows: <UL><LI>If dencl-num is less than 99, the location is as indicated by the content of the rack-num and dencl-num fields. <LI>If dencl-num is equal to 99, the location is unknown. Note that the content of the rack-num field is undefined in this case. <LI>If dencl-num is greater than 99, the HSV110 controller does not have proof of the current location but the last known location is indicated by the content of the rack-num and dencl-num fields. Subtract 100 from the content of those fields to determine the actual last known location. If there have been no configuration changes, the last known location values will be accurate. </UL>Note that the content of the rack-num field will not be valid until a future release. The location of the affected blower (1 or 2) is identified in the alarm-error-code.field.en field. The cause of the improper operation is described by the content of the alarm-error-code.field.ec field as follows: <UL><LI>1 = The blower is operating at a speed that is outside of the Drive Enclosure Environmental Monitoring Unit specified range, possibly because of a bearing problem. <LI>2 = The blower is operating at a speed that is significantly outside of the Drive Enclosure Environmental Monitoring Unit specified range, possibly because of a bearing problem. <LI>3 = The blower has stopped. NOTE: The other blower (if operational) now operates at high speed and is a single point of failure. A single blower operating at high speed can provide sufficient air flow to cool an enclosure and the elements for up to 100 hours. However, operating an enclosure at temperatures approaching an overheating threshold can damage elements and may reduce the MTBF of a specific element. Hewlett-Packard therefore recommends immediate replacement of the defective blower. <LI>4 = The power supply reported an internal blower error. </UL><P> The enclosures array shows the drive enclosures available on the Fibre Channel loop pair (0 = Loop A, 1 = Loop B) identified in the loop field. The location of an available drive enclosure is determined by the content of the enclosures.dencl-num field as follows: <UL><LI>If enclosures.dencl-num is less than 99, the location is as indicated by the content of the enclosures.rack-num and enclosures.dencl-num fields. <LI>If enclosures.dencl-num is equal to 99, the enclosures array entry is not used. Note that the content of the enclosures.rack-num field is undefined in this case. <LI>If enclosures.dencl-num is greater than 99, the HSV110 controller does not have proof of the current location but the last known location is indicated by the content of the enclosures.rack-num and enclosures.dencl-num fields. Subtract 100 from the content of those fields to determine the actual last known location. If there have been no configuration changes, the last known location values will be accurate. </UL>Note that the content of the enclosures.rack-num field will not be valid until a future release."
           --#TYPE      "StorageCell Event"
           --#SUMMARY   "SCellName-TimeDate %s : SWCID %d : ECode: %d : CAC %d : EIP %d."
           --#ARGUMENTS {0,1,2,3,4,}
           --#SEVERITY  CRITICAL
           --#TIMEINDEX 136
           --#STATE     WARNING
        ::= 13603399
 
   sCellEventTrap-d-4b TRAP-TYPE  -- CAC Code: 82
        ENTERPRISE compaq
        VARIABLES  { scellNameDateTime,
                     scellSWComponent,
                     scellECode,
                     scellCAC,
                     scellEIP}
        DESCRIPTION
             "Severity: Critical -- failure or failure imminent. A drive enclosure blower is improperly installed or missing. This affects the drive enclosure air flow and can cause an over temperature condition. The handle field contains the WWN of the drive enclosure containing the Drive Enclosure Environmental Monitoring Unit. This problem was detected by the Drive Enclosure Environmental Monitoring Unit located in the drive enclosure determined by the content of the dencl-num field as follows: <UL><LI>If dencl-num is less than 99, the location is as indicated by the content of the rack-num and dencl-num fields. <LI>If dencl-num is equal to 99, the location is unknown. Note that the content of the rack-num field is undefined in this case. <LI>If dencl-num is greater than 99, the HSV110 controller does not have proof of the current location but the last known location is indicated by the content of the rack-num and dencl-num fields. Subtract 100 from the content of those fields to determine the actual last known location. If there have been no configuration changes, the last known location values will be accurate. </UL>Note that the content of the rack-num field will not be valid until a future release. The location of the affected blower (1 or 2) is identified in the alarm-error-code.field.en field. The enclosures array shows the drive enclosures available on the Fibre Channel loop pair (0 = Loop A, 1 = Loop B) identified in the loop field. The location of an available drive enclosure is determined by the content of the enclosures.dencl-num field as follows: <UL><LI>If enclosures.dencl-num is less than 99, the location is as indicated by the content of the enclosures.rack-num and enclosures.dencl-num fields. <LI>If enclosures.dencl-num is equal to 99, the enclosures array entry is not used. Note that the content of the enclosures.rack-num field is undefined in this case. <LI>If enclosures.dencl-num is greater than 99, the HSV110 controller does not have proof of the current location but the last known location is indicated by the content of the enclosures.rack-num and enclosures.dencl-num fields. Subtract 100 from the content of those fields to determine the actual last known location. If there have been no configuration changes, the last known location values will be accurate. </UL>Note that the content of the enclosures.rack-num field will not be valid until a future release."
           --#TYPE      "StorageCell Event"
           --#SUMMARY   "SCellName-TimeDate %s : SWCID %d : ECode: %d : CAC %d : EIP %d."
           --#ARGUMENTS {0,1,2,3,4,}
           --#SEVERITY  CRITICAL
           --#TIMEINDEX 136
           --#STATE     WARNING
        ::= 13603403
 
   sCellEventTrap-d-4c TRAP-TYPE  -- CAC Code: 84
        ENTERPRISE compaq
        VARIABLES  { scellNameDateTime,
                     scellSWComponent,
                     scellECode,
                     scellCAC,
                     scellEIP}
        DESCRIPTION
             "Severity: Critical -- failure or failure imminent. Both drive enclosure blowers are missing. This severely affects the drive enclosure air flow and can cause an over temperature condition. The operational power supply(s) will automatically shut down after a short period of time, thereby disabling the drive enclosure. This condition remains active until either the problem is corrected, or the operational power supply(s) shut down, whichever occurs first. The handle field contains the WWN of the drive enclosure containing the Drive Enclosure Environmental Monitoring Unit. This problem was detected by the Drive Enclosure Environmental Monitoring Unit located in the drive enclosure determined by the content of the dencl-num field as follows: <UL><LI>If dencl-num is less than 99, the location is as indicated by the content of the rack-num and dencl-num fields. <LI>If dencl-num is equal to 99, the location is unknown. Note that the content of the rack-num field is undefined in this case. <LI>If dencl-num is greater than 99, the HSV110 controller does not have proof of the current location but the last known location is indicated by the content of the rack-num and dencl-num fields. Subtract 100 from the content of those fields to determine the actual last known location. If there have been no configuration changes, the last known location values will be accurate. </UL>Note that the content of the rack-num field will not be valid until a future release. Note that this event is preceded by a 'drive enclosure blower is improperly installed or missing' event that identifies the location of the first missing blower. The location of the second missing blower (1 or 2) is identified in the alarm-error-code.field.en field of this event. The enclosures array shows the drive enclosures available on the Fibre Channel loop pair (0 = Loop A, 1 = Loop B) identified in the loop field. The location of an available drive enclosure is determined by the content of the enclosures.dencl-num field as follows: <UL><LI>If enclosures.dencl-num is less than 99, the location is as indicated by the content of the enclosures.rack-num and enclosures.dencl-num fields. <LI>If enclosures.dencl-num is equal to 99, the enclosures array entry is not used. Note that the content of the enclosures.rack-num field is undefined in this case. <LI>If enclosures.dencl-num is greater than 99, the HSV110 controller does not have proof of the current location but the last known location is indicated by the content of the enclosures.rack-num and enclosures.dencl-num fields. Subtract 100 from the content of those fields to determine the actual last known location. If there have been no configuration changes, the last known location values will be accurate. </UL>Note that the content of the enclosures.rack-num field will not be valid until a future release."
           --#TYPE      "StorageCell Event"
           --#SUMMARY   "SCellName-TimeDate %s : SWCID %d : ECode: %d : CAC %d : EIP %d."
           --#ARGUMENTS {0,1,2,3,4,}
           --#SEVERITY  CRITICAL
           --#TIMEINDEX 136
           --#STATE     WARNING
        ::= 13603404
 
   sCellEventTrap-d-5b TRAP-TYPE  -- CAC Code: 86
        ENTERPRISE compaq
        VARIABLES  { scellNameDateTime,
                     scellSWComponent,
                     scellECode,
                     scellCAC,
                     scellEIP}
        DESCRIPTION
             "Severity: Warning -- not failed but attention recommended or required. A drive enclosure temperature sensor out of range condition has been reported by one of the drive enclosure elements. The handle field contains the WWN of the drive enclosure containing the Drive Enclosure Environmental Monitoring Unit. This problem was detected by the Drive Enclosure Environmental Monitoring Unit located in the drive enclosure determined by the content of the dencl-num field as follows: <UL><LI>If dencl-num is less than 99, the location is as indicated by the content of the rack-num and dencl-num fields. <LI>If dencl-num is equal to 99, the location is unknown. Note that the content of the rack-num field is undefined in this case. <LI>If dencl-num is greater than 99, the HSV110 controller does not have proof of the current location but the last known location is indicated by the content of the rack-num and dencl-num fields. Subtract 100 from the content of those fields to determine the actual last known location. If there have been no configuration changes, the last known location values will be accurate. </UL>Note that the content of the rack-num field will not be valid until a future release. The location of the temperature sensor (1 through 11) is identified in the alarm-error-code.field.en field as follows: <UL><LI>1 = Power Supply 1 Exhaust <LI>2 = Power Supply 2 Exhaust <LI>3 = Drive Enclosure Environmental Monitoring Unit <LI>4 = Drive Bay 1 <LI>5 = Drive Bay 2 <LI>6 = Drive Bay 3 <LI>7 = Drive Bay 4 <LI>8 = Drive Bay 5 <LI>9 = Drive Bay 6 <LI>A = Drive Bay 7 <LI>B = Drive Bay 8 <LI>C = Drive Bay 9 <LI>D = Drive Bay 10 <LI>E = Drive Bay 11 <LI>F = Drive Bay 12 <LI>10 = Drive Bay 13 <LI>11 = Drive Bay 14 </UL><P> The temperature sensor out of range condition is described by the content of the alarm-error-code.field.ec field as follows: <UL><LI>1 = The element temperature is approaching, but has not reached, the high temperature CRITICAL threshold. Continued operation under these conditions may result in a CRITICAL condition and may reduce an element's MTBF. <LI>2 = The element temperature is above the high temperature CRITICAL threshold. Continued operation under these conditions may result in element failure. <LI>3 = The element temperature is approaching, but has not reached, the low temperature CRITICAL threshold. Continued operation under these conditions may result in a CRITICAL condition and may reduce an element's MTBF. <LI>4 = The element temperature has reached the low temperature CRITICAL threshold. Continued operation under these conditions may result in element failure. </UL><P> The actual temperature threshold values can be found in the HSV element manager GUI. The enclosures array shows the drive enclosures available on the Fibre Channel loop pair (0 = Loop A, 1 = Loop B) identified in the loop field. The location of an available drive enclosure is determined by the content of the enclosures.dencl-num field as follows: <UL><LI>If enclosures.dencl-num is less than 99, the location is as indicated by the content of the enclosures.rack-num and enclosures.dencl-num fields. <LI>If enclosures.dencl-num is equal to 99, the enclosures array entry is not used. Note that the content of the enclosures.rack-num field is undefined in this case. <LI>If enclosures.dencl-num is greater than 99, the HSV110 controller does not have proof of the current location but the last known location is indicated by the content of the enclosures.rack-num and enclosures.dencl-num fields. Subtract 100 from the content of those fields to determine the actual last known location. If there have been no configuration changes, the last known location values will be accurate. </UL>Note that the content of the enclosures.rack-num field will not be valid until a future release."
           --#TYPE      "StorageCell Event"
           --#SUMMARY   "SCellName-TimeDate %s : SWCID %d : ECode: %d : CAC %d : EIP %d."
           --#ARGUMENTS {0,1,2,3,4,}
           --#SEVERITY  MINOR
           --#TIMEINDEX 136
           --#STATE     WARNING
        ::= 13603419
 
   sCellEventTrap-d-5f TRAP-TYPE  -- CAC Code: 87
        ENTERPRISE compaq
        VARIABLES  { scellNameDateTime,
                     scellSWComponent,
                     scellECode,
                     scellCAC,
                     scellEIP}
        DESCRIPTION
             "Severity: Critical -- failure or failure imminent. The average temperature of two of the three temperature sensor groups (i.e., Drive Enclosure Environmental Monitoring Unit, Disk Drives, and Power Supplies) exceeds the CRITICAL level. The operational power supply(s) will automatically shut down after a short period of time, thereby disabling the drive enclosure. This condition remains active until either the problem is corrected, or the operational power supply(s) shut down, whichever occurs first. The handle field contains the WWN of the drive enclosure containing the Drive Enclosure Environmental Monitoring Unit. This problem was detected by the Drive Enclosure Environmental Monitoring Unit located in the drive enclosure determined by the content of the dencl-num field as follows: <UL><LI>If dencl-num is less than 99, the location is as indicated by the content of the rack-num and dencl-num fields. <LI>If dencl-num is equal to 99, the location is unknown. Note that the content of the rack-num field is undefined in this case. <LI>If dencl-num is greater than 99, the HSV110 controller does not have proof of the current location but the last known location is indicated by the content of the rack-num and dencl-num fields. Subtract 100 from the content of those fields to determine the actual last known location. If there have been no configuration changes, the last known location values will be accurate. </UL>Note that the content of the rack-num field will not be valid until a future release. Note that in this case the content of the alarm-error-code.field.en field is undefined. <P> The actual temperature threshold values can be found in the HSV element manager GUI. The enclosures array shows the drive enclosures available on the Fibre Channel loop pair (0 = Loop A, 1 = Loop B) identified in the loop field. The location of an available drive enclosure is determined by the content of the enclosures.dencl-num field as follows: <UL><LI>If enclosures.dencl-num is less than 99, the location is as indicated by the content of the enclosures.rack-num and enclosures.dencl-num fields. <LI>If enclosures.dencl-num is equal to 99, the enclosures array entry is not used. Note that the content of the enclosures.rack-num field is undefined in this case. <LI>If enclosures.dencl-num is greater than 99, the HSV110 controller does not have proof of the current location but the last known location is indicated by the content of the enclosures.rack-num and enclosures.dencl-num fields. Subtract 100 from the content of those fields to determine the actual last known location. If there have been no configuration changes, the last known location values will be accurate. </UL>Note that the content of the enclosures.rack-num field will not be valid until a future release."
           --#TYPE      "StorageCell Event"
           --#SUMMARY   "SCellName-TimeDate %s : SWCID %d : ECode: %d : CAC %d : EIP %d."
           --#ARGUMENTS {0,1,2,3,4,}
           --#SEVERITY  CRITICAL
           --#TIMEINDEX 136
           --#STATE     WARNING
        ::= 13603423
 
   sCellEventTrap-d-6f TRAP-TYPE  -- CAC Code: 88
        ENTERPRISE compaq
        VARIABLES  { scellNameDateTime,
                     scellSWComponent,
                     scellECode,
                     scellCAC,
                     scellEIP}
        DESCRIPTION
             "Severity: Warning -- not failed but attention recommended or required. An internal Drive Enclosure Environmental Monitoring Unit error has occurred. The handle field contains the WWN of the drive enclosure containing the Drive Enclosure Environmental Monitoring Unit. This problem was detected by the Drive Enclosure Environmental Monitoring Unit located in the drive enclosure determined by the content of the dencl-num field as follows: <UL><LI>If dencl-num is less than 99, the location is as indicated by the content of the rack-num and dencl-num fields. <LI>If dencl-num is equal to 99, the location is unknown. Note that the content of the rack-num field is undefined in this case. <LI>If dencl-num is greater than 99, the HSV110 controller does not have proof of the current location but the last known location is indicated by the content of the rack-num and dencl-num fields. Subtract 100 from the content of those fields to determine the actual last known location. If there have been no configuration changes, the last known location values will be accurate. </UL>Note that the content of the rack-num field will not be valid until a future release. The alarm-error-code.field.en field contains the value 1 signifying that the Drive Enclosure Environmental Monitoring Unit is the affected element. The cause of the improper operation is described by the content of the alarm-error-code.field.ec field as follows: <UL><LI>1 = An internal Drive Enclosure Environmental Monitoring Unit clock error has occurred. <LI>2 = The Inter-IC (I2C) bus is not processing data and the Drive Enclosure Environmental Monitoring Unit is unable to monitor or report the status of the elements or enclosures. <LI>5 = A Backplane NVRAM error has occurred. </UL><P> The enclosures array shows the drive enclosures available on the Fibre Channel loop pair (0 = Loop A, 1 = Loop B) identified in the loop field. The location of an available drive enclosure is determined by the content of the enclosures.dencl-num field as follows: <UL><LI>If enclosures.dencl-num is less than 99, the location is as indicated by the content of the enclosures.rack-num and enclosures.dencl-num fields. <LI>If enclosures.dencl-num is equal to 99, the enclosures array entry is not used. Note that the content of the enclosures.rack-num field is undefined in this case. <LI>If enclosures.dencl-num is greater than 99, the HSV110 controller does not have proof of the current location but the last known location is indicated by the content of the enclosures.rack-num and enclosures.dencl-num fields. Subtract 100 from the content of those fields to determine the actual last known location. If there have been no configuration changes, the last known location values will be accurate. </UL>Note that the content of the enclosures.rack-num field will not be valid until a future release."
           --#TYPE      "StorageCell Event"
           --#SUMMARY   "SCellName-TimeDate %s : SWCID %d : ECode: %d : CAC %d : EIP %d."
           --#ARGUMENTS {0,1,2,3,4,}
           --#SEVERITY  MINOR
           --#TIMEINDEX 136
           --#STATE     WARNING
        ::= 13603439
 
   sCellEventTrap-d-71 TRAP-TYPE  -- CAC Code: 0
        ENTERPRISE compaq
        VARIABLES  { scellNameDateTime,
                     scellSWComponent,
                     scellECode,
                     scellCAC,
                     scellEIP}
        DESCRIPTION
             "Severity: Normal -- informational in nature. An internal Drive Enclosure Environmental Monitoring Unit error has occurred. The handle field contains the WWN of the drive enclosure containing the Drive Enclosure Environmental Monitoring Unit. This problem was detected by the Drive Enclosure Environmental Monitoring Unit located in the drive enclosure determined by the content of the dencl-num field as follows: <UL><LI>If dencl-num is less than 99, the location is as indicated by the content of the rack-num and dencl-num fields. <LI>If dencl-num is equal to 99, the location is unknown. Note that the content of the rack-num field is undefined in this case. <LI>If dencl-num is greater than 99, the HSV110 controller does not have proof of the current location but the last known location is indicated by the content of the rack-num and dencl-num fields. Subtract 100 from the content of those fields to determine the actual last known location. If there have been no configuration changes, the last known location values will be accurate. </UL>Note that the content of the rack-num field will not be valid until a future release. The alarm-error-code.field.en field contains the value 1 signifying that the Drive Enclosure Environmental Monitoring Unit is the affected element. The cause of the improper operation is described by the content of the alarm-error-code.field.ec field as follows: <UL><LI>3 = A drive enclosure power supply was shut down. <LI>16 = The Drive Enclosure Environmental Monitoring Unit ESI data has been corrupted. </UL><P> The enclosures array shows the drive enclosures available on the Fibre Channel loop pair (0 = Loop A, 1 = Loop B) identified in the loop field. The location of an available drive enclosure is determined by the content of the enclosures.dencl-num field as follows: <UL><LI>If enclosures.dencl-num is less than 99, the location is as indicated by the content of the enclosures.rack-num and enclosures.dencl-num fields. <LI>If enclosures.dencl-num is equal to 99, the enclosures array entry is not used. Note that the content of the enclosures.rack-num field is undefined in this case. <LI>If enclosures.dencl-num is greater than 99, the HSV110 controller does not have proof of the current location but the last known location is indicated by the content of the enclosures.rack-num and enclosures.dencl-num fields. Subtract 100 from the content of those fields to determine the actual last known location. If there have been no configuration changes, the last known location values will be accurate. </UL>Note that the content of the enclosures.rack-num field will not be valid until a future release."
           --#TYPE      "StorageCell Event"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13603441
 
   sCellEventTrap-d-72 TRAP-TYPE  -- CAC Code: 8a
        ENTERPRISE compaq
        VARIABLES  { scellNameDateTime,
                     scellSWComponent,
                     scellECode,
                     scellCAC,
                     scellEIP}
        DESCRIPTION
             "Severity: Warning -- not failed but attention recommended or required. A Drive Enclosure Environmental Monitoring Unit is unable to collect data for the SCSI-3 Enclosure Services (SES) page. The handle field contains the WWN of the drive enclosure containing the Drive Enclosure Environmental Monitoring Unit. This problem was detected by the Drive Enclosure Environmental Monitoring Unit located in the drive enclosure determined by the content of the dencl-num field as follows: <UL><LI>If dencl-num is less than 99, the location is as indicated by the content of the rack-num and dencl-num fields. <LI>If dencl-num is equal to 99, the location is unknown. Note that the content of the rack-num field is undefined in this case. <LI>If dencl-num is greater than 99, the HSV110 controller does not have proof of the current location but the last known location is indicated by the content of the rack-num and dencl-num fields. Subtract 100 from the content of those fields to determine the actual last known location. If there have been no configuration changes, the last known location values will be accurate. </UL>Note that the content of the rack-num field will not be valid until a future release. The alarm-error-code.field.en field contains the value 1 signifying that the Drive Enclosure Environmental Monitoring Unit is the affected element. The enclosures array shows the drive enclosures available on the Fibre Channel loop pair (0 = Loop A, 1 = Loop B) identified in the loop field. The location of an available drive enclosure is determined by the content of the enclosures.dencl-num field as follows: <UL><LI>If enclosures.dencl-num is less than 99, the location is as indicated by the content of the enclosures.rack-num and enclosures.dencl-num fields. <LI>If enclosures.dencl-num is equal to 99, the enclosures array entry is not used. Note that the content of the enclosures.rack-num field is undefined in this case. <LI>If enclosures.dencl-num is greater than 99, the HSV110 controller does not have proof of the current location but the last known location is indicated by the content of the enclosures.rack-num and enclosures.dencl-num fields. Subtract 100 from the content of those fields to determine the actual last known location. If there have been no configuration changes, the last known location values will be accurate. </UL>Note that the content of the enclosures.rack-num field will not be valid until a future release."
           --#TYPE      "StorageCell Event"
           --#SUMMARY   "SCellName-TimeDate %s : SWCID %d : ECode: %d : CAC %d : EIP %d."
           --#ARGUMENTS {0,1,2,3,4,}
           --#SEVERITY  MINOR
           --#TIMEINDEX 136
           --#STATE     WARNING
        ::= 13603442
 
   sCellEventTrap-d-7e TRAP-TYPE  -- CAC Code: 8c
        ENTERPRISE compaq
        VARIABLES  { scellNameDateTime,
                     scellSWComponent,
                     scellECode,
                     scellCAC,
                     scellEIP}
        DESCRIPTION
             "Severity: Warning -- not failed but attention recommended or required. Invalid data was read from a Drive Enclosure Environmental Monitoring Unit NVRAM. The handle field contains the WWN of the drive enclosure containing the Drive Enclosure Environmental Monitoring Unit. This problem was detected by the Drive Enclosure Environmental Monitoring Unit located in the drive enclosure determined by the content of the dencl-num field as follows: <UL><LI>If dencl-num is less than 99, the location is as indicated by the content of the rack-num and dencl-num fields. <LI>If dencl-num is equal to 99, the location is unknown. Note that the content of the rack-num field is undefined in this case. <LI>If dencl-num is greater than 99, the HSV110 controller does not have proof of the current location but the last known location is indicated by the content of the rack-num and dencl-num fields. Subtract 100 from the content of those fields to determine the actual last known location. If there have been no configuration changes, the last known location values will be accurate. </UL>Note that the content of the rack-num field will not be valid until a future release. The alarm-error-code.field.en field contains the value 1 signifying that the Drive Enclosure Environmental Monitoring Unit is the affected element. The enclosures array shows the drive enclosures available on the Fibre Channel loop pair (0 = Loop A, 1 = Loop B) identified in the loop field. The location of an available drive enclosure is determined by the content of the enclosures.dencl-num field as follows: <UL><LI>If enclosures.dencl-num is less than 99, the location is as indicated by the content of the enclosures.rack-num and enclosures.dencl-num fields. <LI>If enclosures.dencl-num is equal to 99, the enclosures array entry is not used. Note that the content of the enclosures.rack-num field is undefined in this case. <LI>If enclosures.dencl-num is greater than 99, the HSV110 controller does not have proof of the current location but the last known location is indicated by the content of the enclosures.rack-num and enclosures.dencl-num fields. Subtract 100 from the content of those fields to determine the actual last known location. If there have been no configuration changes, the last known location values will be accurate. </UL>Note that the content of the enclosures.rack-num field will not be valid until a future release."
           --#TYPE      "StorageCell Event"
           --#SUMMARY   "SCellName-TimeDate %s : SWCID %d : ECode: %d : CAC %d : EIP %d."
           --#ARGUMENTS {0,1,2,3,4,}
           --#SEVERITY  MINOR
           --#TIMEINDEX 136
           --#STATE     WARNING
        ::= 13603454
 
   sCellEventTrap-d-7f TRAP-TYPE  -- CAC Code: 8b
        ENTERPRISE compaq
        VARIABLES  { scellNameDateTime,
                     scellSWComponent,
                     scellECode,
                     scellCAC,
                     scellEIP}
        DESCRIPTION
             "Severity: Warning -- not failed but attention recommended or required. An internal Drive Enclosure Environmental Monitoring Unit error has occurred. The handle field contains the WWN of the drive enclosure containing the Drive Enclosure Environmental Monitoring Unit. This problem was detected by the Drive Enclosure Environmental Monitoring Unit located in the drive enclosure determined by the content of the dencl-num field as follows: <UL><LI>If dencl-num is less than 99, the location is as indicated by the content of the rack-num and dencl-num fields. <LI>If dencl-num is equal to 99, the location is unknown. Note that the content of the rack-num field is undefined in this case. <LI>If dencl-num is greater than 99, the HSV110 controller does not have proof of the current location but the last known location is indicated by the content of the rack-num and dencl-num fields. Subtract 100 from the content of those fields to determine the actual last known location. If there have been no configuration changes, the last known location values will be accurate. </UL>Note that the content of the rack-num field will not be valid until a future release. The alarm-error-code.field.en field contains the value 1 signifying that the Drive Enclosure Environmental Monitoring Unit is the affected element. The cause of the improper operation is described by the content of the alarm-error-code.field.ec field as follows: <UL><LI>11 = The Drive Enclosure Environmental Monitoring Unit cannot write data to the NVRAM. <LI>12 = The Drive Enclosure Environmental Monitoring Unit cannot read data from the NVRAM. <LI>13 = The Field Programmable Gate Array (FPGA) that controls the ESI bus failed to load information required for Drive Enclosure Environmental Monitoring Unit operation. </UL><P> The enclosures array shows the drive enclosures available on the Fibre Channel loop pair (0 = Loop A, 1 = Loop B) identified in the loop field. The location of an available drive enclosure is determined by the content of the enclosures.dencl-num field as follows: <UL><LI>If enclosures.dencl-num is less than 99, the location is as indicated by the content of the enclosures.rack-num and enclosures.dencl-num fields. <LI>If enclosures.dencl-num is equal to 99, the enclosures array entry is not used. Note that the content of the enclosures.rack-num field is undefined in this case. <LI>If enclosures.dencl-num is greater than 99, the HSV110 controller does not have proof of the current location but the last known location is indicated by the content of the enclosures.rack-num and enclosures.dencl-num fields. Subtract 100 from the content of those fields to determine the actual last known location. If there have been no configuration changes, the last known location values will be accurate. </UL>Note that the content of the enclosures.rack-num field will not be valid until a future release."
           --#TYPE      "StorageCell Event"
           --#SUMMARY   "SCellName-TimeDate %s : SWCID %d : ECode: %d : CAC %d : EIP %d."
           --#ARGUMENTS {0,1,2,3,4,}
           --#SEVERITY  MINOR
           --#TIMEINDEX 136
           --#STATE     WARNING
        ::= 13603455
 
   sCellEventTrap-d-82 TRAP-TYPE  -- CAC Code: 8e
        ENTERPRISE compaq
        VARIABLES  { scellNameDateTime,
                     scellSWComponent,
                     scellECode,
                     scellCAC,
                     scellEIP}
        DESCRIPTION
             "Severity: Warning -- not failed but attention recommended or required. A drive enclosure's address is incorrect or the enclosure has no address. The handle field contains the WWN of the drive enclosure containing the Drive Enclosure Environmental Monitoring Unit. This problem was detected by the Drive Enclosure Environmental Monitoring Unit located in the drive enclosure determined by the content of the dencl-num field as follows: <UL><LI>If dencl-num is less than 99, the location is as indicated by the content of the rack-num and dencl-num fields. <LI>If dencl-num is equal to 99, the location is unknown. Note that the content of the rack-num field is undefined in this case. <LI>If dencl-num is greater than 99, the HSV110 controller does not have proof of the current location but the last known location is indicated by the content of the rack-num and dencl-num fields. Subtract 100 from the content of those fields to determine the actual last known location. If there have been no configuration changes, the last known location values will be accurate. </UL>Note that the content of the rack-num field will not be valid until a future release. The alarm-error-code.field.en field contains the value 1 signifying that the Drive Enclosure Environmental Monitoring Unit is the affected element. The enclosures array shows the drive enclosures available on the Fibre Channel loop pair (0 = Loop A, 1 = Loop B) identified in the loop field. The location of an available drive enclosure is determined by the content of the enclosures.dencl-num field as follows: <UL><LI>If enclosures.dencl-num is less than 99, the location is as indicated by the content of the enclosures.rack-num and enclosures.dencl-num fields. <LI>If enclosures.dencl-num is equal to 99, the enclosures array entry is not used. Note that the content of the enclosures.rack-num field is undefined in this case. <LI>If enclosures.dencl-num is greater than 99, the HSV110 controller does not have proof of the current location but the last known location is indicated by the content of the enclosures.rack-num and enclosures.dencl-num fields. Subtract 100 from the content of those fields to determine the actual last known location. If there have been no configuration changes, the last known location values will be accurate. </UL>Note that the content of the enclosures.rack-num field will not be valid until a future release."
           --#TYPE      "StorageCell Event"
           --#SUMMARY   "SCellName-TimeDate %s : SWCID %d : ECode: %d : CAC %d : EIP %d."
           --#ARGUMENTS {0,1,2,3,4,}
           --#SEVERITY  MINOR
           --#TIMEINDEX 136
           --#STATE     WARNING
        ::= 13603458
 
   sCellEventTrap-d-83 TRAP-TYPE  -- CAC Code: 89
        ENTERPRISE compaq
        VARIABLES  { scellNameDateTime,
                     scellSWComponent,
                     scellECode,
                     scellCAC,
                     scellEIP}
        DESCRIPTION
             "Severity: Critical -- failure or failure imminent. A Drive Enclosure Environmental Monitoring Unit has experienced a hardware failure. The handle field contains the WWN of the drive enclosure containing the Drive Enclosure Environmental Monitoring Unit. This problem was detected by the Drive Enclosure Environmental Monitoring Unit located in the drive enclosure determined by the content of the dencl-num field as follows: <UL><LI>If dencl-num is less than 99, the location is as indicated by the content of the rack-num and dencl-num fields. <LI>If dencl-num is equal to 99, the location is unknown. Note that the content of the rack-num field is undefined in this case. <LI>If dencl-num is greater than 99, the HSV110 controller does not have proof of the current location but the last known location is indicated by the content of the rack-num and dencl-num fields. Subtract 100 from the content of those fields to determine the actual last known location. If there have been no configuration changes, the last known location values will be accurate. </UL>Note that the content of the rack-num field will not be valid until a future release. The alarm-error-code.field.en field contains the value 1 signifying that the Drive Enclosure Environmental Monitoring Unit is the affected element. The enclosures array shows the drive enclosures available on the Fibre Channel loop pair (0 = Loop A, 1 = Loop B) identified in the loop field. The The location of an available drive enclosure is determined by the content of the enclosures.dencl-num field as follows: <UL><LI>If enclosures.dencl-num is less than 99, the location is as indicated by the content of the enclosures.rack-num and enclosures.dencl-num fields. <LI>If enclosures.dencl-num is equal to 99, the enclosures array entry is not used. Note that the content of the enclosures.rack-num field is undefined in this case. <LI>If enclosures.dencl-num is greater than 99, the HSV110 controller does not have proof of the current location but the last known location is indicated by the content of the enclosures.rack-num and enclosures.dencl-num fields. Subtract 100 from the content of those fields to determine the actual last known location. If there have been no configuration changes, the last known location values will be accurate. </UL>Note that the content of the enclosures.rack-num field will not be valid until a future release. The cause of the improper operation is described by the content of the alarm-error-code.field.ec field as follows: <UL><LI>15 = Drive Enclosure Environmental Monitoring Unit hardware failure DP. <LI>18 = Drive Enclosure Environmental Monitoring Unit hardware failed BT. <LI>19 = Drive Enclosure Environmental Monitoring Unit ESI driver failure. </UL>"
           --#TYPE      "StorageCell Event"
           --#SUMMARY   "SCellName-TimeDate %s : SWCID %d : ECode: %d : CAC %d : EIP %d."
           --#ARGUMENTS {0,1,2,3,4,}
           --#SEVERITY  CRITICAL
           --#TIMEINDEX 136
           --#STATE     WARNING
        ::= 13603459
 
   sCellEventTrap-d-85 TRAP-TYPE  -- CAC Code: 8f
        ENTERPRISE compaq
        VARIABLES  { scellNameDateTime,
                     scellSWComponent,
                     scellECode,
                     scellCAC,
                     scellEIP}
        DESCRIPTION
             "Severity: Warning -- not failed but attention recommended or required. A drive enclosure power supply failed to respond to a shut down command. The handle field contains the WWN of the drive enclosure containing the Drive Enclosure Environmental Monitoring Unit. This problem was detected by the Drive Enclosure Environmental Monitoring Unit located in the drive enclosure determined by the content of the dencl-num field as follows: <UL><LI>If dencl-num is less than 99, the location is as indicated by the content of the rack-num and dencl-num fields. <LI>If dencl-num is equal to 99, the location is unknown. Note that the content of the rack-num field is undefined in this case. <LI>If dencl-num is greater than 99, the HSV110 controller does not have proof of the current location but the last known location is indicated by the content of the rack-num and dencl-num fields. Subtract 100 from the content of those fields to determine the actual last known location. If there have been no configuration changes, the last known location values will be accurate. </UL>Note that the content of the rack-num field will not be valid until a future release. The alarm-error-code.field.en field contains the value 1 signifying that the Drive Enclosure Environmental Monitoring Unit is the affected element. The enclosures array shows the drive enclosures available on the Fibre Channel loop pair (0 = Loop A, 1 = Loop B) identified in the loop field. The location of an available drive enclosure is determined by the content of the enclosures.dencl-num field as follows: <UL><LI>If enclosures.dencl-num is less than 99, the location is as indicated by the content of the enclosures.rack-num and enclosures.dencl-num fields. <LI>If enclosures.dencl-num is equal to 99, the enclosures array entry is not used. Note that the content of the enclosures.rack-num field is undefined in this case. <LI>If enclosures.dencl-num is greater than 99, the HSV110 controller does not have proof of the current location but the last known location is indicated by the content of the enclosures.rack-num and enclosures.dencl-num fields. Subtract 100 from the content of those fields to determine the actual last known location. If there have been no configuration changes, the last known location values will be accurate. </UL>Note that the content of the enclosures.rack-num field will not be valid until a future release."
           --#TYPE      "StorageCell Event"
           --#SUMMARY   "SCellName-TimeDate %s : SWCID %d : ECode: %d : CAC %d : EIP %d."
           --#ARGUMENTS {0,1,2,3,4,}
           --#SEVERITY  MINOR
           --#TIMEINDEX 136
           --#STATE     WARNING
        ::= 13603461
 
   sCellEventTrap-d-8d TRAP-TYPE  -- CAC Code: 90
        ENTERPRISE compaq
        VARIABLES  { scellNameDateTime,
                     scellSWComponent,
                     scellECode,
                     scellCAC,
                     scellEIP}
        DESCRIPTION
             "Severity: Critical -- failure or failure imminent. A drive enclosure transceiver error has been detected. The handle field contains the WWN of the drive enclosure containing the Drive Enclosure Environmental Monitoring Unit. This problem was detected by the Drive Enclosure Environmental Monitoring Unit located in the drive enclosure determined by the content of the dencl-num field as follows: <UL><LI>If dencl-num is less than 99, the location is as indicated by the content of the rack-num and dencl-num fields. <LI>If dencl-num is equal to 99, the location is unknown. Note that the content of the rack-num field is undefined in this case. <LI>If dencl-num is greater than 99, the HSV110 controller does not have proof of the current location but the last known location is indicated by the content of the rack-num and dencl-num fields. Subtract 100 from the content of those fields to determine the actual last known location. If there have been no configuration changes, the last known location values will be accurate. </UL>Note that the content of the rack-num field will not be valid until a future release. The location of the transceiver (1 through 4) is identified in the alarm-error-code.field.en field as follows: <UL><LI>1 = Transceiver 01 <LI>2 = Transceiver 02 <LI>3 = Transceiver 03 <LI>4 = Transceiver 04 </UL><P> The transceiver error condition is described by the content of the alarm-error-code.field.ec field as follows: <UL><LI>1 = The transceivers on this link are not the same type or they are incompatible with the drive enclosure I/O module. This error prevents the controller from establishing a link with the enclosure drives and eliminates the enclosure dual-loop capability. <LI>2 = The transceiver can no longer detect a data signal. This error prevents the controller from transferring data on a loop and eliminates the enclosure dual-loop capability. <LI>3 = The system has detected an FC-AL bus fault involving a transceiver. This error prevents the controller from transferring data on a loop and eliminates the enclosure dual-loop capability. <LI>4 = The transceiver that was previously in this location has been removed. <LI>5 = The transceiver in the specified location has detected invalid Fibre Channel characters. </UL><P> The enclosures array shows the drive enclosures available on the Fibre Channel loop pair (0 = Loop A, 1 = Loop B) identified in the loop field. The location of an available drive enclosure is determined by the content of the enclosures.dencl-num field as follows: <UL><LI>If enclosures.dencl-num is less than 99, the location is as indicated by the content of the enclosures.rack-num and enclosures.dencl-num fields. <LI>If enclosures.dencl-num is equal to 99, the enclosures array entry is not used. Note that the content of the enclosures.rack-num field is undefined in this case. <LI>If enclosures.dencl-num is greater than 99, the HSV110 controller does not have proof of the current location but the last known location is indicated by the content of the enclosures.rack-num and enclosures.dencl-num fields. Subtract 100 from the content of those fields to determine the actual last known location. If there have been no configuration changes, the last known location values will be accurate. </UL>Note that the content of the enclosures.rack-num field will not be valid until a future release."
           --#TYPE      "StorageCell Event"
           --#SUMMARY   "SCellName-TimeDate %s : SWCID %d : ECode: %d : CAC %d : EIP %d."
           --#ARGUMENTS {0,1,2,3,4,}
           --#SEVERITY  CRITICAL
           --#TIMEINDEX 136
           --#STATE     WARNING
        ::= 13603469
 
   sCellEventTrap-d-a1 TRAP-TYPE  -- CAC Code: 81
        ENTERPRISE compaq
        VARIABLES  { scellNameDateTime,
                     scellSWComponent,
                     scellECode,
                     scellCAC,
                     scellEIP}
        DESCRIPTION
             "Severity: Critical -- failure or failure imminent. A drive enclosure power supply voltage sensor out of range condition has been reported. The handle field contains the WWN of the drive enclosure containing the Drive Enclosure Environmental Monitoring Unit. This problem was detected by the Drive Enclosure Environmental Monitoring Unit located in the drive enclosure determined by the content of the dencl-num field as follows: <UL><LI>If dencl-num is less than 99, the location is as indicated by the content of the rack-num and dencl-num fields. <LI>If dencl-num is equal to 99, the location is unknown. Note that the content of the rack-num field is undefined in this case. <LI>If dencl-num is greater than 99, the HSV110 controller does not have proof of the current location but the last known location is indicated by the content of the rack-num and dencl-num fields. Subtract 100 from the content of those fields to determine the actual last known location. If there have been no configuration changes, the last known location values will be accurate. </UL>Note that the content of the rack-num field will not be valid until a future release. The location of the voltage sensor (1 through 4) is identified in the alarm-error-code.field.en field as follows: <UL><LI>1 = Power Supply 1 +5 VDC <LI>2 = Power Supply 1 +12 VDC <LI>3 = Power Supply 2 +5 VDC <LI>4 = Power Supply 2 +12 VDC </UL><P> The voltage sensor out of range condition is described by the content of the alarm-error-code.field.ec field as follows: <UL><LI>1 = The element voltage is approaching, but has not reached, the high voltage CRITICAL threshold. Continued operation under these conditions may result in a CRITICAL condition. <LI>2 = The element voltage is above the high voltage CRITICAL threshold. <LI>3 = The element voltage is approaching, but has not reached, the low voltage CRITICAL threshold. Continued operation under these conditions may result in a CRITICAL condition. <LI>4 = The element voltage has reached the low voltage CRITICAL threshold. </UL><P> The enclosures array shows the drive enclosures available on the Fibre Channel loop pair (0 = Loop A, 1 = Loop B) identified in the loop field. The location of an available drive enclosure is determined by the content of the enclosures.dencl-num field as follows: <UL><LI>If enclosures.dencl-num is less than 99, the location is as indicated by the content of the enclosures.rack-num and enclosures.dencl-num fields. <LI>If enclosures.dencl-num is equal to 99, the enclosures array entry is not used. Note that the content of the enclosures.rack-num field is undefined in this case. <LI>If enclosures.dencl-num is greater than 99, the HSV110 controller does not have proof of the current location but the last known location is indicated by the content of the enclosures.rack-num and enclosures.dencl-num fields. Subtract 100 from the content of those fields to determine the actual last known location. If there have been no configuration changes, the last known location values will be accurate. </UL>Note that the content of the enclosures.rack-num field will not be valid until a future release."
           --#TYPE      "StorageCell Event"
           --#SUMMARY   "SCellName-TimeDate %s : SWCID %d : ECode: %d : CAC %d : EIP %d."
           --#ARGUMENTS {0,1,2,3,4,}
           --#SEVERITY  CRITICAL
           --#TIMEINDEX 136
           --#STATE     WARNING
        ::= 13603489
 
   sCellEventTrap-d-b5 TRAP-TYPE  -- CAC Code: 81
        ENTERPRISE compaq
        VARIABLES  { scellNameDateTime,
                     scellSWComponent,
                     scellECode,
                     scellCAC,
                     scellEIP}
        DESCRIPTION
             "Severity: Critical -- failure or failure imminent. A drive enclosure power supply current sensor out of range condition has been reported. The handle field contains the WWN of the drive enclosure containing the Drive Enclosure Environmental Monitoring Unit. This problem was detected by the Drive Enclosure Environmental Monitoring Unit located in the drive enclosure determined by the content of the dencl-num field as follows: <UL><LI>If dencl-num is less than 99, the location is as indicated by the content of the rack-num and dencl-num fields. <LI>If dencl-num is equal to 99, the location is unknown. Note that the content of the rack-num field is undefined in this case. <LI>If dencl-num is greater than 99, the HSV110 controller does not have proof of the current location but the last known location is indicated by the content of the rack-num and dencl-num fields. Subtract 100 from the content of those fields to determine the actual last known location. If there have been no configuration changes, the last known location values will be accurate. </UL>Note that the content of the rack-num field will not be valid until a future release. The location of the current sensor (1 through 4) is identified in the alarm-error-code.field.en field as follows: <UL><LI>1 = Power Supply 1 +5 VDC <LI>2 = Power Supply 1 +12 VDC <LI>3 = Power Supply 2 +5 VDC <LI>4 = Power Supply 2 +12 VDC </UL><P> The current sensor out of range condition is described by the content of the alarm-error-code.field.ec field as follows: <UL><LI>1 = The element current is approaching, but has not reached, the high current CRITICAL threshold. Continued operation under these conditions may result in a CRITICAL condition. <LI>2 = The element current is above the high current CRITICAL threshold. </UL><P> The enclosures array shows the drive enclosures available on the Fibre Channel loop pair (0 = Loop A, 1 = Loop B) identified in the loop field. The location of an available drive enclosure is determined by the content of the enclosures.dencl-num field as follows: <UL><LI>If enclosures.dencl-num is less than 99, the location is as indicated by the content of the enclosures.rack-num and enclosures.dencl-num fields. <LI>If enclosures.dencl-num is equal to 99, the enclosures array entry is not used. Note that the content of the enclosures.rack-num field is undefined in this case. <LI>If enclosures.dencl-num is greater than 99, the HSV110 controller does not have proof of the current location but the last known location is indicated by the content of the enclosures.rack-num and enclosures.dencl-num fields. Subtract 100 from the content of those fields to determine the actual last known location. If there have been no configuration changes, the last known location values will be accurate. </UL>Note that the content of the enclosures.rack-num field will not be valid until a future release."
           --#TYPE      "StorageCell Event"
           --#SUMMARY   "SCellName-TimeDate %s : SWCID %d : ECode: %d : CAC %d : EIP %d."
           --#ARGUMENTS {0,1,2,3,4,}
           --#SEVERITY  CRITICAL
           --#TIMEINDEX 136
           --#STATE     WARNING
        ::= 13603509
 
   sCellEventTrap-d-d8 TRAP-TYPE  -- CAC Code: 92
        ENTERPRISE compaq
        VARIABLES  { scellNameDateTime,
                     scellSWComponent,
                     scellECode,
                     scellCAC,
                     scellEIP}
        DESCRIPTION
             "Severity: Warning -- not failed but attention recommended or required. A drive enclosure backplane invalid NVRAM read error has occurred. The handle field contains the WWN of the drive enclosure containing the Drive Enclosure Environmental Monitoring Unit.This problem was detected by the Drive Enclosure Environmental Monitoring Unit located in the drive enclosure determined by the content of the dencl-num field as follows: <UL><LI>If dencl-num is less than 99, the location is as indicated by the content of the rack-num and dencl-num fields. <LI>If dencl-num is equal to 99, the location is unknown. Note that the content of the rack-num field is undefined in this case. <LI>If dencl-num is greater than 99, the HSV110 controller does not have proof of the current location but the last known location is indicated by the content of the rack-num and dencl-num fields. Subtract 100 from the content of those fields to determine the actual last known location. If there have been no configuration changes, the last known location values will be accurate. </UL>Note that the content of the rack-num field will not be valid until a future release. The alarm-error-code.field.en field contains the value 1 signifying that the drive enclosure is the affected element. The enclosures array shows the drive enclosures available on the Fibre Channel loop pair (0 = Loop A, 1 = Loop B) identified in the loop field. The The location of an available drive enclosure is determined by the content of the enclosures.dencl-num field as follows: <UL><LI>If enclosures.dencl-num is less than 99, the location is as indicated by the content of the enclosures.rack-num and enclosures.dencl-num fields. <LI>If enclosures.dencl-num is equal to 99, the enclosures array entry is not used. Note that the content of the enclosures.rack-num field is undefined in this case. <LI>If enclosures.dencl-num is greater than 99, the HSV110 controller does not have proof of the current location but the last known location is indicated by the content of the enclosures.rack-num and enclosures.dencl-num fields. Subtract 100 from the content of those fields to determine the actual last known location. If there have been no configuration changes, the last known location values will be accurate. </UL>Note that the content of the enclosures.rack-num field will not be valid until a future release."
           --#TYPE      "StorageCell Event"
           --#SUMMARY   "SCellName-TimeDate %s : SWCID %d : ECode: %d : CAC %d : EIP %d."
           --#ARGUMENTS {0,1,2,3,4,}
           --#SEVERITY  MINOR
           --#TIMEINDEX 136
           --#STATE     WARNING
        ::= 13603544
 
   sCellEventTrap-d-d9 TRAP-TYPE  -- CAC Code: 91
        ENTERPRISE compaq
        VARIABLES  { scellNameDateTime,
                     scellSWComponent,
                     scellECode,
                     scellCAC,
                     scellEIP}
        DESCRIPTION
             "Severity: Critical -- failure or failure imminent. A drive enclosure backplane error has occurred. The handle field contains the WWN of the drive enclosure containing the Drive Enclosure Environmental Monitoring Unit. This problem was detected by the Drive Enclosure Environmental Monitoring Unit located in the drive enclosure determined by the content of the dencl-num field as follows: <UL><LI>If dencl-num is less than 99, the location is as indicated by the content of the rack-num and dencl-num fields. <LI>If dencl-num is equal to 99, the location is unknown. Note that the content of the rack-num field is undefined in this case. <LI>If dencl-num is greater than 99, the HSV110 controller does not have proof of the current location but the last known location is indicated by the content of the rack-num and dencl-num fields. Subtract 100 from the content of those fields to determine the actual last known location. If there have been no configuration changes, the last known location values will be accurate. </UL>Note that the content of the rack-num field will not be valid until a future release. The alarm-error-code.field.en field contains the value 1 signifying that the drive enclosure is the affected element. The cause of the improper operation is described by the content of the alarm-error-code.field.ec field as follows: <UL><LI>11 = Unable to write data to the NVRAM. This problem prevents communication between elements in the enclosure. <LI>12 = Unable to read data from the NVRAM. This problem prevents communication between elements in the enclosure. <LI>13 = NVRAM has not been initialized properly. This is a manufacturing error. </UL><P> The enclosures array shows the drive enclosures available on the Fibre Channel loop pair (0 = Loop A, 1 = Loop B) identified in the loop field. The location of an available drive enclosure is determined by the content of the enclosures.dencl-num field as follows: <UL><LI>If enclosures.dencl-num is less than 99, the location is as indicated by the content of the enclosures.rack-num and enclosures.dencl-num fields. <LI>If enclosures.dencl-num is equal to 99, the enclosures array entry is not used. Note that the content of the enclosures.rack-num field is undefined in this case. <LI>If enclosures.dencl-num is greater than 99, the HSV110 controller does not have proof of the current location but the last known location is indicated by the content of the enclosures.rack-num and enclosures.dencl-num fields. Subtract 100 from the content of those fields to determine the actual last known location. If there have been no configuration changes, the last known location values will be accurate. </UL>Note that the content of the enclosures.rack-num field will not be valid until a future release."
           --#TYPE      "StorageCell Event"
           --#SUMMARY   "SCellName-TimeDate %s : SWCID %d : ECode: %d : CAC %d : EIP %d."
           --#ARGUMENTS {0,1,2,3,4,}
           --#SEVERITY  CRITICAL
           --#TIMEINDEX 136
           --#STATE     WARNING
        ::= 13603545
 
   sCellEventTrap-d-dd TRAP-TYPE  -- CAC Code: 93
        ENTERPRISE compaq
        VARIABLES  { scellNameDateTime,
                     scellSWComponent,
                     scellECode,
                     scellCAC,
                     scellEIP}
        DESCRIPTION
             "Severity: Critical -- failure or failure imminent. A drive enclosure I/O module error has occurred. The handle field contains the WWN of the drive enclosure containing the Drive Enclosure Environmental Monitoring Unit. This problem was detected by the Drive Enclosure Environmental Monitoring Unit located in the drive enclosure determined by the content of the dencl-num field as follows: <UL><LI>If dencl-num is less than 99, the location is as indicated by the content of the rack-num and dencl-num fields. <LI>If dencl-num is equal to 99, the location is unknown. Note that the content of the rack-num field is undefined in this case. <LI>If dencl-num is greater than 99, the HSV110 controller does not have proof of the current location but the last known location is indicated by the content of the rack-num and dencl-num fields. Subtract 100 from the content of those fields to determine the actual last known location. If there have been no configuration changes, the last known location values will be accurate. </UL>Note that the content of the rack-num field will not be valid until a future release. The location of the I/O module (A (01) and B (02)) is identified in the alarm-error-code.field.en field. The cause of the improper operation is described by the content of the alarm-error-code.field.ec field as follows: <UL><LI>1 = The I/O module's Fibre Channel link speed is not supported by the backplane. This error prevents the controller from establishing a link with enclosure drives and eliminates the enclosure dual-loop capability. <LI>11 = Unable to write data to the I/O module NVRAM. <LI>12 = Unable to read data from the I/O module NVRAM. <LI>13 = The I/O module that was in this location has been removed. </UL><P> The enclosures array shows the drive enclosures available on the Fibre Channel loop pair (0 = Loop A, 1 = Loop B) identified in the loop field. The location of an available drive enclosure is determined by the content of the enclosures.dencl-num field as follows: <UL><LI>If enclosures.dencl-num is less than 99, the location is as indicated by the content of the enclosures.rack-num and enclosures.dencl-num fields. <LI>If enclosures.dencl-num is equal to 99, the enclosures array entry is not used. Note that the content of the enclosures.rack-num field is undefined in this case. <LI>If enclosures.dencl-num is greater than 99, the HSV110 controller does not have proof of the current location but the last known location is indicated by the content of the enclosures.rack-num and enclosures.dencl-num fields. Subtract 100 from the content of those fields to determine the actual last known location. If there have been no configuration changes, the last known location values will be accurate. </UL>Note that the content of the enclosures.rack-num field will not be valid until a future release."
           --#TYPE      "StorageCell Event"
           --#SUMMARY   "SCellName-TimeDate %s : SWCID %d : ECode: %d : CAC %d : EIP %d."
           --#ARGUMENTS {0,1,2,3,4,}
           --#SEVERITY  CRITICAL
           --#TIMEINDEX 136
           --#STATE     WARNING
        ::= 13603549
 
   sCellEventTrap-d-de TRAP-TYPE  -- CAC Code: 95
        ENTERPRISE compaq
        VARIABLES  { scellNameDateTime,
                     scellSWComponent,
                     scellECode,
                     scellCAC,
                     scellEIP}
        DESCRIPTION
             "Severity: Warning -- not failed but attention recommended or required. A drive enclosure I/O module is unable to communicate with the Drive Enclosure Environmental Monitoring Unit. The handle field contains the WWN of the drive enclosure containing the Drive Enclosure Environmental Monitoring Unit. This problem was detected by the Drive Enclosure Environmental Monitoring Unit located in the drive enclosure determined by the content of the dencl-num field as follows: <UL><LI>If dencl-num is less than 99, the location is as indicated by the content of the rack-num and dencl-num fields. <LI>If dencl-num is equal to 99, the location is unknown. Note that the content of the rack-num field is undefined in this case. <LI>If dencl-num is greater than 99, the HSV110 controller does not have proof of the current location but the last known location is indicated by the content of the rack-num and dencl-num fields. Subtract 100 from the content of those fields to determine the actual last known location. If there have been no configuration changes, the last known location values will be accurate. </UL>Note that the content of the rack-num field will not be valid until a future release. The location of the I/O module (A (01) and B (02)) is identified in the alarm-error-code.field.en field. The enclosures array shows the drive enclosures available on the Fibre Channel loop pair (0 = Loop A, 1 = Loop B) identified in the loop field. The location of an available drive enclosure is determined by the content of the enclosures.dencl-num field as follows: <UL><LI>If enclosures.dencl-num is less than 99, the location is as indicated by the content of the enclosures.rack-num and enclosures.dencl-num fields. <LI>If enclosures.dencl-num is equal to 99, the enclosures array entry is not used. Note that the content of the enclosures.rack-num field is undefined in this case. <LI>If enclosures.dencl-num is greater than 99, the HSV110 controller does not have proof of the current location but the last known location is indicated by the content of the enclosures.rack-num and enclosures.dencl-num fields. Subtract 100 from the content of those fields to determine the actual last known location. If there have been no configuration changes, the last known location values will be accurate. </UL>Note that the content of the enclosures.rack-num field will not be valid until a future release."
           --#TYPE      "StorageCell Event"
           --#SUMMARY   "SCellName-TimeDate %s : SWCID %d : ECode: %d : CAC %d : EIP %d."
           --#ARGUMENTS {0,1,2,3,4,}
           --#SEVERITY  MINOR
           --#TIMEINDEX 136
           --#STATE     WARNING
        ::= 13603550
 
   sCellEventTrap-d-ec TRAP-TYPE  -- CAC Code: 94
        ENTERPRISE compaq
        VARIABLES  { scellNameDateTime,
                     scellSWComponent,
                     scellECode,
                     scellCAC,
                     scellEIP}
        DESCRIPTION
             "Severity: Warning -- not failed but attention recommended or required. A drive enclosure I/O module invalid NVRAM read error has occurred. The handle field contains the WWN of the drive enclosure containing the Drive Enclosure Environmental Monitoring Unit.This problem was detected by the Drive Enclosure Environmental Monitoring Unit located in the drive enclosure determined by the content of the dencl-num field as follows: <UL><LI>If dencl-num is less than 99, the location is as indicated by the content of the rack-num and dencl-num fields. <LI>If dencl-num is equal to 99, the location is unknown. Note that the content of the rack-num field is undefined in this case. <LI>If dencl-num is greater than 99, the HSV110 controller does not have proof of the current location but the last known location is indicated by the content of the rack-num and dencl-num fields. Subtract 100 from the content of those fields to determine the actual last known location. If there have been no configuration changes, the last known location values will be accurate. </UL>Note that the content of the rack-num field will not be valid until a future release. The location of the I/O module (A (01) or B (02)) is identified in the alarm-error-code.field.en field. The enclosures array shows the drive enclosures available on the Fibre Channel loop pair (0 = Loop A, 1 = Loop B) identified in the loop field. The location of an available drive enclosure is determined by the content of the enclosures.dencl-num field as follows: <UL><LI>If enclosures.dencl-num is less than 99, the location is as indicated by the content of the enclosures.rack-num and enclosures.dencl-num fields. <LI>If enclosures.dencl-num is equal to 99, the enclosures array entry is not used. Note that the content of the enclosures.rack-num field is undefined in this case. <LI>If enclosures.dencl-num is greater than 99, the HSV110 controller does not have proof of the current location but the last known location is indicated by the content of the enclosures.rack-num and enclosures.dencl-num fields. Subtract 100 from the content of those fields to determine the actual last known location. If there have been no configuration changes, the last known location values will be accurate. </UL>Note that the content of the enclosures.rack-num field will not be valid until a future release."
           --#TYPE      "StorageCell Event"
           --#SUMMARY   "SCellName-TimeDate %s : SWCID %d : ECode: %d : CAC %d : EIP %d."
           --#ARGUMENTS {0,1,2,3,4,}
           --#SEVERITY  MINOR
           --#TIMEINDEX 136
           --#STATE     WARNING
        ::= 13603564
 
   sCellEventTrap-d-f0 TRAP-TYPE  -- CAC Code: 0
        ENTERPRISE compaq
        VARIABLES  { scellNameDateTime,
                     scellSWComponent,
                     scellECode,
                     scellCAC,
                     scellEIP}
        DESCRIPTION
             "Severity: Normal -- informational in nature. The status has changed on one or more of the drive enclosures. This is an informational event triggered by the occurrence of a change in the status of a drive enclosure. This event is generated for the HSV element manager GUI and contains no user information. The content of the handle, alarm-error-code field, dencl-num, and rack-num fields have no meaning for this event. The enclosures array shows the drive enclosures available on the Fibre Channel loop pair (0 = Loop A, 1 = Loop B) identified in the loop field. The location of an available drive enclosure is determined by the content of the enclosures.dencl-num field as follows: <UL><LI>If enclosures.dencl-num is less than 99, the location is as indicated by the content of the enclosures.rack-num and enclosures.dencl-num fields. <LI>If enclosures.dencl-num is equal to 99, the enclosures array entry is not used. Note that the content of the enclosures.rack-num field is undefined in this case. <LI>If enclosures.dencl-num is greater than 99, the HSV110 controller does not have proof of the current location but the last known location is indicated by the content of the enclosures.rack-num and enclosures.dencl-num fields. Subtract 100 from the content of those fields to determine the actual last known location. If there have been no configuration changes, the last known location values will be accurate. </UL>Note that the content of the enclosures.rack-num field will not be valid until a future release."
           --#TYPE      "StorageCell Event"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13603568
 
   sCellEventTrap-42-0 TRAP-TYPE  -- CAC Code: 0
        ENTERPRISE compaq
        VARIABLES  { scellNameDateTime,
                     scellSWComponent,
                     scellECode,
                     scellCAC,
                     scellEIP}
        DESCRIPTION
             "Severity: Normal -- informational in nature. Indicated Host Fibre Channel port transitioned to link down."
           --#TYPE      "StorageCell Event"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13616896
 
   sCellEventTrap-42-1 TRAP-TYPE  -- CAC Code: 0
        ENTERPRISE compaq
        VARIABLES  { scellNameDateTime,
                     scellSWComponent,
                     scellECode,
                     scellCAC,
                     scellEIP}
        DESCRIPTION
             "Severity: Normal -- informational in nature. Indicated Host Fibre Channel port transitioned to link failed."
           --#TYPE      "StorageCell Event"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13616897
 
   sCellEventTrap-42-3 TRAP-TYPE  -- CAC Code: 0
        ENTERPRISE compaq
        VARIABLES  { scellNameDateTime,
                     scellSWComponent,
                     scellECode,
                     scellCAC,
                     scellEIP}
        DESCRIPTION
             "Severity: Normal -- informational in nature. An excessive number of link errors were detected on a HSV110 controller's Fibre Channel port. The identity of the affected Fibre Channel port is contained in the cerp-id field. The HSV110 controller internal Fibre Channel port number of the affected Fibre Channel port is contained in the port field. This is an informational event triggered by the occurrence of an excessive number of Tachyon chip link status errors detected within a particular link status error type. The number of occurrences of each link status error type is contained in a separate type-specific field (e.g., loss-of-signal, bad-rx-char, etc.). The HSV110 controller checks each of its Fibre Channel port's for excessive link status errors periodically."
           --#TYPE      "StorageCell Event"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13616899
 
   sCellEventTrap-42-4 TRAP-TYPE  -- CAC Code: 4a
        ENTERPRISE compaq
        VARIABLES  { scellNameDateTime,
                     scellSWComponent,
                     scellECode,
                     scellCAC,
                     scellEIP}
        DESCRIPTION
             "Severity: Warning -- not failed but attention recommended or required. A Fibre Channel port on the HSV110 controller has failed to respond. The identity of the affected Fibre Channel port is contained in the cerp-id field. The HSV110 controller internal Fibre Channel port number of the affected Fibre Channel port is contained in the port field. The peb array contains the port event block information. The peq-frz-prod-index field contains the index to the port event block in use when the Tachyon chip entered the frozen state. The peq-prod-index field contains the index to the next port event block. The peq-cons-index field contains the index to the next port event block to be acted upon."
           --#TYPE      "StorageCell Event"
           --#SUMMARY   "SCellName-TimeDate %s : SWCID %d : ECode: %d : CAC %d : EIP %d."
           --#ARGUMENTS {0,1,2,3,4,}
           --#SEVERITY  MINOR
           --#TIMEINDEX 136
           --#STATE     WARNING
        ::= 13616900
 
   sCellEventTrap-42-5 TRAP-TYPE  -- CAC Code: 0
        ENTERPRISE compaq
        VARIABLES  { scellNameDateTime,
                     scellSWComponent,
                     scellECode,
                     scellCAC,
                     scellEIP}
        DESCRIPTION
             "Severity: Normal -- informational in nature. Indicated Host Fibre Channel port transitioned to link wedged."
           --#TYPE      "StorageCell Event"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13616901
 
   sCellEventTrap-83-0 TRAP-TYPE  -- CAC Code: 20
        ENTERPRISE compaq
        VARIABLES  { scellNameDateTime,
                     scellSWComponent,
                     scellECode,
                     scellCAC,
                     scellEIP}
        DESCRIPTION
             "Severity: Critical -- failure or failure imminent. A failure was detected during the execution of this HSV110 controller's on board diagnostics."
           --#TYPE      "StorageCell Event"
           --#SUMMARY   "SCellName-TimeDate %s : SWCID %d : ECode: %d : CAC %d : EIP %d."
           --#ARGUMENTS {0,1,2,3,4,}
           --#SEVERITY  CRITICAL
           --#TIMEINDEX 136
           --#STATE     WARNING
        ::= 13633536
 
   sCellEventTrap-83-1 TRAP-TYPE  -- CAC Code: 30
        ENTERPRISE compaq
        VARIABLES  { scellNameDateTime,
                     scellSWComponent,
                     scellECode,
                     scellCAC,
                     scellEIP}
        DESCRIPTION
             "Severity: Warning -- not failed but attention recommended or required. A GBIC SFF Serial ID Data check code failure was detected during the execution of this HSV110 controller's on board diagnostics."
           --#TYPE      "StorageCell Event"
           --#SUMMARY   "SCellName-TimeDate %s : SWCID %d : ECode: %d : CAC %d : EIP %d."
           --#ARGUMENTS {0,1,2,3,4,}
           --#SEVERITY  MINOR
           --#TIMEINDEX 136
           --#STATE     WARNING
        ::= 13633537
 
   sCellEventTrap-83-2 TRAP-TYPE  -- CAC Code: 22
        ENTERPRISE compaq
        VARIABLES  { scellNameDateTime,
                     scellSWComponent,
                     scellECode,
                     scellCAC,
                     scellEIP}
        DESCRIPTION
             "Severity: Critical -- failure or failure imminent. A battery assembly failure was detected during the execution of this HSV110 controller's on board diagnostics."
           --#TYPE      "StorageCell Event"
           --#SUMMARY   "SCellName-TimeDate %s : SWCID %d : ECode: %d : CAC %d : EIP %d."
           --#ARGUMENTS {0,1,2,3,4,}
           --#SEVERITY  CRITICAL
           --#TIMEINDEX 136
           --#STATE     WARNING
        ::= 13633538
 
   sCellEventTrap-83-3 TRAP-TYPE  -- CAC Code: 23
        ENTERPRISE compaq
        VARIABLES  { scellNameDateTime,
                     scellSWComponent,
                     scellECode,
                     scellCAC,
                     scellEIP}
        DESCRIPTION
             "Severity: Critical -- failure or failure imminent. A battery assembly failure was detected during the execution of this HSV110 controller's on board diagnostics."
           --#TYPE      "StorageCell Event"
           --#SUMMARY   "SCellName-TimeDate %s : SWCID %d : ECode: %d : CAC %d : EIP %d."
           --#ARGUMENTS {0,1,2,3,4,}
           --#SEVERITY  CRITICAL
           --#TIMEINDEX 136
           --#STATE     WARNING
        ::= 13633539
 
   sCellEventTrap-83-4 TRAP-TYPE  -- CAC Code: 31
        ENTERPRISE compaq
        VARIABLES  { scellNameDateTime,
                     scellSWComponent,
                     scellECode,
                     scellCAC,
                     scellEIP}
        DESCRIPTION
             "Severity: Critical -- failure or failure imminent. A battery assembly communication failure was detected during the execution of this HSV110 controller's on board diagnostics."
           --#TYPE      "StorageCell Event"
           --#SUMMARY   "SCellName-TimeDate %s : SWCID %d : ECode: %d : CAC %d : EIP %d."
           --#ARGUMENTS {0,1,2,3,4,}
           --#SEVERITY  CRITICAL
           --#TIMEINDEX 136
           --#STATE     WARNING
        ::= 13633540
 
   sCellEventTrap-83-5 TRAP-TYPE  -- CAC Code: 32
        ENTERPRISE compaq
        VARIABLES  { scellNameDateTime,
                     scellSWComponent,
                     scellECode,
                     scellCAC,
                     scellEIP}
        DESCRIPTION
             "Severity: Critical -- failure or failure imminent. A battery assembly communication failure was detected during the execution of this HSV110 controller's on board diagnostics."
           --#TYPE      "StorageCell Event"
           --#SUMMARY   "SCellName-TimeDate %s : SWCID %d : ECode: %d : CAC %d : EIP %d."
           --#ARGUMENTS {0,1,2,3,4,}
           --#SEVERITY  CRITICAL
           --#TIMEINDEX 136
           --#STATE     WARNING
        ::= 13633541
 
   sCellEventTrap-83-6 TRAP-TYPE  -- CAC Code: 33
        ENTERPRISE compaq
        VARIABLES  { scellNameDateTime,
                     scellSWComponent,
                     scellECode,
                     scellCAC,
                     scellEIP}
        DESCRIPTION
             "Severity: Critical -- failure or failure imminent. A soft cache memory ECC error or indication of low battery voltage was detected during the execution of this HSV110 controller's on board diagnostics."
           --#TYPE      "StorageCell Event"
           --#SUMMARY   "SCellName-TimeDate %s : SWCID %d : ECode: %d : CAC %d : EIP %d."
           --#ARGUMENTS {0,1,2,3,4,}
           --#SEVERITY  CRITICAL
           --#TIMEINDEX 136
           --#STATE     WARNING
        ::= 13633542
 
-- Following are the traps defined for the HSV Management Agent
-- The trap name is constructed from the unique status code for
-- the Management Event.  This numbers is represented as 
-- a decimal number.
-- For example: mngmtAgentTrap-5009   has: 
--   Status Code of 5009
 
-- The Trap number is calculated by using the status code + a base
-- In our example above: mngmtAgentTrap-5009 the trap number is -
-- Base = 136000000  (which preserves our unique OID sub-identifier of 136) +
--        + status code 5009 =  136005009
-- This allows for a large number of uniquely mapped events and
-- avoids trap number collisions with StorageCell Event traps.
 
 
   mngmtAgentTrap-1 TRAP-TYPE
        ENTERPRISE compaq
        VARIABLES  { hostName,
                     scellNameDateTime,
                     agentEventCode,
                     agentEventDescription }
        DESCRIPTION
             "Object Already Exists"
           --#TYPE      "Management Agent Event"
           --#SUMMARY   "Host %s : SCellName-TimeDate %s : EventCode %d : Description %s"
           --#ARGUMENTS {0,1,2,3,}
            --#SEVERITY  INFORMATIONAL
            --#TIMEINDEX 136
        ::= 136000001
 
   mngmtAgentTrap-2 TRAP-TYPE
        ENTERPRISE compaq
        VARIABLES  { hostName,
                     scellNameDateTime,
                     agentEventCode,
                     agentEventDescription }
        DESCRIPTION
             "Supplied Buffer Too Small"
           --#TYPE      "Management Agent Event"
           --#SUMMARY   "Host %s : SCellName-TimeDate %s : EventCode %d : Description %s"
           --#ARGUMENTS {0,1,2,3,}
            --#SEVERITY  INFORMATIONAL
            --#TIMEINDEX 136
        ::= 136000002
 
   mngmtAgentTrap-3 TRAP-TYPE
        ENTERPRISE compaq
        VARIABLES  { hostName,
                     scellNameDateTime,
                     agentEventCode,
                     agentEventDescription }
        DESCRIPTION
             "Object Already Assigned"
           --#TYPE      "Management Agent Event"
           --#SUMMARY   "Host %s : SCellName-TimeDate %s : EventCode %d : Description %s"
           --#ARGUMENTS {0,1,2,3,}
            --#SEVERITY  INFORMATIONAL
            --#TIMEINDEX 136
        ::= 136000003
 
   mngmtAgentTrap-4 TRAP-TYPE
        ENTERPRISE compaq
        VARIABLES  { hostName,
                     scellNameDateTime,
                     agentEventCode,
                     agentEventDescription }
        DESCRIPTION
             "Insufficient Available Data Storage"
           --#TYPE      "Management Agent Event"
           --#SUMMARY   "Host %s : SCellName-TimeDate %s : EventCode %d : Description %s"
           --#ARGUMENTS {0,1,2,3,}
            --#SEVERITY  CRITICAL
            --#TIMEINDEX 136
        ::= 136000004
 
   mngmtAgentTrap-5 TRAP-TYPE
        ENTERPRISE compaq
        VARIABLES  { hostName,
                     scellNameDateTime,
                     agentEventCode,
                     agentEventDescription }
        DESCRIPTION
             "Internal Error"
           --#TYPE      "Management Agent Event"
           --#SUMMARY   "Host %s : SCellName-TimeDate %s : EventCode %d : Description %s"
           --#ARGUMENTS {0,1,2,3,}
            --#SEVERITY  MINOR
            --#TIMEINDEX 136
        ::= 136000005
 
   mngmtAgentTrap-6 TRAP-TYPE
        ENTERPRISE compaq
        VARIABLES  { hostName,
                     scellNameDateTime,
                     agentEventCode,
                     agentEventDescription }
        DESCRIPTION
             "Invalid status for logical disk"
           --#TYPE      "Management Agent Event"
           --#SUMMARY   "Host %s : SCellName-TimeDate %s : EventCode %d : Description %s"
           --#ARGUMENTS {0,1,2,3,}
            --#SEVERITY  INFORMATIONAL
            --#TIMEINDEX 136
        ::= 136000006
 
   mngmtAgentTrap-7 TRAP-TYPE
        ENTERPRISE compaq
        VARIABLES  { hostName,
                     scellNameDateTime,
                     agentEventCode,
                     agentEventDescription }
        DESCRIPTION
             "Invalid Class"
           --#TYPE      "Management Agent Event"
           --#SUMMARY   "Host %s : SCellName-TimeDate %s : EventCode %d : Description %s"
           --#ARGUMENTS {0,1,2,3,}
            --#SEVERITY  INFORMATIONAL
            --#TIMEINDEX 136
        ::= 136000007
 
   mngmtAgentTrap-8 TRAP-TYPE
        ENTERPRISE compaq
        VARIABLES  { hostName,
                     scellNameDateTime,
                     agentEventCode,
                     agentEventDescription }
        DESCRIPTION
             "Invalid Function"
           --#TYPE      "Management Agent Event"
           --#SUMMARY   "Host %s : SCellName-TimeDate %s : EventCode %d : Description %s"
           --#ARGUMENTS {0,1,2,3,}
            --#SEVERITY  INFORMATIONAL
            --#TIMEINDEX 136
        ::= 136000008
 
   mngmtAgentTrap-9 TRAP-TYPE
        ENTERPRISE compaq
        VARIABLES  { hostName,
                     scellNameDateTime,
                     agentEventCode,
                     agentEventDescription }
        DESCRIPTION
             "Invalid Logical Disk Block State"
           --#TYPE      "Management Agent Event"
           --#SUMMARY   "Host %s : SCellName-TimeDate %s : EventCode %d : Description %s"
           --#ARGUMENTS {0,1,2,3,}
            --#SEVERITY  INFORMATIONAL
            --#TIMEINDEX 136
        ::= 136000009
 
   mngmtAgentTrap-10 TRAP-TYPE
        ENTERPRISE compaq
        VARIABLES  { hostName,
                     scellNameDateTime,
                     agentEventCode,
                     agentEventDescription }
        DESCRIPTION
             "Invalid Loop Configuration"
           --#TYPE      "Management Agent Event"
           --#SUMMARY   "Host %s : SCellName-TimeDate %s : EventCode %d : Description %s"
           --#ARGUMENTS {0,1,2,3,}
            --#SEVERITY  INFORMATIONAL
            --#TIMEINDEX 136
        ::= 136000010
 
   mngmtAgentTrap-11 TRAP-TYPE
        ENTERPRISE compaq
        VARIABLES  { hostName,
                     scellNameDateTime,
                     agentEventCode,
                     agentEventDescription }
        DESCRIPTION
             "Invalid Parameter"
           --#TYPE      "Management Agent Event"
           --#SUMMARY   "Host %s : SCellName-TimeDate %s : EventCode %d : Description %s"
           --#ARGUMENTS {0,1,2,3,}
            --#SEVERITY  INFORMATIONAL
            --#TIMEINDEX 136
        ::= 136000011
 
   mngmtAgentTrap-12 TRAP-TYPE
        ENTERPRISE compaq
        VARIABLES  { hostName,
                     scellNameDateTime,
                     agentEventCode,
                     agentEventDescription }
        DESCRIPTION
             "Invalid Parameter handle"
           --#TYPE      "Management Agent Event"
           --#SUMMARY   "Host %s : SCellName-TimeDate %s : EventCode %d : Description %s"
           --#ARGUMENTS {0,1,2,3,}
            --#SEVERITY  INFORMATIONAL
            --#TIMEINDEX 136
        ::= 136000012
 
   mngmtAgentTrap-13 TRAP-TYPE
        ENTERPRISE compaq
        VARIABLES  { hostName,
                     scellNameDateTime,
                     agentEventCode,
                     agentEventDescription }
        DESCRIPTION
             "Invalid Parameter Id"
           --#TYPE      "Management Agent Event"
           --#SUMMARY   "Host %s : SCellName-TimeDate %s : EventCode %d : Description %s"
           --#ARGUMENTS {0,1,2,3,}
            --#SEVERITY  INFORMATIONAL
            --#TIMEINDEX 136
        ::= 136000013
 
   mngmtAgentTrap-14 TRAP-TYPE
        ENTERPRISE compaq
        VARIABLES  { hostName,
                     scellNameDateTime,
                     agentEventCode,
                     agentEventDescription }
        DESCRIPTION
             "Invalid Quorum Configuration"
           --#TYPE      "Management Agent Event"
           --#SUMMARY   "Host %s : SCellName-TimeDate %s : EventCode %d : Description %s"
           --#ARGUMENTS {0,1,2,3,}
            --#SEVERITY  INFORMATIONAL
            --#TIMEINDEX 136
        ::= 136000014
 
   mngmtAgentTrap-15 TRAP-TYPE
        ENTERPRISE compaq
        VARIABLES  { hostName,
                     scellNameDateTime,
                     agentEventCode,
                     agentEventDescription }
        DESCRIPTION
             "Invalid Target Handle"
           --#TYPE      "Management Agent Event"
           --#SUMMARY   "Host %s : SCellName-TimeDate %s : EventCode %d : Description %s"
           --#ARGUMENTS {0,1,2,3,}
            --#SEVERITY  INFORMATIONAL
            --#TIMEINDEX 136
        ::= 136000015
 
   mngmtAgentTrap-16 TRAP-TYPE
        ENTERPRISE compaq
        VARIABLES  { hostName,
                     scellNameDateTime,
                     agentEventCode,
                     agentEventDescription }
        DESCRIPTION
             "Invalid Target Id"
           --#TYPE      "Management Agent Event"
           --#SUMMARY   "Host %s : SCellName-TimeDate %s : EventCode %d : Description %s"
           --#ARGUMENTS {0,1,2,3,}
            --#SEVERITY  INFORMATIONAL
            --#TIMEINDEX 136
        ::= 136000016
 
   mngmtAgentTrap-17 TRAP-TYPE
        ENTERPRISE compaq
        VARIABLES  { hostName,
                     scellNameDateTime,
                     agentEventCode,
                     agentEventDescription }
        DESCRIPTION
             "Invalid Time"
           --#TYPE      "Management Agent Event"
           --#SUMMARY   "Host %s : SCellName-TimeDate %s : EventCode %d : Description %s"
           --#ARGUMENTS {0,1,2,3,}
            --#SEVERITY  INFORMATIONAL
            --#TIMEINDEX 136
        ::= 136000017
 
   mngmtAgentTrap-18 TRAP-TYPE
        ENTERPRISE compaq
        VARIABLES  { hostName,
                     scellNameDateTime,
                     agentEventCode,
                     agentEventDescription }
        DESCRIPTION
             "Media is Inaccessible"
           --#TYPE      "Management Agent Event"
           --#SUMMARY   "Host %s : SCellName-TimeDate %s : EventCode %d : Description %s"
           --#ARGUMENTS {0,1,2,3,}
            --#SEVERITY  MINOR
            --#TIMEINDEX 136
        ::= 136000018
 
   mngmtAgentTrap-19 TRAP-TYPE
        ENTERPRISE compaq
        VARIABLES  { hostName,
                     scellNameDateTime,
                     agentEventCode,
                     agentEventDescription }
        DESCRIPTION
             "No Fibre Channel Port"
           --#TYPE      "Management Agent Event"
           --#SUMMARY   "Host %s : SCellName-TimeDate %s : EventCode %d : Description %s"
           --#ARGUMENTS {0,1,2,3,}
            --#SEVERITY  MINOR
            --#TIMEINDEX 136
        ::= 136000019
 
   mngmtAgentTrap-20 TRAP-TYPE
        ENTERPRISE compaq
        VARIABLES  { hostName,
                     scellNameDateTime,
                     agentEventCode,
                     agentEventDescription }
        DESCRIPTION
             "No Image"
           --#TYPE      "Management Agent Event"
           --#SUMMARY   "Host %s : SCellName-TimeDate %s : EventCode %d : Description %s"
           --#ARGUMENTS {0,1,2,3,}
            --#SEVERITY  INFORMATIONAL
            --#TIMEINDEX 136
        ::= 136000020
 
   mngmtAgentTrap-21 TRAP-TYPE
        ENTERPRISE compaq
        VARIABLES  { hostName,
                     scellNameDateTime,
                     agentEventCode,
                     agentEventDescription }
        DESCRIPTION
             "No Permission"
           --#TYPE      "Management Agent Event"
           --#SUMMARY   "Host %s : SCellName-TimeDate %s : EventCode %d : Description %s"
           --#ARGUMENTS {0,1,2,3,}
            --#SEVERITY  INFORMATIONAL
            --#TIMEINDEX 136
        ::= 136000021
 
   mngmtAgentTrap-22 TRAP-TYPE
        ENTERPRISE compaq
        VARIABLES  { hostName,
                     scellNameDateTime,
                     agentEventCode,
                     agentEventDescription }
        DESCRIPTION
             "Storage system not initialized"
           --#TYPE      "Management Agent Event"
           --#SUMMARY   "Host %s : SCellName-TimeDate %s : EventCode %d : Description %s"
           --#ARGUMENTS {0,1,2,3,}
            --#SEVERITY  INFORMATIONAL
            --#TIMEINDEX 136
        ::= 136000022
 
   mngmtAgentTrap-23 TRAP-TYPE
        ENTERPRISE compaq
        VARIABLES  { hostName,
                     scellNameDateTime,
                     agentEventCode,
                     agentEventDescription }
        DESCRIPTION
             "Not a Loop Port"
           --#TYPE      "Management Agent Event"
           --#SUMMARY   "Host %s : SCellName-TimeDate %s : EventCode %d : Description %s"
           --#ARGUMENTS {0,1,2,3,}
            --#SEVERITY  INFORMATIONAL
            --#TIMEINDEX 136
        ::= 136000023
 
   mngmtAgentTrap-24 TRAP-TYPE
        ENTERPRISE compaq
        VARIABLES  { hostName,
                     scellNameDateTime,
                     agentEventCode,
                     agentEventDescription }
        DESCRIPTION
             "Not a Participating Controller"
           --#TYPE      "Management Agent Event"
           --#SUMMARY   "Host %s : SCellName-TimeDate %s : EventCode %d : Description %s"
           --#ARGUMENTS {0,1,2,3,}
            --#SEVERITY  INFORMATIONAL
            --#TIMEINDEX 136
        ::= 136000024
 
   mngmtAgentTrap-25 TRAP-TYPE
        ENTERPRISE compaq
        VARIABLES  { hostName,
                     scellNameDateTime,
                     agentEventCode,
                     agentEventDescription }
        DESCRIPTION
             "Objects in your system are in use, and their state prevents the operation you wish to perform."
           --#TYPE      "Management Agent Event"
           --#SUMMARY   "Host %s : SCellName-TimeDate %s : EventCode %d : Description %s"
           --#ARGUMENTS {0,1,2,3,}
            --#SEVERITY  INFORMATIONAL
            --#TIMEINDEX 136
        ::= 136000025
 
   mngmtAgentTrap-26 TRAP-TYPE
        ENTERPRISE compaq
        VARIABLES  { hostName,
                     scellNameDateTime,
                     agentEventCode,
                     agentEventDescription }
        DESCRIPTION
             "Parameter Object Does Not Exist"
           --#TYPE      "Management Agent Event"
           --#SUMMARY   "Host %s : SCellName-TimeDate %s : EventCode %d : Description %s"
           --#ARGUMENTS {0,1,2,3,}
            --#SEVERITY  INFORMATIONAL
            --#TIMEINDEX 136
        ::= 136000026
 
   mngmtAgentTrap-27 TRAP-TYPE
        ENTERPRISE compaq
        VARIABLES  { hostName,
                     scellNameDateTime,
                     agentEventCode,
                     agentEventDescription }
        DESCRIPTION
             "Target Object Does Not Exist"
           --#TYPE      "Management Agent Event"
           --#SUMMARY   "Host %s : SCellName-TimeDate %s : EventCode %d : Description %s"
           --#ARGUMENTS {0,1,2,3,}
            --#SEVERITY  INFORMATIONAL
            --#TIMEINDEX 136
        ::= 136000027
 
   mngmtAgentTrap-28 TRAP-TYPE
        ENTERPRISE compaq
        VARIABLES  { hostName,
                     scellNameDateTime,
                     agentEventCode,
                     agentEventDescription }
        DESCRIPTION
             "Timeout"
           --#TYPE      "Management Agent Event"
           --#SUMMARY   "Host %s : SCellName-TimeDate %s : EventCode %d : Description %s"
           --#ARGUMENTS {0,1,2,3,}
            --#SEVERITY  INFORMATIONAL
            --#TIMEINDEX 136
        ::= 136000028
 
   mngmtAgentTrap-29 TRAP-TYPE
        ENTERPRISE compaq
        VARIABLES  { hostName,
                     scellNameDateTime,
                     agentEventCode,
                     agentEventDescription }
        DESCRIPTION
             "Unknown Id"
           --#TYPE      "Management Agent Event"
           --#SUMMARY   "Host %s : SCellName-TimeDate %s : EventCode %d : Description %s"
           --#ARGUMENTS {0,1,2,3,}
            --#SEVERITY  INFORMATIONAL
            --#TIMEINDEX 136
        ::= 136000029
 
   mngmtAgentTrap-30 TRAP-TYPE
        ENTERPRISE compaq
        VARIABLES  { hostName,
                     scellNameDateTime,
                     agentEventCode,
                     agentEventDescription }
        DESCRIPTION
             "Unknown Parameter Handle"
           --#TYPE      "Management Agent Event"
           --#SUMMARY   "Host %s : SCellName-TimeDate %s : EventCode %d : Description %s"
           --#ARGUMENTS {0,1,2,3,}
            --#SEVERITY  INFORMATIONAL
            --#TIMEINDEX 136
        ::= 136000030
 
   mngmtAgentTrap-31 TRAP-TYPE
        ENTERPRISE compaq
        VARIABLES  { hostName,
                     scellNameDateTime,
                     agentEventCode,
                     agentEventDescription }
        DESCRIPTION
             "Unrecoverable Media Error"
           --#TYPE      "Management Agent Event"
           --#SUMMARY   "Host %s : SCellName-TimeDate %s : EventCode %d : Description %s"
           --#ARGUMENTS {0,1,2,3,}
            --#SEVERITY  MAJOR
            --#TIMEINDEX 136
        ::= 136000031
 
   mngmtAgentTrap-32 TRAP-TYPE
        ENTERPRISE compaq
        VARIABLES  { hostName,
                     scellNameDateTime,
                     agentEventCode,
                     agentEventDescription }
        DESCRIPTION
             "Invalid State"
           --#TYPE      "Management Agent Event"
           --#SUMMARY   "Host %s : SCellName-TimeDate %s : EventCode %d : Description %s"
           --#ARGUMENTS {0,1,2,3,}
            --#SEVERITY  INFORMATIONAL
            --#TIMEINDEX 136
        ::= 136000032
 
   mngmtAgentTrap-33 TRAP-TYPE
        ENTERPRISE compaq
        VARIABLES  { hostName,
                     scellNameDateTime,
                     agentEventCode,
                     agentEventDescription }
        DESCRIPTION
             "Transport Error"
           --#TYPE      "Management Agent Event"
           --#SUMMARY   "Host %s : SCellName-TimeDate %s : EventCode %d : Description %s"
           --#ARGUMENTS {0,1,2,3,}
            --#SEVERITY  MINOR
            --#TIMEINDEX 136
        ::= 136000033
 
   mngmtAgentTrap-34 TRAP-TYPE
        ENTERPRISE compaq
        VARIABLES  { hostName,
                     scellNameDateTime,
                     agentEventCode,
                     agentEventDescription }
        DESCRIPTION
             "Volume is Missing"
           --#TYPE      "Management Agent Event"
           --#SUMMARY   "Host %s : SCellName-TimeDate %s : EventCode %d : Description %s"
           --#ARGUMENTS {0,1,2,3,}
            --#SEVERITY  MINOR
            --#TIMEINDEX 136
        ::= 136000034
 
   mngmtAgentTrap-35 TRAP-TYPE
        ENTERPRISE compaq
        VARIABLES  { hostName,
                     scellNameDateTime,
                     agentEventCode,
                     agentEventDescription }
        DESCRIPTION
             "Invalid Cursor"
           --#TYPE      "Management Agent Event"
           --#SUMMARY   "Host %s : SCellName-TimeDate %s : EventCode %d : Description %s"
           --#ARGUMENTS {0,1,2,3,}
            --#SEVERITY  INFORMATIONAL
            --#TIMEINDEX 136
        ::= 136000035
 
   mngmtAgentTrap-36 TRAP-TYPE
        ENTERPRISE compaq
        VARIABLES  { hostName,
                     scellNameDateTime,
                     agentEventCode,
                     agentEventDescription }
        DESCRIPTION
             "Invalid Target for the Operation"
           --#TYPE      "Management Agent Event"
           --#SUMMARY   "Host %s : SCellName-TimeDate %s : EventCode %d : Description %s"
           --#ARGUMENTS {0,1,2,3,}
            --#SEVERITY  INFORMATIONAL
            --#TIMEINDEX 136
        ::= 136000036
 
   mngmtAgentTrap-37 TRAP-TYPE
        ENTERPRISE compaq
        VARIABLES  { hostName,
                     scellNameDateTime,
                     agentEventCode,
                     agentEventDescription }
        DESCRIPTION
             "No More Events"
           --#TYPE      "Management Agent Event"
           --#SUMMARY   "Host %s : SCellName-TimeDate %s : EventCode %d : Description %s"
           --#ARGUMENTS {0,1,2,3,}
            --#SEVERITY  INFORMATIONAL
            --#TIMEINDEX 136
        ::= 136000037
 
   mngmtAgentTrap-38 TRAP-TYPE
        ENTERPRISE compaq
        VARIABLES  { hostName,
                     scellNameDateTime,
                     agentEventCode,
                     agentEventDescription }
        DESCRIPTION
             "Lock Busy"
           --#TYPE      "Management Agent Event"
           --#SUMMARY   "Host %s : SCellName-TimeDate %s : EventCode %d : Description %s"
           --#ARGUMENTS {0,1,2,3,}
            --#SEVERITY  INFORMATIONAL
            --#TIMEINDEX 136
        ::= 136000038
 
   mngmtAgentTrap-39 TRAP-TYPE
        ENTERPRISE compaq
        VARIABLES  { hostName,
                     scellNameDateTime,
                     agentEventCode,
                     agentEventDescription }
        DESCRIPTION
             "Time Not Set"
           --#TYPE      "Management Agent Event"
           --#SUMMARY   "Host %s : SCellName-TimeDate %s : EventCode %d : Description %s"
           --#ARGUMENTS {0,1,2,3,}
            --#SEVERITY  INFORMATIONAL
            --#TIMEINDEX 136
        ::= 136000039
 
   mngmtAgentTrap-40 TRAP-TYPE
        ENTERPRISE compaq
        VARIABLES  { hostName,
                     scellNameDateTime,
                     agentEventCode,
                     agentEventDescription }
        DESCRIPTION
             "Not a Supported Version"
           --#TYPE      "Management Agent Event"
           --#SUMMARY   "Host %s : SCellName-TimeDate %s : EventCode %d : Description %s"
           --#ARGUMENTS {0,1,2,3,}
            --#SEVERITY  INFORMATIONAL
            --#TIMEINDEX 136
        ::= 136000040
 
   mngmtAgentTrap-41 TRAP-TYPE
        ENTERPRISE compaq
        VARIABLES  { hostName,
                     scellNameDateTime,
                     agentEventCode,
                     agentEventDescription }
        DESCRIPTION
             "No Logical Disk for Vdisk"
           --#TYPE      "Management Agent Event"
           --#SUMMARY   "Host %s : SCellName-TimeDate %s : EventCode %d : Description %s"
           --#ARGUMENTS {0,1,2,3,}
            --#SEVERITY  INFORMATIONAL
            --#TIMEINDEX 136
        ::= 136000041
 
   mngmtAgentTrap-42 TRAP-TYPE
        ENTERPRISE compaq
        VARIABLES  { hostName,
                     scellNameDateTime,
                     agentEventCode,
                     agentEventDescription }
        DESCRIPTION
             "Logical disk Presented"
           --#TYPE      "Management Agent Event"
           --#SUMMARY   "Host %s : SCellName-TimeDate %s : EventCode %d : Description %s"
           --#ARGUMENTS {0,1,2,3,}
            --#SEVERITY  INFORMATIONAL
            --#TIMEINDEX 136
        ::= 136000042
 
   mngmtAgentTrap-43 TRAP-TYPE
        ENTERPRISE compaq
        VARIABLES  { hostName,
                     scellNameDateTime,
                     agentEventCode,
                     agentEventDescription }
        DESCRIPTION
             "Operation Denied On Slave"
           --#TYPE      "Management Agent Event"
           --#SUMMARY   "Host %s : SCellName-TimeDate %s : EventCode %d : Description %s"
           --#ARGUMENTS {0,1,2,3,}
            --#SEVERITY  MINOR
            --#TIMEINDEX 136
        ::= 136000043
 
   mngmtAgentTrap-44 TRAP-TYPE
        ENTERPRISE compaq
        VARIABLES  { hostName,
                     scellNameDateTime,
                     agentEventCode,
                     agentEventDescription }
        DESCRIPTION
             "Not licensed for data replication"
           --#TYPE      "Management Agent Event"
           --#SUMMARY   "Host %s : SCellName-TimeDate %s : EventCode %d : Description %s"
           --#ARGUMENTS {0,1,2,3,}
            --#SEVERITY  INFORMATIONAL
            --#TIMEINDEX 136
        ::= 136000044
 
   mngmtAgentTrap-45 TRAP-TYPE
        ENTERPRISE compaq
        VARIABLES  { hostName,
                     scellNameDateTime,
                     agentEventCode,
                     agentEventDescription }
        DESCRIPTION
             "Not DR group member"
           --#TYPE      "Management Agent Event"
           --#SUMMARY   "Host %s : SCellName-TimeDate %s : EventCode %d : Description %s"
           --#ARGUMENTS {0,1,2,3,}
            --#SEVERITY  INFORMATIONAL
            --#TIMEINDEX 136
        ::= 136000045
 
   mngmtAgentTrap-46 TRAP-TYPE
        ENTERPRISE compaq
        VARIABLES  { hostName,
                     scellNameDateTime,
                     agentEventCode,
                     agentEventDescription }
        DESCRIPTION
             "Invalid DR mode"
           --#TYPE      "Management Agent Event"
           --#SUMMARY   "Host %s : SCellName-TimeDate %s : EventCode %d : Description %s"
           --#ARGUMENTS {0,1,2,3,}
            --#SEVERITY  INFORMATIONAL
            --#TIMEINDEX 136
        ::= 136000046
 
   mngmtAgentTrap-47 TRAP-TYPE
        ENTERPRISE compaq
        VARIABLES  { hostName,
                     scellNameDateTime,
                     agentEventCode,
                     agentEventDescription }
        DESCRIPTION
             "Invalid DR State"
           --#TYPE      "Management Agent Event"
           --#SUMMARY   "Host %s : SCellName-TimeDate %s : EventCode %d : Description %s"
           --#ARGUMENTS {0,1,2,3,}
            --#SEVERITY  INFORMATIONAL
            --#TIMEINDEX 136
        ::= 136000047
 
   mngmtAgentTrap-48 TRAP-TYPE
        ENTERPRISE compaq
        VARIABLES  { hostName,
                     scellNameDateTime,
                     agentEventCode,
                     agentEventDescription }
        DESCRIPTION
             "Security credentials needed. Please update your system's ID and password in the Storage System Access menu."
           --#TYPE      "Management Agent Event"
           --#SUMMARY   "Host %s : SCellName-TimeDate %s : EventCode %d : Description %s"
           --#ARGUMENTS {0,1,2,3,}
            --#SEVERITY  INFORMATIONAL
            --#TIMEINDEX 136
        ::= 136000048
 
   mngmtAgentTrap-49 TRAP-TYPE
        ENTERPRISE compaq
        VARIABLES  { hostName,
                     scellNameDateTime,
                     agentEventCode,
                     agentEventDescription }
        DESCRIPTION
             "Security credentials supplied were invalid. Please update your system's ID and password in the Storage System Access menu."
           --#TYPE      "Management Agent Event"
           --#SUMMARY   "Host %s : SCellName-TimeDate %s : EventCode %d : Description %s"
           --#ARGUMENTS {0,1,2,3,}
            --#SEVERITY  INFORMATIONAL
            --#TIMEINDEX 136
        ::= 136000049
 
   mngmtAgentTrap-50 TRAP-TYPE
        ENTERPRISE compaq
        VARIABLES  { hostName,
                     scellNameDateTime,
                     agentEventCode,
                     agentEventDescription }
        DESCRIPTION
             "Security credentials supplied were invalid. Please update your system's ID and password in the Storage System Access menu."
           --#TYPE      "Management Agent Event"
           --#SUMMARY   "Host %s : SCellName-TimeDate %s : EventCode %d : Description %s"
           --#ARGUMENTS {0,1,2,3,}
            --#SEVERITY  INFORMATIONAL
            --#TIMEINDEX 136
        ::= 136000050
 
   mngmtAgentTrap-51 TRAP-TYPE
        ENTERPRISE compaq
        VARIABLES  { hostName,
                     scellNameDateTime,
                     agentEventCode,
                     agentEventDescription }
        DESCRIPTION
             "Storage system connection down"
           --#TYPE      "Management Agent Event"
           --#SUMMARY   "Host %s : SCellName-TimeDate %s : EventCode %d : Description %s"
           --#ARGUMENTS {0,1,2,3,}
            --#SEVERITY  MINOR
            --#TIMEINDEX 136
        ::= 136000051
 
   mngmtAgentTrap-52 TRAP-TYPE
        ENTERPRISE compaq
        VARIABLES  { hostName,
                     scellNameDateTime,
                     agentEventCode,
                     agentEventDescription }
        DESCRIPTION
             "DR group empty"
           --#TYPE      "Management Agent Event"
           --#SUMMARY   "Host %s : SCellName-TimeDate %s : EventCode %d : Description %s"
           --#ARGUMENTS {0,1,2,3,}
            --#SEVERITY  INFORMATIONAL
            --#TIMEINDEX 136
        ::= 136000052
 
   mngmtAgentTrap-53 TRAP-TYPE
        ENTERPRISE compaq
        VARIABLES  { hostName,
                     scellNameDateTime,
                     agentEventCode,
                     agentEventDescription }
        DESCRIPTION
             "Incompatible attribute"
           --#TYPE      "Management Agent Event"
           --#SUMMARY   "Host %s : SCellName-TimeDate %s : EventCode %d : Description %s"
           --#ARGUMENTS {0,1,2,3,}
            --#SEVERITY  INFORMATIONAL
            --#TIMEINDEX 136
        ::= 136000053
 
   mngmtAgentTrap-54 TRAP-TYPE
        ENTERPRISE compaq
        VARIABLES  { hostName,
                     scellNameDateTime,
                     agentEventCode,
                     agentEventDescription }
        DESCRIPTION
             "Vdisk is a DR group member"
           --#TYPE      "Management Agent Event"
           --#SUMMARY   "Host %s : SCellName-TimeDate %s : EventCode %d : Description %s"
           --#ARGUMENTS {0,1,2,3,}
            --#SEVERITY  INFORMATIONAL
            --#TIMEINDEX 136
        ::= 136000054
 
   mngmtAgentTrap-55 TRAP-TYPE
        ENTERPRISE compaq
        VARIABLES  { hostName,
                     scellNameDateTime,
                     agentEventCode,
                     agentEventDescription }
        DESCRIPTION
             "Vdisk is a DR log unit"
           --#TYPE      "Management Agent Event"
           --#SUMMARY   "Host %s : SCellName-TimeDate %s : EventCode %d : Description %s"
           --#ARGUMENTS {0,1,2,3,}
            --#SEVERITY  INFORMATIONAL
            --#TIMEINDEX 136
        ::= 136000055
 
   mngmtAgentTrap-56 TRAP-TYPE
        ENTERPRISE compaq
        VARIABLES  { hostName,
                     scellNameDateTime,
                     agentEventCode,
                     agentEventDescription }
        DESCRIPTION
             "Cache batteries failed or missing."
           --#TYPE      "Management Agent Event"
           --#SUMMARY   "Host %s : SCellName-TimeDate %s : EventCode %d : Description %s"
           --#ARGUMENTS {0,1,2,3,}
            --#SEVERITY  INFORMATIONAL
            --#TIMEINDEX 136
        ::= 136000056
 
   mngmtAgentTrap-57 TRAP-TYPE
        ENTERPRISE compaq
        VARIABLES  { hostName,
                     scellNameDateTime,
                     agentEventCode,
                     agentEventDescription }
        DESCRIPTION
             "Vdisk is not presented"
           --#TYPE      "Management Agent Event"
           --#SUMMARY   "Host %s : SCellName-TimeDate %s : EventCode %d : Description %s"
           --#ARGUMENTS {0,1,2,3,}
            --#SEVERITY  INFORMATIONAL
            --#TIMEINDEX 136
        ::= 136000057
 
   mngmtAgentTrap-58 TRAP-TYPE
        ENTERPRISE compaq
        VARIABLES  { hostName,
                     scellNameDateTime,
                     agentEventCode,
                     agentEventDescription }
        DESCRIPTION
             "Other controller failed"
           --#TYPE      "Management Agent Event"
           --#SUMMARY   "Host %s : SCellName-TimeDate %s : EventCode %d : Description %s"
           --#ARGUMENTS {0,1,2,3,}
            --#SEVERITY  MINOR
            --#TIMEINDEX 136
        ::= 136000058
 
   mngmtAgentTrap-59 TRAP-TYPE
        ENTERPRISE compaq
        VARIABLES  { hostName,
                     scellNameDateTime,
                     agentEventCode,
                     agentEventDescription }
        DESCRIPTION
             "Maximum Number of Objects Exceeded."
           --#TYPE      "Management Agent Event"
           --#SUMMARY   "Host %s : SCellName-TimeDate %s : EventCode %d : Description %s"
           --#ARGUMENTS {0,1,2,3,}
            --#SEVERITY  INFORMATIONAL
            --#TIMEINDEX 136
        ::= 136000059
 
   mngmtAgentTrap-60 TRAP-TYPE
        ENTERPRISE compaq
        VARIABLES  { hostName,
                     scellNameDateTime,
                     agentEventCode,
                     agentEventDescription }
        DESCRIPTION
             "Max size"
           --#TYPE      "Management Agent Event"
           --#SUMMARY   "Host %s : SCellName-TimeDate %s : EventCode %d : Description %s"
           --#ARGUMENTS {0,1,2,3,}
            --#SEVERITY  INFORMATIONAL
            --#TIMEINDEX 136
        ::= 136000060
 
   mngmtAgentTrap-61 TRAP-TYPE
        ENTERPRISE compaq
        VARIABLES  { hostName,
                     scellNameDateTime,
                     agentEventCode,
                     agentEventDescription }
        DESCRIPTION
             "Password mismatch. Please update your system's password in the Storage System Access menu. Continued attempts to access this storage system with an incorrect password will disable management of this storage system."
           --#TYPE      "Management Agent Event"
           --#SUMMARY   "Host %s : SCellName-TimeDate %s : EventCode %d : Description %s"
           --#ARGUMENTS {0,1,2,3,}
            --#SEVERITY  INFORMATIONAL
            --#TIMEINDEX 136
        ::= 136000061
 
   mngmtAgentTrap-62 TRAP-TYPE
        ENTERPRISE compaq
        VARIABLES  { hostName,
                     scellNameDateTime,
                     agentEventCode,
                     agentEventDescription }
        DESCRIPTION
             "DR group is merging"
           --#TYPE      "Management Agent Event"
           --#SUMMARY   "Host %s : SCellName-TimeDate %s : EventCode %d : Description %s"
           --#ARGUMENTS {0,1,2,3,}
            --#SEVERITY  INFORMATIONAL
            --#TIMEINDEX 136
        ::= 136000062
 
   mngmtAgentTrap-63 TRAP-TYPE
        ENTERPRISE compaq
        VARIABLES  { hostName,
                     scellNameDateTime,
                     agentEventCode,
                     agentEventDescription }
        DESCRIPTION
             "DR group is logging"
           --#TYPE      "Management Agent Event"
           --#SUMMARY   "Host %s : SCellName-TimeDate %s : EventCode %d : Description %s"
           --#ARGUMENTS {0,1,2,3,}
            --#SEVERITY  INFORMATIONAL
            --#TIMEINDEX 136
        ::= 136000063
 
   mngmtAgentTrap-64 TRAP-TYPE
        ENTERPRISE compaq
        VARIABLES  { hostName,
                     scellNameDateTime,
                     agentEventCode,
                     agentEventDescription }
        DESCRIPTION
             "Connection is suspended"
           --#TYPE      "Management Agent Event"
           --#SUMMARY   "Host %s : SCellName-TimeDate %s : EventCode %d : Description %s"
           --#ARGUMENTS {0,1,2,3,}
            --#SEVERITY  INFORMATIONAL
            --#TIMEINDEX 136
        ::= 136000064
 
   mngmtAgentTrap-65 TRAP-TYPE
        ENTERPRISE compaq
        VARIABLES  { hostName,
                     scellNameDateTime,
                     agentEventCode,
                     agentEventDescription }
        DESCRIPTION
             "Bad image header"
           --#TYPE      "Management Agent Event"
           --#SUMMARY   "Host %s : SCellName-TimeDate %s : EventCode %d : Description %s"
           --#ARGUMENTS {0,1,2,3,}
            --#SEVERITY  INFORMATIONAL
            --#TIMEINDEX 136
        ::= 136000065
 
   mngmtAgentTrap-66 TRAP-TYPE
        ENTERPRISE compaq
        VARIABLES  { hostName,
                     scellNameDateTime,
                     agentEventCode,
                     agentEventDescription }
        DESCRIPTION
             "Bad image"
           --#TYPE      "Management Agent Event"
           --#SUMMARY   "Host %s : SCellName-TimeDate %s : EventCode %d : Description %s"
           --#ARGUMENTS {0,1,2,3,}
            --#SEVERITY  INFORMATIONAL
            --#TIMEINDEX 136
        ::= 136000066
 
   mngmtAgentTrap-67 TRAP-TYPE
        ENTERPRISE compaq
        VARIABLES  { hostName,
                     scellNameDateTime,
                     agentEventCode,
                     agentEventDescription }
        DESCRIPTION
             "Image too large"
           --#TYPE      "Management Agent Event"
           --#SUMMARY   "Host %s : SCellName-TimeDate %s : EventCode %d : Description %s"
           --#ARGUMENTS {0,1,2,3,}
            --#SEVERITY  INFORMATIONAL
            --#TIMEINDEX 136
        ::= 136000067
 
   mngmtAgentTrap-68 TRAP-TYPE
        ENTERPRISE compaq
        VARIABLES  { hostName,
                     scellNameDateTime,
                     agentEventCode,
                     agentEventDescription }
        DESCRIPTION
             "EMU not available"
           --#TYPE      "Management Agent Event"
           --#SUMMARY   "Host %s : SCellName-TimeDate %s : EventCode %d : Description %s"
           --#ARGUMENTS {0,1,2,3,}
            --#SEVERITY  INFORMATIONAL
            --#TIMEINDEX 136
        ::= 136000068
 
   mngmtAgentTrap-69 TRAP-TYPE
        ENTERPRISE compaq
        VARIABLES  { hostName,
                     scellNameDateTime,
                     agentEventCode,
                     agentEventDescription }
        DESCRIPTION
             "EMU indefinite delay"
           --#TYPE      "Management Agent Event"
           --#SUMMARY   "Host %s : SCellName-TimeDate %s : EventCode %d : Description %s"
           --#ARGUMENTS {0,1,2,3,}
            --#SEVERITY  INFORMATIONAL
            --#TIMEINDEX 136
        ::= 136000069
 
   mngmtAgentTrap-70 TRAP-TYPE
        ENTERPRISE compaq
        VARIABLES  { hostName,
                     scellNameDateTime,
                     agentEventCode,
                     agentEventDescription }
        DESCRIPTION
             "Image incompatible with system configuration. Version conflict in upgrade or downgrade not allowed."
           --#TYPE      "Management Agent Event"
           --#SUMMARY   "Host %s : SCellName-TimeDate %s : EventCode %d : Description %s"
           --#ARGUMENTS {0,1,2,3,}
            --#SEVERITY  INFORMATIONAL
            --#TIMEINDEX 136
        ::= 136000070
 
   mngmtAgentTrap-71 TRAP-TYPE
        ENTERPRISE compaq
        VARIABLES  { hostName,
                     scellNameDateTime,
                     agentEventCode,
                     agentEventDescription }
        DESCRIPTION
             "Bad image segment"
           --#TYPE      "Management Agent Event"
           --#SUMMARY   "Host %s : SCellName-TimeDate %s : EventCode %d : Description %s"
           --#ARGUMENTS {0,1,2,3,}
            --#SEVERITY  INFORMATIONAL
            --#TIMEINDEX 136
        ::= 136000071
 
   mngmtAgentTrap-72 TRAP-TYPE
        ENTERPRISE compaq
        VARIABLES  { hostName,
                     scellNameDateTime,
                     agentEventCode,
                     agentEventDescription }
        DESCRIPTION
             "Image already loaded"
           --#TYPE      "Management Agent Event"
           --#SUMMARY   "Host %s : SCellName-TimeDate %s : EventCode %d : Description %s"
           --#ARGUMENTS {0,1,2,3,}
            --#SEVERITY  INFORMATIONAL
            --#TIMEINDEX 136
        ::= 136000072
 
   mngmtAgentTrap-73 TRAP-TYPE
        ENTERPRISE compaq
        VARIABLES  { hostName,
                     scellNameDateTime,
                     agentEventCode,
                     agentEventDescription }
        DESCRIPTION
             "Image Write Error"
           --#TYPE      "Management Agent Event"
           --#SUMMARY   "Host %s : SCellName-TimeDate %s : EventCode %d : Description %s"
           --#ARGUMENTS {0,1,2,3,}
            --#SEVERITY  INFORMATIONAL
            --#TIMEINDEX 136
        ::= 136000073
 
   mngmtAgentTrap-74 TRAP-TYPE
        ENTERPRISE compaq
        VARIABLES  { hostName,
                     scellNameDateTime,
                     agentEventCode,
                     agentEventDescription }
        DESCRIPTION
             "Logical Disk Sharing"
           --#TYPE      "Management Agent Event"
           --#SUMMARY   "Host %s : SCellName-TimeDate %s : EventCode %d : Description %s"
           --#ARGUMENTS {0,1,2,3,}
            --#SEVERITY  INFORMATIONAL
            --#TIMEINDEX 136
        ::= 136000074
 
   mngmtAgentTrap-75 TRAP-TYPE
        ENTERPRISE compaq
        VARIABLES  { hostName,
                     scellNameDateTime,
                     agentEventCode,
                     agentEventDescription }
        DESCRIPTION
             "Bad Image Size"
           --#TYPE      "Management Agent Event"
           --#SUMMARY   "Host %s : SCellName-TimeDate %s : EventCode %d : Description %s"
           --#ARGUMENTS {0,1,2,3,}
            --#SEVERITY  INFORMATIONAL
            --#TIMEINDEX 136
        ::= 136000075
 
   mngmtAgentTrap-76 TRAP-TYPE
        ENTERPRISE compaq
        VARIABLES  { hostName,
                     scellNameDateTime,
                     agentEventCode,
                     agentEventDescription }
        DESCRIPTION
             "Image Load Busy"
           --#TYPE      "Management Agent Event"
           --#SUMMARY   "Host %s : SCellName-TimeDate %s : EventCode %d : Description %s"
           --#ARGUMENTS {0,1,2,3,}
            --#SEVERITY  INFORMATIONAL
            --#TIMEINDEX 136
        ::= 136000076
 
   mngmtAgentTrap-77 TRAP-TYPE
        ENTERPRISE compaq
        VARIABLES  { hostName,
                     scellNameDateTime,
                     agentEventCode,
                     agentEventDescription }
        DESCRIPTION
             "Volume Failure Predicted"
           --#TYPE      "Management Agent Event"
           --#SUMMARY   "Host %s : SCellName-TimeDate %s : EventCode %d : Description %s"
           --#ARGUMENTS {0,1,2,3,}
            --#SEVERITY  CRITICAL
            --#TIMEINDEX 136
        ::= 136000077
 
   mngmtAgentTrap-78 TRAP-TYPE
        ENTERPRISE compaq
        VARIABLES  { hostName,
                     scellNameDateTime,
                     agentEventCode,
                     agentEventDescription }
        DESCRIPTION
             "Background allocation on the destination member is in progress. This action must complete before any others can be initiated ."
           --#TYPE      "Management Agent Event"
           --#SUMMARY   "Host %s : SCellName-TimeDate %s : EventCode %d : Description %s"
           --#ARGUMENTS {0,1,2,3,}
            --#SEVERITY  INFORMATIONAL
            --#TIMEINDEX 136
        ::= 136000078
 
   mngmtAgentTrap-79 TRAP-TYPE
        ENTERPRISE compaq
        VARIABLES  { hostName,
                     scellNameDateTime,
                     agentEventCode,
                     agentEventDescription }
        DESCRIPTION
             "Invalid Predecessor Vdisk Condition"
           --#TYPE      "Management Agent Event"
           --#SUMMARY   "Host %s : SCellName-TimeDate %s : EventCode %d : Description %s"
           --#ARGUMENTS {0,1,2,3,}
            --#SEVERITY  INFORMATIONAL
            --#TIMEINDEX 136
        ::= 136000079
 
   mngmtAgentTrap-80 TRAP-TYPE
        ENTERPRISE compaq
        VARIABLES  { hostName,
                     scellNameDateTime,
                     agentEventCode,
                     agentEventDescription }
        DESCRIPTION
             "Invalid Volume Usage"
           --#TYPE      "Management Agent Event"
           --#SUMMARY   "Host %s : SCellName-TimeDate %s : EventCode %d : Description %s"
           --#ARGUMENTS {0,1,2,3,}
            --#SEVERITY  INFORMATIONAL
            --#TIMEINDEX 136
        ::= 136000080
 
   mngmtAgentTrap-81 TRAP-TYPE
        ENTERPRISE compaq
        VARIABLES  { hostName,
                     scellNameDateTime,
                     agentEventCode,
                     agentEventDescription }
        DESCRIPTION
             "Minimum Volumes In Disk Group"
           --#TYPE      "Management Agent Event"
           --#SUMMARY   "Host %s : SCellName-TimeDate %s : EventCode %d : Description %s"
           --#ARGUMENTS {0,1,2,3,}
            --#SEVERITY  INFORMATIONAL
            --#TIMEINDEX 136
        ::= 136000081
 
   mngmtAgentTrap-82 TRAP-TYPE
        ENTERPRISE compaq
        VARIABLES  { hostName,
                     scellNameDateTime,
                     agentEventCode,
                     agentEventDescription }
        DESCRIPTION
             "Shutdown In Progress"
           --#TYPE      "Management Agent Event"
           --#SUMMARY   "Host %s : SCellName-TimeDate %s : EventCode %d : Description %s"
           --#ARGUMENTS {0,1,2,3,}
            --#SEVERITY  INFORMATIONAL
            --#TIMEINDEX 136
        ::= 136000082
 
   mngmtAgentTrap-83 TRAP-TYPE
        ENTERPRISE compaq
        VARIABLES  { hostName,
                     scellNameDateTime,
                     agentEventCode,
                     agentEventDescription }
        DESCRIPTION
             "Not Ready"
           --#TYPE      "Management Agent Event"
           --#SUMMARY   "Host %s : SCellName-TimeDate %s : EventCode %d : Description %s"
           --#ARGUMENTS {0,1,2,3,}
            --#SEVERITY  INFORMATIONAL
            --#TIMEINDEX 136
        ::= 136000083
 
   mngmtAgentTrap-84 TRAP-TYPE
        ENTERPRISE compaq
        VARIABLES  { hostName,
                     scellNameDateTime,
                     agentEventCode,
                     agentEventDescription }
        DESCRIPTION
             "Is Snapshot"
           --#TYPE      "Management Agent Event"
           --#SUMMARY   "Host %s : SCellName-TimeDate %s : EventCode %d : Description %s"
           --#ARGUMENTS {0,1,2,3,}
            --#SEVERITY  INFORMATIONAL
            --#TIMEINDEX 136
        ::= 136000084
 
   mngmtAgentTrap-85 TRAP-TYPE
        ENTERPRISE compaq
        VARIABLES  { hostName,
                     scellNameDateTime,
                     agentEventCode,
                     agentEventDescription }
        DESCRIPTION
             "Cannot add or remove DR group member. Mirror cache must be active for this Vdisk. Check controller cache condition."
           --#TYPE      "Management Agent Event"
           --#SUMMARY   "Host %s : SCellName-TimeDate %s : EventCode %d : Description %s"
           --#ARGUMENTS {0,1,2,3,}
            --#SEVERITY  INFORMATIONAL
            --#TIMEINDEX 136
        ::= 136000085
 
   mngmtAgentTrap-86 TRAP-TYPE
        ENTERPRISE compaq
        VARIABLES  { hostName,
                     scellNameDateTime,
                     agentEventCode,
                     agentEventDescription }
        DESCRIPTION
             "Inoperative"
           --#TYPE      "Management Agent Event"
           --#SUMMARY   "Host %s : SCellName-TimeDate %s : EventCode %d : Description %s"
           --#ARGUMENTS {0,1,2,3,}
            --#SEVERITY  INFORMATIONAL
            --#TIMEINDEX 136
        ::= 136000086
 
   mngmtAgentTrap-87 TRAP-TYPE
        ENTERPRISE compaq
        VARIABLES  { hostName,
                     scellNameDateTime,
                     agentEventCode,
                     agentEventDescription }
        DESCRIPTION
             "Disk group inoperative or less than 8 disks in group"
           --#TYPE      "Management Agent Event"
           --#SUMMARY   "Host %s : SCellName-TimeDate %s : EventCode %d : Description %s"
           --#ARGUMENTS {0,1,2,3,}
            --#SEVERITY  MINOR
            --#TIMEINDEX 136
        ::= 136000087
 
   mngmtAgentTrap-88 TRAP-TYPE
        ENTERPRISE compaq
        VARIABLES  { hostName,
                     scellNameDateTime,
                     agentEventCode,
                     agentEventDescription }
        DESCRIPTION
             "Storage system inoperative"
           --#TYPE      "Management Agent Event"
           --#SUMMARY   "Host %s : SCellName-TimeDate %s : EventCode %d : Description %s"
           --#ARGUMENTS {0,1,2,3,}
            --#SEVERITY  CRITICAL
            --#TIMEINDEX 136
        ::= 136000088
 
   mngmtAgentTrap-89 TRAP-TYPE
        ENTERPRISE compaq
        VARIABLES  { hostName,
                     scellNameDateTime,
                     agentEventCode,
                     agentEventDescription }
        DESCRIPTION
             "Failsafe Locked"
           --#TYPE      "Management Agent Event"
           --#SUMMARY   "Host %s : SCellName-TimeDate %s : EventCode %d : Description %s"
           --#ARGUMENTS {0,1,2,3,}
            --#SEVERITY  INFORMATIONAL
            --#TIMEINDEX 136
        ::= 136000089
 
   mngmtAgentTrap-90 TRAP-TYPE
        ENTERPRISE compaq
        VARIABLES  { hostName,
                     scellNameDateTime,
                     agentEventCode,
                     agentEventDescription }
        DESCRIPTION
             "Data Flush Incomplete"
           --#TYPE      "Management Agent Event"
           --#SUMMARY   "Host %s : SCellName-TimeDate %s : EventCode %d : Description %s"
           --#ARGUMENTS {0,1,2,3,}
            --#SEVERITY  MINOR
            --#TIMEINDEX 136
        ::= 136000090
 
   mngmtAgentTrap-91 TRAP-TYPE
        ENTERPRISE compaq
        VARIABLES  { hostName,
                     scellNameDateTime,
                     agentEventCode,
                     agentEventDescription }
        DESCRIPTION
             "Redundancy Mirrored Inoperative"
           --#TYPE      "Management Agent Event"
           --#SUMMARY   "Host %s : SCellName-TimeDate %s : EventCode %d : Description %s"
           --#ARGUMENTS {0,1,2,3,}
            --#SEVERITY  INFORMATIONAL
            --#TIMEINDEX 136
        ::= 136000091
 
   mngmtAgentTrap-92 TRAP-TYPE
        ENTERPRISE compaq
        VARIABLES  { hostName,
                     scellNameDateTime,
                     agentEventCode,
                     agentEventDescription }
        DESCRIPTION
             "Duplicate LUN"
           --#TYPE      "Management Agent Event"
           --#SUMMARY   "Host %s : SCellName-TimeDate %s : EventCode %d : Description %s"
           --#ARGUMENTS {0,1,2,3,}
            --#SEVERITY  INFORMATIONAL
            --#TIMEINDEX 136
        ::= 136000092
 
   mngmtAgentTrap-93 TRAP-TYPE
        ENTERPRISE compaq
        VARIABLES  { hostName,
                     scellNameDateTime,
                     agentEventCode,
                     agentEventDescription }
        DESCRIPTION
             "Other remote controller failed"
           --#TYPE      "Management Agent Event"
           --#SUMMARY   "Host %s : SCellName-TimeDate %s : EventCode %d : Description %s"
           --#ARGUMENTS {0,1,2,3,}
            --#SEVERITY  MINOR
            --#TIMEINDEX 136
        ::= 136000093
 
   mngmtAgentTrap-94 TRAP-TYPE
        ENTERPRISE compaq
        VARIABLES  { hostName,
                     scellNameDateTime,
                     agentEventCode,
                     agentEventDescription }
        DESCRIPTION
             "Unknown remote Vdisk"
           --#TYPE      "Management Agent Event"
           --#SUMMARY   "Host %s : SCellName-TimeDate %s : EventCode %d : Description %s"
           --#ARGUMENTS {0,1,2,3,}
            --#SEVERITY  INFORMATIONAL
            --#TIMEINDEX 136
        ::= 136000094
 
   mngmtAgentTrap-95 TRAP-TYPE
        ENTERPRISE compaq
        VARIABLES  { hostName,
                     scellNameDateTime,
                     agentEventCode,
                     agentEventDescription }
        DESCRIPTION
             "Unknown remote DR group"
           --#TYPE      "Management Agent Event"
           --#SUMMARY   "Host %s : SCellName-TimeDate %s : EventCode %d : Description %s"
           --#ARGUMENTS {0,1,2,3,}
            --#SEVERITY  INFORMATIONAL
            --#TIMEINDEX 136
        ::= 136000095
 
   mngmtAgentTrap-96 TRAP-TYPE
        ENTERPRISE compaq
        VARIABLES  { hostName,
                     scellNameDateTime,
                     agentEventCode,
                     agentEventDescription }
        DESCRIPTION
             "PLDMC failed"
           --#TYPE      "Management Agent Event"
           --#SUMMARY   "Host %s : SCellName-TimeDate %s : EventCode %d : Description %s"
           --#ARGUMENTS {0,1,2,3,}
            --#SEVERITY  CRITICAL
            --#TIMEINDEX 136
        ::= 136000096
 
   mngmtAgentTrap-97 TRAP-TYPE
        ENTERPRISE compaq
        VARIABLES  { hostName,
                     scellNameDateTime,
                     agentEventCode,
                     agentEventDescription }
        DESCRIPTION
             "Storage system could not be locked. System busy. Try command again. "
           --#TYPE      "Management Agent Event"
           --#SUMMARY   "Host %s : SCellName-TimeDate %s : EventCode %d : Description %s"
           --#ARGUMENTS {0,1,2,3,}
            --#SEVERITY  CRITICAL
            --#TIMEINDEX 136
        ::= 136000097
 
   mngmtAgentTrap-98 TRAP-TYPE
        ENTERPRISE compaq
        VARIABLES  { hostName,
                     scellNameDateTime,
                     agentEventCode,
                     agentEventDescription }
        DESCRIPTION
             "Error on remote storage system."
           --#TYPE      "Management Agent Event"
           --#SUMMARY   "Host %s : SCellName-TimeDate %s : EventCode %d : Description %s"
           --#ARGUMENTS {0,1,2,3,}
            --#SEVERITY  INFORMATIONAL
            --#TIMEINDEX 136
        ::= 136000098
 
   mngmtAgentTrap-99 TRAP-TYPE
        ENTERPRISE compaq
        VARIABLES  { hostName,
                     scellNameDateTime,
                     agentEventCode,
                     agentEventDescription }
        DESCRIPTION
             "This operation can only be completed when the source-destination connection is down."
           --#TYPE      "Management Agent Event"
           --#SUMMARY   "Host %s : SCellName-TimeDate %s : EventCode %d : Description %s"
           --#ARGUMENTS {0,1,2,3,}
            --#SEVERITY  INFORMATIONAL
            --#TIMEINDEX 136
        ::= 136000099
 
   mngmtAgentTrap-100 TRAP-TYPE
        ENTERPRISE compaq
        VARIABLES  { hostName,
                     scellNameDateTime,
                     agentEventCode,
                     agentEventDescription }
        DESCRIPTION
             "Login required - password changed."
           --#TYPE      "Management Agent Event"
           --#SUMMARY   "Host %s : SCellName-TimeDate %s : EventCode %d : Description %s"
           --#ARGUMENTS {0,1,2,3,}
            --#SEVERITY  INFORMATIONAL
            --#TIMEINDEX 136
        ::= 136000100
 
   mngmtAgentTrap-101 TRAP-TYPE
        ENTERPRISE compaq
        VARIABLES  { hostName,
                     scellNameDateTime,
                     agentEventCode,
                     agentEventDescription }
        DESCRIPTION
             "Numerous login attempts have been detected that uses an incorrect password. Please update your system's password in the Storage System Access menu."
           --#TYPE      "Management Agent Event"
           --#SUMMARY   "Host %s : SCellName-TimeDate %s : EventCode %d : Description %s"
           --#ARGUMENTS {0,1,2,3,}
            --#SEVERITY  INFORMATIONAL
            --#TIMEINDEX 136
        ::= 136000101
 
   mngmtAgentTrap-102 TRAP-TYPE
        ENTERPRISE compaq
        VARIABLES  { hostName,
                     scellNameDateTime,
                     agentEventCode,
                     agentEventDescription }
        DESCRIPTION
             "Invalid cookie"
           --#TYPE      "Management Agent Event"
           --#SUMMARY   "Host %s : SCellName-TimeDate %s : EventCode %d : Description %s"
           --#ARGUMENTS {0,1,2,3,}
            --#SEVERITY  INFORMATIONAL
            --#TIMEINDEX 136
        ::= 136000102
 
   mngmtAgentTrap-103 TRAP-TYPE
        ENTERPRISE compaq
        VARIABLES  { hostName,
                     scellNameDateTime,
                     agentEventCode,
                     agentEventDescription }
        DESCRIPTION
             "Login timed out"
           --#TYPE      "Management Agent Event"
           --#SUMMARY   "Host %s : SCellName-TimeDate %s : EventCode %d : Description %s"
           --#ARGUMENTS {0,1,2,3,}
            --#SEVERITY  INFORMATIONAL
            --#TIMEINDEX 136
        ::= 136000103
 
   mngmtAgentTrap-104 TRAP-TYPE
        ENTERPRISE compaq
        VARIABLES  { hostName,
                     scellNameDateTime,
                     agentEventCode,
                     agentEventDescription }
        DESCRIPTION
             "Max snapshot depth reached"
           --#TYPE      "Management Agent Event"
           --#SUMMARY   "Host %s : SCellName-TimeDate %s : EventCode %d : Description %s"
           --#ARGUMENTS {0,1,2,3,}
            --#SEVERITY  INFORMATIONAL
            --#TIMEINDEX 136
        ::= 136000104
 
   mngmtAgentTrap-105 TRAP-TYPE
        ENTERPRISE compaq
        VARIABLES  { hostName,
                     scellNameDateTime,
                     agentEventCode,
                     agentEventDescription }
        DESCRIPTION
             "Attribute mismatch"
           --#TYPE      "Management Agent Event"
           --#SUMMARY   "Host %s : SCellName-TimeDate %s : EventCode %d : Description %s"
           --#ARGUMENTS {0,1,2,3,}
            --#SEVERITY  INFORMATIONAL
            --#TIMEINDEX 136
        ::= 136000105
 
   mngmtAgentTrap-106 TRAP-TYPE
        ENTERPRISE compaq
        VARIABLES  { hostName,
                     scellNameDateTime,
                     agentEventCode,
                     agentEventDescription }
        DESCRIPTION
             "The password has been set in Command View EVA. The same password still needs to be set in the controllers."
           --#TYPE      "Management Agent Event"
           --#SUMMARY   "Host %s : SCellName-TimeDate %s : EventCode %d : Description %s"
           --#ARGUMENTS {0,1,2,3,}
            --#SEVERITY  INFORMATIONAL
            --#TIMEINDEX 136
        ::= 136000106
 
   mngmtAgentTrap-107 TRAP-TYPE
        ENTERPRISE compaq
        VARIABLES  { hostName,
                     scellNameDateTime,
                     agentEventCode,
                     agentEventDescription }
        DESCRIPTION
             "Not host port"
           --#TYPE      "Management Agent Event"
           --#SUMMARY   "Host %s : SCellName-TimeDate %s : EventCode %d : Description %s"
           --#ARGUMENTS {0,1,2,3,}
            --#SEVERITY  INFORMATIONAL
            --#TIMEINDEX 136
        ::= 136000107
 
   mngmtAgentTrap-108 TRAP-TYPE
        ENTERPRISE compaq
        VARIABLES  { hostName,
                     scellNameDateTime,
                     agentEventCode,
                     agentEventDescription }
        DESCRIPTION
             "Duplicate Lun WWID"
           --#TYPE      "Management Agent Event"
           --#SUMMARY   "Host %s : SCellName-TimeDate %s : EventCode %d : Description %s"
           --#ARGUMENTS {0,1,2,3,}
            --#SEVERITY  INFORMATIONAL
            --#TIMEINDEX 136
        ::= 136000108
 
   mngmtAgentTrap-109 TRAP-TYPE
        ENTERPRISE compaq
        VARIABLES  { hostName,
                     scellNameDateTime,
                     agentEventCode,
                     agentEventDescription }
        DESCRIPTION
             "System Inoperative"
           --#TYPE      "Management Agent Event"
           --#SUMMARY   "Host %s : SCellName-TimeDate %s : EventCode %d : Description %s"
           --#ARGUMENTS {0,1,2,3,}
            --#SEVERITY  INFORMATIONAL
            --#TIMEINDEX 136
        ::= 136000109
 
   mngmtAgentTrap-110 TRAP-TYPE
        ENTERPRISE compaq
        VARIABLES  { hostName,
                     scellNameDateTime,
                     agentEventCode,
                     agentEventDescription }
        DESCRIPTION
             "SnapClone Active"
           --#TYPE      "Management Agent Event"
           --#SUMMARY   "Host %s : SCellName-TimeDate %s : EventCode %d : Description %s"
           --#ARGUMENTS {0,1,2,3,}
            --#SEVERITY  INFORMATIONAL
            --#TIMEINDEX 136
        ::= 136000110
 
   mngmtAgentTrap-111 TRAP-TYPE
        ENTERPRISE compaq
        VARIABLES  { hostName,
                     scellNameDateTime,
                     agentEventCode,
                     agentEventDescription }
        DESCRIPTION
             "Emu Load Busy"
           --#TYPE      "Management Agent Event"
           --#SUMMARY   "Host %s : SCellName-TimeDate %s : EventCode %d : Description %s"
           --#ARGUMENTS {0,1,2,3,}
            --#SEVERITY  INFORMATIONAL
            --#TIMEINDEX 136
        ::= 136000111
 
   mngmtAgentTrap-112 TRAP-TYPE
        ENTERPRISE compaq
        VARIABLES  { hostName,
                     scellNameDateTime,
                     agentEventCode,
                     agentEventDescription }
        DESCRIPTION
             "Duplicate User Name"
           --#TYPE      "Management Agent Event"
           --#SUMMARY   "Host %s : SCellName-TimeDate %s : EventCode %d : Description %s"
           --#ARGUMENTS {0,1,2,3,}
            --#SEVERITY  INFORMATIONAL
            --#TIMEINDEX 136
        ::= 136000112
 
   mngmtAgentTrap-113 TRAP-TYPE
        ENTERPRISE compaq
        VARIABLES  { hostName,
                     scellNameDateTime,
                     agentEventCode,
                     agentEventDescription }
        DESCRIPTION
             "Drive Reserved For Code Load"
           --#TYPE      "Management Agent Event"
           --#SUMMARY   "Host %s : SCellName-TimeDate %s : EventCode %d : Description %s"
           --#ARGUMENTS {0,1,2,3,}
            --#SEVERITY  INFORMATIONAL
            --#TIMEINDEX 136
        ::= 136000113
 
   mngmtAgentTrap-114 TRAP-TYPE
        ENTERPRISE compaq
        VARIABLES  { hostName,
                     scellNameDateTime,
                     agentEventCode,
                     agentEventDescription }
        DESCRIPTION
             "Already Presented"
           --#TYPE      "Management Agent Event"
           --#SUMMARY   "Host %s : SCellName-TimeDate %s : EventCode %d : Description %s"
           --#ARGUMENTS {0,1,2,3,}
            --#SEVERITY  INFORMATIONAL
            --#TIMEINDEX 136
        ::= 136000114
 
   mngmtAgentTrap-115 TRAP-TYPE
        ENTERPRISE compaq
        VARIABLES  { hostName,
                     scellNameDateTime,
                     agentEventCode,
                     agentEventDescription }
        DESCRIPTION
             "Invalid remote storage system"
           --#TYPE      "Management Agent Event"
           --#SUMMARY   "Host %s : SCellName-TimeDate %s : EventCode %d : Description %s"
           --#ARGUMENTS {0,1,2,3,}
            --#SEVERITY  INFORMATIONAL
            --#TIMEINDEX 136
        ::= 136000115
 
   mngmtAgentTrap-116 TRAP-TYPE
        ENTERPRISE compaq
        VARIABLES  { hostName,
                     scellNameDateTime,
                     agentEventCode,
                     agentEventDescription }
        DESCRIPTION
             "No Lock"
           --#TYPE      "Management Agent Event"
           --#SUMMARY   "Host %s : SCellName-TimeDate %s : EventCode %d : Description %s"
           --#ARGUMENTS {0,1,2,3,}
            --#SEVERITY  INFORMATIONAL
            --#TIMEINDEX 136
        ::= 136000116
 
   mngmtAgentTrap-117 TRAP-TYPE
        ENTERPRISE compaq
        VARIABLES  { hostName,
                     scellNameDateTime,
                     agentEventCode,
                     agentEventDescription }
        DESCRIPTION
             "Maximum Number of Members Exceeded"
           --#TYPE      "Management Agent Event"
           --#SUMMARY   "Host %s : SCellName-TimeDate %s : EventCode %d : Description %s"
           --#ARGUMENTS {0,1,2,3,}
            --#SEVERITY  INFORMATIONAL
            --#TIMEINDEX 136
        ::= 136000117
 
   mngmtAgentTrap-118 TRAP-TYPE
        ENTERPRISE compaq
        VARIABLES  { hostName,
                     scellNameDateTime,
                     agentEventCode,
                     agentEventDescription }
        DESCRIPTION
             "Max Destinations"
           --#TYPE      "Management Agent Event"
           --#SUMMARY   "Host %s : SCellName-TimeDate %s : EventCode %d : Description %s"
           --#ARGUMENTS {0,1,2,3,}
            --#SEVERITY  INFORMATIONAL
            --#TIMEINDEX 136
        ::= 136000118
 
   mngmtAgentTrap-119 TRAP-TYPE
        ENTERPRISE compaq
        VARIABLES  { hostName,
                     scellNameDateTime,
                     agentEventCode,
                     agentEventDescription }
        DESCRIPTION
             "Empty User Name"
           --#TYPE      "Management Agent Event"
           --#SUMMARY   "Host %s : SCellName-TimeDate %s : EventCode %d : Description %s"
           --#ARGUMENTS {0,1,2,3,}
            --#SEVERITY  INFORMATIONAL
            --#TIMEINDEX 136
        ::= 136000119
 
   mngmtAgentTrap-120 TRAP-TYPE
        ENTERPRISE compaq
        VARIABLES  { hostName,
                     scellNameDateTime,
                     agentEventCode,
                     agentEventDescription }
        DESCRIPTION
             "Storage system already initialized"
           --#TYPE      "Management Agent Event"
           --#SUMMARY   "Host %s : SCellName-TimeDate %s : EventCode %d : Description %s"
           --#ARGUMENTS {0,1,2,3,}
            --#SEVERITY  INFORMATIONAL
            --#TIMEINDEX 136
        ::= 136000120
 
   mngmtAgentTrap-121 TRAP-TYPE
        ENTERPRISE compaq
        VARIABLES  { hostName,
                     scellNameDateTime,
                     agentEventCode,
                     agentEventDescription }
        DESCRIPTION
             "Already Open"
           --#TYPE      "Management Agent Event"
           --#SUMMARY   "Host %s : SCellName-TimeDate %s : EventCode %d : Description %s"
           --#ARGUMENTS {0,1,2,3,}
            --#SEVERITY  INFORMATIONAL
            --#TIMEINDEX 136
        ::= 136000121
 
   mngmtAgentTrap-122 TRAP-TYPE
        ENTERPRISE compaq
        VARIABLES  { hostName,
                     scellNameDateTime,
                     agentEventCode,
                     agentEventDescription }
        DESCRIPTION
             "Session Not Open"
           --#TYPE      "Management Agent Event"
           --#SUMMARY   "Host %s : SCellName-TimeDate %s : EventCode %d : Description %s"
           --#ARGUMENTS {0,1,2,3,}
            --#SEVERITY  INFORMATIONAL
            --#TIMEINDEX 136
        ::= 136000122
 
   mngmtAgentTrap-123 TRAP-TYPE
        ENTERPRISE compaq
        VARIABLES  { hostName,
                     scellNameDateTime,
                     agentEventCode,
                     agentEventDescription }
        DESCRIPTION
             "Not Marked Inoperative"
           --#TYPE      "Management Agent Event"
           --#SUMMARY   "Host %s : SCellName-TimeDate %s : EventCode %d : Description %s"
           --#ARGUMENTS {0,1,2,3,}
            --#SEVERITY  INFORMATIONAL
            --#TIMEINDEX 136
        ::= 136000123
 
   mngmtAgentTrap-124 TRAP-TYPE
        ENTERPRISE compaq
        VARIABLES  { hostName,
                     scellNameDateTime,
                     agentEventCode,
                     agentEventDescription }
        DESCRIPTION
             "Media Not Available"
           --#TYPE      "Management Agent Event"
           --#SUMMARY   "Host %s : SCellName-TimeDate %s : EventCode %d : Description %s"
           --#ARGUMENTS {0,1,2,3,}
            --#SEVERITY  INFORMATIONAL
            --#TIMEINDEX 136
        ::= 136000124
 
   mngmtAgentTrap-125 TRAP-TYPE
        ENTERPRISE compaq
        VARIABLES  { hostName,
                     scellNameDateTime,
                     agentEventCode,
                     agentEventDescription }
        DESCRIPTION
             "Battery System Failed"
           --#TYPE      "Management Agent Event"
           --#SUMMARY   "Host %s : SCellName-TimeDate %s : EventCode %d : Description %s"
           --#ARGUMENTS {0,1,2,3,}
            --#SEVERITY  INFORMATIONAL
            --#TIMEINDEX 136
        ::= 136000125
 
   mngmtAgentTrap-126 TRAP-TYPE
        ENTERPRISE compaq
        VARIABLES  { hostName,
                     scellNameDateTime,
                     agentEventCode,
                     agentEventDescription }
        DESCRIPTION
             "DR Group Member Is Cache Data Lost"
           --#TYPE      "Management Agent Event"
           --#SUMMARY   "Host %s : SCellName-TimeDate %s : EventCode %d : Description %s"
           --#ARGUMENTS {0,1,2,3,}
            --#SEVERITY  INFORMATIONAL
            --#TIMEINDEX 136
        ::= 136000126
 
   mngmtAgentTrap-127 TRAP-TYPE
        ENTERPRISE compaq
        VARIABLES  { hostName,
                     scellNameDateTime,
                     agentEventCode,
                     agentEventDescription }
        DESCRIPTION
             "Internal Lock Collision"
           --#TYPE      "Management Agent Event"
           --#SUMMARY   "Host %s : SCellName-TimeDate %s : EventCode %d : Description %s"
           --#ARGUMENTS {0,1,2,3,}
            --#SEVERITY  INFORMATIONAL
            --#TIMEINDEX 136
        ::= 136000127
 
   mngmtAgentTrap-128 TRAP-TYPE
        ENTERPRISE compaq
        VARIABLES  { hostName,
                     scellNameDateTime,
                     agentEventCode,
                     agentEventDescription }
        DESCRIPTION
             "OCP Error"
           --#TYPE      "Management Agent Event"
           --#SUMMARY   "Host %s : SCellName-TimeDate %s : EventCode %d : Description %s"
           --#ARGUMENTS {0,1,2,3,}
            --#SEVERITY  INFORMATIONAL
            --#TIMEINDEX 136
        ::= 136000128
 
   mngmtAgentTrap-129 TRAP-TYPE
        ENTERPRISE compaq
        VARIABLES  { hostName,
                     scellNameDateTime,
                     agentEventCode,
                     agentEventDescription }
        DESCRIPTION
             "Mirror Offline"
           --#TYPE      "Management Agent Event"
           --#SUMMARY   "Host %s : SCellName-TimeDate %s : EventCode %d : Description %s"
           --#ARGUMENTS {0,1,2,3,}
            --#SEVERITY  INFORMATIONAL
            --#TIMEINDEX 136
        ::= 136000129
 
   mngmtAgentTrap-130 TRAP-TYPE
        ENTERPRISE compaq
        VARIABLES  { hostName,
                     scellNameDateTime,
                     agentEventCode,
                     agentEventDescription }
        DESCRIPTION
             "This operation cannot be completed if failsafe mode is enabled."
           --#TYPE      "Management Agent Event"
           --#SUMMARY   "Host %s : SCellName-TimeDate %s : EventCode %d : Description %s"
           --#ARGUMENTS {0,1,2,3,}
            --#SEVERITY  INFORMATIONAL
            --#TIMEINDEX 136
        ::= 136000130
 
   mngmtAgentTrap-131 TRAP-TYPE
        ENTERPRISE compaq
        VARIABLES  { hostName,
                     scellNameDateTime,
                     agentEventCode,
                     agentEventDescription }
        DESCRIPTION
             "Drive firmware load abort due to Raid0 virtual disk(s)."
           --#TYPE      "Management Agent Event"
           --#SUMMARY   "Host %s : SCellName-TimeDate %s : EventCode %d : Description %s"
           --#ARGUMENTS {0,1,2,3,}
            --#SEVERITY  INFORMATIONAL
            --#TIMEINDEX 136
        ::= 136000131
 
   mngmtAgentTrap-132 TRAP-TYPE
        ENTERPRISE compaq
        VARIABLES  { hostName,
                     scellNameDateTime,
                     agentEventCode,
                     agentEventDescription }
        DESCRIPTION
             "Fibre channel ports are unavailable."
           --#TYPE      "Management Agent Event"
           --#SUMMARY   "Host %s : SCellName-TimeDate %s : EventCode %d : Description %s"
           --#ARGUMENTS {0,1,2,3,}
            --#SEVERITY  INFORMATIONAL
            --#TIMEINDEX 136
        ::= 136000132
 
   mngmtAgentTrap-133 TRAP-TYPE
        ENTERPRISE compaq
        VARIABLES  { hostName,
                     scellNameDateTime,
                     agentEventCode,
                     agentEventDescription }
        DESCRIPTION
             "The storage system has reached its maximum number of DR relationship."
           --#TYPE      "Management Agent Event"
           --#SUMMARY   "Host %s : SCellName-TimeDate %s : EventCode %d : Description %s"
           --#ARGUMENTS {0,1,2,3,}
            --#SEVERITY  INFORMATIONAL
            --#TIMEINDEX 136
        ::= 136000133
 
   mngmtAgentTrap-1000 TRAP-TYPE
        ENTERPRISE compaq
        VARIABLES  { hostName,
                     scellNameDateTime,
                     agentEventCode,
                     agentEventDescription }
        DESCRIPTION
             "Logical Disk Condition Change"
           --#TYPE      "Management Agent Event"
           --#SUMMARY   "Host %s : SCellName-TimeDate %s : EventCode %d : Description %s"
           --#ARGUMENTS {0,1,2,3,}
            --#SEVERITY  INFORMATIONAL
            --#TIMEINDEX 136
        ::= 136001000
 
   mngmtAgentTrap-1001 TRAP-TYPE
        ENTERPRISE compaq
        VARIABLES  { hostName,
                     scellNameDateTime,
                     agentEventCode,
                     agentEventDescription }
        DESCRIPTION
             "Storage system is FULL  **critical**"
           --#TYPE      "Management Agent Event"
           --#SUMMARY   "Host %s : SCellName-TimeDate %s : EventCode %d : Description %s"
           --#ARGUMENTS {0,1,2,3,}
            --#SEVERITY  CRITICAL
            --#TIMEINDEX 136
        ::= 136001001
 
   mngmtAgentTrap-1002 TRAP-TYPE
        ENTERPRISE compaq
        VARIABLES  { hostName,
                     scellNameDateTime,
                     agentEventCode,
                     agentEventDescription }
        DESCRIPTION
             "Storage system is almost FULL. Disk group at or above maximum capacity warning level."
           --#TYPE      "Management Agent Event"
           --#SUMMARY   "Host %s : SCellName-TimeDate %s : EventCode %d : Description %s"
           --#ARGUMENTS {0,1,2,3,}
            --#SEVERITY  MINOR
            --#TIMEINDEX 136
        ::= 136001002
 
   mngmtAgentTrap-1003 TRAP-TYPE
        ENTERPRISE compaq
        VARIABLES  { hostName,
                     scellNameDateTime,
                     agentEventCode,
                     agentEventDescription }
        DESCRIPTION
             "Controller Cache Battery Condition Change"
           --#TYPE      "Management Agent Event"
           --#SUMMARY   "Host %s : SCellName-TimeDate %s : EventCode %d : Description %s"
           --#ARGUMENTS {0,1,2,3,}
            --#SEVERITY  INFORMATIONAL
            --#TIMEINDEX 136
        ::= 136001003
 
   mngmtAgentTrap-1004 TRAP-TYPE
        ENTERPRISE compaq
        VARIABLES  { hostName,
                     scellNameDateTime,
                     agentEventCode,
                     agentEventDescription }
        DESCRIPTION
             "Controller Cache Condition Change"
           --#TYPE      "Management Agent Event"
           --#SUMMARY   "Host %s : SCellName-TimeDate %s : EventCode %d : Description %s"
           --#ARGUMENTS {0,1,2,3,}
            --#SEVERITY  INFORMATIONAL
            --#TIMEINDEX 136
        ::= 136001004
 
   mngmtAgentTrap-1005 TRAP-TYPE
        ENTERPRISE compaq
        VARIABLES  { hostName,
                     scellNameDateTime,
                     agentEventCode,
                     agentEventDescription }
        DESCRIPTION
             "Controller Condition Change"
           --#TYPE      "Management Agent Event"
           --#SUMMARY   "Host %s : SCellName-TimeDate %s : EventCode %d : Description %s"
           --#ARGUMENTS {0,1,2,3,}
            --#SEVERITY  INFORMATIONAL
            --#TIMEINDEX 136
        ::= 136001005
 
   mngmtAgentTrap-1006 TRAP-TYPE
        ENTERPRISE compaq
        VARIABLES  { hostName,
                     scellNameDateTime,
                     agentEventCode,
                     agentEventDescription }
        DESCRIPTION
             "Controller FC Port Condition Change"
           --#TYPE      "Management Agent Event"
           --#SUMMARY   "Host %s : SCellName-TimeDate %s : EventCode %d : Description %s"
           --#ARGUMENTS {0,1,2,3,}
            --#SEVERITY  INFORMATIONAL
            --#TIMEINDEX 136
        ::= 136001006
 
   mngmtAgentTrap-1007 TRAP-TYPE
        ENTERPRISE compaq
        VARIABLES  { hostName,
                     scellNameDateTime,
                     agentEventCode,
                     agentEventDescription }
        DESCRIPTION
             "Physical Device Condition Change"
           --#TYPE      "Management Agent Event"
           --#SUMMARY   "Host %s : SCellName-TimeDate %s : EventCode %d : Description %s"
           --#ARGUMENTS {0,1,2,3,}
            --#SEVERITY  INFORMATIONAL
            --#TIMEINDEX 136
        ::= 136001007
 
   mngmtAgentTrap-1008 TRAP-TYPE
        ENTERPRISE compaq
        VARIABLES  { hostName,
                     scellNameDateTime,
                     agentEventCode,
                     agentEventDescription }
        DESCRIPTION
             "Physical Store Condition Change"
           --#TYPE      "Management Agent Event"
           --#SUMMARY   "Host %s : SCellName-TimeDate %s : EventCode %d : Description %s"
           --#ARGUMENTS {0,1,2,3,}
            --#SEVERITY  INFORMATIONAL
            --#TIMEINDEX 136
        ::= 136001008
 
   mngmtAgentTrap-1009 TRAP-TYPE
        ENTERPRISE compaq
        VARIABLES  { hostName,
                     scellNameDateTime,
                     agentEventCode,
                     agentEventDescription }
        DESCRIPTION
             "Host condition change"
           --#TYPE      "Management Agent Event"
           --#SUMMARY   "Host %s : SCellName-TimeDate %s : EventCode %d : Description %s"
           --#ARGUMENTS {0,1,2,3,}
            --#SEVERITY  INFORMATIONAL
            --#TIMEINDEX 136
        ::= 136001009
 
   mngmtAgentTrap-1010 TRAP-TYPE
        ENTERPRISE compaq
        VARIABLES  { hostName,
                     scellNameDateTime,
                     agentEventCode,
                     agentEventDescription }
        DESCRIPTION
             "Storage system time has been set"
           --#TYPE      "Management Agent Event"
           --#SUMMARY   "Host %s : SCellName-TimeDate %s : EventCode %d : Description %s"
           --#ARGUMENTS {0,1,2,3,}
            --#SEVERITY  INFORMATIONAL
            --#TIMEINDEX 136
        ::= 136001010
 
   mngmtAgentTrap-1011 TRAP-TYPE
        ENTERPRISE compaq
        VARIABLES  { hostName,
                     scellNameDateTime,
                     agentEventCode,
                     agentEventDescription }
        DESCRIPTION
             "Volume Condition change"
           --#TYPE      "Management Agent Event"
           --#SUMMARY   "Host %s : SCellName-TimeDate %s : EventCode %d : Description %s"
           --#ARGUMENTS {0,1,2,3,}
            --#SEVERITY  INFORMATIONAL
            --#TIMEINDEX 136
        ::= 136001011
 
   mngmtAgentTrap-1012 TRAP-TYPE
        ENTERPRISE compaq
        VARIABLES  { hostName,
                     scellNameDateTime,
                     agentEventCode,
                     agentEventDescription }
        DESCRIPTION
             "Volume insufficient-resources condition change"
           --#TYPE      "Management Agent Event"
           --#SUMMARY   "Host %s : SCellName-TimeDate %s : EventCode %d : Description %s"
           --#ARGUMENTS {0,1,2,3,}
            --#SEVERITY  INFORMATIONAL
            --#TIMEINDEX 136
        ::= 136001012
 
   mngmtAgentTrap-1013 TRAP-TYPE
        ENTERPRISE compaq
        VARIABLES  { hostName,
                     scellNameDateTime,
                     agentEventCode,
                     agentEventDescription }
        DESCRIPTION
             "Volume Quorum Disk change"
           --#TYPE      "Management Agent Event"
           --#SUMMARY   "Host %s : SCellName-TimeDate %s : EventCode %d : Description %s"
           --#ARGUMENTS {0,1,2,3,}
            --#SEVERITY  INFORMATIONAL
            --#TIMEINDEX 136
        ::= 136001013
 
   mngmtAgentTrap-1014 TRAP-TYPE
        ENTERPRISE compaq
        VARIABLES  { hostName,
                     scellNameDateTime,
                     agentEventCode,
                     agentEventDescription }
        DESCRIPTION
             "The state of an object in the system has changed. View adjacent events for more detail."
           --#TYPE      "Management Agent Event"
           --#SUMMARY   "Host %s : SCellName-TimeDate %s : EventCode %d : Description %s"
           --#ARGUMENTS {0,1,2,3,}
            --#SEVERITY  INFORMATIONAL
            --#TIMEINDEX 136
        ::= 136001014
 
   mngmtAgentTrap-2001 TRAP-TYPE
        ENTERPRISE compaq
        VARIABLES  { hostName,
                     scellNameDateTime,
                     agentEventCode,
                     agentEventDescription }
        DESCRIPTION
             "Startup Failed"
           --#TYPE      "Management Agent Event"
           --#SUMMARY   "Host %s : SCellName-TimeDate %s : EventCode %d : Description %s"
           --#ARGUMENTS {0,1,2,3,}
            --#SEVERITY  CRITICAL
            --#TIMEINDEX 136
        ::= 136002001
 
   mngmtAgentTrap-2002 TRAP-TYPE
        ENTERPRISE compaq
        VARIABLES  { hostName,
                     scellNameDateTime,
                     agentEventCode,
                     agentEventDescription }
        DESCRIPTION
             "Management agent event log cleared successfully"
           --#TYPE      "Management Agent Event"
           --#SUMMARY   "Host %s : SCellName-TimeDate %s : EventCode %d : Description %s"
           --#ARGUMENTS {0,1,2,3,}
            --#SEVERITY  INFORMATIONAL
            --#TIMEINDEX 136
        ::= 136002002
 
   mngmtAgentTrap-2003 TRAP-TYPE
        ENTERPRISE compaq
        VARIABLES  { hostName,
                     scellNameDateTime,
                     agentEventCode,
                     agentEventDescription }
        DESCRIPTION
             "Invalid name specified for storage system"
           --#TYPE      "Management Agent Event"
           --#SUMMARY   "Host %s : SCellName-TimeDate %s : EventCode %d : Description %s"
           --#ARGUMENTS {0,1,2,3,}
            --#SEVERITY  MINOR
            --#TIMEINDEX 136
        ::= 136002003
 
   mngmtAgentTrap-2004 TRAP-TYPE
        ENTERPRISE compaq
        VARIABLES  { hostName,
                     scellNameDateTime,
                     agentEventCode,
                     agentEventDescription }
        DESCRIPTION
             "Storage system is not initialized"
           --#TYPE      "Management Agent Event"
           --#SUMMARY   "Host %s : SCellName-TimeDate %s : EventCode %d : Description %s"
           --#ARGUMENTS {0,1,2,3,}
            --#SEVERITY  INFORMATIONAL
            --#TIMEINDEX 136
        ::= 136002004
 
   mngmtAgentTrap-2006 TRAP-TYPE
        ENTERPRISE compaq
        VARIABLES  { hostName,
                     scellNameDateTime,
                     agentEventCode,
                     agentEventDescription }
        DESCRIPTION
             "Invalid name specified for Vdisk"
           --#TYPE      "Management Agent Event"
           --#SUMMARY   "Host %s : SCellName-TimeDate %s : EventCode %d : Description %s"
           --#ARGUMENTS {0,1,2,3,}
            --#SEVERITY  MINOR
            --#TIMEINDEX 136
        ::= 136002006
 
   mngmtAgentTrap-2007 TRAP-TYPE
        ENTERPRISE compaq
        VARIABLES  { hostName,
                     scellNameDateTime,
                     agentEventCode,
                     agentEventDescription }
        DESCRIPTION
             "Vdisk name exceeds maximum length"
           --#TYPE      "Management Agent Event"
           --#SUMMARY   "Host %s : SCellName-TimeDate %s : EventCode %d : Description %s"
           --#ARGUMENTS {0,1,2,3,}
            --#SEVERITY  MINOR
            --#TIMEINDEX 136
        ::= 136002007
 
   mngmtAgentTrap-2008 TRAP-TYPE
        ENTERPRISE compaq
        VARIABLES  { hostName,
                     scellNameDateTime,
                     agentEventCode,
                     agentEventDescription }
        DESCRIPTION
             "Invalid parameter specified for Vdisk"
           --#TYPE      "Management Agent Event"
           --#SUMMARY   "Host %s : SCellName-TimeDate %s : EventCode %d : Description %s"
           --#ARGUMENTS {0,1,2,3,}
            --#SEVERITY  MINOR
            --#TIMEINDEX 136
        ::= 136002008
 
   mngmtAgentTrap-2010 TRAP-TYPE
        ENTERPRISE compaq
        VARIABLES  { hostName,
                     scellNameDateTime,
                     agentEventCode,
                     agentEventDescription }
        DESCRIPTION
             "Specified Vdisk size exceeds available size"
           --#TYPE      "Management Agent Event"
           --#SUMMARY   "Host %s : SCellName-TimeDate %s : EventCode %d : Description %s"
           --#ARGUMENTS {0,1,2,3,}
            --#SEVERITY  MINOR
            --#TIMEINDEX 136
        ::= 136002010
 
   mngmtAgentTrap-2011 TRAP-TYPE
        ENTERPRISE compaq
        VARIABLES  { hostName,
                     scellNameDateTime,
                     agentEventCode,
                     agentEventDescription }
        DESCRIPTION
             "There are not enough disk drives to create a disk group"
           --#TYPE      "Management Agent Event"
           --#SUMMARY   "Host %s : SCellName-TimeDate %s : EventCode %d : Description %s"
           --#ARGUMENTS {0,1,2,3,}
            --#SEVERITY  INFORMATIONAL
            --#TIMEINDEX 136
        ::= 136002011
 
   mngmtAgentTrap-2012 TRAP-TYPE
        ENTERPRISE compaq
        VARIABLES  { hostName,
                     scellNameDateTime,
                     agentEventCode,
                     agentEventDescription }
        DESCRIPTION
             "Number of devices exceeds the available number of disks"
           --#TYPE      "Management Agent Event"
           --#SUMMARY   "Host %s : SCellName-TimeDate %s : EventCode %d : Description %s"
           --#ARGUMENTS {0,1,2,3,}
            --#SEVERITY  MINOR
            --#TIMEINDEX 136
        ::= 136002012
 
   mngmtAgentTrap-2013 TRAP-TYPE
        ENTERPRISE compaq
        VARIABLES  { hostName,
                     scellNameDateTime,
                     agentEventCode,
                     agentEventDescription }
        DESCRIPTION
             "Number of devices is less than the minimum number required to create a disk group"
           --#TYPE      "Management Agent Event"
           --#SUMMARY   "Host %s : SCellName-TimeDate %s : EventCode %d : Description %s"
           --#ARGUMENTS {0,1,2,3,}
            --#SEVERITY  MINOR
            --#TIMEINDEX 136
        ::= 136002013
 
   mngmtAgentTrap-2016 TRAP-TYPE
        ENTERPRISE compaq
        VARIABLES  { hostName,
                     scellNameDateTime,
                     agentEventCode,
                     agentEventDescription }
        DESCRIPTION
             "Completed unpresenting virtual disk to host"
           --#TYPE      "Management Agent Event"
           --#SUMMARY   "Host %s : SCellName-TimeDate %s : EventCode %d : Description %s"
           --#ARGUMENTS {0,1,2,3,}
            --#SEVERITY  MINOR
            --#TIMEINDEX 136
        ::= 136002016
 
   mngmtAgentTrap-2021 TRAP-TYPE
        ENTERPRISE compaq
        VARIABLES  { hostName,
                     scellNameDateTime,
                     agentEventCode,
                     agentEventDescription }
        DESCRIPTION
             "Invalid refresh interval value. Should be numeric and non-negative."
           --#TYPE      "Management Agent Event"
           --#SUMMARY   "Host %s : SCellName-TimeDate %s : EventCode %d : Description %s"
           --#ARGUMENTS {0,1,2,3,}
            --#SEVERITY  MINOR
            --#TIMEINDEX 136
        ::= 136002021
 
   mngmtAgentTrap-2022 TRAP-TYPE
        ENTERPRISE compaq
        VARIABLES  { hostName,
                     scellNameDateTime,
                     agentEventCode,
                     agentEventDescription }
        DESCRIPTION
             "Invalid security message. Should not be blank."
           --#TYPE      "Management Agent Event"
           --#SUMMARY   "Host %s : SCellName-TimeDate %s : EventCode %d : Description %s"
           --#ARGUMENTS {0,1,2,3,}
            --#SEVERITY  MINOR
            --#TIMEINDEX 136
        ::= 136002022
 
   mngmtAgentTrap-2023 TRAP-TYPE
        ENTERPRISE compaq
        VARIABLES  { hostName,
                     scellNameDateTime,
                     agentEventCode,
                     agentEventDescription }
        DESCRIPTION
             "Vdisk Create Complete"
           --#TYPE      "Management Agent Event"
           --#SUMMARY   "Host %s : SCellName-TimeDate %s : EventCode %d : Description %s"
           --#ARGUMENTS {0,1,2,3,}
            --#SEVERITY  INFORMATIONAL
            --#TIMEINDEX 136
        ::= 136002023
 
   mngmtAgentTrap-2025 TRAP-TYPE
        ENTERPRISE compaq
        VARIABLES  { hostName,
                     scellNameDateTime,
                     agentEventCode,
                     agentEventDescription }
        DESCRIPTION
             "Storage system successfully initialized"
           --#TYPE      "Management Agent Event"
           --#SUMMARY   "Host %s : SCellName-TimeDate %s : EventCode %d : Description %s"
           --#ARGUMENTS {0,1,2,3,}
            --#SEVERITY  INFORMATIONAL
            --#TIMEINDEX 136
        ::= 136002025
 
   mngmtAgentTrap-2026 TRAP-TYPE
        ENTERPRISE compaq
        VARIABLES  { hostName,
                     scellNameDateTime,
                     agentEventCode,
                     agentEventDescription }
        DESCRIPTION
             "Device Added Successfully"
           --#TYPE      "Management Agent Event"
           --#SUMMARY   "Host %s : SCellName-TimeDate %s : EventCode %d : Description %s"
           --#ARGUMENTS {0,1,2,3,}
            --#SEVERITY  INFORMATIONAL
            --#TIMEINDEX 136
        ::= 136002026
 
   mngmtAgentTrap-2030 TRAP-TYPE
        ENTERPRISE compaq
        VARIABLES  { hostName,
                     scellNameDateTime,
                     agentEventCode,
                     agentEventDescription }
        DESCRIPTION
             "Refresh Interval Changed"
           --#TYPE      "Management Agent Event"
           --#SUMMARY   "Host %s : SCellName-TimeDate %s : EventCode %d : Description %s"
           --#ARGUMENTS {0,1,2,3,}
            --#SEVERITY  INFORMATIONAL
            --#TIMEINDEX 136
        ::= 136002030
 
   mngmtAgentTrap-2031 TRAP-TYPE
        ENTERPRISE compaq
        VARIABLES  { hostName,
                     scellNameDateTime,
                     agentEventCode,
                     agentEventDescription }
        DESCRIPTION
             "Security Message Changed"
           --#TYPE      "Management Agent Event"
           --#SUMMARY   "Host %s : SCellName-TimeDate %s : EventCode %d : Description %s"
           --#ARGUMENTS {0,1,2,3,}
            --#SEVERITY  INFORMATIONAL
            --#TIMEINDEX 136
        ::= 136002031
 
   mngmtAgentTrap-2032 TRAP-TYPE
        ENTERPRISE compaq
        VARIABLES  { hostName,
                     scellNameDateTime,
                     agentEventCode,
                     agentEventDescription }
        DESCRIPTION
             "Present Vdisk to a Host - Complete"
           --#TYPE      "Management Agent Event"
           --#SUMMARY   "Host %s : SCellName-TimeDate %s : EventCode %d : Description %s"
           --#ARGUMENTS {0,1,2,3,}
            --#SEVERITY  INFORMATIONAL
            --#TIMEINDEX 136
        ::= 136002032
 
   mngmtAgentTrap-2033 TRAP-TYPE
        ENTERPRISE compaq
        VARIABLES  { hostName,
                     scellNameDateTime,
                     agentEventCode,
                     agentEventDescription }
        DESCRIPTION
             "Control Startup Complete"
           --#TYPE      "Management Agent Event"
           --#SUMMARY   "Host %s : SCellName-TimeDate %s : EventCode %d : Description %s"
           --#ARGUMENTS {0,1,2,3,}
            --#SEVERITY  INFORMATIONAL
            --#TIMEINDEX 136
        ::= 136002033
 
   mngmtAgentTrap-2034 TRAP-TYPE
        ENTERPRISE compaq
        VARIABLES  { hostName,
                     scellNameDateTime,
                     agentEventCode,
                     agentEventDescription }
        DESCRIPTION
             "Change Device Usage Complete"
           --#TYPE      "Management Agent Event"
           --#SUMMARY   "Host %s : SCellName-TimeDate %s : EventCode %d : Description %s"
           --#ARGUMENTS {0,1,2,3,}
            --#SEVERITY  INFORMATIONAL
            --#TIMEINDEX 136
        ::= 136002034
 
   mngmtAgentTrap-2035 TRAP-TYPE
        ENTERPRISE compaq
        VARIABLES  { hostName,
                     scellNameDateTime,
                     agentEventCode,
                     agentEventDescription }
        DESCRIPTION
             "Control Shutdown - Complete"
           --#TYPE      "Management Agent Event"
           --#SUMMARY   "Host %s : SCellName-TimeDate %s : EventCode %d : Description %s"
           --#ARGUMENTS {0,1,2,3,}
            --#SEVERITY  INFORMATIONAL
            --#TIMEINDEX 136
        ::= 136002035
 
   mngmtAgentTrap-2036 TRAP-TYPE
        ENTERPRISE compaq
        VARIABLES  { hostName,
                     scellNameDateTime,
                     agentEventCode,
                     agentEventDescription }
        DESCRIPTION
             "Controller Shutdown - Complete"
           --#TYPE      "Management Agent Event"
           --#SUMMARY   "Host %s : SCellName-TimeDate %s : EventCode %d : Description %s"
           --#ARGUMENTS {0,1,2,3,}
            --#SEVERITY  INFORMATIONAL
            --#TIMEINDEX 136
        ::= 136002036
 
   mngmtAgentTrap-2038 TRAP-TYPE
        ENTERPRISE compaq
        VARIABLES  { hostName,
                     scellNameDateTime,
                     agentEventCode,
                     agentEventDescription }
        DESCRIPTION
             "Control Memory Allocation Failure"
           --#TYPE      "Management Agent Event"
           --#SUMMARY   "Host %s : SCellName-TimeDate %s : EventCode %d : Description %s"
           --#ARGUMENTS {0,1,2,3,}
            --#SEVERITY  CRITICAL
            --#TIMEINDEX 136
        ::= 136002038
 
   mngmtAgentTrap-2040 TRAP-TYPE
        ENTERPRISE compaq
        VARIABLES  { hostName,
                     scellNameDateTime,
                     agentEventCode,
                     agentEventDescription }
        DESCRIPTION
             "Access level denied or session activity timeout. Please log in again."
           --#TYPE      "Management Agent Event"
           --#SUMMARY   "Host %s : SCellName-TimeDate %s : EventCode %d : Description %s"
           --#ARGUMENTS {0,1,2,3,}
            --#SEVERITY  INFORMATIONAL
            --#TIMEINDEX 136
        ::= 136002040
 
   mngmtAgentTrap-2041 TRAP-TYPE
        ENTERPRISE compaq
        VARIABLES  { hostName,
                     scellNameDateTime,
                     agentEventCode,
                     agentEventDescription }
        DESCRIPTION
             "Vdisk Snapshot - Completed"
           --#TYPE      "Management Agent Event"
           --#SUMMARY   "Host %s : SCellName-TimeDate %s : EventCode %d : Description %s"
           --#ARGUMENTS {0,1,2,3,}
            --#SEVERITY  INFORMATIONAL
            --#TIMEINDEX 136
        ::= 136002041
 
   mngmtAgentTrap-2042 TRAP-TYPE
        ENTERPRISE compaq
        VARIABLES  { hostName,
                     scellNameDateTime,
                     agentEventCode,
                     agentEventDescription }
        DESCRIPTION
             "Vdisk Snapclone - Completed"
           --#TYPE      "Management Agent Event"
           --#SUMMARY   "Host %s : SCellName-TimeDate %s : EventCode %d : Description %s"
           --#ARGUMENTS {0,1,2,3,}
            --#SEVERITY  INFORMATIONAL
            --#TIMEINDEX 136
        ::= 136002042
 
   mngmtAgentTrap-2047 TRAP-TYPE
        ENTERPRISE compaq
        VARIABLES  { hostName,
                     scellNameDateTime,
                     agentEventCode,
                     agentEventDescription }
        DESCRIPTION
             "Host record added successfully"
           --#TYPE      "Management Agent Event"
           --#SUMMARY   "Host %s : SCellName-TimeDate %s : EventCode %d : Description %s"
           --#ARGUMENTS {0,1,2,3,}
            --#SEVERITY  INFORMATIONAL
            --#TIMEINDEX 136
        ::= 136002047
 
   mngmtAgentTrap-2048 TRAP-TYPE
        ENTERPRISE compaq
        VARIABLES  { hostName,
                     scellNameDateTime,
                     agentEventCode,
                     agentEventDescription }
        DESCRIPTION
             "Logical component deleted successfully"
           --#TYPE      "Management Agent Event"
           --#SUMMARY   "Host %s : SCellName-TimeDate %s : EventCode %d : Description %s"
           --#ARGUMENTS {0,1,2,3,}
            --#SEVERITY  INFORMATIONAL
            --#TIMEINDEX 136
        ::= 136002048
 
   mngmtAgentTrap-2049 TRAP-TYPE
        ENTERPRISE compaq
        VARIABLES  { hostName,
                     scellNameDateTime,
                     agentEventCode,
                     agentEventDescription }
        DESCRIPTION
             "Invalid host adapter ID"
           --#TYPE      "Management Agent Event"
           --#SUMMARY   "Host %s : SCellName-TimeDate %s : EventCode %d : Description %s"
           --#ARGUMENTS {0,1,2,3,}
            --#SEVERITY  INFORMATIONAL
            --#TIMEINDEX 136
        ::= 136002049
 
   mngmtAgentTrap-2050 TRAP-TYPE
        ENTERPRISE compaq
        VARIABLES  { hostName,
                     scellNameDateTime,
                     agentEventCode,
                     agentEventDescription }
        DESCRIPTION
             "Specified device is already a member of the system"
           --#TYPE      "Management Agent Event"
           --#SUMMARY   "Host %s : SCellName-TimeDate %s : EventCode %d : Description %s"
           --#ARGUMENTS {0,1,2,3,}
            --#SEVERITY  INFORMATIONAL
            --#TIMEINDEX 136
        ::= 136002050
 
   mngmtAgentTrap-2051 TRAP-TYPE
        ENTERPRISE compaq
        VARIABLES  { hostName,
                     scellNameDateTime,
                     agentEventCode,
                     agentEventDescription }
        DESCRIPTION
             "Create Folder - Completed"
           --#TYPE      "Management Agent Event"
           --#SUMMARY   "Host %s : SCellName-TimeDate %s : EventCode %d : Description %s"
           --#ARGUMENTS {0,1,2,3,}
            --#SEVERITY  INFORMATIONAL
            --#TIMEINDEX 136
        ::= 136002051
 
   mngmtAgentTrap-2052 TRAP-TYPE
        ENTERPRISE compaq
        VARIABLES  { hostName,
                     scellNameDateTime,
                     agentEventCode,
                     agentEventDescription }
        DESCRIPTION
             "Change Object Properties - Completed"
           --#TYPE      "Management Agent Event"
           --#SUMMARY   "Host %s : SCellName-TimeDate %s : EventCode %d : Description %s"
           --#ARGUMENTS {0,1,2,3,}
            --#SEVERITY  INFORMATIONAL
            --#TIMEINDEX 136
        ::= 136002052
 
   mngmtAgentTrap-2057 TRAP-TYPE
        ENTERPRISE compaq
        VARIABLES  { hostName,
                     scellNameDateTime,
                     agentEventCode,
                     agentEventDescription }
        DESCRIPTION
             "Completed disk group creation"
           --#TYPE      "Management Agent Event"
           --#SUMMARY   "Host %s : SCellName-TimeDate %s : EventCode %d : Description %s"
           --#ARGUMENTS {0,1,2,3,}
            --#SEVERITY  INFORMATIONAL
            --#TIMEINDEX 136
        ::= 136002057
 
   mngmtAgentTrap-2058 TRAP-TYPE
        ENTERPRISE compaq
        VARIABLES  { hostName,
                     scellNameDateTime,
                     agentEventCode,
                     agentEventDescription }
        DESCRIPTION
             "Added host port"
           --#TYPE      "Management Agent Event"
           --#SUMMARY   "Host %s : SCellName-TimeDate %s : EventCode %d : Description %s"
           --#ARGUMENTS {0,1,2,3,}
            --#SEVERITY  INFORMATIONAL
            --#TIMEINDEX 136
        ::= 136002058
 
   mngmtAgentTrap-2059 TRAP-TYPE
        ENTERPRISE compaq
        VARIABLES  { hostName,
                     scellNameDateTime,
                     agentEventCode,
                     agentEventDescription }
        DESCRIPTION
             "Discarded host port"
           --#TYPE      "Management Agent Event"
           --#SUMMARY   "Host %s : SCellName-TimeDate %s : EventCode %d : Description %s"
           --#ARGUMENTS {0,1,2,3,}
            --#SEVERITY  INFORMATIONAL
            --#TIMEINDEX 136
        ::= 136002059
 
   mngmtAgentTrap-2060 TRAP-TYPE
        ENTERPRISE compaq
        VARIABLES  { hostName,
                     scellNameDateTime,
                     agentEventCode,
                     agentEventDescription }
        DESCRIPTION
             "EMU/Shelf code load complete"
           --#TYPE      "Management Agent Event"
           --#SUMMARY   "Host %s : SCellName-TimeDate %s : EventCode %d : Description %s"
           --#ARGUMENTS {0,1,2,3,}
            --#SEVERITY  INFORMATIONAL
            --#TIMEINDEX 136
        ::= 136002060
 
   mngmtAgentTrap-2061 TRAP-TYPE
        ENTERPRISE compaq
        VARIABLES  { hostName,
                     scellNameDateTime,
                     agentEventCode,
                     agentEventDescription }
        DESCRIPTION
             "Operation will exceed the available capacity of the disk group"
           --#TYPE      "Management Agent Event"
           --#SUMMARY   "Host %s : SCellName-TimeDate %s : EventCode %d : Description %s"
           --#ARGUMENTS {0,1,2,3,}
            --#SEVERITY  INFORMATIONAL
            --#TIMEINDEX 136
        ::= 136002061
 
   mngmtAgentTrap-2062 TRAP-TYPE
        ENTERPRISE compaq
        VARIABLES  { hostName,
                     scellNameDateTime,
                     agentEventCode,
                     agentEventDescription }
        DESCRIPTION
             "Controller(s) code load complete"
           --#TYPE      "Management Agent Event"
           --#SUMMARY   "Host %s : SCellName-TimeDate %s : EventCode %d : Description %s"
           --#ARGUMENTS {0,1,2,3,}
            --#SEVERITY  INFORMATIONAL
            --#TIMEINDEX 136
        ::= 136002062
 
   mngmtAgentTrap-2063 TRAP-TYPE
        ENTERPRISE compaq
        VARIABLES  { hostName,
                     scellNameDateTime,
                     agentEventCode,
                     agentEventDescription }
        DESCRIPTION
             "The target device is not in the right condition to perform the operation"
           --#TYPE      "Management Agent Event"
           --#SUMMARY   "Host %s : SCellName-TimeDate %s : EventCode %d : Description %s"
           --#ARGUMENTS {0,1,2,3,}
            --#SEVERITY  INFORMATIONAL
            --#TIMEINDEX 136
        ::= 136002063
 
   mngmtAgentTrap-2064 TRAP-TYPE
        ENTERPRISE compaq
        VARIABLES  { hostName,
                     scellNameDateTime,
                     agentEventCode,
                     agentEventDescription }
        DESCRIPTION
             "Storage system Device Addition Policy changed successfully"
           --#TYPE      "Management Agent Event"
           --#SUMMARY   "Host %s : SCellName-TimeDate %s : EventCode %d : Description %s"
           --#ARGUMENTS {0,1,2,3,}
            --#SEVERITY  INFORMATIONAL
            --#TIMEINDEX 136
        ::= 136002064
 
   mngmtAgentTrap-2065 TRAP-TYPE
        ENTERPRISE compaq
        VARIABLES  { hostName,
                     scellNameDateTime,
                     agentEventCode,
                     agentEventDescription }
        DESCRIPTION
             "Maximum number of disk groups exceeded"
           --#TYPE      "Management Agent Event"
           --#SUMMARY   "Host %s : SCellName-TimeDate %s : EventCode %d : Description %s"
           --#ARGUMENTS {0,1,2,3,}
            --#SEVERITY  INFORMATIONAL
            --#TIMEINDEX 136
        ::= 136002065
 
   mngmtAgentTrap-2066 TRAP-TYPE
        ENTERPRISE compaq
        VARIABLES  { hostName,
                     scellNameDateTime,
                     agentEventCode,
                     agentEventDescription }
        DESCRIPTION
             "Nsa object discard failed."
           --#TYPE      "Management Agent Event"
           --#SUMMARY   "Host %s : SCellName-TimeDate %s : EventCode %d : Description %s"
           --#ARGUMENTS {0,1,2,3,}
            --#SEVERITY  MINOR
            --#TIMEINDEX 136
        ::= 136002066
 
   mngmtAgentTrap-2067 TRAP-TYPE
        ENTERPRISE compaq
        VARIABLES  { hostName,
                     scellNameDateTime,
                     agentEventCode,
                     agentEventDescription }
        DESCRIPTION
             "There are not enough disks to meet the minimum number requirement"
           --#TYPE      "Management Agent Event"
           --#SUMMARY   "Host %s : SCellName-TimeDate %s : EventCode %d : Description %s"
           --#ARGUMENTS {0,1,2,3,}
            --#SEVERITY  MINOR
            --#TIMEINDEX 136
        ::= 136002067
 
   mngmtAgentTrap-2068 TRAP-TYPE
        ENTERPRISE compaq
        VARIABLES  { hostName,
                     scellNameDateTime,
                     agentEventCode,
                     agentEventDescription }
        DESCRIPTION
             "Entry added successfully in the password file"
           --#TYPE      "Management Agent Event"
           --#SUMMARY   "Host %s : SCellName-TimeDate %s : EventCode %d : Description %s"
           --#ARGUMENTS {0,1,2,3,}
            --#SEVERITY  INFORMATIONAL
            --#TIMEINDEX 136
        ::= 136002068
 
   mngmtAgentTrap-2069 TRAP-TYPE
        ENTERPRISE compaq
        VARIABLES  { hostName,
                     scellNameDateTime,
                     agentEventCode,
                     agentEventDescription }
        DESCRIPTION
             "Entry updated successfully in the password file"
           --#TYPE      "Management Agent Event"
           --#SUMMARY   "Host %s : SCellName-TimeDate %s : EventCode %d : Description %s"
           --#ARGUMENTS {0,1,2,3,}
            --#SEVERITY  INFORMATIONAL
            --#TIMEINDEX 136
        ::= 136002069
 
   mngmtAgentTrap-2070 TRAP-TYPE
        ENTERPRISE compaq
        VARIABLES  { hostName,
                     scellNameDateTime,
                     agentEventCode,
                     agentEventDescription }
        DESCRIPTION
             "Entry discarded successfully in the password file"
           --#TYPE      "Management Agent Event"
           --#SUMMARY   "Host %s : SCellName-TimeDate %s : EventCode %d : Description %s"
           --#ARGUMENTS {0,1,2,3,}
            --#SEVERITY  INFORMATIONAL
            --#TIMEINDEX 136
        ::= 136002070
 
   mngmtAgentTrap-2071 TRAP-TYPE
        ENTERPRISE compaq
        VARIABLES  { hostName,
                     scellNameDateTime,
                     agentEventCode,
                     agentEventDescription }
        DESCRIPTION
             "Storage system is not responding in a timely manner and has been placed into an unknown state. This may be due to a prior command with an excessively long execution time, high I/O load, or a network communications error.  Recovery will automatically occur when the storage system is able to respond.  "
           --#TYPE      "Management Agent Event"
           --#SUMMARY   "Host %s : SCellName-TimeDate %s : EventCode %d : Description %s"
           --#ARGUMENTS {0,1,2,3,}
            --#SEVERITY  INFORMATIONAL
            --#TIMEINDEX 136
        ::= 136002071
 
   mngmtAgentTrap-2072 TRAP-TYPE
        ENTERPRISE compaq
        VARIABLES  { hostName,
                     scellNameDateTime,
                     agentEventCode,
                     agentEventDescription }
        DESCRIPTION
             "Object not found. Operation on this object is completed"
           --#TYPE      "Management Agent Event"
           --#SUMMARY   "Host %s : SCellName-TimeDate %s : EventCode %d : Description %s"
           --#ARGUMENTS {0,1,2,3,}
            --#SEVERITY  INFORMATIONAL
            --#TIMEINDEX 136
        ::= 136002072
 
   mngmtAgentTrap-2073 TRAP-TYPE
        ENTERPRISE compaq
        VARIABLES  { hostName,
                     scellNameDateTime,
                     agentEventCode,
                     agentEventDescription }
        DESCRIPTION
             "There is no more available space to create a Vdisk"
           --#TYPE      "Management Agent Event"
           --#SUMMARY   "Host %s : SCellName-TimeDate %s : EventCode %d : Description %s"
           --#ARGUMENTS {0,1,2,3,}
            --#SEVERITY  INFORMATIONAL
            --#TIMEINDEX 136
        ::= 136002073
 
   mngmtAgentTrap-2074 TRAP-TYPE
        ENTERPRISE compaq
        VARIABLES  { hostName,
                     scellNameDateTime,
                     agentEventCode,
                     agentEventDescription }
        DESCRIPTION
             "Name or comments contains invalid character(s)"
           --#TYPE      "Management Agent Event"
           --#SUMMARY   "Host %s : SCellName-TimeDate %s : EventCode %d : Description %s"
           --#ARGUMENTS {0,1,2,3,}
            --#SEVERITY  INFORMATIONAL
            --#TIMEINDEX 136
        ::= 136002074
 
   mngmtAgentTrap-2075 TRAP-TYPE
        ENTERPRISE compaq
        VARIABLES  { hostName,
                     scellNameDateTime,
                     agentEventCode,
                     agentEventDescription }
        DESCRIPTION
             "Duplicate - Another object with the same name exists."
           --#TYPE      "Management Agent Event"
           --#SUMMARY   "Host %s : SCellName-TimeDate %s : EventCode %d : Description %s"
           --#ARGUMENTS {0,1,2,3,}
            --#SEVERITY  INFORMATIONAL
            --#TIMEINDEX 136
        ::= 136002075
 
   mngmtAgentTrap-2076 TRAP-TYPE
        ENTERPRISE compaq
        VARIABLES  { hostName,
                     scellNameDateTime,
                     agentEventCode,
                     agentEventDescription }
        DESCRIPTION
             "No healthy disk group(s) to create a Vdisk. Resolve any abnormal conditions in the disk group first."
           --#TYPE      "Management Agent Event"
           --#SUMMARY   "Host %s : SCellName-TimeDate %s : EventCode %d : Description %s"
           --#ARGUMENTS {0,1,2,3,}
            --#SEVERITY  INFORMATIONAL
            --#TIMEINDEX 136
        ::= 136002076
 
   mngmtAgentTrap-2077 TRAP-TYPE
        ENTERPRISE compaq
        VARIABLES  { hostName,
                     scellNameDateTime,
                     agentEventCode,
                     agentEventDescription }
        DESCRIPTION
             "Operating System ID must be a valid number."
           --#TYPE      "Management Agent Event"
           --#SUMMARY   "Host %s : SCellName-TimeDate %s : EventCode %d : Description %s"
           --#ARGUMENTS {0,1,2,3,}
            --#SEVERITY  INFORMATIONAL
            --#TIMEINDEX 136
        ::= 136002077
 
   mngmtAgentTrap-2078 TRAP-TYPE
        ENTERPRISE compaq
        VARIABLES  { hostName,
                     scellNameDateTime,
                     agentEventCode,
                     agentEventDescription }
        DESCRIPTION
             "Watchdog successfully started"
           --#TYPE      "Management Agent Event"
           --#SUMMARY   "Host %s : SCellName-TimeDate %s : EventCode %d : Description %s"
           --#ARGUMENTS {0,1,2,3,}
            --#SEVERITY  INFORMATIONAL
            --#TIMEINDEX 136
        ::= 136002078
 
   mngmtAgentTrap-2079 TRAP-TYPE
        ENTERPRISE compaq
        VARIABLES  { hostName,
                     scellNameDateTime,
                     agentEventCode,
                     agentEventDescription }
        DESCRIPTION
             "Watchdog successfully stopped"
           --#TYPE      "Management Agent Event"
           --#SUMMARY   "Host %s : SCellName-TimeDate %s : EventCode %d : Description %s"
           --#ARGUMENTS {0,1,2,3,}
            --#SEVERITY  INFORMATIONAL
            --#TIMEINDEX 136
        ::= 136002079
 
   mngmtAgentTrap-2080 TRAP-TYPE
        ENTERPRISE compaq
        VARIABLES  { hostName,
                     scellNameDateTime,
                     agentEventCode,
                     agentEventDescription }
        DESCRIPTION
             "Delete Event Config List failed"
           --#TYPE      "Management Agent Event"
           --#SUMMARY   "Host %s : SCellName-TimeDate %s : EventCode %d : Description %s"
           --#ARGUMENTS {0,1,2,3,}
            --#SEVERITY  MINOR
            --#TIMEINDEX 136
        ::= 136002080
 
   mngmtAgentTrap-2081 TRAP-TYPE
        ENTERPRISE compaq
        VARIABLES  { hostName,
                     scellNameDateTime,
                     agentEventCode,
                     agentEventDescription }
        DESCRIPTION
             "Disk group meltdown repaired successfully."
           --#TYPE      "Management Agent Event"
           --#SUMMARY   "Host %s : SCellName-TimeDate %s : EventCode %d : Description %s"
           --#ARGUMENTS {0,1,2,3,}
            --#SEVERITY  INFORMATIONAL
            --#TIMEINDEX 136
        ::= 136002081
 
   mngmtAgentTrap-2082 TRAP-TYPE
        ENTERPRISE compaq
        VARIABLES  { hostName,
                     scellNameDateTime,
                     agentEventCode,
                     agentEventDescription }
        DESCRIPTION
             "There are no available LUNs to present this Vdisk."
           --#TYPE      "Management Agent Event"
           --#SUMMARY   "Host %s : SCellName-TimeDate %s : EventCode %d : Description %s"
           --#ARGUMENTS {0,1,2,3,}
            --#SEVERITY  INFORMATIONAL
            --#TIMEINDEX 136
        ::= 136002082
 
   mngmtAgentTrap-2083 TRAP-TYPE
        ENTERPRISE compaq
        VARIABLES  { hostName,
                     scellNameDateTime,
                     agentEventCode,
                     agentEventDescription }
        DESCRIPTION
             "Controller time synchronization turned on."
           --#TYPE      "Management Agent Event"
           --#SUMMARY   "Host %s : SCellName-TimeDate %s : EventCode %d : Description %s"
           --#ARGUMENTS {0,1,2,3,}
            --#SEVERITY  INFORMATIONAL
            --#TIMEINDEX 136
        ::= 136002083
 
   mngmtAgentTrap-2084 TRAP-TYPE
        ENTERPRISE compaq
        VARIABLES  { hostName,
                     scellNameDateTime,
                     agentEventCode,
                     agentEventDescription }
        DESCRIPTION
             "Controller time synchronization turned off."
           --#TYPE      "Management Agent Event"
           --#SUMMARY   "Host %s : SCellName-TimeDate %s : EventCode %d : Description %s"
           --#ARGUMENTS {0,1,2,3,}
            --#SEVERITY  INFORMATIONAL
            --#TIMEINDEX 136
        ::= 136002084
 
   mngmtAgentTrap-2085 TRAP-TYPE
        ENTERPRISE compaq
        VARIABLES  { hostName,
                     scellNameDateTime,
                     agentEventCode,
                     agentEventDescription }
        DESCRIPTION
             "System login failed. Invalid password."
           --#TYPE      "Management Agent Event"
           --#SUMMARY   "Host %s : SCellName-TimeDate %s : EventCode %d : Description %s"
           --#ARGUMENTS {0,1,2,3,}
            --#SEVERITY  INFORMATIONAL
            --#TIMEINDEX 136
        ::= 136002085
 
   mngmtAgentTrap-2086 TRAP-TYPE
        ENTERPRISE compaq
        VARIABLES  { hostName,
                     scellNameDateTime,
                     agentEventCode,
                     agentEventDescription }
        DESCRIPTION
             "System is not set for password validation."
           --#TYPE      "Management Agent Event"
           --#SUMMARY   "Host %s : SCellName-TimeDate %s : EventCode %d : Description %s"
           --#ARGUMENTS {0,1,2,3,}
            --#SEVERITY  INFORMATIONAL
            --#TIMEINDEX 136
        ::= 136002086
 
   mngmtAgentTrap-2087 TRAP-TYPE
        ENTERPRISE compaq
        VARIABLES  { hostName,
                     scellNameDateTime,
                     agentEventCode,
                     agentEventDescription }
        DESCRIPTION
             "Agent is already logged in to this system."
           --#TYPE      "Management Agent Event"
           --#SUMMARY   "Host %s : SCellName-TimeDate %s : EventCode %d : Description %s"
           --#ARGUMENTS {0,1,2,3,}
            --#SEVERITY  INFORMATIONAL
            --#TIMEINDEX 136
        ::= 136002087
 
   mngmtAgentTrap-2088 TRAP-TYPE
        ENTERPRISE compaq
        VARIABLES  { hostName,
                     scellNameDateTime,
                     agentEventCode,
                     agentEventDescription }
        DESCRIPTION
             "Storage system time set to custom time. Controller time synchronization automatically turned off."
           --#TYPE      "Management Agent Event"
           --#SUMMARY   "Host %s : SCellName-TimeDate %s : EventCode %d : Description %s"
           --#ARGUMENTS {0,1,2,3,}
            --#SEVERITY  INFORMATIONAL
            --#TIMEINDEX 136
        ::= 136002088
 
   mngmtAgentTrap-2089 TRAP-TYPE
        ENTERPRISE compaq
        VARIABLES  { hostName,
                     scellNameDateTime,
                     agentEventCode,
                     agentEventDescription }
        DESCRIPTION
             "Storage system time set to SAN appliance time."
           --#TYPE      "Management Agent Event"
           --#SUMMARY   "Host %s : SCellName-TimeDate %s : EventCode %d : Description %s"
           --#ARGUMENTS {0,1,2,3,}
            --#SEVERITY  INFORMATIONAL
            --#TIMEINDEX 136
        ::= 136002089
 
   mngmtAgentTrap-2090 TRAP-TYPE
        ENTERPRISE compaq
        VARIABLES  { hostName,
                     scellNameDateTime,
                     agentEventCode,
                     agentEventDescription }
        DESCRIPTION
             "Storage system time set to browser time. Controller time synchronization automatically turned off."
           --#TYPE      "Management Agent Event"
           --#SUMMARY   "Host %s : SCellName-TimeDate %s : EventCode %d : Description %s"
           --#ARGUMENTS {0,1,2,3,}
            --#SEVERITY  INFORMATIONAL
            --#TIMEINDEX 136
        ::= 136002090
 
   mngmtAgentTrap-2091 TRAP-TYPE
        ENTERPRISE compaq
        VARIABLES  { hostName,
                     scellNameDateTime,
                     agentEventCode,
                     agentEventDescription }
        DESCRIPTION
             "Storage system time set to controller time. Controller time synchronization automatically turned off."
           --#TYPE      "Management Agent Event"
           --#SUMMARY   "Host %s : SCellName-TimeDate %s : EventCode %d : Description %s"
           --#ARGUMENTS {0,1,2,3,}
            --#SEVERITY  INFORMATIONAL
            --#TIMEINDEX 136
        ::= 136002091
 
   mngmtAgentTrap-2092 TRAP-TYPE
        ENTERPRISE compaq
        VARIABLES  { hostName,
                     scellNameDateTime,
                     agentEventCode,
                     agentEventDescription }
        DESCRIPTION
             "Unable to find DR Group on remote storage system."
           --#TYPE      "Management Agent Event"
           --#SUMMARY   "Host %s : SCellName-TimeDate %s : EventCode %d : Description %s"
           --#ARGUMENTS {0,1,2,3,}
            --#SEVERITY  INFORMATIONAL
            --#TIMEINDEX 136
        ::= 136002092
 
   mngmtAgentTrap-2093 TRAP-TYPE
        ENTERPRISE compaq
        VARIABLES  { hostName,
                     scellNameDateTime,
                     agentEventCode,
                     agentEventDescription }
        DESCRIPTION
             "A host must have at least one port. Cannot delete the only host port available."
           --#TYPE      "Management Agent Event"
           --#SUMMARY   "Host %s : SCellName-TimeDate %s : EventCode %d : Description %s"
           --#ARGUMENTS {0,1,2,3,}
            --#SEVERITY  INFORMATIONAL
            --#TIMEINDEX 136
        ::= 136002093
 
   mngmtAgentTrap-2095 TRAP-TYPE
        ENTERPRISE compaq
        VARIABLES  { hostName,
                     scellNameDateTime,
                     agentEventCode,
                     agentEventDescription }
        DESCRIPTION
             "Host creation failed. Maximum number of hosts reached."
           --#TYPE      "Management Agent Event"
           --#SUMMARY   "Host %s : SCellName-TimeDate %s : EventCode %d : Description %s"
           --#ARGUMENTS {0,1,2,3,}
            --#SEVERITY  INFORMATIONAL
            --#TIMEINDEX 136
        ::= 136002095
 
   mngmtAgentTrap-2096 TRAP-TYPE
        ENTERPRISE compaq
        VARIABLES  { hostName,
                     scellNameDateTime,
                     agentEventCode,
                     agentEventDescription }
        DESCRIPTION
             "Port already exists for this host."
           --#TYPE      "Management Agent Event"
           --#SUMMARY   "Host %s : SCellName-TimeDate %s : EventCode %d : Description %s"
           --#ARGUMENTS {0,1,2,3,}
            --#SEVERITY  INFORMATIONAL
            --#TIMEINDEX 136
        ::= 136002096
 
   mngmtAgentTrap-2097 TRAP-TYPE
        ENTERPRISE compaq
        VARIABLES  { hostName,
                     scellNameDateTime,
                     agentEventCode,
                     agentEventDescription }
        DESCRIPTION
             "Error reading parameter string. String is empty."
           --#TYPE      "Management Agent Event"
           --#SUMMARY   "Host %s : SCellName-TimeDate %s : EventCode %d : Description %s"
           --#ARGUMENTS {0,1,2,3,}
            --#SEVERITY  INFORMATIONAL
            --#TIMEINDEX 136
        ::= 136002097
 
   mngmtAgentTrap-2098 TRAP-TYPE
        ENTERPRISE compaq
        VARIABLES  { hostName,
                     scellNameDateTime,
                     agentEventCode,
                     agentEventDescription }
        DESCRIPTION
             "Command could not be completed on Master. Controller not found."
           --#TYPE      "Management Agent Event"
           --#SUMMARY   "Host %s : SCellName-TimeDate %s : EventCode %d : Description %s"
           --#ARGUMENTS {0,1,2,3,}
            --#SEVERITY  INFORMATIONAL
            --#TIMEINDEX 136
        ::= 136002098
 
   mngmtAgentTrap-2099 TRAP-TYPE
        ENTERPRISE compaq
        VARIABLES  { hostName,
                     scellNameDateTime,
                     agentEventCode,
                     agentEventDescription }
        DESCRIPTION
             "Command could not be completed on Slave. Controller not found."
           --#TYPE      "Management Agent Event"
           --#SUMMARY   "Host %s : SCellName-TimeDate %s : EventCode %d : Description %s"
           --#ARGUMENTS {0,1,2,3,}
            --#SEVERITY  INFORMATIONAL
            --#TIMEINDEX 136
        ::= 136002099
 
   mngmtAgentTrap-2100 TRAP-TYPE
        ENTERPRISE compaq
        VARIABLES  { hostName,
                     scellNameDateTime,
                     agentEventCode,
                     agentEventDescription }
        DESCRIPTION
             "Password access for all known storage systems is already enabled or set."
           --#TYPE      "Management Agent Event"
           --#SUMMARY   "Host %s : SCellName-TimeDate %s : EventCode %d : Description %s"
           --#ARGUMENTS {0,1,2,3,}
            --#SEVERITY  INFORMATIONAL
            --#TIMEINDEX 136
        ::= 136002100
 
   mngmtAgentTrap-2102 TRAP-TYPE
        ENTERPRISE compaq
        VARIABLES  { hostName,
                     scellNameDateTime,
                     agentEventCode,
                     agentEventDescription }
        DESCRIPTION
             "The local storage system has reached the maximum allowable DR relationship."
           --#TYPE      "Management Agent Event"
           --#SUMMARY   "Host %s : SCellName-TimeDate %s : EventCode %d : Description %s"
           --#ARGUMENTS {0,1,2,3,}
            --#SEVERITY  INFORMATIONAL
            --#TIMEINDEX 136
        ::= 136002102
 
   mngmtAgentTrap-2103 TRAP-TYPE
        ENTERPRISE compaq
        VARIABLES  { hostName,
                     scellNameDateTime,
                     agentEventCode,
                     agentEventDescription }
        DESCRIPTION
             "The remote storage system has reached the maximum allowable DR relationship."
           --#TYPE      "Management Agent Event"
           --#SUMMARY   "Host %s : SCellName-TimeDate %s : EventCode %d : Description %s"
           --#ARGUMENTS {0,1,2,3,}
            --#SEVERITY  INFORMATIONAL
            --#TIMEINDEX 136
        ::= 136002103
 
   mngmtAgentTrap-3001 TRAP-TYPE
        ENTERPRISE compaq
        VARIABLES  { hostName,
                     scellNameDateTime,
                     agentEventCode,
                     agentEventDescription }
        DESCRIPTION
             "Event Manager Offline"
           --#TYPE      "Management Agent Event"
           --#SUMMARY   "Host %s : SCellName-TimeDate %s : EventCode %d : Description %s"
           --#ARGUMENTS {0,1,2,3,}
            --#SEVERITY  INFORMATIONAL
            --#TIMEINDEX 136
        ::= 136003001
 
   mngmtAgentTrap-3002 TRAP-TYPE
        ENTERPRISE compaq
        VARIABLES  { hostName,
                     scellNameDateTime,
                     agentEventCode,
                     agentEventDescription }
        DESCRIPTION
             "Event Manager Online"
           --#TYPE      "Management Agent Event"
           --#SUMMARY   "Host %s : SCellName-TimeDate %s : EventCode %d : Description %s"
           --#ARGUMENTS {0,1,2,3,}
            --#SEVERITY  INFORMATIONAL
            --#TIMEINDEX 136
        ::= 136003002
 
   mngmtAgentTrap-3003 TRAP-TYPE
        ENTERPRISE compaq
        VARIABLES  { hostName,
                     scellNameDateTime,
                     agentEventCode,
                     agentEventDescription }
        DESCRIPTION
             "Event Manager - Startup Failed"
           --#TYPE      "Management Agent Event"
           --#SUMMARY   "Host %s : SCellName-TimeDate %s : EventCode %d : Description %s"
           --#ARGUMENTS {0,1,2,3,}
            --#SEVERITY  CRITICAL
            --#TIMEINDEX 136
        ::= 136003003
 
   mngmtAgentTrap-3004 TRAP-TYPE
        ENTERPRISE compaq
        VARIABLES  { hostName,
                     scellNameDateTime,
                     agentEventCode,
                     agentEventDescription }
        DESCRIPTION
             "Event Manager - Startup Complete"
           --#TYPE      "Management Agent Event"
           --#SUMMARY   "Host %s : SCellName-TimeDate %s : EventCode %d : Description %s"
           --#ARGUMENTS {0,1,2,3,}
            --#SEVERITY  INFORMATIONAL
            --#TIMEINDEX 136
        ::= 136003004
 
   mngmtAgentTrap-3007 TRAP-TYPE
        ENTERPRISE compaq
        VARIABLES  { hostName,
                     scellNameDateTime,
                     agentEventCode,
                     agentEventDescription }
        DESCRIPTION
             "Event Manager - Shutdown Complete"
           --#TYPE      "Management Agent Event"
           --#SUMMARY   "Host %s : SCellName-TimeDate %s : EventCode %d : Description %s"
           --#ARGUMENTS {0,1,2,3,}
            --#SEVERITY  INFORMATIONAL
            --#TIMEINDEX 136
        ::= 136003007
 
   mngmtAgentTrap-3009 TRAP-TYPE
        ENTERPRISE compaq
        VARIABLES  { hostName,
                     scellNameDateTime,
                     agentEventCode,
                     agentEventDescription }
        DESCRIPTION
             "Unable to open NSA Local Event Log File"
           --#TYPE      "Management Agent Event"
           --#SUMMARY   "Host %s : SCellName-TimeDate %s : EventCode %d : Description %s"
           --#ARGUMENTS {0,1,2,3,}
            --#SEVERITY  MINOR
            --#TIMEINDEX 136
        ::= 136003009
 
   mngmtAgentTrap-3012 TRAP-TYPE
        ENTERPRISE compaq
        VARIABLES  { hostName,
                     scellNameDateTime,
                     agentEventCode,
                     agentEventDescription }
        DESCRIPTION
             "Unable to open Local Temp Event File - possibly no initialized SC"
           --#TYPE      "Management Agent Event"
           --#SUMMARY   "Host %s : SCellName-TimeDate %s : EventCode %d : Description %s"
           --#ARGUMENTS {0,1,2,3,}
            --#SEVERITY  MINOR
            --#TIMEINDEX 136
        ::= 136003012
 
   mngmtAgentTrap-3013 TRAP-TYPE
        ENTERPRISE compaq
        VARIABLES  { hostName,
                     scellNameDateTime,
                     agentEventCode,
                     agentEventDescription }
        DESCRIPTION
             "Unable to clear NSA Local Event Log File"
           --#TYPE      "Management Agent Event"
           --#SUMMARY   "Host %s : SCellName-TimeDate %s : EventCode %d : Description %s"
           --#ARGUMENTS {0,1,2,3,}
            --#SEVERITY  MINOR
            --#TIMEINDEX 136
        ::= 136003013
 
   mngmtAgentTrap-3015 TRAP-TYPE
        ENTERPRISE compaq
        VARIABLES  { hostName,
                     scellNameDateTime,
                     agentEventCode,
                     agentEventDescription }
        DESCRIPTION
             "Unable to clear NSA Event Log File"
           --#TYPE      "Management Agent Event"
           --#SUMMARY   "Host %s : SCellName-TimeDate %s : EventCode %d : Description %s"
           --#ARGUMENTS {0,1,2,3,}
            --#SEVERITY  MINOR
            --#TIMEINDEX 136
        ::= 136003015
 
   mngmtAgentTrap-3016 TRAP-TYPE
        ENTERPRISE compaq
        VARIABLES  { hostName,
                     scellNameDateTime,
                     agentEventCode,
                     agentEventDescription }
        DESCRIPTION
             "Local log file found on startup"
           --#TYPE      "Management Agent Event"
           --#SUMMARY   "Host %s : SCellName-TimeDate %s : EventCode %d : Description %s"
           --#ARGUMENTS {0,1,2,3,}
            --#SEVERITY  MINOR
            --#TIMEINDEX 136
        ::= 136003016
 
   mngmtAgentTrap-3017 TRAP-TYPE
        ENTERPRISE compaq
        VARIABLES  { hostName,
                     scellNameDateTime,
                     agentEventCode,
                     agentEventDescription }
        DESCRIPTION
             "Event Queue Flush Error"
           --#TYPE      "Management Agent Event"
           --#SUMMARY   "Host %s : SCellName-TimeDate %s : EventCode %d : Description %s"
           --#ARGUMENTS {0,1,2,3,}
            --#SEVERITY  MINOR
            --#TIMEINDEX 136
        ::= 136003017
 
   mngmtAgentTrap-3019 TRAP-TYPE
        ENTERPRISE compaq
        VARIABLES  { hostName,
                     scellNameDateTime,
                     agentEventCode,
                     agentEventDescription }
        DESCRIPTION
             "EM File Manager Online"
           --#TYPE      "Management Agent Event"
           --#SUMMARY   "Host %s : SCellName-TimeDate %s : EventCode %d : Description %s"
           --#ARGUMENTS {0,1,2,3,}
            --#SEVERITY  INFORMATIONAL
            --#TIMEINDEX 136
        ::= 136003019
 
   mngmtAgentTrap-3020 TRAP-TYPE
        ENTERPRISE compaq
        VARIABLES  { hostName,
                     scellNameDateTime,
                     agentEventCode,
                     agentEventDescription }
        DESCRIPTION
             "EM File Manager Offline"
           --#TYPE      "Management Agent Event"
           --#SUMMARY   "Host %s : SCellName-TimeDate %s : EventCode %d : Description %s"
           --#ARGUMENTS {0,1,2,3,}
            --#SEVERITY  INFORMATIONAL
            --#TIMEINDEX 136
        ::= 136003020
 
   mngmtAgentTrap-3021 TRAP-TYPE
        ENTERPRISE compaq
        VARIABLES  { hostName,
                     scellNameDateTime,
                     agentEventCode,
                     agentEventDescription }
        DESCRIPTION
             "EM Log Manager Online"
           --#TYPE      "Management Agent Event"
           --#SUMMARY   "Host %s : SCellName-TimeDate %s : EventCode %d : Description %s"
           --#ARGUMENTS {0,1,2,3,}
            --#SEVERITY  INFORMATIONAL
            --#TIMEINDEX 136
        ::= 136003021
 
   mngmtAgentTrap-3022 TRAP-TYPE
        ENTERPRISE compaq
        VARIABLES  { hostName,
                     scellNameDateTime,
                     agentEventCode,
                     agentEventDescription }
        DESCRIPTION
             "EM Log Manager Offline"
           --#TYPE      "Management Agent Event"
           --#SUMMARY   "Host %s : SCellName-TimeDate %s : EventCode %d : Description %s"
           --#ARGUMENTS {0,1,2,3,}
            --#SEVERITY  INFORMATIONAL
            --#TIMEINDEX 136
        ::= 136003022
 
   mngmtAgentTrap-3024 TRAP-TYPE
        ENTERPRISE compaq
        VARIABLES  { hostName,
                     scellNameDateTime,
                     agentEventCode,
                     agentEventDescription }
        DESCRIPTION
             "Local NSA logfile is empty"
           --#TYPE      "Management Agent Event"
           --#SUMMARY   "Host %s : SCellName-TimeDate %s : EventCode %d : Description %s"
           --#ARGUMENTS {0,1,2,3,}
            --#SEVERITY  INFORMATIONAL
            --#TIMEINDEX 136
        ::= 136003024
 
   mngmtAgentTrap-3025 TRAP-TYPE
        ENTERPRISE compaq
        VARIABLES  { hostName,
                     scellNameDateTime,
                     agentEventCode,
                     agentEventDescription }
        DESCRIPTION
             "Event Queue Online"
           --#TYPE      "Management Agent Event"
           --#SUMMARY   "Host %s : SCellName-TimeDate %s : EventCode %d : Description %s"
           --#ARGUMENTS {0,1,2,3,}
            --#SEVERITY  INFORMATIONAL
            --#TIMEINDEX 136
        ::= 136003025
 
   mngmtAgentTrap-3028 TRAP-TYPE
        ENTERPRISE compaq
        VARIABLES  { hostName,
                     scellNameDateTime,
                     agentEventCode,
                     agentEventDescription }
        DESCRIPTION
             "Status Descriptions Unavailable"
           --#TYPE      "Management Agent Event"
           --#SUMMARY   "Host %s : SCellName-TimeDate %s : EventCode %d : Description %s"
           --#ARGUMENTS {0,1,2,3,}
            --#SEVERITY  MINOR
            --#TIMEINDEX 136
        ::= 136003028
 
   mngmtAgentTrap-3029 TRAP-TYPE
        ENTERPRISE compaq
        VARIABLES  { hostName,
                     scellNameDateTime,
                     agentEventCode,
                     agentEventDescription }
        DESCRIPTION
             "EM Description Mngr Online"
           --#TYPE      "Management Agent Event"
           --#SUMMARY   "Host %s : SCellName-TimeDate %s : EventCode %d : Description %s"
           --#ARGUMENTS {0,1,2,3,}
            --#SEVERITY  INFORMATIONAL
            --#TIMEINDEX 136
        ::= 136003029
 
   mngmtAgentTrap-3035 TRAP-TYPE
        ENTERPRISE compaq
        VARIABLES  { hostName,
                     scellNameDateTime,
                     agentEventCode,
                     agentEventDescription }
        DESCRIPTION
             "EM: NSA log file unavailable"
           --#TYPE      "Management Agent Event"
           --#SUMMARY   "Host %s : SCellName-TimeDate %s : EventCode %d : Description %s"
           --#ARGUMENTS {0,1,2,3,}
            --#SEVERITY  MINOR
            --#TIMEINDEX 136
        ::= 136003035
 
   mngmtAgentTrap-3036 TRAP-TYPE
        ENTERPRISE compaq
        VARIABLES  { hostName,
                     scellNameDateTime,
                     agentEventCode,
                     agentEventDescription }
        DESCRIPTION
             "EM Memory Allocation Error"
           --#TYPE      "Management Agent Event"
           --#SUMMARY   "Host %s : SCellName-TimeDate %s : EventCode %d : Description %s"
           --#ARGUMENTS {0,1,2,3,}
            --#SEVERITY  CRITICAL
            --#TIMEINDEX 136
        ::= 136003036
 
   mngmtAgentTrap-3037 TRAP-TYPE
        ENTERPRISE compaq
        VARIABLES  { hostName,
                     scellNameDateTime,
                     agentEventCode,
                     agentEventDescription }
        DESCRIPTION
             "EM: Local Event Configuration File Unavailable"
           --#TYPE      "Management Agent Event"
           --#SUMMARY   "Host %s : SCellName-TimeDate %s : EventCode %d : Description %s"
           --#ARGUMENTS {0,1,2,3,}
            --#SEVERITY  MINOR
            --#TIMEINDEX 136
        ::= 136003037
 
   mngmtAgentTrap-3038 TRAP-TYPE
        ENTERPRISE compaq
        VARIABLES  { hostName,
                     scellNameDateTime,
                     agentEventCode,
                     agentEventDescription }
        DESCRIPTION
             "EM: MLD Notification File Unavailable - retrieving local backup copy"
           --#TYPE      "Management Agent Event"
           --#SUMMARY   "Host %s : SCellName-TimeDate %s : EventCode %d : Description %s"
           --#ARGUMENTS {0,1,2,3,}
            --#SEVERITY  MINOR
            --#TIMEINDEX 136
        ::= 136003038
 
   mngmtAgentTrap-3039 TRAP-TYPE
        ENTERPRISE compaq
        VARIABLES  { hostName,
                     scellNameDateTime,
                     agentEventCode,
                     agentEventDescription }
        DESCRIPTION
             "EM: Local Notification Host List File Unavailable"
           --#TYPE      "Management Agent Event"
           --#SUMMARY   "Host %s : SCellName-TimeDate %s : EventCode %d : Description %s"
           --#ARGUMENTS {0,1,2,3,}
            --#SEVERITY  MINOR
            --#TIMEINDEX 136
        ::= 136003039
 
   mngmtAgentTrap-3044 TRAP-TYPE
        ENTERPRISE compaq
        VARIABLES  { hostName,
                     scellNameDateTime,
                     agentEventCode,
                     agentEventDescription }
        DESCRIPTION
             "Override this description with missing filename"
           --#TYPE      "Management Agent Event"
           --#SUMMARY   "Host %s : SCellName-TimeDate %s : EventCode %d : Description %s"
           --#ARGUMENTS {0,1,2,3,}
            --#SEVERITY  INFORMATIONAL
            --#TIMEINDEX 136
        ::= 136003044
 
   mngmtAgentTrap-3045 TRAP-TYPE
        ENTERPRISE compaq
        VARIABLES  { hostName,
                     scellNameDateTime,
                     agentEventCode,
                     agentEventDescription }
        DESCRIPTION
             "Invalid storage system event sequence number - can't retrieve event"
           --#TYPE      "Management Agent Event"
           --#SUMMARY   "Host %s : SCellName-TimeDate %s : EventCode %d : Description %s"
           --#ARGUMENTS {0,1,2,3,}
            --#SEVERITY  INFORMATIONAL
            --#TIMEINDEX 136
        ::= 136003045
 
   mngmtAgentTrap-3046 TRAP-TYPE
        ENTERPRISE compaq
        VARIABLES  { hostName,
                     scellNameDateTime,
                     agentEventCode,
                     agentEventDescription }
        DESCRIPTION
             "Invalid SC termination event sequence number - can't retrieve event"
           --#TYPE      "Management Agent Event"
           --#SUMMARY   "Host %s : SCellName-TimeDate %s : EventCode %d : Description %s"
           --#ARGUMENTS {0,1,2,3,}
            --#SEVERITY  INFORMATIONAL
            --#TIMEINDEX 136
        ::= 136003046
 
   mngmtAgentTrap-3047 TRAP-TYPE
        ENTERPRISE compaq
        VARIABLES  { hostName,
                     scellNameDateTime,
                     agentEventCode,
                     agentEventDescription }
        DESCRIPTION
             "EM: Event config file unavailable from MLD - retrieving local backup copy"
           --#TYPE      "Management Agent Event"
           --#SUMMARY   "Host %s : SCellName-TimeDate %s : EventCode %d : Description %s"
           --#ARGUMENTS {0,1,2,3,}
            --#SEVERITY  MINOR
            --#TIMEINDEX 136
        ::= 136003047
 
   mngmtAgentTrap-3048 TRAP-TYPE
        ENTERPRISE compaq
        VARIABLES  { hostName,
                     scellNameDateTime,
                     agentEventCode,
                     agentEventDescription }
        DESCRIPTION
             "EM: Local user defined event state file unavailable"
           --#TYPE      "Management Agent Event"
           --#SUMMARY   "Host %s : SCellName-TimeDate %s : EventCode %d : Description %s"
           --#ARGUMENTS {0,1,2,3,}
            --#SEVERITY  INFORMATIONAL
            --#TIMEINDEX 136
        ::= 136003048
 
   mngmtAgentTrap-3049 TRAP-TYPE
        ENTERPRISE compaq
        VARIABLES  { hostName,
                     scellNameDateTime,
                     agentEventCode,
                     agentEventDescription }
        DESCRIPTION
             "EM: EMU event monitoring thread unable to start"
           --#TYPE      "Management Agent Event"
           --#SUMMARY   "Host %s : SCellName-TimeDate %s : EventCode %d : Description %s"
           --#ARGUMENTS {0,1,2,3,}
            --#SEVERITY  INFORMATIONAL
            --#TIMEINDEX 136
        ::= 136003049
 
   mngmtAgentTrap-3050 TRAP-TYPE
        ENTERPRISE compaq
        VARIABLES  { hostName,
                     scellNameDateTime,
                     agentEventCode,
                     agentEventDescription }
        DESCRIPTION
             "EM: EMU event - this description will be overwritten"
           --#TYPE      "Management Agent Event"
           --#SUMMARY   "Host %s : SCellName-TimeDate %s : EventCode %d : Description %s"
           --#ARGUMENTS {0,1,2,3,}
            --#SEVERITY  CRITICAL
            --#TIMEINDEX 136
        ::= 136003050
 
   mngmtAgentTrap-3051 TRAP-TYPE
        ENTERPRISE compaq
        VARIABLES  { hostName,
                     scellNameDateTime,
                     agentEventCode,
                     agentEventDescription }
        DESCRIPTION
             "EM: Failed to write Event Config file to MLD"
           --#TYPE      "Management Agent Event"
           --#SUMMARY   "Host %s : SCellName-TimeDate %s : EventCode %d : Description %s"
           --#ARGUMENTS {0,1,2,3,}
            --#SEVERITY  MINOR
            --#TIMEINDEX 136
        ::= 136003051
 
   mngmtAgentTrap-3053 TRAP-TYPE
        ENTERPRISE compaq
        VARIABLES  { hostName,
                     scellNameDateTime,
                     agentEventCode,
                     agentEventDescription }
        DESCRIPTION
             "EM: Event Configuration Filename Error or File empty"
           --#TYPE      "Management Agent Event"
           --#SUMMARY   "Host %s : SCellName-TimeDate %s : EventCode %d : Description %s"
           --#ARGUMENTS {0,1,2,3,}
            --#SEVERITY  INFORMATIONAL
            --#TIMEINDEX 136
        ::= 136003053
 
   mngmtAgentTrap-3054 TRAP-TYPE
        ENTERPRISE compaq
        VARIABLES  { hostName,
                     scellNameDateTime,
                     agentEventCode,
                     agentEventDescription }
        DESCRIPTION
             "EM: Notification Hostlist Filename Error or File empty"
           --#TYPE      "Management Agent Event"
           --#SUMMARY   "Host %s : SCellName-TimeDate %s : EventCode %d : Description %s"
           --#ARGUMENTS {0,1,2,3,}
            --#SEVERITY  INFORMATIONAL
            --#TIMEINDEX 136
        ::= 136003054
 
   mngmtAgentTrap-3055 TRAP-TYPE
        ENTERPRISE compaq
        VARIABLES  { hostName,
                     scellNameDateTime,
                     agentEventCode,
                     agentEventDescription }
        DESCRIPTION
             "EM: Event Config List Object Reference Error"
           --#TYPE      "Management Agent Event"
           --#SUMMARY   "Host %s : SCellName-TimeDate %s : EventCode %d : Description %s"
           --#ARGUMENTS {0,1,2,3,}
            --#SEVERITY  MINOR
            --#TIMEINDEX 136
        ::= 136003055
 
   mngmtAgentTrap-3056 TRAP-TYPE
        ENTERPRISE compaq
        VARIABLES  { hostName,
                     scellNameDateTime,
                     agentEventCode,
                     agentEventDescription }
        DESCRIPTION
             "EM: SC Parse File successfully uploaded"
           --#TYPE      "Management Agent Event"
           --#SUMMARY   "Host %s : SCellName-TimeDate %s : EventCode %d : Description %s"
           --#ARGUMENTS {0,1,2,3,}
            --#SEVERITY  INFORMATIONAL
            --#TIMEINDEX 136
        ::= 136003056
 
   mngmtAgentTrap-3057 TRAP-TYPE
        ENTERPRISE compaq
        VARIABLES  { hostName,
                     scellNameDateTime,
                     agentEventCode,
                     agentEventDescription }
        DESCRIPTION
             "EM: SC Parse File upload failed"
           --#TYPE      "Management Agent Event"
           --#SUMMARY   "Host %s : SCellName-TimeDate %s : EventCode %d : Description %s"
           --#ARGUMENTS {0,1,2,3,}
            --#SEVERITY  INFORMATIONAL
            --#TIMEINDEX 136
        ::= 136003057
 
   mngmtAgentTrap-3058 TRAP-TYPE
        ENTERPRISE compaq
        VARIABLES  { hostName,
                     scellNameDateTime,
                     agentEventCode,
                     agentEventDescription }
        DESCRIPTION
             "EM: Contents of the uploaded parse file invalid - unexpected contents"
           --#TYPE      "Management Agent Event"
           --#SUMMARY   "Host %s : SCellName-TimeDate %s : EventCode %d : Description %s"
           --#ARGUMENTS {0,1,2,3,}
            --#SEVERITY  MINOR
            --#TIMEINDEX 136
        ::= 136003058
 
   mngmtAgentTrap-3059 TRAP-TYPE
        ENTERPRISE compaq
        VARIABLES  { hostName,
                     scellNameDateTime,
                     agentEventCode,
                     agentEventDescription }
        DESCRIPTION
             "EM: Parse file is empty"
           --#TYPE      "Management Agent Event"
           --#SUMMARY   "Host %s : SCellName-TimeDate %s : EventCode %d : Description %s"
           --#ARGUMENTS {0,1,2,3,}
            --#SEVERITY  MINOR
            --#TIMEINDEX 136
        ::= 136003059
 
   mngmtAgentTrap-3060 TRAP-TYPE
        ENTERPRISE compaq
        VARIABLES  { hostName,
                     scellNameDateTime,
                     agentEventCode,
                     agentEventDescription }
        DESCRIPTION
             "Storage system being shutdown due to a command failure."
           --#TYPE      "Management Agent Event"
           --#SUMMARY   "Host %s : SCellName-TimeDate %s : EventCode %d : Description %s"
           --#ARGUMENTS {0,1,2,3,}
            --#SEVERITY  CRITICAL
            --#TIMEINDEX 136
        ::= 136003060
 
   mngmtAgentTrap-3061 TRAP-TYPE
        ENTERPRISE compaq
        VARIABLES  { hostName,
                     scellNameDateTime,
                     agentEventCode,
                     agentEventDescription }
        DESCRIPTION
             "EM: Could not retrieve a storage system event"
           --#TYPE      "Management Agent Event"
           --#SUMMARY   "Host %s : SCellName-TimeDate %s : EventCode %d : Description %s"
           --#ARGUMENTS {0,1,2,3,}
            --#SEVERITY  INFORMATIONAL
            --#TIMEINDEX 136
        ::= 136003061
 
   mngmtAgentTrap-3062 TRAP-TYPE
        ENTERPRISE compaq
        VARIABLES  { hostName,
                     scellNameDateTime,
                     agentEventCode,
                     agentEventDescription }
        DESCRIPTION
             "EM: Init SC Event config list failed"
           --#TYPE      "Management Agent Event"
           --#SUMMARY   "Host %s : SCellName-TimeDate %s : EventCode %d : Description %s"
           --#ARGUMENTS {0,1,2,3,}
            --#SEVERITY  INFORMATIONAL
            --#TIMEINDEX 136
        ::= 136003062
 
   mngmtAgentTrap-3063 TRAP-TYPE
        ENTERPRISE compaq
        VARIABLES  { hostName,
                     scellNameDateTime,
                     agentEventCode,
                     agentEventDescription }
        DESCRIPTION
             "Could not initialize Comm infrastructure for event logging to system log"
           --#TYPE      "Management Agent Event"
           --#SUMMARY   "Host %s : SCellName-TimeDate %s : EventCode %d : Description %s"
           --#ARGUMENTS {0,1,2,3,}
            --#SEVERITY  MINOR
            --#TIMEINDEX 136
        ::= 136003063
 
   mngmtAgentTrap-3064 TRAP-TYPE
        ENTERPRISE compaq
        VARIABLES  { hostName,
                     scellNameDateTime,
                     agentEventCode,
                     agentEventDescription }
        DESCRIPTION
             "EM: Storage system pointer is NULL!"
           --#TYPE      "Management Agent Event"
           --#SUMMARY   "Host %s : SCellName-TimeDate %s : EventCode %d : Description %s"
           --#ARGUMENTS {0,1,2,3,}
            --#SEVERITY  CRITICAL
            --#TIMEINDEX 136
        ::= 136003064
 
   mngmtAgentTrap-3065 TRAP-TYPE
        ENTERPRISE compaq
        VARIABLES  { hostName,
                     scellNameDateTime,
                     agentEventCode,
                     agentEventDescription }
        DESCRIPTION
             "EM: Failed to log event to the Appliance event log: check if log is full"
           --#TYPE      "Management Agent Event"
           --#SUMMARY   "Host %s : SCellName-TimeDate %s : EventCode %d : Description %s"
           --#ARGUMENTS {0,1,2,3,}
            --#SEVERITY  CRITICAL
            --#TIMEINDEX 136
        ::= 136003065
 
   mngmtAgentTrap-3066 TRAP-TYPE
        ENTERPRISE compaq
        VARIABLES  { hostName,
                     scellNameDateTime,
                     agentEventCode,
                     agentEventDescription }
        DESCRIPTION
             "EM: Description Mngr initialize storage system failed"
           --#TYPE      "Management Agent Event"
           --#SUMMARY   "Host %s : SCellName-TimeDate %s : EventCode %d : Description %s"
           --#ARGUMENTS {0,1,2,3,}
            --#SEVERITY  MINOR
            --#TIMEINDEX 136
        ::= 136003066
 
   mngmtAgentTrap-3067 TRAP-TYPE
        ENTERPRISE compaq
        VARIABLES  { hostName,
                     scellNameDateTime,
                     agentEventCode,
                     agentEventDescription }
        DESCRIPTION
             "EM: Description file too small. File read problem Or Incomplete file."
           --#TYPE      "Management Agent Event"
           --#SUMMARY   "Host %s : SCellName-TimeDate %s : EventCode %d : Description %s"
           --#ARGUMENTS {0,1,2,3,}
            --#SEVERITY  MINOR
            --#TIMEINDEX 136
        ::= 136003067
 
   mngmtAgentTrap-3068 TRAP-TYPE
        ENTERPRISE compaq
        VARIABLES  { hostName,
                     scellNameDateTime,
                     agentEventCode,
                     agentEventDescription }
        DESCRIPTION
             "EM: Can't init NT Event object pointer"
           --#TYPE      "Management Agent Event"
           --#SUMMARY   "Host %s : SCellName-TimeDate %s : EventCode %d : Description %s"
           --#ARGUMENTS {0,1,2,3,}
            --#SEVERITY  CRITICAL
            --#TIMEINDEX 136
        ::= 136003068
 
   mngmtAgentTrap-3069 TRAP-TYPE
        ENTERPRISE compaq
        VARIABLES  { hostName,
                     scellNameDateTime,
                     agentEventCode,
                     agentEventDescription }
        DESCRIPTION
             "EM: Can't init NT Notification object pointer"
           --#TYPE      "Management Agent Event"
           --#SUMMARY   "Host %s : SCellName-TimeDate %s : EventCode %d : Description %s"
           --#ARGUMENTS {0,1,2,3,}
            --#SEVERITY  CRITICAL
            --#TIMEINDEX 136
        ::= 136003069
 
   mngmtAgentTrap-3070 TRAP-TYPE
        ENTERPRISE compaq
        VARIABLES  { hostName,
                     scellNameDateTime,
                     agentEventCode,
                     agentEventDescription }
        DESCRIPTION
             "EM: Appliance Event Logging Failure - log may be full"
           --#TYPE      "Management Agent Event"
           --#SUMMARY   "Host %s : SCellName-TimeDate %s : EventCode %d : Description %s"
           --#ARGUMENTS {0,1,2,3,}
            --#SEVERITY  CRITICAL
            --#TIMEINDEX 136
        ::= 136003070
 
   mngmtAgentTrap-3071 TRAP-TYPE
        ENTERPRISE compaq
        VARIABLES  { hostName,
                     scellNameDateTime,
                     agentEventCode,
                     agentEventDescription }
        DESCRIPTION
             "EM: SCMI returned bad additional events number"
           --#TYPE      "Management Agent Event"
           --#SUMMARY   "Host %s : SCellName-TimeDate %s : EventCode %d : Description %s"
           --#ARGUMENTS {0,1,2,3,}
            --#SEVERITY  MINOR
            --#TIMEINDEX 136
        ::= 136003071
 
   mngmtAgentTrap-3072 TRAP-TYPE
        ENTERPRISE compaq
        VARIABLES  { hostName,
                     scellNameDateTime,
                     agentEventCode,
                     agentEventDescription }
        DESCRIPTION
             "EM: SCMI returned zero sized SC Event"
           --#TYPE      "Management Agent Event"
           --#SUMMARY   "Host %s : SCellName-TimeDate %s : EventCode %d : Description %s"
           --#ARGUMENTS {0,1,2,3,}
            --#SEVERITY  MINOR
            --#TIMEINDEX 136
        ::= 136003072
 
   mngmtAgentTrap-3075 TRAP-TYPE
        ENTERPRISE compaq
        VARIABLES  { hostName,
                     scellNameDateTime,
                     agentEventCode,
                     agentEventDescription }
        DESCRIPTION
             "EventQueue index passed is out of bounds"
           --#TYPE      "Management Agent Event"
           --#SUMMARY   "Host %s : SCellName-TimeDate %s : EventCode %d : Description %s"
           --#ARGUMENTS {0,1,2,3,}
            --#SEVERITY  INFORMATIONAL
            --#TIMEINDEX 136
        ::= 136003075
 
   mngmtAgentTrap-3076 TRAP-TYPE
        ENTERPRISE compaq
        VARIABLES  { hostName,
                     scellNameDateTime,
                     agentEventCode,
                     agentEventDescription }
        DESCRIPTION
             "EM: An abnormal number of duplicate events logged - dropping duplicates"
           --#TYPE      "Management Agent Event"
           --#SUMMARY   "Host %s : SCellName-TimeDate %s : EventCode %d : Description %s"
           --#ARGUMENTS {0,1,2,3,}
            --#SEVERITY  MINOR
            --#TIMEINDEX 136
        ::= 136003076
 
   mngmtAgentTrap-3077 TRAP-TYPE
        ENTERPRISE compaq
        VARIABLES  { hostName,
                     scellNameDateTime,
                     agentEventCode,
                     agentEventDescription }
        DESCRIPTION
             "EM: Update of the MLD Status Description file failed"
           --#TYPE      "Management Agent Event"
           --#SUMMARY   "Host %s : SCellName-TimeDate %s : EventCode %d : Description %s"
           --#ARGUMENTS {0,1,2,3,}
            --#SEVERITY  INFORMATIONAL
            --#TIMEINDEX 136
        ::= 136003077
 
   mngmtAgentTrap-3078 TRAP-TYPE
        ENTERPRISE compaq
        VARIABLES  { hostName,
                     scellNameDateTime,
                     agentEventCode,
                     agentEventDescription }
        DESCRIPTION
             "EM: NsaStatusDescriptions.txt open file error"
           --#TYPE      "Management Agent Event"
           --#SUMMARY   "Host %s : SCellName-TimeDate %s : EventCode %d : Description %s"
           --#ARGUMENTS {0,1,2,3,}
            --#SEVERITY  INFORMATIONAL
            --#TIMEINDEX 136
        ::= 136003078
 
   mngmtAgentTrap-3079 TRAP-TYPE
        ENTERPRISE compaq
        VARIABLES  { hostName,
                     scellNameDateTime,
                     agentEventCode,
                     agentEventDescription }
        DESCRIPTION
             "EM: NsaStatusDescriptions.txt file error - file size discrepancy from mld list"
           --#TYPE      "Management Agent Event"
           --#SUMMARY   "Host %s : SCellName-TimeDate %s : EventCode %d : Description %s"
           --#ARGUMENTS {0,1,2,3,}
            --#SEVERITY  INFORMATIONAL
            --#TIMEINDEX 136
        ::= 136003079
 
   mngmtAgentTrap-3080 TRAP-TYPE
        ENTERPRISE compaq
        VARIABLES  { hostName,
                     scellNameDateTime,
                     agentEventCode,
                     agentEventDescription }
        DESCRIPTION
             "SC Event Log has been cleared and restarted.  Possible RAID1 Meltdown."
           --#TYPE      "Management Agent Event"
           --#SUMMARY   "Host %s : SCellName-TimeDate %s : EventCode %d : Description %s"
           --#ARGUMENTS {0,1,2,3,}
            --#SEVERITY  CRITICAL
            --#TIMEINDEX 136
        ::= 136003080
 
   mngmtAgentTrap-3081 TRAP-TYPE
        ENTERPRISE compaq
        VARIABLES  { hostName,
                     scellNameDateTime,
                     agentEventCode,
                     agentEventDescription }
        DESCRIPTION
             "Invalid logType parameter"
           --#TYPE      "Management Agent Event"
           --#SUMMARY   "Host %s : SCellName-TimeDate %s : EventCode %d : Description %s"
           --#ARGUMENTS {0,1,2,3,}
            --#SEVERITY  INFORMATIONAL
            --#TIMEINDEX 136
        ::= 136003081
 
   mngmtAgentTrap-3083 TRAP-TYPE
        ENTERPRISE compaq
        VARIABLES  { hostName,
                     scellNameDateTime,
                     agentEventCode,
                     agentEventDescription }
        DESCRIPTION
             "Log file is empty"
           --#TYPE      "Management Agent Event"
           --#SUMMARY   "Host %s : SCellName-TimeDate %s : EventCode %d : Description %s"
           --#ARGUMENTS {0,1,2,3,}
            --#SEVERITY  INFORMATIONAL
            --#TIMEINDEX 136
        ::= 136003083
 
   mngmtAgentTrap-3084 TRAP-TYPE
        ENTERPRISE compaq
        VARIABLES  { hostName,
                     scellNameDateTime,
                     agentEventCode,
                     agentEventDescription }
        DESCRIPTION
             "Storage System with this WWN is not visible to this agent or the WWN is invalid"
           --#TYPE      "Management Agent Event"
           --#SUMMARY   "Host %s : SCellName-TimeDate %s : EventCode %d : Description %s"
           --#ARGUMENTS {0,1,2,3,}
            --#SEVERITY  INFORMATIONAL
            --#TIMEINDEX 136
        ::= 136003084
 
   mngmtAgentTrap-3086 TRAP-TYPE
        ENTERPRISE compaq
        VARIABLES  { hostName,
                     scellNameDateTime,
                     agentEventCode,
                     agentEventDescription }
        DESCRIPTION
             "Parsefile for current firmware version not found.  Upload correct parse file."
           --#TYPE      "Management Agent Event"
           --#SUMMARY   "Host %s : SCellName-TimeDate %s : EventCode %d : Description %s"
           --#ARGUMENTS {0,1,2,3,}
            --#SEVERITY  INFORMATIONAL
            --#TIMEINDEX 136
        ::= 136003086
 
   mngmtAgentTrap-3090 TRAP-TYPE
        ENTERPRISE compaq
        VARIABLES  { hostName,
                     scellNameDateTime,
                     agentEventCode,
                     agentEventDescription }
        DESCRIPTION
             "The contents of this file appear to be invalid"
           --#TYPE      "Management Agent Event"
           --#SUMMARY   "Host %s : SCellName-TimeDate %s : EventCode %d : Description %s"
           --#ARGUMENTS {0,1,2,3,}
            --#SEVERITY  INFORMATIONAL
            --#TIMEINDEX 136
        ::= 136003090
 
   mngmtAgentTrap-3091 TRAP-TYPE
        ENTERPRISE compaq
        VARIABLES  { hostName,
                     scellNameDateTime,
                     agentEventCode,
                     agentEventDescription }
        DESCRIPTION
             "The MIB failed to build due to a missing parse file."
           --#TYPE      "Management Agent Event"
           --#SUMMARY   "Host %s : SCellName-TimeDate %s : EventCode %d : Description %s"
           --#ARGUMENTS {0,1,2,3,}
            --#SEVERITY  INFORMATIONAL
            --#TIMEINDEX 136
        ::= 136003091
 
   mngmtAgentTrap-3092 TRAP-TYPE
        ENTERPRISE compaq
        VARIABLES  { hostName,
                     scellNameDateTime,
                     agentEventCode,
                     agentEventDescription }
        DESCRIPTION
             "MLD description file is older than local file but system is downrev"
           --#TYPE      "Management Agent Event"
           --#SUMMARY   "Host %s : SCellName-TimeDate %s : EventCode %d : Description %s"
           --#ARGUMENTS {0,1,2,3,}
            --#SEVERITY  INFORMATIONAL
            --#TIMEINDEX 136
        ::= 136003092
 
   mngmtAgentTrap-3094 TRAP-TYPE
        ENTERPRISE compaq
        VARIABLES  { hostName,
                     scellNameDateTime,
                     agentEventCode,
                     agentEventDescription }
        DESCRIPTION
             "System is initialized: can't get activeQ events"
           --#TYPE      "Management Agent Event"
           --#SUMMARY   "Host %s : SCellName-TimeDate %s : EventCode %d : Description %s"
           --#ARGUMENTS {0,1,2,3,}
            --#SEVERITY  INFORMATIONAL
            --#TIMEINDEX 136
        ::= 136003094
 
   mngmtAgentTrap-3095 TRAP-TYPE
        ENTERPRISE compaq
        VARIABLES  { hostName,
                     scellNameDateTime,
                     agentEventCode,
                     agentEventDescription }
        DESCRIPTION
             "Failed to write file - file could not be opened."
           --#TYPE      "Management Agent Event"
           --#SUMMARY   "Host %s : SCellName-TimeDate %s : EventCode %d : Description %s"
           --#ARGUMENTS {0,1,2,3,}
            --#SEVERITY  INFORMATIONAL
            --#TIMEINDEX 136
        ::= 136003095
 
   mngmtAgentTrap-4000 TRAP-TYPE
        ENTERPRISE compaq
        VARIABLES  { hostName,
                     scellNameDateTime,
                     agentEventCode,
                     agentEventDescription }
        DESCRIPTION
             "MLD Manager Subsystem Error"
           --#TYPE      "Management Agent Event"
           --#SUMMARY   "Host %s : SCellName-TimeDate %s : EventCode %d : Description %s"
           --#ARGUMENTS {0,1,2,3,}
            --#SEVERITY  INFORMATIONAL
            --#TIMEINDEX 136
        ::= 136004000
 
   mngmtAgentTrap-4001 TRAP-TYPE
        ENTERPRISE compaq
        VARIABLES  { hostName,
                     scellNameDateTime,
                     agentEventCode,
                     agentEventDescription }
        DESCRIPTION
             "MLD Manager Offline"
           --#TYPE      "Management Agent Event"
           --#SUMMARY   "Host %s : SCellName-TimeDate %s : EventCode %d : Description %s"
           --#ARGUMENTS {0,1,2,3,}
            --#SEVERITY  INFORMATIONAL
            --#TIMEINDEX 136
        ::= 136004001
 
   mngmtAgentTrap-4004 TRAP-TYPE
        ENTERPRISE compaq
        VARIABLES  { hostName,
                     scellNameDateTime,
                     agentEventCode,
                     agentEventDescription }
        DESCRIPTION
             "MLD Manager Startup Complete"
           --#TYPE      "Management Agent Event"
           --#SUMMARY   "Host %s : SCellName-TimeDate %s : EventCode %d : Description %s"
           --#ARGUMENTS {0,1,2,3,}
            --#SEVERITY  INFORMATIONAL
            --#TIMEINDEX 136
        ::= 136004004
 
   mngmtAgentTrap-4005 TRAP-TYPE
        ENTERPRISE compaq
        VARIABLES  { hostName,
                     scellNameDateTime,
                     agentEventCode,
                     agentEventDescription }
        DESCRIPTION
             "MLD Manager Abnormal Startup"
           --#TYPE      "Management Agent Event"
           --#SUMMARY   "Host %s : SCellName-TimeDate %s : EventCode %d : Description %s"
           --#ARGUMENTS {0,1,2,3,}
            --#SEVERITY  INFORMATIONAL
            --#TIMEINDEX 136
        ::= 136004005
 
   mngmtAgentTrap-4007 TRAP-TYPE
        ENTERPRISE compaq
        VARIABLES  { hostName,
                     scellNameDateTime,
                     agentEventCode,
                     agentEventDescription }
        DESCRIPTION
             "MLD Manager Shutdown Complete"
           --#TYPE      "Management Agent Event"
           --#SUMMARY   "Host %s : SCellName-TimeDate %s : EventCode %d : Description %s"
           --#ARGUMENTS {0,1,2,3,}
            --#SEVERITY  INFORMATIONAL
            --#TIMEINDEX 136
        ::= 136004007
 
   mngmtAgentTrap-4011 TRAP-TYPE
        ENTERPRISE compaq
        VARIABLES  { hostName,
                     scellNameDateTime,
                     agentEventCode,
                     agentEventDescription }
        DESCRIPTION
             "Invalid Host IP Address specified"
           --#TYPE      "Management Agent Event"
           --#SUMMARY   "Host %s : SCellName-TimeDate %s : EventCode %d : Description %s"
           --#ARGUMENTS {0,1,2,3,}
            --#SEVERITY  INFORMATIONAL
            --#TIMEINDEX 136
        ::= 136004011
 
   mngmtAgentTrap-4012 TRAP-TYPE
        ENTERPRISE compaq
        VARIABLES  { hostName,
                     scellNameDateTime,
                     agentEventCode,
                     agentEventDescription }
        DESCRIPTION
             "Unable to open the NsaMldMgr.dat file for Write"
           --#TYPE      "Management Agent Event"
           --#SUMMARY   "Host %s : SCellName-TimeDate %s : EventCode %d : Description %s"
           --#ARGUMENTS {0,1,2,3,}
            --#SEVERITY  INFORMATIONAL
            --#TIMEINDEX 136
        ::= 136004012
 
   mngmtAgentTrap-4013 TRAP-TYPE
        ENTERPRISE compaq
        VARIABLES  { hostName,
                     scellNameDateTime,
                     agentEventCode,
                     agentEventDescription }
        DESCRIPTION
             "Unable to open the NsaMldMgr.dat file for Read"
           --#TYPE      "Management Agent Event"
           --#SUMMARY   "Host %s : SCellName-TimeDate %s : EventCode %d : Description %s"
           --#ARGUMENTS {0,1,2,3,}
            --#SEVERITY  INFORMATIONAL
            --#TIMEINDEX 136
        ::= 136004013
 
   mngmtAgentTrap-4014 TRAP-TYPE
        ENTERPRISE compaq
        VARIABLES  { hostName,
                     scellNameDateTime,
                     agentEventCode,
                     agentEventDescription }
        DESCRIPTION
             "Agent Uid does not exist"
           --#TYPE      "Management Agent Event"
           --#SUMMARY   "Host %s : SCellName-TimeDate %s : EventCode %d : Description %s"
           --#ARGUMENTS {0,1,2,3,}
            --#SEVERITY  INFORMATIONAL
            --#TIMEINDEX 136
        ::= 136004014
 
   mngmtAgentTrap-4015 TRAP-TYPE
        ENTERPRISE compaq
        VARIABLES  { hostName,
                     scellNameDateTime,
                     agentEventCode,
                     agentEventDescription }
        DESCRIPTION
             "Unable to find object"
           --#TYPE      "Management Agent Event"
           --#SUMMARY   "Host %s : SCellName-TimeDate %s : EventCode %d : Description %s"
           --#ARGUMENTS {0,1,2,3,}
            --#SEVERITY  INFORMATIONAL
            --#TIMEINDEX 136
        ::= 136004015
 
   mngmtAgentTrap-4016 TRAP-TYPE
        ENTERPRISE compaq
        VARIABLES  { hostName,
                     scellNameDateTime,
                     agentEventCode,
                     agentEventDescription }
        DESCRIPTION
             "Unable to store object"
           --#TYPE      "Management Agent Event"
           --#SUMMARY   "Host %s : SCellName-TimeDate %s : EventCode %d : Description %s"
           --#ARGUMENTS {0,1,2,3,}
            --#SEVERITY  INFORMATIONAL
            --#TIMEINDEX 136
        ::= 136004016
 
   mngmtAgentTrap-4017 TRAP-TYPE
        ENTERPRISE compaq
        VARIABLES  { hostName,
                     scellNameDateTime,
                     agentEventCode,
                     agentEventDescription }
        DESCRIPTION
             "Unable to find storage system object"
           --#TYPE      "Management Agent Event"
           --#SUMMARY   "Host %s : SCellName-TimeDate %s : EventCode %d : Description %s"
           --#ARGUMENTS {0,1,2,3,}
            --#SEVERITY  INFORMATIONAL
            --#TIMEINDEX 136
        ::= 136004017
 
   mngmtAgentTrap-4018 TRAP-TYPE
        ENTERPRISE compaq
        VARIABLES  { hostName,
                     scellNameDateTime,
                     agentEventCode,
                     agentEventDescription }
        DESCRIPTION
             "Unable to create MLD"
           --#TYPE      "Management Agent Event"
           --#SUMMARY   "Host %s : SCellName-TimeDate %s : EventCode %d : Description %s"
           --#ARGUMENTS {0,1,2,3,}
            --#SEVERITY  INFORMATIONAL
            --#TIMEINDEX 136
        ::= 136004018
 
   mngmtAgentTrap-4020 TRAP-TYPE
        ENTERPRISE compaq
        VARIABLES  { hostName,
                     scellNameDateTime,
                     agentEventCode,
                     agentEventDescription }
        DESCRIPTION
             "lastSafeChoiceDelay Expired"
           --#TYPE      "Management Agent Event"
           --#SUMMARY   "Host %s : SCellName-TimeDate %s : EventCode %d : Description %s"
           --#ARGUMENTS {0,1,2,3,}
            --#SEVERITY  INFORMATIONAL
            --#TIMEINDEX 136
        ::= 136004020
 
   mngmtAgentTrap-4021 TRAP-TYPE
        ENTERPRISE compaq
        VARIABLES  { hostName,
                     scellNameDateTime,
                     agentEventCode,
                     agentEventDescription }
        DESCRIPTION
             "crashDetectDelay Expired"
           --#TYPE      "Management Agent Event"
           --#SUMMARY   "Host %s : SCellName-TimeDate %s : EventCode %d : Description %s"
           --#ARGUMENTS {0,1,2,3,}
            --#SEVERITY  INFORMATIONAL
            --#TIMEINDEX 136
        ::= 136004021
 
   mngmtAgentTrap-4023 TRAP-TYPE
        ENTERPRISE compaq
        VARIABLES  { hostName,
                     scellNameDateTime,
                     agentEventCode,
                     agentEventDescription }
        DESCRIPTION
             "Unable to read Copy1 of MLD"
           --#TYPE      "Management Agent Event"
           --#SUMMARY   "Host %s : SCellName-TimeDate %s : EventCode %d : Description %s"
           --#ARGUMENTS {0,1,2,3,}
            --#SEVERITY  INFORMATIONAL
            --#TIMEINDEX 136
        ::= 136004023
 
   mngmtAgentTrap-4024 TRAP-TYPE
        ENTERPRISE compaq
        VARIABLES  { hostName,
                     scellNameDateTime,
                     agentEventCode,
                     agentEventDescription }
        DESCRIPTION
             "Copy 1 of MLD Invalid"
           --#TYPE      "Management Agent Event"
           --#SUMMARY   "Host %s : SCellName-TimeDate %s : EventCode %d : Description %s"
           --#ARGUMENTS {0,1,2,3,}
            --#SEVERITY  INFORMATIONAL
            --#TIMEINDEX 136
        ::= 136004024
 
   mngmtAgentTrap-4025 TRAP-TYPE
        ENTERPRISE compaq
        VARIABLES  { hostName,
                     scellNameDateTime,
                     agentEventCode,
                     agentEventDescription }
        DESCRIPTION
             "Invalid Copy block of MLD"
           --#TYPE      "Management Agent Event"
           --#SUMMARY   "Host %s : SCellName-TimeDate %s : EventCode %d : Description %s"
           --#ARGUMENTS {0,1,2,3,}
            --#SEVERITY  INFORMATIONAL
            --#TIMEINDEX 136
        ::= 136004025
 
   mngmtAgentTrap-4027 TRAP-TYPE
        ENTERPRISE compaq
        VARIABLES  { hostName,
                     scellNameDateTime,
                     agentEventCode,
                     agentEventDescription }
        DESCRIPTION
             "MLD database capacity not equal to true MLD capacity"
           --#TYPE      "Management Agent Event"
           --#SUMMARY   "Host %s : SCellName-TimeDate %s : EventCode %d : Description %s"
           --#ARGUMENTS {0,1,2,3,}
            --#SEVERITY  INFORMATIONAL
            --#TIMEINDEX 136
        ::= 136004027
 
   mngmtAgentTrap-4028 TRAP-TYPE
        ENTERPRISE compaq
        VARIABLES  { hostName,
                     scellNameDateTime,
                     agentEventCode,
                     agentEventDescription }
        DESCRIPTION
             "Backup range out of bounds of copy 1 range"
           --#TYPE      "Management Agent Event"
           --#SUMMARY   "Host %s : SCellName-TimeDate %s : EventCode %d : Description %s"
           --#ARGUMENTS {0,1,2,3,}
            --#SEVERITY  INFORMATIONAL
            --#TIMEINDEX 136
        ::= 136004028
 
   mngmtAgentTrap-4029 TRAP-TYPE
        ENTERPRISE compaq
        VARIABLES  { hostName,
                     scellNameDateTime,
                     agentEventCode,
                     agentEventDescription }
        DESCRIPTION
             "MLD Manager Lock Crash DetectDelay has expired, just taking lock!"
           --#TYPE      "Management Agent Event"
           --#SUMMARY   "Host %s : SCellName-TimeDate %s : EventCode %d : Description %s"
           --#ARGUMENTS {0,1,2,3,}
            --#SEVERITY  INFORMATIONAL
            --#TIMEINDEX 136
        ::= 136004029
 
   mngmtAgentTrap-4030 TRAP-TYPE
        ENTERPRISE compaq
        VARIABLES  { hostName,
                     scellNameDateTime,
                     agentEventCode,
                     agentEventDescription }
        DESCRIPTION
             "MLD Copy 1 Restored"
           --#TYPE      "Management Agent Event"
           --#SUMMARY   "Host %s : SCellName-TimeDate %s : EventCode %d : Description %s"
           --#ARGUMENTS {0,1,2,3,}
            --#SEVERITY  INFORMATIONAL
            --#TIMEINDEX 136
        ::= 136004030
 
   mngmtAgentTrap-4031 TRAP-TYPE
        ENTERPRISE compaq
        VARIABLES  { hostName,
                     scellNameDateTime,
                     agentEventCode,
                     agentEventDescription }
        DESCRIPTION
             "MLD Copy 2 Restored"
           --#TYPE      "Management Agent Event"
           --#SUMMARY   "Host %s : SCellName-TimeDate %s : EventCode %d : Description %s"
           --#ARGUMENTS {0,1,2,3,}
            --#SEVERITY  INFORMATIONAL
            --#TIMEINDEX 136
        ::= 136004031
 
   mngmtAgentTrap-4032 TRAP-TYPE
        ENTERPRISE compaq
        VARIABLES  { hostName,
                     scellNameDateTime,
                     agentEventCode,
                     agentEventDescription }
        DESCRIPTION
             "Unable to find UidAssoc Object"
           --#TYPE      "Management Agent Event"
           --#SUMMARY   "Host %s : SCellName-TimeDate %s : EventCode %d : Description %s"
           --#ARGUMENTS {0,1,2,3,}
            --#SEVERITY  INFORMATIONAL
            --#TIMEINDEX 136
        ::= 136004032
 
   mngmtAgentTrap-4033 TRAP-TYPE
        ENTERPRISE compaq
        VARIABLES  { hostName,
                     scellNameDateTime,
                     agentEventCode,
                     agentEventDescription }
        DESCRIPTION
             "Unable to store UID Association Object"
           --#TYPE      "Management Agent Event"
           --#SUMMARY   "Host %s : SCellName-TimeDate %s : EventCode %d : Description %s"
           --#ARGUMENTS {0,1,2,3,}
            --#SEVERITY  INFORMATIONAL
            --#TIMEINDEX 136
        ::= 136004033
 
   mngmtAgentTrap-4034 TRAP-TYPE
        ENTERPRISE compaq
        VARIABLES  { hostName,
                     scellNameDateTime,
                     agentEventCode,
                     agentEventDescription }
        DESCRIPTION
             "Unable to find UidAssoc Object"
           --#TYPE      "Management Agent Event"
           --#SUMMARY   "Host %s : SCellName-TimeDate %s : EventCode %d : Description %s"
           --#ARGUMENTS {0,1,2,3,}
            --#SEVERITY  INFORMATIONAL
            --#TIMEINDEX 136
        ::= 136004034
 
   mngmtAgentTrap-4035 TRAP-TYPE
        ENTERPRISE compaq
        VARIABLES  { hostName,
                     scellNameDateTime,
                     agentEventCode,
                     agentEventDescription }
        DESCRIPTION
             "Unable to read last Fusion event read"
           --#TYPE      "Management Agent Event"
           --#SUMMARY   "Host %s : SCellName-TimeDate %s : EventCode %d : Description %s"
           --#ARGUMENTS {0,1,2,3,}
            --#SEVERITY  INFORMATIONAL
            --#TIMEINDEX 136
        ::= 136004035
 
   mngmtAgentTrap-4036 TRAP-TYPE
        ENTERPRISE compaq
        VARIABLES  { hostName,
                     scellNameDateTime,
                     agentEventCode,
                     agentEventDescription }
        DESCRIPTION
             "MLD Notification Queue Empty"
           --#TYPE      "Management Agent Event"
           --#SUMMARY   "Host %s : SCellName-TimeDate %s : EventCode %d : Description %s"
           --#ARGUMENTS {0,1,2,3,}
            --#SEVERITY  INFORMATIONAL
            --#TIMEINDEX 136
        ::= 136004036
 
   mngmtAgentTrap-4037 TRAP-TYPE
        ENTERPRISE compaq
        VARIABLES  { hostName,
                     scellNameDateTime,
                     agentEventCode,
                     agentEventDescription }
        DESCRIPTION
             "Unable to find Notification Object"
           --#TYPE      "Management Agent Event"
           --#SUMMARY   "Host %s : SCellName-TimeDate %s : EventCode %d : Description %s"
           --#ARGUMENTS {0,1,2,3,}
            --#SEVERITY  INFORMATIONAL
            --#TIMEINDEX 136
        ::= 136004037
 
   mngmtAgentTrap-4040 TRAP-TYPE
        ENTERPRISE compaq
        VARIABLES  { hostName,
                     scellNameDateTime,
                     agentEventCode,
                     agentEventDescription }
        DESCRIPTION
             "Unable to read Event Log Pointer"
           --#TYPE      "Management Agent Event"
           --#SUMMARY   "Host %s : SCellName-TimeDate %s : EventCode %d : Description %s"
           --#ARGUMENTS {0,1,2,3,}
            --#SEVERITY  INFORMATIONAL
            --#TIMEINDEX 136
        ::= 136004040
 
   mngmtAgentTrap-4041 TRAP-TYPE
        ENTERPRISE compaq
        VARIABLES  { hostName,
                     scellNameDateTime,
                     agentEventCode,
                     agentEventDescription }
        DESCRIPTION
             "Unable to read Event Log"
           --#TYPE      "Management Agent Event"
           --#SUMMARY   "Host %s : SCellName-TimeDate %s : EventCode %d : Description %s"
           --#ARGUMENTS {0,1,2,3,}
            --#SEVERITY  INFORMATIONAL
            --#TIMEINDEX 136
        ::= 136004041
 
   mngmtAgentTrap-4042 TRAP-TYPE
        ENTERPRISE compaq
        VARIABLES  { hostName,
                     scellNameDateTime,
                     agentEventCode,
                     agentEventDescription }
        DESCRIPTION
             "Unable to store Event Log"
           --#TYPE      "Management Agent Event"
           --#SUMMARY   "Host %s : SCellName-TimeDate %s : EventCode %d : Description %s"
           --#ARGUMENTS {0,1,2,3,}
            --#SEVERITY  INFORMATIONAL
            --#TIMEINDEX 136
        ::= 136004042
 
   mngmtAgentTrap-4043 TRAP-TYPE
        ENTERPRISE compaq
        VARIABLES  { hostName,
                     scellNameDateTime,
                     agentEventCode,
                     agentEventDescription }
        DESCRIPTION
             "Unable to read Event Log"
           --#TYPE      "Management Agent Event"
           --#SUMMARY   "Host %s : SCellName-TimeDate %s : EventCode %d : Description %s"
           --#ARGUMENTS {0,1,2,3,}
            --#SEVERITY  INFORMATIONAL
            --#TIMEINDEX 136
        ::= 136004043
 
   mngmtAgentTrap-4047 TRAP-TYPE
        ENTERPRISE compaq
        VARIABLES  { hostName,
                     scellNameDateTime,
                     agentEventCode,
                     agentEventDescription }
        DESCRIPTION
             "Previously Read Object Properties do not Match"
           --#TYPE      "Management Agent Event"
           --#SUMMARY   "Host %s : SCellName-TimeDate %s : EventCode %d : Description %s"
           --#ARGUMENTS {0,1,2,3,}
            --#SEVERITY  INFORMATIONAL
            --#TIMEINDEX 136
        ::= 136004047
 
   mngmtAgentTrap-4048 TRAP-TYPE
        ENTERPRISE compaq
        VARIABLES  { hostName,
                     scellNameDateTime,
                     agentEventCode,
                     agentEventDescription }
        DESCRIPTION
             "Previously Read Object Properties do not Match"
           --#TYPE      "Management Agent Event"
           --#SUMMARY   "Host %s : SCellName-TimeDate %s : EventCode %d : Description %s"
           --#ARGUMENTS {0,1,2,3,}
            --#SEVERITY  INFORMATIONAL
            --#TIMEINDEX 136
        ::= 136004048
 
   mngmtAgentTrap-4049 TRAP-TYPE
        ENTERPRISE compaq
        VARIABLES  { hostName,
                     scellNameDateTime,
                     agentEventCode,
                     agentEventDescription }
        DESCRIPTION
             "Unable to read  Notification Host List"
           --#TYPE      "Management Agent Event"
           --#SUMMARY   "Host %s : SCellName-TimeDate %s : EventCode %d : Description %s"
           --#ARGUMENTS {0,1,2,3,}
            --#SEVERITY  INFORMATIONAL
            --#TIMEINDEX 136
        ::= 136004049
 
   mngmtAgentTrap-4050 TRAP-TYPE
        ENTERPRISE compaq
        VARIABLES  { hostName,
                     scellNameDateTime,
                     agentEventCode,
                     agentEventDescription }
        DESCRIPTION
             "Unable to store Notification Host List"
           --#TYPE      "Management Agent Event"
           --#SUMMARY   "Host %s : SCellName-TimeDate %s : EventCode %d : Description %s"
           --#ARGUMENTS {0,1,2,3,}
            --#SEVERITY  INFORMATIONAL
            --#TIMEINDEX 136
        ::= 136004050
 
   mngmtAgentTrap-4051 TRAP-TYPE
        ENTERPRISE compaq
        VARIABLES  { hostName,
                     scellNameDateTime,
                     agentEventCode,
                     agentEventDescription }
        DESCRIPTION
             "Unable to store Notification Host List and free Lock"
           --#TYPE      "Management Agent Event"
           --#SUMMARY   "Host %s : SCellName-TimeDate %s : EventCode %d : Description %s"
           --#ARGUMENTS {0,1,2,3,}
            --#SEVERITY  INFORMATIONAL
            --#TIMEINDEX 136
        ::= 136004051
 
   mngmtAgentTrap-4052 TRAP-TYPE
        ENTERPRISE compaq
        VARIABLES  { hostName,
                     scellNameDateTime,
                     agentEventCode,
                     agentEventDescription }
        DESCRIPTION
             "Unable to read  Event Configuration List"
           --#TYPE      "Management Agent Event"
           --#SUMMARY   "Host %s : SCellName-TimeDate %s : EventCode %d : Description %s"
           --#ARGUMENTS {0,1,2,3,}
            --#SEVERITY  INFORMATIONAL
            --#TIMEINDEX 136
        ::= 136004052
 
   mngmtAgentTrap-4053 TRAP-TYPE
        ENTERPRISE compaq
        VARIABLES  { hostName,
                     scellNameDateTime,
                     agentEventCode,
                     agentEventDescription }
        DESCRIPTION
             "Unable to store Event Configuration List"
           --#TYPE      "Management Agent Event"
           --#SUMMARY   "Host %s : SCellName-TimeDate %s : EventCode %d : Description %s"
           --#ARGUMENTS {0,1,2,3,}
            --#SEVERITY  INFORMATIONAL
            --#TIMEINDEX 136
        ::= 136004053
 
   mngmtAgentTrap-4054 TRAP-TYPE
        ENTERPRISE compaq
        VARIABLES  { hostName,
                     scellNameDateTime,
                     agentEventCode,
                     agentEventDescription }
        DESCRIPTION
             "Unable to store Event Configuration List and free Lock"
           --#TYPE      "Management Agent Event"
           --#SUMMARY   "Host %s : SCellName-TimeDate %s : EventCode %d : Description %s"
           --#ARGUMENTS {0,1,2,3,}
            --#SEVERITY  INFORMATIONAL
            --#TIMEINDEX 136
        ::= 136004054
 
   mngmtAgentTrap-4058 TRAP-TYPE
        ENTERPRISE compaq
        VARIABLES  { hostName,
                     scellNameDateTime,
                     agentEventCode,
                     agentEventDescription }
        DESCRIPTION
             "MLD Manager Mutex Timeout error"
           --#TYPE      "Management Agent Event"
           --#SUMMARY   "Host %s : SCellName-TimeDate %s : EventCode %d : Description %s"
           --#ARGUMENTS {0,1,2,3,}
            --#SEVERITY  INFORMATIONAL
            --#TIMEINDEX 136
        ::= 136004058
 
   mngmtAgentTrap-4059 TRAP-TYPE
        ENTERPRISE compaq
        VARIABLES  { hostName,
                     scellNameDateTime,
                     agentEventCode,
                     agentEventDescription }
        DESCRIPTION
             "MLD Manager list is empty"
           --#TYPE      "Management Agent Event"
           --#SUMMARY   "Host %s : SCellName-TimeDate %s : EventCode %d : Description %s"
           --#ARGUMENTS {0,1,2,3,}
            --#SEVERITY  INFORMATIONAL
            --#TIMEINDEX 136
        ::= 136004059
 
   mngmtAgentTrap-5001 TRAP-TYPE
        ENTERPRISE compaq
        VARIABLES  { hostName,
                     scellNameDateTime,
                     agentEventCode,
                     agentEventDescription }
        DESCRIPTION
             "Monitor Startup Complete"
           --#TYPE      "Management Agent Event"
           --#SUMMARY   "Host %s : SCellName-TimeDate %s : EventCode %d : Description %s"
           --#ARGUMENTS {0,1,2,3,}
            --#SEVERITY  INFORMATIONAL
            --#TIMEINDEX 136
        ::= 136005001
 
   mngmtAgentTrap-5002 TRAP-TYPE
        ENTERPRISE compaq
        VARIABLES  { hostName,
                     scellNameDateTime,
                     agentEventCode,
                     agentEventDescription }
        DESCRIPTION
             "Monitor Startup Failed"
           --#TYPE      "Management Agent Event"
           --#SUMMARY   "Host %s : SCellName-TimeDate %s : EventCode %d : Description %s"
           --#ARGUMENTS {0,1,2,3,}
            --#SEVERITY  INFORMATIONAL
            --#TIMEINDEX 136
        ::= 136005002
 
   mngmtAgentTrap-5003 TRAP-TYPE
        ENTERPRISE compaq
        VARIABLES  { hostName,
                     scellNameDateTime,
                     agentEventCode,
                     agentEventDescription }
        DESCRIPTION
             "Monitor ShutDown Complete"
           --#TYPE      "Management Agent Event"
           --#SUMMARY   "Host %s : SCellName-TimeDate %s : EventCode %d : Description %s"
           --#ARGUMENTS {0,1,2,3,}
            --#SEVERITY  INFORMATIONAL
            --#TIMEINDEX 136
        ::= 136005003
 
   mngmtAgentTrap-5004 TRAP-TYPE
        ENTERPRISE compaq
        VARIABLES  { hostName,
                     scellNameDateTime,
                     agentEventCode,
                     agentEventDescription }
        DESCRIPTION
             "Monitor Memory Allocation Failure"
           --#TYPE      "Management Agent Event"
           --#SUMMARY   "Host %s : SCellName-TimeDate %s : EventCode %d : Description %s"
           --#ARGUMENTS {0,1,2,3,}
            --#SEVERITY  CRITICAL
            --#TIMEINDEX 136
        ::= 136005004
 
   mngmtAgentTrap-5005 TRAP-TYPE
        ENTERPRISE compaq
        VARIABLES  { hostName,
                     scellNameDateTime,
                     agentEventCode,
                     agentEventDescription }
        DESCRIPTION
             "Monitor Mark Agent as Inactive"
           --#TYPE      "Management Agent Event"
           --#SUMMARY   "Host %s : SCellName-TimeDate %s : EventCode %d : Description %s"
           --#ARGUMENTS {0,1,2,3,}
            --#SEVERITY  INFORMATIONAL
            --#TIMEINDEX 136
        ::= 136005005
 
   mngmtAgentTrap-5006 TRAP-TYPE
        ENTERPRISE compaq
        VARIABLES  { hostName,
                     scellNameDateTime,
                     agentEventCode,
                     agentEventDescription }
        DESCRIPTION
             "Monitor create thread error"
           --#TYPE      "Management Agent Event"
           --#SUMMARY   "Host %s : SCellName-TimeDate %s : EventCode %d : Description %s"
           --#ARGUMENTS {0,1,2,3,}
            --#SEVERITY  INFORMATIONAL
            --#TIMEINDEX 136
        ::= 136005006
 
   mngmtAgentTrap-5007 TRAP-TYPE
        ENTERPRISE compaq
        VARIABLES  { hostName,
                     scellNameDateTime,
                     agentEventCode,
                     agentEventDescription }
        DESCRIPTION
             "Monitor create timer error"
           --#TYPE      "Management Agent Event"
           --#SUMMARY   "Host %s : SCellName-TimeDate %s : EventCode %d : Description %s"
           --#ARGUMENTS {0,1,2,3,}
            --#SEVERITY  INFORMATIONAL
            --#TIMEINDEX 136
        ::= 136005007
 
   mngmtAgentTrap-5008 TRAP-TYPE
        ENTERPRISE compaq
        VARIABLES  { hostName,
                     scellNameDateTime,
                     agentEventCode,
                     agentEventDescription }
        DESCRIPTION
             "Monitor agent registration - Complete"
           --#TYPE      "Management Agent Event"
           --#SUMMARY   "Host %s : SCellName-TimeDate %s : EventCode %d : Description %s"
           --#ARGUMENTS {0,1,2,3,}
            --#SEVERITY  INFORMATIONAL
            --#TIMEINDEX 136
        ::= 136005008
 
   mngmtAgentTrap-5010 TRAP-TYPE
        ENTERPRISE compaq
        VARIABLES  { hostName,
                     scellNameDateTime,
                     agentEventCode,
                     agentEventDescription }
        DESCRIPTION
             "Monitor initiated a storage system management shutdown because of controller failures"
           --#TYPE      "Management Agent Event"
           --#SUMMARY   "Host %s : SCellName-TimeDate %s : EventCode %d : Description %s"
           --#ARGUMENTS {0,1,2,3,}
            --#SEVERITY  MINOR
            --#TIMEINDEX 136
        ::= 136005010
 
   mngmtAgentTrap-5011 TRAP-TYPE
        ENTERPRISE compaq
        VARIABLES  { hostName,
                     scellNameDateTime,
                     agentEventCode,
                     agentEventDescription }
        DESCRIPTION
             "Unknown storage system rediscovery complete "
           --#TYPE      "Management Agent Event"
           --#SUMMARY   "Host %s : SCellName-TimeDate %s : EventCode %d : Description %s"
           --#ARGUMENTS {0,1,2,3,}
            --#SEVERITY  INFORMATIONAL
            --#TIMEINDEX 136
        ::= 136005011
 
   mngmtAgentTrap-5012 TRAP-TYPE
        ENTERPRISE compaq
        VARIABLES  { hostName,
                     scellNameDateTime,
                     agentEventCode,
                     agentEventDescription }
        DESCRIPTION
             "Start monitoring thread for storage system - Complete"
           --#TYPE      "Management Agent Event"
           --#SUMMARY   "Host %s : SCellName-TimeDate %s : EventCode %d : Description %s"
           --#ARGUMENTS {0,1,2,3,}
            --#SEVERITY  INFORMATIONAL
            --#TIMEINDEX 136
        ::= 136005012
 
   mngmtAgentTrap-5013 TRAP-TYPE
        ENTERPRISE compaq
        VARIABLES  { hostName,
                     scellNameDateTime,
                     agentEventCode,
                     agentEventDescription }
        DESCRIPTION
             "Start monitoring thread for storage system - Fail"
           --#TYPE      "Management Agent Event"
           --#SUMMARY   "Host %s : SCellName-TimeDate %s : EventCode %d : Description %s"
           --#ARGUMENTS {0,1,2,3,}
            --#SEVERITY  INFORMATIONAL
            --#TIMEINDEX 136
        ::= 136005013
 
   mngmtAgentTrap-5014 TRAP-TYPE
        ENTERPRISE compaq
        VARIABLES  { hostName,
                     scellNameDateTime,
                     agentEventCode,
                     agentEventDescription }
        DESCRIPTION
             "Monitoring thread for storage system terminated"
           --#TYPE      "Management Agent Event"
           --#SUMMARY   "Host %s : SCellName-TimeDate %s : EventCode %d : Description %s"
           --#ARGUMENTS {0,1,2,3,}
            --#SEVERITY  INFORMATIONAL
            --#TIMEINDEX 136
        ::= 136005014
 
   mngmtAgentTrap-5015 TRAP-TYPE
        ENTERPRISE compaq
        VARIABLES  { hostName,
                     scellNameDateTime,
                     agentEventCode,
                     agentEventDescription }
        DESCRIPTION
             "Rediscover unknown storage system - Error"
           --#TYPE      "Management Agent Event"
           --#SUMMARY   "Host %s : SCellName-TimeDate %s : EventCode %d : Description %s"
           --#ARGUMENTS {0,1,2,3,}
            --#SEVERITY  INFORMATIONAL
            --#TIMEINDEX 136
        ::= 136005015
 
   mngmtAgentTrap-5016 TRAP-TYPE
        ENTERPRISE compaq
        VARIABLES  { hostName,
                     scellNameDateTime,
                     agentEventCode,
                     agentEventDescription }
        DESCRIPTION
             "Controller time synchronized to appliance time."
           --#TYPE      "Management Agent Event"
           --#SUMMARY   "Host %s : SCellName-TimeDate %s : EventCode %d : Description %s"
           --#ARGUMENTS {0,1,2,3,}
            --#SEVERITY  INFORMATIONAL
            --#TIMEINDEX 136
        ::= 136005016
 
   mngmtAgentTrap-5017 TRAP-TYPE
        ENTERPRISE compaq
        VARIABLES  { hostName,
                     scellNameDateTime,
                     agentEventCode,
                     agentEventDescription }
        DESCRIPTION
             "Appliance and controller time checked for synchronization."
           --#TYPE      "Management Agent Event"
           --#SUMMARY   "Host %s : SCellName-TimeDate %s : EventCode %d : Description %s"
           --#ARGUMENTS {0,1,2,3,}
            --#SEVERITY  INFORMATIONAL
            --#TIMEINDEX 136
        ::= 136005017
 
   mngmtAgentTrap-5018 TRAP-TYPE
        ENTERPRISE compaq
        VARIABLES  { hostName,
                     scellNameDateTime,
                     agentEventCode,
                     agentEventDescription }
        DESCRIPTION
             "Controller and appliance time are the same. No need to synchronize."
           --#TYPE      "Management Agent Event"
           --#SUMMARY   "Host %s : SCellName-TimeDate %s : EventCode %d : Description %s"
           --#ARGUMENTS {0,1,2,3,}
            --#SEVERITY  INFORMATIONAL
            --#TIMEINDEX 136
        ::= 136005018
 
   mngmtAgentTrap-5019 TRAP-TYPE
        ENTERPRISE compaq
        VARIABLES  { hostName,
                     scellNameDateTime,
                     agentEventCode,
                     agentEventDescription }
        DESCRIPTION
             "Exception caught in monitoring process."
           --#TYPE      "Management Agent Event"
           --#SUMMARY   "Host %s : SCellName-TimeDate %s : EventCode %d : Description %s"
           --#ARGUMENTS {0,1,2,3,}
            --#SEVERITY  INFORMATIONAL
            --#TIMEINDEX 136
        ::= 136005019
 
   mngmtAgentTrap-6001 TRAP-TYPE
        ENTERPRISE compaq
        VARIABLES  { hostName,
                     scellNameDateTime,
                     agentEventCode,
                     agentEventDescription }
        DESCRIPTION
             "Ready"
           --#TYPE      "Management Agent Event"
           --#SUMMARY   "Host %s : SCellName-TimeDate %s : EventCode %d : Description %s"
           --#ARGUMENTS {0,1,2,3,}
            --#SEVERITY  INFORMATIONAL
            --#TIMEINDEX 136
        ::= 136006001
 
   mngmtAgentTrap-6002 TRAP-TYPE
        ENTERPRISE compaq
        VARIABLES  { hostName,
                     scellNameDateTime,
                     agentEventCode,
                     agentEventDescription }
        DESCRIPTION
             "Index Out of Range"
           --#TYPE      "Management Agent Event"
           --#SUMMARY   "Host %s : SCellName-TimeDate %s : EventCode %d : Description %s"
           --#ARGUMENTS {0,1,2,3,}
            --#SEVERITY  INFORMATIONAL
            --#TIMEINDEX 136
        ::= 136006002
 
   mngmtAgentTrap-6003 TRAP-TYPE
        ENTERPRISE compaq
        VARIABLES  { hostName,
                     scellNameDateTime,
                     agentEventCode,
                     agentEventDescription }
        DESCRIPTION
             "Cannot access storage system. Communications error."
           --#TYPE      "Management Agent Event"
           --#SUMMARY   "Host %s : SCellName-TimeDate %s : EventCode %d : Description %s"
           --#ARGUMENTS {0,1,2,3,}
            --#SEVERITY  CRITICAL
            --#TIMEINDEX 136
        ::= 136006003
 
   mngmtAgentTrap-6004 TRAP-TYPE
        ENTERPRISE compaq
        VARIABLES  { hostName,
                     scellNameDateTime,
                     agentEventCode,
                     agentEventDescription }
        DESCRIPTION
             "No controllers found"
           --#TYPE      "Management Agent Event"
           --#SUMMARY   "Host %s : SCellName-TimeDate %s : EventCode %d : Description %s"
           --#ARGUMENTS {0,1,2,3,}
            --#SEVERITY  INFORMATIONAL
            --#TIMEINDEX 136
        ::= 136006004
 
   mngmtAgentTrap-6005 TRAP-TYPE
        ENTERPRISE compaq
        VARIABLES  { hostName,
                     scellNameDateTime,
                     agentEventCode,
                     agentEventDescription }
        DESCRIPTION
             "Invalid Index"
           --#TYPE      "Management Agent Event"
           --#SUMMARY   "Host %s : SCellName-TimeDate %s : EventCode %d : Description %s"
           --#ARGUMENTS {0,1,2,3,}
            --#SEVERITY  INFORMATIONAL
            --#TIMEINDEX 136
        ::= 136006005
 
   mngmtAgentTrap-6006 TRAP-TYPE
        ENTERPRISE compaq
        VARIABLES  { hostName,
                     scellNameDateTime,
                     agentEventCode,
                     agentEventDescription }
        DESCRIPTION
             "Memory allocation failure"
           --#TYPE      "Management Agent Event"
           --#SUMMARY   "Host %s : SCellName-TimeDate %s : EventCode %d : Description %s"
           --#ARGUMENTS {0,1,2,3,}
            --#SEVERITY  CRITICAL
            --#TIMEINDEX 136
        ::= 136006006
 
   mngmtAgentTrap-6007 TRAP-TYPE
        ENTERPRISE compaq
        VARIABLES  { hostName,
                     scellNameDateTime,
                     agentEventCode,
                     agentEventDescription }
        DESCRIPTION
             "No physical stores found"
           --#TYPE      "Management Agent Event"
           --#SUMMARY   "Host %s : SCellName-TimeDate %s : EventCode %d : Description %s"
           --#ARGUMENTS {0,1,2,3,}
            --#SEVERITY  INFORMATIONAL
            --#TIMEINDEX 136
        ::= 136006007
 
   mngmtAgentTrap-6008 TRAP-TYPE
        ENTERPRISE compaq
        VARIABLES  { hostName,
                     scellNameDateTime,
                     agentEventCode,
                     agentEventDescription }
        DESCRIPTION
             "No storage system found"
           --#TYPE      "Management Agent Event"
           --#SUMMARY   "Host %s : SCellName-TimeDate %s : EventCode %d : Description %s"
           --#ARGUMENTS {0,1,2,3,}
            --#SEVERITY  INFORMATIONAL
            --#TIMEINDEX 136
        ::= 136006008
 
   mngmtAgentTrap-6009 TRAP-TYPE
        ENTERPRISE compaq
        VARIABLES  { hostName,
                     scellNameDateTime,
                     agentEventCode,
                     agentEventDescription }
        DESCRIPTION
             "No disk group found"
           --#TYPE      "Management Agent Event"
           --#SUMMARY   "Host %s : SCellName-TimeDate %s : EventCode %d : Description %s"
           --#ARGUMENTS {0,1,2,3,}
            --#SEVERITY  INFORMATIONAL
            --#TIMEINDEX 136
        ::= 136006009
 
   mngmtAgentTrap-6010 TRAP-TYPE
        ENTERPRISE compaq
        VARIABLES  { hostName,
                     scellNameDateTime,
                     agentEventCode,
                     agentEventDescription }
        DESCRIPTION
             "Too many disk groups"
           --#TYPE      "Management Agent Event"
           --#SUMMARY   "Host %s : SCellName-TimeDate %s : EventCode %d : Description %s"
           --#ARGUMENTS {0,1,2,3,}
            --#SEVERITY  INFORMATIONAL
            --#TIMEINDEX 136
        ::= 136006010
 
   mngmtAgentTrap-6011 TRAP-TYPE
        ENTERPRISE compaq
        VARIABLES  { hostName,
                     scellNameDateTime,
                     agentEventCode,
                     agentEventDescription }
        DESCRIPTION
             "No volumes found"
           --#TYPE      "Management Agent Event"
           --#SUMMARY   "Host %s : SCellName-TimeDate %s : EventCode %d : Description %s"
           --#ARGUMENTS {0,1,2,3,}
            --#SEVERITY  INFORMATIONAL
            --#TIMEINDEX 136
        ::= 136006011
 
   mngmtAgentTrap-6012 TRAP-TYPE
        ENTERPRISE compaq
        VARIABLES  { hostName,
                     scellNameDateTime,
                     agentEventCode,
                     agentEventDescription }
        DESCRIPTION
             "No Logical Disks Found"
           --#TYPE      "Management Agent Event"
           --#SUMMARY   "Host %s : SCellName-TimeDate %s : EventCode %d : Description %s"
           --#ARGUMENTS {0,1,2,3,}
            --#SEVERITY  INFORMATIONAL
            --#TIMEINDEX 136
        ::= 136006012
 
   mngmtAgentTrap-6013 TRAP-TYPE
        ENTERPRISE compaq
        VARIABLES  { hostName,
                     scellNameDateTime,
                     agentEventCode,
                     agentEventDescription }
        DESCRIPTION
             "Context ID changed during operation"
           --#TYPE      "Management Agent Event"
           --#SUMMARY   "Host %s : SCellName-TimeDate %s : EventCode %d : Description %s"
           --#ARGUMENTS {0,1,2,3,}
            --#SEVERITY  INFORMATIONAL
            --#TIMEINDEX 136
        ::= 136006013
 
   mngmtAgentTrap-6014 TRAP-TYPE
        ENTERPRISE compaq
        VARIABLES  { hostName,
                     scellNameDateTime,
                     agentEventCode,
                     agentEventDescription }
        DESCRIPTION
             "No Name"
           --#TYPE      "Management Agent Event"
           --#SUMMARY   "Host %s : SCellName-TimeDate %s : EventCode %d : Description %s"
           --#ARGUMENTS {0,1,2,3,}
            --#SEVERITY  INFORMATIONAL
            --#TIMEINDEX 136
        ::= 136006014
 
   mngmtAgentTrap-6015 TRAP-TYPE
        ENTERPRISE compaq
        VARIABLES  { hostName,
                     scellNameDateTime,
                     agentEventCode,
                     agentEventDescription }
        DESCRIPTION
             "Name Size Exceeded"
           --#TYPE      "Management Agent Event"
           --#SUMMARY   "Host %s : SCellName-TimeDate %s : EventCode %d : Description %s"
           --#ARGUMENTS {0,1,2,3,}
            --#SEVERITY  INFORMATIONAL
            --#TIMEINDEX 136
        ::= 136006015
 
   mngmtAgentTrap-6016 TRAP-TYPE
        ENTERPRISE compaq
        VARIABLES  { hostName,
                     scellNameDateTime,
                     agentEventCode,
                     agentEventDescription }
        DESCRIPTION
             "Shutdown Complete"
           --#TYPE      "Management Agent Event"
           --#SUMMARY   "Host %s : SCellName-TimeDate %s : EventCode %d : Description %s"
           --#ARGUMENTS {0,1,2,3,}
            --#SEVERITY  INFORMATIONAL
            --#TIMEINDEX 136
        ::= 136006016
 
   mngmtAgentTrap-6017 TRAP-TYPE
        ENTERPRISE compaq
        VARIABLES  { hostName,
                     scellNameDateTime,
                     agentEventCode,
                     agentEventDescription }
        DESCRIPTION
             "Mutex Creation Failure"
           --#TYPE      "Management Agent Event"
           --#SUMMARY   "Host %s : SCellName-TimeDate %s : EventCode %d : Description %s"
           --#ARGUMENTS {0,1,2,3,}
            --#SEVERITY  INFORMATIONAL
            --#TIMEINDEX 136
        ::= 136006017
 
   mngmtAgentTrap-6018 TRAP-TYPE
        ENTERPRISE compaq
        VARIABLES  { hostName,
                     scellNameDateTime,
                     agentEventCode,
                     agentEventDescription }
        DESCRIPTION
             "The command has timed out. Storage system is busy processing previous command."
           --#TYPE      "Management Agent Event"
           --#SUMMARY   "Host %s : SCellName-TimeDate %s : EventCode %d : Description %s"
           --#ARGUMENTS {0,1,2,3,}
            --#SEVERITY  INFORMATIONAL
            --#TIMEINDEX 136
        ::= 136006018
 
   mngmtAgentTrap-6019 TRAP-TYPE
        ENTERPRISE compaq
        VARIABLES  { hostName,
                     scellNameDateTime,
                     agentEventCode,
                     agentEventDescription }
        DESCRIPTION
             "No MLD Handle Set"
           --#TYPE      "Management Agent Event"
           --#SUMMARY   "Host %s : SCellName-TimeDate %s : EventCode %d : Description %s"
           --#ARGUMENTS {0,1,2,3,}
            --#SEVERITY  INFORMATIONAL
            --#TIMEINDEX 136
        ::= 136006019
 
   mngmtAgentTrap-6020 TRAP-TYPE
        ENTERPRISE compaq
        VARIABLES  { hostName,
                     scellNameDateTime,
                     agentEventCode,
                     agentEventDescription }
        DESCRIPTION
             "Failed Transport Layer Communication - No Such Id"
           --#TYPE      "Management Agent Event"
           --#SUMMARY   "Host %s : SCellName-TimeDate %s : EventCode %d : Description %s"
           --#ARGUMENTS {0,1,2,3,}
            --#SEVERITY  INFORMATIONAL
            --#TIMEINDEX 136
        ::= 136006020
 
   mngmtAgentTrap-6021 TRAP-TYPE
        ENTERPRISE compaq
        VARIABLES  { hostName,
                     scellNameDateTime,
                     agentEventCode,
                     agentEventDescription }
        DESCRIPTION
             "Failed Transport Layer Communication - TimeOut"
           --#TYPE      "Management Agent Event"
           --#SUMMARY   "Host %s : SCellName-TimeDate %s : EventCode %d : Description %s"
           --#ARGUMENTS {0,1,2,3,}
            --#SEVERITY  INFORMATIONAL
            --#TIMEINDEX 136
        ::= 136006021
 
   mngmtAgentTrap-6022 TRAP-TYPE
        ENTERPRISE compaq
        VARIABLES  { hostName,
                     scellNameDateTime,
                     agentEventCode,
                     agentEventDescription }
        DESCRIPTION
             "No initialized storage system objects found"
           --#TYPE      "Management Agent Event"
           --#SUMMARY   "Host %s : SCellName-TimeDate %s : EventCode %d : Description %s"
           --#ARGUMENTS {0,1,2,3,}
            --#SEVERITY  INFORMATIONAL
            --#TIMEINDEX 136
        ::= 136006022
 
   mngmtAgentTrap-6023 TRAP-TYPE
        ENTERPRISE compaq
        VARIABLES  { hostName,
                     scellNameDateTime,
                     agentEventCode,
                     agentEventDescription }
        DESCRIPTION
             "No Attached Port Found"
           --#TYPE      "Management Agent Event"
           --#SUMMARY   "Host %s : SCellName-TimeDate %s : EventCode %d : Description %s"
           --#ARGUMENTS {0,1,2,3,}
            --#SEVERITY  INFORMATIONAL
            --#TIMEINDEX 136
        ::= 136006023
 
   mngmtAgentTrap-6024 TRAP-TYPE
        ENTERPRISE compaq
        VARIABLES  { hostName,
                     scellNameDateTime,
                     agentEventCode,
                     agentEventDescription }
        DESCRIPTION
             "Failed to get SCMI Object Handle"
           --#TYPE      "Management Agent Event"
           --#SUMMARY   "Host %s : SCellName-TimeDate %s : EventCode %d : Description %s"
           --#ARGUMENTS {0,1,2,3,}
            --#SEVERITY  INFORMATIONAL
            --#TIMEINDEX 136
        ::= 136006024
 
   mngmtAgentTrap-6025 TRAP-TYPE
        ENTERPRISE compaq
        VARIABLES  { hostName,
                     scellNameDateTime,
                     agentEventCode,
                     agentEventDescription }
        DESCRIPTION
             "Shutdown Both Restart And Power Off Requested"
           --#TYPE      "Management Agent Event"
           --#SUMMARY   "Host %s : SCellName-TimeDate %s : EventCode %d : Description %s"
           --#ARGUMENTS {0,1,2,3,}
            --#SEVERITY  INFORMATIONAL
            --#TIMEINDEX 136
        ::= 136006025
 
   mngmtAgentTrap-6026 TRAP-TYPE
        ENTERPRISE compaq
        VARIABLES  { hostName,
                     scellNameDateTime,
                     agentEventCode,
                     agentEventDescription }
        DESCRIPTION
             "Shutdown Drive Shelf Power Off But No Enclosure Power Off Requested"
           --#TYPE      "Management Agent Event"
           --#SUMMARY   "Host %s : SCellName-TimeDate %s : EventCode %d : Description %s"
           --#ARGUMENTS {0,1,2,3,}
            --#SEVERITY  INFORMATIONAL
            --#TIMEINDEX 136
        ::= 136006026
 
   mngmtAgentTrap-6027 TRAP-TYPE
        ENTERPRISE compaq
        VARIABLES  { hostName,
                     scellNameDateTime,
                     agentEventCode,
                     agentEventDescription }
        DESCRIPTION
             "Shutdown Disable Battery But No Enclosure Power Off Requested"
           --#TYPE      "Management Agent Event"
           --#SUMMARY   "Host %s : SCellName-TimeDate %s : EventCode %d : Description %s"
           --#ARGUMENTS {0,1,2,3,}
            --#SEVERITY  INFORMATIONAL
            --#TIMEINDEX 136
        ::= 136006027
 
   mngmtAgentTrap-6028 TRAP-TYPE
        ENTERPRISE compaq
        VARIABLES  { hostName,
                     scellNameDateTime,
                     agentEventCode,
                     agentEventDescription }
        DESCRIPTION
             "Shutdown Disable Battery But Shutdown Unconditional Requested"
           --#TYPE      "Management Agent Event"
           --#SUMMARY   "Host %s : SCellName-TimeDate %s : EventCode %d : Description %s"
           --#ARGUMENTS {0,1,2,3,}
            --#SEVERITY  INFORMATIONAL
            --#TIMEINDEX 136
        ::= 136006028
 
   mngmtAgentTrap-6029 TRAP-TYPE
        ENTERPRISE compaq
        VARIABLES  { hostName,
                     scellNameDateTime,
                     agentEventCode,
                     agentEventDescription }
        DESCRIPTION
             "Shutdown Delay Out Of Range"
           --#TYPE      "Management Agent Event"
           --#SUMMARY   "Host %s : SCellName-TimeDate %s : EventCode %d : Description %s"
           --#ARGUMENTS {0,1,2,3,}
            --#SEVERITY  INFORMATIONAL
            --#TIMEINDEX 136
        ::= 136006029
 
   mngmtAgentTrap-6030 TRAP-TYPE
        ENTERPRISE compaq
        VARIABLES  { hostName,
                     scellNameDateTime,
                     agentEventCode,
                     agentEventDescription }
        DESCRIPTION
             "Cache Write Failure"
           --#TYPE      "Management Agent Event"
           --#SUMMARY   "Host %s : SCellName-TimeDate %s : EventCode %d : Description %s"
           --#ARGUMENTS {0,1,2,3,}
            --#SEVERITY  INFORMATIONAL
            --#TIMEINDEX 136
        ::= 136006030
 
   mngmtAgentTrap-6031 TRAP-TYPE
        ENTERPRISE compaq
        VARIABLES  { hostName,
                     scellNameDateTime,
                     agentEventCode,
                     agentEventDescription }
        DESCRIPTION
             "Battery Disable Failure"
           --#TYPE      "Management Agent Event"
           --#SUMMARY   "Host %s : SCellName-TimeDate %s : EventCode %d : Description %s"
           --#ARGUMENTS {0,1,2,3,}
            --#SEVERITY  INFORMATIONAL
            --#TIMEINDEX 136
        ::= 136006031
 
   mngmtAgentTrap-6032 TRAP-TYPE
        ENTERPRISE compaq
        VARIABLES  { hostName,
                     scellNameDateTime,
                     agentEventCode,
                     agentEventDescription }
        DESCRIPTION
             "Drive Shelf Disable Failure"
           --#TYPE      "Management Agent Event"
           --#SUMMARY   "Host %s : SCellName-TimeDate %s : EventCode %d : Description %s"
           --#ARGUMENTS {0,1,2,3,}
            --#SEVERITY  INFORMATIONAL
            --#TIMEINDEX 136
        ::= 136006032
 
   mngmtAgentTrap-6033 TRAP-TYPE
        ENTERPRISE compaq
        VARIABLES  { hostName,
                     scellNameDateTime,
                     agentEventCode,
                     agentEventDescription }
        DESCRIPTION
             "Battery Disable Failed on Both Controllers Batteries"
           --#TYPE      "Management Agent Event"
           --#SUMMARY   "Host %s : SCellName-TimeDate %s : EventCode %d : Description %s"
           --#ARGUMENTS {0,1,2,3,}
            --#SEVERITY  INFORMATIONAL
            --#TIMEINDEX 136
        ::= 136006033
 
   mngmtAgentTrap-6034 TRAP-TYPE
        ENTERPRISE compaq
        VARIABLES  { hostName,
                     scellNameDateTime,
                     agentEventCode,
                     agentEventDescription }
        DESCRIPTION
             "Battery Disable Failed on This Controllers Battery"
           --#TYPE      "Management Agent Event"
           --#SUMMARY   "Host %s : SCellName-TimeDate %s : EventCode %d : Description %s"
           --#ARGUMENTS {0,1,2,3,}
            --#SEVERITY  INFORMATIONAL
            --#TIMEINDEX 136
        ::= 136006034
 
   mngmtAgentTrap-6035 TRAP-TYPE
        ENTERPRISE compaq
        VARIABLES  { hostName,
                     scellNameDateTime,
                     agentEventCode,
                     agentEventDescription }
        DESCRIPTION
             "Battery Disable Failed on the Other Controllers Battery"
           --#TYPE      "Management Agent Event"
           --#SUMMARY   "Host %s : SCellName-TimeDate %s : EventCode %d : Description %s"
           --#ARGUMENTS {0,1,2,3,}
            --#SEVERITY  INFORMATIONAL
            --#TIMEINDEX 136
        ::= 136006035
 
   mngmtAgentTrap-6036 TRAP-TYPE
        ENTERPRISE compaq
        VARIABLES  { hostName,
                     scellNameDateTime,
                     agentEventCode,
                     agentEventDescription }
        DESCRIPTION
             "Requested disk failure protection level is set. Actual level will change when sufficient disk space is available."
           --#TYPE      "Management Agent Event"
           --#SUMMARY   "Host %s : SCellName-TimeDate %s : EventCode %d : Description %s"
           --#ARGUMENTS {0,1,2,3,}
            --#SEVERITY  INFORMATIONAL
            --#TIMEINDEX 136
        ::= 136006036
 
   mngmtAgentTrap-6037 TRAP-TYPE
        ENTERPRISE compaq
        VARIABLES  { hostName,
                     scellNameDateTime,
                     agentEventCode,
                     agentEventDescription }
        DESCRIPTION
             "Physical Store Contains Stale or Foreign Volume Information."
           --#TYPE      "Management Agent Event"
           --#SUMMARY   "Host %s : SCellName-TimeDate %s : EventCode %d : Description %s"
           --#ARGUMENTS {0,1,2,3,}
            --#SEVERITY  INFORMATIONAL
            --#TIMEINDEX 136
        ::= 136006037
 
   mngmtAgentTrap-6038 TRAP-TYPE
        ENTERPRISE compaq
        VARIABLES  { hostName,
                     scellNameDateTime,
                     agentEventCode,
                     agentEventDescription }
        DESCRIPTION
             "Controller Resynchronization or Reboot Occurred. Context Error"
           --#TYPE      "Management Agent Event"
           --#SUMMARY   "Host %s : SCellName-TimeDate %s : EventCode %d : Description %s"
           --#ARGUMENTS {0,1,2,3,}
            --#SEVERITY  MINOR
            --#TIMEINDEX 136
        ::= 136006038
 
   mngmtAgentTrap-8001 TRAP-TYPE
        ENTERPRISE compaq
        VARIABLES  { hostName,
                     scellNameDateTime,
                     agentEventCode,
                     agentEventDescription }
        DESCRIPTION
             "Invalid Operation"
           --#TYPE      "Management Agent Event"
           --#SUMMARY   "Host %s : SCellName-TimeDate %s : EventCode %d : Description %s"
           --#ARGUMENTS {0,1,2,3,}
            --#SEVERITY  INFORMATIONAL
            --#TIMEINDEX 136
        ::= 136008001
 
   mngmtAgentTrap-8002 TRAP-TYPE
        ENTERPRISE compaq
        VARIABLES  { hostName,
                     scellNameDateTime,
                     agentEventCode,
                     agentEventDescription }
        DESCRIPTION
             "Storage system already created"
           --#TYPE      "Management Agent Event"
           --#SUMMARY   "Host %s : SCellName-TimeDate %s : EventCode %d : Description %s"
           --#ARGUMENTS {0,1,2,3,}
            --#SEVERITY  INFORMATIONAL
            --#TIMEINDEX 136
        ::= 136008002
 
   mngmtAgentTrap-8003 TRAP-TYPE
        ENTERPRISE compaq
        VARIABLES  { hostName,
                     scellNameDateTime,
                     agentEventCode,
                     agentEventDescription }
        DESCRIPTION
             "Controller already part of storage system configuration"
           --#TYPE      "Management Agent Event"
           --#SUMMARY   "Host %s : SCellName-TimeDate %s : EventCode %d : Description %s"
           --#ARGUMENTS {0,1,2,3,}
            --#SEVERITY  INFORMATIONAL
            --#TIMEINDEX 136
        ::= 136008003
 
   mngmtAgentTrap-8004 TRAP-TYPE
        ENTERPRISE compaq
        VARIABLES  { hostName,
                     scellNameDateTime,
                     agentEventCode,
                     agentEventDescription }
        DESCRIPTION
             "Physical Store Count Below Minimum"
           --#TYPE      "Management Agent Event"
           --#SUMMARY   "Host %s : SCellName-TimeDate %s : EventCode %d : Description %s"
           --#ARGUMENTS {0,1,2,3,}
            --#SEVERITY  INFORMATIONAL
            --#TIMEINDEX 136
        ::= 136008004
 
   mngmtAgentTrap-8005 TRAP-TYPE
        ENTERPRISE compaq
        VARIABLES  { hostName,
                     scellNameDateTime,
                     agentEventCode,
                     agentEventDescription }
        DESCRIPTION
             "Controller not part of storage system configuration"
           --#TYPE      "Management Agent Event"
           --#SUMMARY   "Host %s : SCellName-TimeDate %s : EventCode %d : Description %s"
           --#ARGUMENTS {0,1,2,3,}
            --#SEVERITY  INFORMATIONAL
            --#TIMEINDEX 136
        ::= 136008005
 
   mngmtAgentTrap-8006 TRAP-TYPE
        ENTERPRISE compaq
        VARIABLES  { hostName,
                     scellNameDateTime,
                     agentEventCode,
                     agentEventDescription }
        DESCRIPTION
             "Failed to uninitialize storage system"
           --#TYPE      "Management Agent Event"
           --#SUMMARY   "Host %s : SCellName-TimeDate %s : EventCode %d : Description %s"
           --#ARGUMENTS {0,1,2,3,}
            --#SEVERITY  INFORMATIONAL
            --#TIMEINDEX 136
        ::= 136008006
 
   mngmtAgentTrap-8007 TRAP-TYPE
        ENTERPRISE compaq
        VARIABLES  { hostName,
                     scellNameDateTime,
                     agentEventCode,
                     agentEventDescription }
        DESCRIPTION
             "Storage system File Open Error"
           --#TYPE      "Management Agent Event"
           --#SUMMARY   "Host %s : SCellName-TimeDate %s : EventCode %d : Description %s"
           --#ARGUMENTS {0,1,2,3,}
            --#SEVERITY  MINOR
            --#TIMEINDEX 136
        ::= 136008007
 
   mngmtAgentTrap-8008 TRAP-TYPE
        ENTERPRISE compaq
        VARIABLES  { hostName,
                     scellNameDateTime,
                     agentEventCode,
                     agentEventDescription }
        DESCRIPTION
             "Storage system File Write Error"
           --#TYPE      "Management Agent Event"
           --#SUMMARY   "Host %s : SCellName-TimeDate %s : EventCode %d : Description %s"
           --#ARGUMENTS {0,1,2,3,}
            --#SEVERITY  MINOR
            --#TIMEINDEX 136
        ::= 136008008
 
   mngmtAgentTrap-8009 TRAP-TYPE
        ENTERPRISE compaq
        VARIABLES  { hostName,
                     scellNameDateTime,
                     agentEventCode,
                     agentEventDescription }
        DESCRIPTION
             "Storage system File Read Error"
           --#TYPE      "Management Agent Event"
           --#SUMMARY   "Host %s : SCellName-TimeDate %s : EventCode %d : Description %s"
           --#ARGUMENTS {0,1,2,3,}
            --#SEVERITY  MINOR
            --#TIMEINDEX 136
        ::= 136008009
 
   mngmtAgentTrap-8010 TRAP-TYPE
        ENTERPRISE compaq
        VARIABLES  { hostName,
                     scellNameDateTime,
                     agentEventCode,
                     agentEventDescription }
        DESCRIPTION
             "Name too long"
           --#TYPE      "Management Agent Event"
           --#SUMMARY   "Host %s : SCellName-TimeDate %s : EventCode %d : Description %s"
           --#ARGUMENTS {0,1,2,3,}
            --#SEVERITY  INFORMATIONAL
            --#TIMEINDEX 136
        ::= 136008010
 
   mngmtAgentTrap-8011 TRAP-TYPE
        ENTERPRISE compaq
        VARIABLES  { hostName,
                     scellNameDateTime,
                     agentEventCode,
                     agentEventDescription }
        DESCRIPTION
             "No String Error"
           --#TYPE      "Management Agent Event"
           --#SUMMARY   "Host %s : SCellName-TimeDate %s : EventCode %d : Description %s"
           --#ARGUMENTS {0,1,2,3,}
            --#SEVERITY  INFORMATIONAL
            --#TIMEINDEX 136
        ::= 136008011
 
   mngmtAgentTrap-8012 TRAP-TYPE
        ENTERPRISE compaq
        VARIABLES  { hostName,
                     scellNameDateTime,
                     agentEventCode,
                     agentEventDescription }
        DESCRIPTION
             "No MLD Handle Found"
           --#TYPE      "Management Agent Event"
           --#SUMMARY   "Host %s : SCellName-TimeDate %s : EventCode %d : Description %s"
           --#ARGUMENTS {0,1,2,3,}
            --#SEVERITY  INFORMATIONAL
            --#TIMEINDEX 136
        ::= 136008012
 
   mngmtAgentTrap-8013 TRAP-TYPE
        ENTERPRISE compaq
        VARIABLES  { hostName,
                     scellNameDateTime,
                     agentEventCode,
                     agentEventDescription }
        DESCRIPTION
             "No Controllers Found"
           --#TYPE      "Management Agent Event"
           --#SUMMARY   "Host %s : SCellName-TimeDate %s : EventCode %d : Description %s"
           --#ARGUMENTS {0,1,2,3,}
            --#SEVERITY  INFORMATIONAL
            --#TIMEINDEX 136
        ::= 136008013
 
   mngmtAgentTrap-8014 TRAP-TYPE
        ENTERPRISE compaq
        VARIABLES  { hostName,
                     scellNameDateTime,
                     agentEventCode,
                     agentEventDescription }
        DESCRIPTION
             "Controller Not Found On Loop"
           --#TYPE      "Management Agent Event"
           --#SUMMARY   "Host %s : SCellName-TimeDate %s : EventCode %d : Description %s"
           --#ARGUMENTS {0,1,2,3,}
            --#SEVERITY  INFORMATIONAL
            --#TIMEINDEX 136
        ::= 136008014
 
   mngmtAgentTrap-8015 TRAP-TYPE
        ENTERPRISE compaq
        VARIABLES  { hostName,
                     scellNameDateTime,
                     agentEventCode,
                     agentEventDescription }
        DESCRIPTION
             "No Disk Groups Found"
           --#TYPE      "Management Agent Event"
           --#SUMMARY   "Host %s : SCellName-TimeDate %s : EventCode %d : Description %s"
           --#ARGUMENTS {0,1,2,3,}
            --#SEVERITY  INFORMATIONAL
            --#TIMEINDEX 136
        ::= 136008015
 
   mngmtAgentTrap-8016 TRAP-TYPE
        ENTERPRISE compaq
        VARIABLES  { hostName,
                     scellNameDateTime,
                     agentEventCode,
                     agentEventDescription }
        DESCRIPTION
             "No Volumes Found"
           --#TYPE      "Management Agent Event"
           --#SUMMARY   "Host %s : SCellName-TimeDate %s : EventCode %d : Description %s"
           --#ARGUMENTS {0,1,2,3,}
            --#SEVERITY  INFORMATIONAL
            --#TIMEINDEX 136
        ::= 136008016
 
   mngmtAgentTrap-8017 TRAP-TYPE
        ENTERPRISE compaq
        VARIABLES  { hostName,
                     scellNameDateTime,
                     agentEventCode,
                     agentEventDescription }
        DESCRIPTION
             "No Physical Stores Found"
           --#TYPE      "Management Agent Event"
           --#SUMMARY   "Host %s : SCellName-TimeDate %s : EventCode %d : Description %s"
           --#ARGUMENTS {0,1,2,3,}
            --#SEVERITY  INFORMATIONAL
            --#TIMEINDEX 136
        ::= 136008017
 
   mngmtAgentTrap-8018 TRAP-TYPE
        ENTERPRISE compaq
        VARIABLES  { hostName,
                     scellNameDateTime,
                     agentEventCode,
                     agentEventDescription }
        DESCRIPTION
             "No Vdisks Found"
           --#TYPE      "Management Agent Event"
           --#SUMMARY   "Host %s : SCellName-TimeDate %s : EventCode %d : Description %s"
           --#ARGUMENTS {0,1,2,3,}
            --#SEVERITY  INFORMATIONAL
            --#TIMEINDEX 136
        ::= 136008018
 
   mngmtAgentTrap-8019 TRAP-TYPE
        ENTERPRISE compaq
        VARIABLES  { hostName,
                     scellNameDateTime,
                     agentEventCode,
                     agentEventDescription }
        DESCRIPTION
             "No Hosts Found"
           --#TYPE      "Management Agent Event"
           --#SUMMARY   "Host %s : SCellName-TimeDate %s : EventCode %d : Description %s"
           --#ARGUMENTS {0,1,2,3,}
            --#SEVERITY  INFORMATIONAL
            --#TIMEINDEX 136
        ::= 136008019
 
   mngmtAgentTrap-8020 TRAP-TYPE
        ENTERPRISE compaq
        VARIABLES  { hostName,
                     scellNameDateTime,
                     agentEventCode,
                     agentEventDescription }
        DESCRIPTION
             "Name already exists"
           --#TYPE      "Management Agent Event"
           --#SUMMARY   "Host %s : SCellName-TimeDate %s : EventCode %d : Description %s"
           --#ARGUMENTS {0,1,2,3,}
            --#SEVERITY  INFORMATIONAL
            --#TIMEINDEX 136
        ::= 136008020
 
   mngmtAgentTrap-8021 TRAP-TYPE
        ENTERPRISE compaq
        VARIABLES  { hostName,
                     scellNameDateTime,
                     agentEventCode,
                     agentEventDescription }
        DESCRIPTION
             "Folder is not empty"
           --#TYPE      "Management Agent Event"
           --#SUMMARY   "Host %s : SCellName-TimeDate %s : EventCode %d : Description %s"
           --#ARGUMENTS {0,1,2,3,}
            --#SEVERITY  INFORMATIONAL
            --#TIMEINDEX 136
        ::= 136008021
 
   mngmtAgentTrap-8022 TRAP-TYPE
        ENTERPRISE compaq
        VARIABLES  { hostName,
                     scellNameDateTime,
                     agentEventCode,
                     agentEventDescription }
        DESCRIPTION
             "Spares goal could not be met"
           --#TYPE      "Management Agent Event"
           --#SUMMARY   "Host %s : SCellName-TimeDate %s : EventCode %d : Description %s"
           --#ARGUMENTS {0,1,2,3,}
            --#SEVERITY  INFORMATIONAL
            --#TIMEINDEX 136
        ::= 136008022
 
   mngmtAgentTrap-8023 TRAP-TYPE
        ENTERPRISE compaq
        VARIABLES  { hostName,
                     scellNameDateTime,
                     agentEventCode,
                     agentEventDescription }
        DESCRIPTION
             "Storage system object found"
           --#TYPE      "Management Agent Event"
           --#SUMMARY   "Host %s : SCellName-TimeDate %s : EventCode %d : Description %s"
           --#ARGUMENTS {0,1,2,3,}
            --#SEVERITY  INFORMATIONAL
            --#TIMEINDEX 136
        ::= 136008023
 
   mngmtAgentTrap-8024 TRAP-TYPE
        ENTERPRISE compaq
        VARIABLES  { hostName,
                     scellNameDateTime,
                     agentEventCode,
                     agentEventDescription }
        DESCRIPTION
             "Storage system object not found"
           --#TYPE      "Management Agent Event"
           --#SUMMARY   "Host %s : SCellName-TimeDate %s : EventCode %d : Description %s"
           --#ARGUMENTS {0,1,2,3,}
            --#SEVERITY  INFORMATIONAL
            --#TIMEINDEX 136
        ::= 136008024
 
   mngmtAgentTrap-8025 TRAP-TYPE
        ENTERPRISE compaq
        VARIABLES  { hostName,
                     scellNameDateTime,
                     agentEventCode,
                     agentEventDescription }
        DESCRIPTION
             "New Physical Store Detected But Not Found In Physical Store List"
           --#TYPE      "Management Agent Event"
           --#SUMMARY   "Host %s : SCellName-TimeDate %s : EventCode %d : Description %s"
           --#ARGUMENTS {0,1,2,3,}
            --#SEVERITY  INFORMATIONAL
            --#TIMEINDEX 136
        ::= 136008025
 
   mngmtAgentTrap-8026 TRAP-TYPE
        ENTERPRISE compaq
        VARIABLES  { hostName,
                     scellNameDateTime,
                     agentEventCode,
                     agentEventDescription }
        DESCRIPTION
             "MldManager Handle is NULL"
           --#TYPE      "Management Agent Event"
           --#SUMMARY   "Host %s : SCellName-TimeDate %s : EventCode %d : Description %s"
           --#ARGUMENTS {0,1,2,3,}
            --#SEVERITY  MINOR
            --#TIMEINDEX 136
        ::= 136008026
 
   mngmtAgentTrap-8027 TRAP-TYPE
        ENTERPRISE compaq
        VARIABLES  { hostName,
                     scellNameDateTime,
                     agentEventCode,
                     agentEventDescription }
        DESCRIPTION
             "NscMngrInterface Handle is NULL"
           --#TYPE      "Management Agent Event"
           --#SUMMARY   "Host %s : SCellName-TimeDate %s : EventCode %d : Description %s"
           --#ARGUMENTS {0,1,2,3,}
            --#SEVERITY  MINOR
            --#TIMEINDEX 136
        ::= 136008027
 
   mngmtAgentTrap-8028 TRAP-TYPE
        ENTERPRISE compaq
        VARIABLES  { hostName,
                     scellNameDateTime,
                     agentEventCode,
                     agentEventDescription }
        DESCRIPTION
             "ScLockMngr Handle is NULL"
           --#TYPE      "Management Agent Event"
           --#SUMMARY   "Host %s : SCellName-TimeDate %s : EventCode %d : Description %s"
           --#ARGUMENTS {0,1,2,3,}
            --#SEVERITY  MINOR
            --#TIMEINDEX 136
        ::= 136008028
 
   mngmtAgentTrap-8029 TRAP-TYPE
        ENTERPRISE compaq
        VARIABLES  { hostName,
                     scellNameDateTime,
                     agentEventCode,
                     agentEventDescription }
        DESCRIPTION
             "Storage system initialization failed"
           --#TYPE      "Management Agent Event"
           --#SUMMARY   "Host %s : SCellName-TimeDate %s : EventCode %d : Description %s"
           --#ARGUMENTS {0,1,2,3,}
            --#SEVERITY  CRITICAL
            --#TIMEINDEX 136
        ::= 136008029
 
   mngmtAgentTrap-8030 TRAP-TYPE
        ENTERPRISE compaq
        VARIABLES  { hostName,
                     scellNameDateTime,
                     agentEventCode,
                     agentEventDescription }
        DESCRIPTION
             "MldMngr, NscMngrInterfaceMngr, or ScLockMngr Handle is NULL"
           --#TYPE      "Management Agent Event"
           --#SUMMARY   "Host %s : SCellName-TimeDate %s : EventCode %d : Description %s"
           --#ARGUMENTS {0,1,2,3,}
            --#SEVERITY  MINOR
            --#TIMEINDEX 136
        ::= 136008030
 
   mngmtAgentTrap-8031 TRAP-TYPE
        ENTERPRISE compaq
        VARIABLES  { hostName,
                     scellNameDateTime,
                     agentEventCode,
                     agentEventDescription }
        DESCRIPTION
             "Storage system initialization failed"
           --#TYPE      "Management Agent Event"
           --#SUMMARY   "Host %s : SCellName-TimeDate %s : EventCode %d : Description %s"
           --#ARGUMENTS {0,1,2,3,}
            --#SEVERITY  CRITICAL
            --#TIMEINDEX 136
        ::= 136008031
 
   mngmtAgentTrap-8032 TRAP-TYPE
        ENTERPRISE compaq
        VARIABLES  { hostName,
                     scellNameDateTime,
                     agentEventCode,
                     agentEventDescription }
        DESCRIPTION
             "Storage system discovery failed"
           --#TYPE      "Management Agent Event"
           --#SUMMARY   "Host %s : SCellName-TimeDate %s : EventCode %d : Description %s"
           --#ARGUMENTS {0,1,2,3,}
            --#SEVERITY  MINOR
            --#TIMEINDEX 136
        ::= 136008032
 
   mngmtAgentTrap-8033 TRAP-TYPE
        ENTERPRISE compaq
        VARIABLES  { hostName,
                     scellNameDateTime,
                     agentEventCode,
                     agentEventDescription }
        DESCRIPTION
             "Storage system already uninitialized or does not exist"
           --#TYPE      "Management Agent Event"
           --#SUMMARY   "Host %s : SCellName-TimeDate %s : EventCode %d : Description %s"
           --#ARGUMENTS {0,1,2,3,}
            --#SEVERITY  INFORMATIONAL
            --#TIMEINDEX 136
        ::= 136008033
 
   mngmtAgentTrap-8034 TRAP-TYPE
        ENTERPRISE compaq
        VARIABLES  { hostName,
                     scellNameDateTime,
                     agentEventCode,
                     agentEventDescription }
        DESCRIPTION
             "Get Total Storage Failed"
           --#TYPE      "Management Agent Event"
           --#SUMMARY   "Host %s : SCellName-TimeDate %s : EventCode %d : Description %s"
           --#ARGUMENTS {0,1,2,3,}
            --#SEVERITY  MINOR
            --#TIMEINDEX 136
        ::= 136008034
 
   mngmtAgentTrap-8035 TRAP-TYPE
        ENTERPRISE compaq
        VARIABLES  { hostName,
                     scellNameDateTime,
                     agentEventCode,
                     agentEventDescription }
        DESCRIPTION
             "Storage system is uninitialized"
           --#TYPE      "Management Agent Event"
           --#SUMMARY   "Host %s : SCellName-TimeDate %s : EventCode %d : Description %s"
           --#ARGUMENTS {0,1,2,3,}
            --#SEVERITY  INFORMATIONAL
            --#TIMEINDEX 136
        ::= 136008035
 
   mngmtAgentTrap-8036 TRAP-TYPE
        ENTERPRISE compaq
        VARIABLES  { hostName,
                     scellNameDateTime,
                     agentEventCode,
                     agentEventDescription }
        DESCRIPTION
             "Get Total Storage Available Failed"
           --#TYPE      "Management Agent Event"
           --#SUMMARY   "Host %s : SCellName-TimeDate %s : EventCode %d : Description %s"
           --#ARGUMENTS {0,1,2,3,}
            --#SEVERITY  MINOR
            --#TIMEINDEX 136
        ::= 136008036
 
   mngmtAgentTrap-8037 TRAP-TYPE
        ENTERPRISE compaq
        VARIABLES  { hostName,
                     scellNameDateTime,
                     agentEventCode,
                     agentEventDescription }
        DESCRIPTION
             "Get Total Storage Occupied Failed"
           --#TYPE      "Management Agent Event"
           --#SUMMARY   "Host %s : SCellName-TimeDate %s : EventCode %d : Description %s"
           --#ARGUMENTS {0,1,2,3,}
            --#SEVERITY  MINOR
            --#TIMEINDEX 136
        ::= 136008037
 
   mngmtAgentTrap-8038 TRAP-TYPE
        ENTERPRISE compaq
        VARIABLES  { hostName,
                     scellNameDateTime,
                     agentEventCode,
                     agentEventDescription }
        DESCRIPTION
             "Get Total Storage Free Failed"
           --#TYPE      "Management Agent Event"
           --#SUMMARY   "Host %s : SCellName-TimeDate %s : EventCode %d : Description %s"
           --#ARGUMENTS {0,1,2,3,}
            --#SEVERITY  MINOR
            --#TIMEINDEX 136
        ::= 136008038
 
   mngmtAgentTrap-8039 TRAP-TYPE
        ENTERPRISE compaq
        VARIABLES  { hostName,
                     scellNameDateTime,
                     agentEventCode,
                     agentEventDescription }
        DESCRIPTION
             "Get Disk Group Failed"
           --#TYPE      "Management Agent Event"
           --#SUMMARY   "Host %s : SCellName-TimeDate %s : EventCode %d : Description %s"
           --#ARGUMENTS {0,1,2,3,}
            --#SEVERITY  MINOR
            --#TIMEINDEX 136
        ::= 136008039
 
   mngmtAgentTrap-8040 TRAP-TYPE
        ENTERPRISE compaq
        VARIABLES  { hostName,
                     scellNameDateTime,
                     agentEventCode,
                     agentEventDescription }
        DESCRIPTION
             "Get Disk Group List Failed"
           --#TYPE      "Management Agent Event"
           --#SUMMARY   "Host %s : SCellName-TimeDate %s : EventCode %d : Description %s"
           --#ARGUMENTS {0,1,2,3,}
            --#SEVERITY  MINOR
            --#TIMEINDEX 136
        ::= 136008040
 
   mngmtAgentTrap-8041 TRAP-TYPE
        ENTERPRISE compaq
        VARIABLES  { hostName,
                     scellNameDateTime,
                     agentEventCode,
                     agentEventDescription }
        DESCRIPTION
             "Get Disk Group Count Failed"
           --#TYPE      "Management Agent Event"
           --#SUMMARY   "Host %s : SCellName-TimeDate %s : EventCode %d : Description %s"
           --#ARGUMENTS {0,1,2,3,}
            --#SEVERITY  MINOR
            --#TIMEINDEX 136
        ::= 136008041
 
   mngmtAgentTrap-8042 TRAP-TYPE
        ENTERPRISE compaq
        VARIABLES  { hostName,
                     scellNameDateTime,
                     agentEventCode,
                     agentEventDescription }
        DESCRIPTION
             "Create Volume Failed"
           --#TYPE      "Management Agent Event"
           --#SUMMARY   "Host %s : SCellName-TimeDate %s : EventCode %d : Description %s"
           --#ARGUMENTS {0,1,2,3,}
            --#SEVERITY  MINOR
            --#TIMEINDEX 136
        ::= 136008042
 
   mngmtAgentTrap-8043 TRAP-TYPE
        ENTERPRISE compaq
        VARIABLES  { hostName,
                     scellNameDateTime,
                     agentEventCode,
                     agentEventDescription }
        DESCRIPTION
             "Get Volume Failed"
           --#TYPE      "Management Agent Event"
           --#SUMMARY   "Host %s : SCellName-TimeDate %s : EventCode %d : Description %s"
           --#ARGUMENTS {0,1,2,3,}
            --#SEVERITY  MINOR
            --#TIMEINDEX 136
        ::= 136008043
 
   mngmtAgentTrap-8044 TRAP-TYPE
        ENTERPRISE compaq
        VARIABLES  { hostName,
                     scellNameDateTime,
                     agentEventCode,
                     agentEventDescription }
        DESCRIPTION
             "Get Volumes Failed"
           --#TYPE      "Management Agent Event"
           --#SUMMARY   "Host %s : SCellName-TimeDate %s : EventCode %d : Description %s"
           --#ARGUMENTS {0,1,2,3,}
            --#SEVERITY  MINOR
            --#TIMEINDEX 136
        ::= 136008044
 
   mngmtAgentTrap-8045 TRAP-TYPE
        ENTERPRISE compaq
        VARIABLES  { hostName,
                     scellNameDateTime,
                     agentEventCode,
                     agentEventDescription }
        DESCRIPTION
             "Get Volumes Count Failed"
           --#TYPE      "Management Agent Event"
           --#SUMMARY   "Host %s : SCellName-TimeDate %s : EventCode %d : Description %s"
           --#ARGUMENTS {0,1,2,3,}
            --#SEVERITY  MINOR
            --#TIMEINDEX 136
        ::= 136008045
 
   mngmtAgentTrap-8046 TRAP-TYPE
        ENTERPRISE compaq
        VARIABLES  { hostName,
                     scellNameDateTime,
                     agentEventCode,
                     agentEventDescription }
        DESCRIPTION
             "Get Vdisk Failed"
           --#TYPE      "Management Agent Event"
           --#SUMMARY   "Host %s : SCellName-TimeDate %s : EventCode %d : Description %s"
           --#ARGUMENTS {0,1,2,3,}
            --#SEVERITY  MINOR
            --#TIMEINDEX 136
        ::= 136008046
 
   mngmtAgentTrap-8047 TRAP-TYPE
        ENTERPRISE compaq
        VARIABLES  { hostName,
                     scellNameDateTime,
                     agentEventCode,
                     agentEventDescription }
        DESCRIPTION
             "Get Vdisk List Failed"
           --#TYPE      "Management Agent Event"
           --#SUMMARY   "Host %s : SCellName-TimeDate %s : EventCode %d : Description %s"
           --#ARGUMENTS {0,1,2,3,}
            --#SEVERITY  MINOR
            --#TIMEINDEX 136
        ::= 136008047
 
   mngmtAgentTrap-8048 TRAP-TYPE
        ENTERPRISE compaq
        VARIABLES  { hostName,
                     scellNameDateTime,
                     agentEventCode,
                     agentEventDescription }
        DESCRIPTION
             "Get Physical Store Failed"
           --#TYPE      "Management Agent Event"
           --#SUMMARY   "Host %s : SCellName-TimeDate %s : EventCode %d : Description %s"
           --#ARGUMENTS {0,1,2,3,}
            --#SEVERITY  MINOR
            --#TIMEINDEX 136
        ::= 136008048
 
   mngmtAgentTrap-8049 TRAP-TYPE
        ENTERPRISE compaq
        VARIABLES  { hostName,
                     scellNameDateTime,
                     agentEventCode,
                     agentEventDescription }
        DESCRIPTION
             "Get Physical Stores Failed"
           --#TYPE      "Management Agent Event"
           --#SUMMARY   "Host %s : SCellName-TimeDate %s : EventCode %d : Description %s"
           --#ARGUMENTS {0,1,2,3,}
            --#SEVERITY  MINOR
            --#TIMEINDEX 136
        ::= 136008049
 
   mngmtAgentTrap-8050 TRAP-TYPE
        ENTERPRISE compaq
        VARIABLES  { hostName,
                     scellNameDateTime,
                     agentEventCode,
                     agentEventDescription }
        DESCRIPTION
             "Get Physical Stores Count Failed"
           --#TYPE      "Management Agent Event"
           --#SUMMARY   "Host %s : SCellName-TimeDate %s : EventCode %d : Description %s"
           --#ARGUMENTS {0,1,2,3,}
            --#SEVERITY  MINOR
            --#TIMEINDEX 136
        ::= 136008050
 
   mngmtAgentTrap-8051 TRAP-TYPE
        ENTERPRISE compaq
        VARIABLES  { hostName,
                     scellNameDateTime,
                     agentEventCode,
                     agentEventDescription }
        DESCRIPTION
             "Create Vdisk Failed"
           --#TYPE      "Management Agent Event"
           --#SUMMARY   "Host %s : SCellName-TimeDate %s : EventCode %d : Description %s"
           --#ARGUMENTS {0,1,2,3,}
            --#SEVERITY  MINOR
            --#TIMEINDEX 136
        ::= 136008051
 
   mngmtAgentTrap-8052 TRAP-TYPE
        ENTERPRISE compaq
        VARIABLES  { hostName,
                     scellNameDateTime,
                     agentEventCode,
                     agentEventDescription }
        DESCRIPTION
             "Delete Vdisk Failed"
           --#TYPE      "Management Agent Event"
           --#SUMMARY   "Host %s : SCellName-TimeDate %s : EventCode %d : Description %s"
           --#ARGUMENTS {0,1,2,3,}
            --#SEVERITY  MINOR
            --#TIMEINDEX 136
        ::= 136008052
 
   mngmtAgentTrap-8053 TRAP-TYPE
        ENTERPRISE compaq
        VARIABLES  { hostName,
                     scellNameDateTime,
                     agentEventCode,
                     agentEventDescription }
        DESCRIPTION
             "Get Device Addition Policy Failed"
           --#TYPE      "Management Agent Event"
           --#SUMMARY   "Host %s : SCellName-TimeDate %s : EventCode %d : Description %s"
           --#ARGUMENTS {0,1,2,3,}
            --#SEVERITY  MINOR
            --#TIMEINDEX 136
        ::= 136008053
 
   mngmtAgentTrap-8054 TRAP-TYPE
        ENTERPRISE compaq
        VARIABLES  { hostName,
                     scellNameDateTime,
                     agentEventCode,
                     agentEventDescription }
        DESCRIPTION
             "Get Spares Current Failed"
           --#TYPE      "Management Agent Event"
           --#SUMMARY   "Host %s : SCellName-TimeDate %s : EventCode %d : Description %s"
           --#ARGUMENTS {0,1,2,3,}
            --#SEVERITY  MINOR
            --#TIMEINDEX 136
        ::= 136008054
 
   mngmtAgentTrap-8055 TRAP-TYPE
        ENTERPRISE compaq
        VARIABLES  { hostName,
                     scellNameDateTime,
                     agentEventCode,
                     agentEventDescription }
        DESCRIPTION
             "Get Spares Goal Failed"
           --#TYPE      "Management Agent Event"
           --#SUMMARY   "Host %s : SCellName-TimeDate %s : EventCode %d : Description %s"
           --#ARGUMENTS {0,1,2,3,}
            --#SEVERITY  MINOR
            --#TIMEINDEX 136
        ::= 136008055
 
   mngmtAgentTrap-8056 TRAP-TYPE
        ENTERPRISE compaq
        VARIABLES  { hostName,
                     scellNameDateTime,
                     agentEventCode,
                     agentEventDescription }
        DESCRIPTION
             "Get storage system events failed"
           --#TYPE      "Management Agent Event"
           --#SUMMARY   "Host %s : SCellName-TimeDate %s : EventCode %d : Description %s"
           --#ARGUMENTS {0,1,2,3,}
            --#SEVERITY  MINOR
            --#TIMEINDEX 136
        ::= 136008056
 
   mngmtAgentTrap-8057 TRAP-TYPE
        ENTERPRISE compaq
        VARIABLES  { hostName,
                     scellNameDateTime,
                     agentEventCode,
                     agentEventDescription }
        DESCRIPTION
             "Get Volume Replacement Delay Failed"
           --#TYPE      "Management Agent Event"
           --#SUMMARY   "Host %s : SCellName-TimeDate %s : EventCode %d : Description %s"
           --#ARGUMENTS {0,1,2,3,}
            --#SEVERITY  MINOR
            --#TIMEINDEX 136
        ::= 136008057
 
   mngmtAgentTrap-8058 TRAP-TYPE
        ENTERPRISE compaq
        VARIABLES  { hostName,
                     scellNameDateTime,
                     agentEventCode,
                     agentEventDescription }
        DESCRIPTION
             "Set Device Addition Policy Failed"
           --#TYPE      "Management Agent Event"
           --#SUMMARY   "Host %s : SCellName-TimeDate %s : EventCode %d : Description %s"
           --#ARGUMENTS {0,1,2,3,}
            --#SEVERITY  MINOR
            --#TIMEINDEX 136
        ::= 136008058
 
   mngmtAgentTrap-8059 TRAP-TYPE
        ENTERPRISE compaq
        VARIABLES  { hostName,
                     scellNameDateTime,
                     agentEventCode,
                     agentEventDescription }
        DESCRIPTION
             "Set Spares Goal Failed"
           --#TYPE      "Management Agent Event"
           --#SUMMARY   "Host %s : SCellName-TimeDate %s : EventCode %d : Description %s"
           --#ARGUMENTS {0,1,2,3,}
            --#SEVERITY  MINOR
            --#TIMEINDEX 136
        ::= 136008059
 
   mngmtAgentTrap-8060 TRAP-TYPE
        ENTERPRISE compaq
        VARIABLES  { hostName,
                     scellNameDateTime,
                     agentEventCode,
                     agentEventDescription }
        DESCRIPTION
             "Set Volume Replacement Delay Failed"
           --#TYPE      "Management Agent Event"
           --#SUMMARY   "Host %s : SCellName-TimeDate %s : EventCode %d : Description %s"
           --#ARGUMENTS {0,1,2,3,}
            --#SEVERITY  MINOR
            --#TIMEINDEX 136
        ::= 136008060
 
   mngmtAgentTrap-8061 TRAP-TYPE
        ENTERPRISE compaq
        VARIABLES  { hostName,
                     scellNameDateTime,
                     agentEventCode,
                     agentEventDescription }
        DESCRIPTION
             "Create controller Failed"
           --#TYPE      "Management Agent Event"
           --#SUMMARY   "Host %s : SCellName-TimeDate %s : EventCode %d : Description %s"
           --#ARGUMENTS {0,1,2,3,}
            --#SEVERITY  MINOR
            --#TIMEINDEX 136
        ::= 136008061
 
   mngmtAgentTrap-8062 TRAP-TYPE
        ENTERPRISE compaq
        VARIABLES  { hostName,
                     scellNameDateTime,
                     agentEventCode,
                     agentEventDescription }
        DESCRIPTION
             "Update controller Failed"
           --#TYPE      "Management Agent Event"
           --#SUMMARY   "Host %s : SCellName-TimeDate %s : EventCode %d : Description %s"
           --#ARGUMENTS {0,1,2,3,}
            --#SEVERITY  MINOR
            --#TIMEINDEX 136
        ::= 136008062
 
   mngmtAgentTrap-8063 TRAP-TYPE
        ENTERPRISE compaq
        VARIABLES  { hostName,
                     scellNameDateTime,
                     agentEventCode,
                     agentEventDescription }
        DESCRIPTION
             "Create Host Failed"
           --#TYPE      "Management Agent Event"
           --#SUMMARY   "Host %s : SCellName-TimeDate %s : EventCode %d : Description %s"
           --#ARGUMENTS {0,1,2,3,}
            --#SEVERITY  MINOR
            --#TIMEINDEX 136
        ::= 136008063
 
   mngmtAgentTrap-8064 TRAP-TYPE
        ENTERPRISE compaq
        VARIABLES  { hostName,
                     scellNameDateTime,
                     agentEventCode,
                     agentEventDescription }
        DESCRIPTION
             "Discard Host Failed"
           --#TYPE      "Management Agent Event"
           --#SUMMARY   "Host %s : SCellName-TimeDate %s : EventCode %d : Description %s"
           --#ARGUMENTS {0,1,2,3,}
            --#SEVERITY  MINOR
            --#TIMEINDEX 136
        ::= 136008064
 
   mngmtAgentTrap-8065 TRAP-TYPE
        ENTERPRISE compaq
        VARIABLES  { hostName,
                     scellNameDateTime,
                     agentEventCode,
                     agentEventDescription }
        DESCRIPTION
             "Get Host Failed"
           --#TYPE      "Management Agent Event"
           --#SUMMARY   "Host %s : SCellName-TimeDate %s : EventCode %d : Description %s"
           --#ARGUMENTS {0,1,2,3,}
            --#SEVERITY  MINOR
            --#TIMEINDEX 136
        ::= 136008065
 
   mngmtAgentTrap-8066 TRAP-TYPE
        ENTERPRISE compaq
        VARIABLES  { hostName,
                     scellNameDateTime,
                     agentEventCode,
                     agentEventDescription }
        DESCRIPTION
             "Get Host List Failed"
           --#TYPE      "Management Agent Event"
           --#SUMMARY   "Host %s : SCellName-TimeDate %s : EventCode %d : Description %s"
           --#ARGUMENTS {0,1,2,3,}
            --#SEVERITY  MINOR
            --#TIMEINDEX 136
        ::= 136008066
 
   mngmtAgentTrap-8067 TRAP-TYPE
        ENTERPRISE compaq
        VARIABLES  { hostName,
                     scellNameDateTime,
                     agentEventCode,
                     agentEventDescription }
        DESCRIPTION
             "Get Host Count Failed"
           --#TYPE      "Management Agent Event"
           --#SUMMARY   "Host %s : SCellName-TimeDate %s : EventCode %d : Description %s"
           --#ARGUMENTS {0,1,2,3,}
            --#SEVERITY  MINOR
            --#TIMEINDEX 136
        ::= 136008067
 
   mngmtAgentTrap-8068 TRAP-TYPE
        ENTERPRISE compaq
        VARIABLES  { hostName,
                     scellNameDateTime,
                     agentEventCode,
                     agentEventDescription }
        DESCRIPTION
             "Get Presented Unit List Failed"
           --#TYPE      "Management Agent Event"
           --#SUMMARY   "Host %s : SCellName-TimeDate %s : EventCode %d : Description %s"
           --#ARGUMENTS {0,1,2,3,}
            --#SEVERITY  MINOR
            --#TIMEINDEX 136
        ::= 136008068
 
   mngmtAgentTrap-8069 TRAP-TYPE
        ENTERPRISE compaq
        VARIABLES  { hostName,
                     scellNameDateTime,
                     agentEventCode,
                     agentEventDescription }
        DESCRIPTION
             "Get Presented Unit Count Failed"
           --#TYPE      "Management Agent Event"
           --#SUMMARY   "Host %s : SCellName-TimeDate %s : EventCode %d : Description %s"
           --#ARGUMENTS {0,1,2,3,}
            --#SEVERITY  MINOR
            --#TIMEINDEX 136
        ::= 136008069
 
   mngmtAgentTrap-8070 TRAP-TYPE
        ENTERPRISE compaq
        VARIABLES  { hostName,
                     scellNameDateTime,
                     agentEventCode,
                     agentEventDescription }
        DESCRIPTION
             "Free View Failed"
           --#TYPE      "Management Agent Event"
           --#SUMMARY   "Host %s : SCellName-TimeDate %s : EventCode %d : Description %s"
           --#ARGUMENTS {0,1,2,3,}
            --#SEVERITY  MINOR
            --#TIMEINDEX 136
        ::= 136008070
 
   mngmtAgentTrap-8071 TRAP-TYPE
        ENTERPRISE compaq
        VARIABLES  { hostName,
                     scellNameDateTime,
                     agentEventCode,
                     agentEventDescription }
        DESCRIPTION
             "Storage system shutdown Failed"
           --#TYPE      "Management Agent Event"
           --#SUMMARY   "Host %s : SCellName-TimeDate %s : EventCode %d : Description %s"
           --#ARGUMENTS {0,1,2,3,}
            --#SEVERITY  MINOR
            --#TIMEINDEX 136
        ::= 136008071
 
   mngmtAgentTrap-8073 TRAP-TYPE
        ENTERPRISE compaq
        VARIABLES  { hostName,
                     scellNameDateTime,
                     agentEventCode,
                     agentEventDescription }
        DESCRIPTION
             "Get Derived Unit List Failed"
           --#TYPE      "Management Agent Event"
           --#SUMMARY   "Host %s : SCellName-TimeDate %s : EventCode %d : Description %s"
           --#ARGUMENTS {0,1,2,3,}
            --#SEVERITY  MINOR
            --#TIMEINDEX 136
        ::= 136008073
 
   mngmtAgentTrap-8074 TRAP-TYPE
        ENTERPRISE compaq
        VARIABLES  { hostName,
                     scellNameDateTime,
                     agentEventCode,
                     agentEventDescription }
        DESCRIPTION
             "Get Derived Unit Count Failed"
           --#TYPE      "Management Agent Event"
           --#SUMMARY   "Host %s : SCellName-TimeDate %s : EventCode %d : Description %s"
           --#ARGUMENTS {0,1,2,3,}
            --#SEVERITY  MINOR
            --#TIMEINDEX 136
        ::= 136008074
 
   mngmtAgentTrap-8075 TRAP-TYPE
        ENTERPRISE compaq
        VARIABLES  { hostName,
                     scellNameDateTime,
                     agentEventCode,
                     agentEventDescription }
        DESCRIPTION
             "Get Vdisk list failed"
           --#TYPE      "Management Agent Event"
           --#SUMMARY   "Host %s : SCellName-TimeDate %s : EventCode %d : Description %s"
           --#ARGUMENTS {0,1,2,3,}
            --#SEVERITY  MINOR
            --#TIMEINDEX 136
        ::= 136008075
 
   mngmtAgentTrap-8076 TRAP-TYPE
        ENTERPRISE compaq
        VARIABLES  { hostName,
                     scellNameDateTime,
                     agentEventCode,
                     agentEventDescription }
        DESCRIPTION
             "Get Vdisk count failed"
           --#TYPE      "Management Agent Event"
           --#SUMMARY   "Host %s : SCellName-TimeDate %s : EventCode %d : Description %s"
           --#ARGUMENTS {0,1,2,3,}
            --#SEVERITY  MINOR
            --#TIMEINDEX 136
        ::= 136008076
 
   mngmtAgentTrap-8077 TRAP-TYPE
        ENTERPRISE compaq
        VARIABLES  { hostName,
                     scellNameDateTime,
                     agentEventCode,
                     agentEventDescription }
        DESCRIPTION
             "Error while building Vdisk root view"
           --#TYPE      "Management Agent Event"
           --#SUMMARY   "Host %s : SCellName-TimeDate %s : EventCode %d : Description %s"
           --#ARGUMENTS {0,1,2,3,}
            --#SEVERITY  MINOR
            --#TIMEINDEX 136
        ::= 136008077
 
   mngmtAgentTrap-8078 TRAP-TYPE
        ENTERPRISE compaq
        VARIABLES  { hostName,
                     scellNameDateTime,
                     agentEventCode,
                     agentEventDescription }
        DESCRIPTION
             "Error while building host root view"
           --#TYPE      "Management Agent Event"
           --#SUMMARY   "Host %s : SCellName-TimeDate %s : EventCode %d : Description %s"
           --#ARGUMENTS {0,1,2,3,}
            --#SEVERITY  MINOR
            --#TIMEINDEX 136
        ::= 136008078
 
   mngmtAgentTrap-8079 TRAP-TYPE
        ENTERPRISE compaq
        VARIABLES  { hostName,
                     scellNameDateTime,
                     agentEventCode,
                     agentEventDescription }
        DESCRIPTION
             "Error while building disk group root view"
           --#TYPE      "Management Agent Event"
           --#SUMMARY   "Host %s : SCellName-TimeDate %s : EventCode %d : Description %s"
           --#ARGUMENTS {0,1,2,3,}
            --#SEVERITY  MINOR
            --#TIMEINDEX 136
        ::= 136008079
 
   mngmtAgentTrap-8080 TRAP-TYPE
        ENTERPRISE compaq
        VARIABLES  { hostName,
                     scellNameDateTime,
                     agentEventCode,
                     agentEventDescription }
        DESCRIPTION
             "Error while building hardware root view"
           --#TYPE      "Management Agent Event"
           --#SUMMARY   "Host %s : SCellName-TimeDate %s : EventCode %d : Description %s"
           --#ARGUMENTS {0,1,2,3,}
            --#SEVERITY  MINOR
            --#TIMEINDEX 136
        ::= 136008080
 
   mngmtAgentTrap-8081 TRAP-TYPE
        ENTERPRISE compaq
        VARIABLES  { hostName,
                     scellNameDateTime,
                     agentEventCode,
                     agentEventDescription }
        DESCRIPTION
             "Specified time format is incorrect"
           --#TYPE      "Management Agent Event"
           --#SUMMARY   "Host %s : SCellName-TimeDate %s : EventCode %d : Description %s"
           --#ARGUMENTS {0,1,2,3,}
            --#SEVERITY  MINOR
            --#TIMEINDEX 136
        ::= 136008081
 
   mngmtAgentTrap-8082 TRAP-TYPE
        ENTERPRISE compaq
        VARIABLES  { hostName,
                     scellNameDateTime,
                     agentEventCode,
                     agentEventDescription }
        DESCRIPTION
             "Error creating/opening time synchronization file."
           --#TYPE      "Management Agent Event"
           --#SUMMARY   "Host %s : SCellName-TimeDate %s : EventCode %d : Description %s"
           --#ARGUMENTS {0,1,2,3,}
            --#SEVERITY  MINOR
            --#TIMEINDEX 136
        ::= 136008082
 
   mngmtAgentTrap-8083 TRAP-TYPE
        ENTERPRISE compaq
        VARIABLES  { hostName,
                     scellNameDateTime,
                     agentEventCode,
                     agentEventDescription }
        DESCRIPTION
             "NSCList reordered."
           --#TYPE      "Management Agent Event"
           --#SUMMARY   "Host %s : SCellName-TimeDate %s : EventCode %d : Description %s"
           --#ARGUMENTS {0,1,2,3,}
            --#SEVERITY  MINOR
            --#TIMEINDEX 136
        ::= 136008083
 
   mngmtAgentTrap-8084 TRAP-TYPE
        ENTERPRISE compaq
        VARIABLES  { hostName,
                     scellNameDateTime,
                     agentEventCode,
                     agentEventDescription }
        DESCRIPTION
             "NscList mutex Get error"
           --#TYPE      "Management Agent Event"
           --#SUMMARY   "Host %s : SCellName-TimeDate %s : EventCode %d : Description %s"
           --#ARGUMENTS {0,1,2,3,}
            --#SEVERITY  MINOR
            --#TIMEINDEX 136
        ::= 136008084
 
   mngmtAgentTrap-8085 TRAP-TYPE
        ENTERPRISE compaq
        VARIABLES  { hostName,
                     scellNameDateTime,
                     agentEventCode,
                     agentEventDescription }
        DESCRIPTION
             "Storage System is managed by another agent"
           --#TYPE      "Management Agent Event"
           --#SUMMARY   "Host %s : SCellName-TimeDate %s : EventCode %d : Description %s"
           --#ARGUMENTS {0,1,2,3,}
            --#SEVERITY  INFORMATIONAL
            --#TIMEINDEX 136
        ::= 136008085
 
   mngmtAgentTrap-8086 TRAP-TYPE
        ENTERPRISE compaq
        VARIABLES  { hostName,
                     scellNameDateTime,
                     agentEventCode,
                     agentEventDescription }
        DESCRIPTION
             "Memory allocation failure"
           --#TYPE      "Management Agent Event"
           --#SUMMARY   "Host %s : SCellName-TimeDate %s : EventCode %d : Description %s"
           --#ARGUMENTS {0,1,2,3,}
            --#SEVERITY  INFORMATIONAL
            --#TIMEINDEX 136
        ::= 136008086
 
   mngmtAgentTrap-8087 TRAP-TYPE
        ENTERPRISE compaq
        VARIABLES  { hostName,
                     scellNameDateTime,
                     agentEventCode,
                     agentEventDescription }
        DESCRIPTION
             "Failed to obtain list of DR Groups"
           --#TYPE      "Management Agent Event"
           --#SUMMARY   "Host %s : SCellName-TimeDate %s : EventCode %d : Description %s"
           --#ARGUMENTS {0,1,2,3,}
            --#SEVERITY  INFORMATIONAL
            --#TIMEINDEX 136
        ::= 136008087
 
   mngmtAgentTrap-8088 TRAP-TYPE
        ENTERPRISE compaq
        VARIABLES  { hostName,
                     scellNameDateTime,
                     agentEventCode,
                     agentEventDescription }
        DESCRIPTION
             "Failed to obtain count of DR Groups"
           --#TYPE      "Management Agent Event"
           --#SUMMARY   "Host %s : SCellName-TimeDate %s : EventCode %d : Description %s"
           --#ARGUMENTS {0,1,2,3,}
            --#SEVERITY  INFORMATIONAL
            --#TIMEINDEX 136
        ::= 136008088
 
   mngmtAgentTrap-8089 TRAP-TYPE
        ENTERPRISE compaq
        VARIABLES  { hostName,
                     scellNameDateTime,
                     agentEventCode,
                     agentEventDescription }
        DESCRIPTION
             "Failed to build DR Group view"
           --#TYPE      "Management Agent Event"
           --#SUMMARY   "Host %s : SCellName-TimeDate %s : EventCode %d : Description %s"
           --#ARGUMENTS {0,1,2,3,}
            --#SEVERITY  INFORMATIONAL
            --#TIMEINDEX 136
        ::= 136008089
 
   mngmtAgentTrap-8090 TRAP-TYPE
        ENTERPRISE compaq
        VARIABLES  { hostName,
                     scellNameDateTime,
                     agentEventCode,
                     agentEventDescription }
        DESCRIPTION
             "No Devices found on Controller Back End Loops"
           --#TYPE      "Management Agent Event"
           --#SUMMARY   "Host %s : SCellName-TimeDate %s : EventCode %d : Description %s"
           --#ARGUMENTS {0,1,2,3,}
            --#SEVERITY  MINOR
            --#TIMEINDEX 136
        ::= 136008090
 
   mngmtAgentTrap-9001 TRAP-TYPE
        ENTERPRISE compaq
        VARIABLES  { hostName,
                     scellNameDateTime,
                     agentEventCode,
                     agentEventDescription }
        DESCRIPTION
             "Vdisk File Open Error"
           --#TYPE      "Management Agent Event"
           --#SUMMARY   "Host %s : SCellName-TimeDate %s : EventCode %d : Description %s"
           --#ARGUMENTS {0,1,2,3,}
            --#SEVERITY  MINOR
            --#TIMEINDEX 136
        ::= 136009001
 
   mngmtAgentTrap-9002 TRAP-TYPE
        ENTERPRISE compaq
        VARIABLES  { hostName,
                     scellNameDateTime,
                     agentEventCode,
                     agentEventDescription }
        DESCRIPTION
             "Vdisk File Write Error"
           --#TYPE      "Management Agent Event"
           --#SUMMARY   "Host %s : SCellName-TimeDate %s : EventCode %d : Description %s"
           --#ARGUMENTS {0,1,2,3,}
            --#SEVERITY  MINOR
            --#TIMEINDEX 136
        ::= 136009002
 
   mngmtAgentTrap-9003 TRAP-TYPE
        ENTERPRISE compaq
        VARIABLES  { hostName,
                     scellNameDateTime,
                     agentEventCode,
                     agentEventDescription }
        DESCRIPTION
             "Vdisk File Read Error"
           --#TYPE      "Management Agent Event"
           --#SUMMARY   "Host %s : SCellName-TimeDate %s : EventCode %d : Description %s"
           --#ARGUMENTS {0,1,2,3,}
            --#SEVERITY  MINOR
            --#TIMEINDEX 136
        ::= 136009003
 
   mngmtAgentTrap-9004 TRAP-TYPE
        ENTERPRISE compaq
        VARIABLES  { hostName,
                     scellNameDateTime,
                     agentEventCode,
                     agentEventDescription }
        DESCRIPTION
             "Vdisk name too long"
           --#TYPE      "Management Agent Event"
           --#SUMMARY   "Host %s : SCellName-TimeDate %s : EventCode %d : Description %s"
           --#ARGUMENTS {0,1,2,3,}
            --#SEVERITY  INFORMATIONAL
            --#TIMEINDEX 136
        ::= 136009004
 
   mngmtAgentTrap-9005 TRAP-TYPE
        ENTERPRISE compaq
        VARIABLES  { hostName,
                     scellNameDateTime,
                     agentEventCode,
                     agentEventDescription }
        DESCRIPTION
             "Vdisk No String Error"
           --#TYPE      "Management Agent Event"
           --#SUMMARY   "Host %s : SCellName-TimeDate %s : EventCode %d : Description %s"
           --#ARGUMENTS {0,1,2,3,}
            --#SEVERITY  INFORMATIONAL
            --#TIMEINDEX 136
        ::= 136009005
 
   mngmtAgentTrap-9006 TRAP-TYPE
        ENTERPRISE compaq
        VARIABLES  { hostName,
                     scellNameDateTime,
                     agentEventCode,
                     agentEventDescription }
        DESCRIPTION
             "Vdisk No Object Error"
           --#TYPE      "Management Agent Event"
           --#SUMMARY   "Host %s : SCellName-TimeDate %s : EventCode %d : Description %s"
           --#ARGUMENTS {0,1,2,3,}
            --#SEVERITY  INFORMATIONAL
            --#TIMEINDEX 136
        ::= 136009006
 
   mngmtAgentTrap-9007 TRAP-TYPE
        ENTERPRISE compaq
        VARIABLES  { hostName,
                     scellNameDateTime,
                     agentEventCode,
                     agentEventDescription }
        DESCRIPTION
             "Vdisk still exists"
           --#TYPE      "Management Agent Event"
           --#SUMMARY   "Host %s : SCellName-TimeDate %s : EventCode %d : Description %s"
           --#ARGUMENTS {0,1,2,3,}
            --#SEVERITY  INFORMATIONAL
            --#TIMEINDEX 136
        ::= 136009007
 
   mngmtAgentTrap-9008 TRAP-TYPE
        ENTERPRISE compaq
        VARIABLES  { hostName,
                     scellNameDateTime,
                     agentEventCode,
                     agentEventDescription }
        DESCRIPTION
             "Vdisk Invalid Value"
           --#TYPE      "Management Agent Event"
           --#SUMMARY   "Host %s : SCellName-TimeDate %s : EventCode %d : Description %s"
           --#ARGUMENTS {0,1,2,3,}
            --#SEVERITY  INFORMATIONAL
            --#TIMEINDEX 136
        ::= 136009008
 
   mngmtAgentTrap-9009 TRAP-TYPE
        ENTERPRISE compaq
        VARIABLES  { hostName,
                     scellNameDateTime,
                     agentEventCode,
                     agentEventDescription }
        DESCRIPTION
             "An outstanding command is still in progress for the Vdisk"
           --#TYPE      "Management Agent Event"
           --#SUMMARY   "Host %s : SCellName-TimeDate %s : EventCode %d : Description %s"
           --#ARGUMENTS {0,1,2,3,}
            --#SEVERITY  INFORMATIONAL
            --#TIMEINDEX 136
        ::= 136009009
 
   mngmtAgentTrap-9010 TRAP-TYPE
        ENTERPRISE compaq
        VARIABLES  { hostName,
                     scellNameDateTime,
                     agentEventCode,
                     agentEventDescription }
        DESCRIPTION
             "Requested Vdisk size exceeds the available size"
           --#TYPE      "Management Agent Event"
           --#SUMMARY   "Host %s : SCellName-TimeDate %s : EventCode %d : Description %s"
           --#ARGUMENTS {0,1,2,3,}
            --#SEVERITY  INFORMATIONAL
            --#TIMEINDEX 136
        ::= 136009010
 
   mngmtAgentTrap-9011 TRAP-TYPE
        ENTERPRISE compaq
        VARIABLES  { hostName,
                     scellNameDateTime,
                     agentEventCode,
                     agentEventDescription }
        DESCRIPTION
             "Vdisk size may be expanded but not reduced"
           --#TYPE      "Management Agent Event"
           --#SUMMARY   "Host %s : SCellName-TimeDate %s : EventCode %d : Description %s"
           --#ARGUMENTS {0,1,2,3,}
            --#SEVERITY  INFORMATIONAL
            --#TIMEINDEX 136
        ::= 136009011
 
   mngmtAgentTrap-9012 TRAP-TYPE
        ENTERPRISE compaq
        VARIABLES  { hostName,
                     scellNameDateTime,
                     agentEventCode,
                     agentEventDescription }
        DESCRIPTION
             "Operation on a fast Vdisk deletion completed"
           --#TYPE      "Management Agent Event"
           --#SUMMARY   "Host %s : SCellName-TimeDate %s : EventCode %d : Description %s"
           --#ARGUMENTS {0,1,2,3,}
            --#SEVERITY  INFORMATIONAL
            --#TIMEINDEX 136
        ::= 136009012
 
   mngmtAgentTrap-9013 TRAP-TYPE
        ENTERPRISE compaq
        VARIABLES  { hostName,
                     scellNameDateTime,
                     agentEventCode,
                     agentEventDescription }
        DESCRIPTION
             "Operation on a fast Vdisk creation completed"
           --#TYPE      "Management Agent Event"
           --#SUMMARY   "Host %s : SCellName-TimeDate %s : EventCode %d : Description %s"
           --#ARGUMENTS {0,1,2,3,}
            --#SEVERITY  INFORMATIONAL
            --#TIMEINDEX 136
        ::= 136009013
 
   mngmtAgentTrap-9014 TRAP-TYPE
        ENTERPRISE compaq
        VARIABLES  { hostName,
                     scellNameDateTime,
                     agentEventCode,
                     agentEventDescription }
        DESCRIPTION
             "Operation on a fast Vdisk size expansion completed"
           --#TYPE      "Management Agent Event"
           --#SUMMARY   "Host %s : SCellName-TimeDate %s : EventCode %d : Description %s"
           --#ARGUMENTS {0,1,2,3,}
            --#SEVERITY  INFORMATIONAL
            --#TIMEINDEX 136
        ::= 136009014
 
   mngmtAgentTrap-9015 TRAP-TYPE
        ENTERPRISE compaq
        VARIABLES  { hostName,
                     scellNameDateTime,
                     agentEventCode,
                     agentEventDescription }
        DESCRIPTION
             "Vdisk cache data lost error"
           --#TYPE      "Management Agent Event"
           --#SUMMARY   "Host %s : SCellName-TimeDate %s : EventCode %d : Description %s"
           --#ARGUMENTS {0,1,2,3,}
            --#SEVERITY  INFORMATIONAL
            --#TIMEINDEX 136
        ::= 136009015
 
   mngmtAgentTrap-9016 TRAP-TYPE
        ENTERPRISE compaq
        VARIABLES  { hostName,
                     scellNameDateTime,
                     agentEventCode,
                     agentEventDescription }
        DESCRIPTION
             "Vdisk data lost error resolved"
           --#TYPE      "Management Agent Event"
           --#SUMMARY   "Host %s : SCellName-TimeDate %s : EventCode %d : Description %s"
           --#ARGUMENTS {0,1,2,3,}
            --#SEVERITY  INFORMATIONAL
            --#TIMEINDEX 136
        ::= 136009016
 
   mngmtAgentTrap-9017 TRAP-TYPE
        ENTERPRISE compaq
        VARIABLES  { hostName,
                     scellNameDateTime,
                     agentEventCode,
                     agentEventDescription }
        DESCRIPTION
             "Operation rejected - The Vdisk has a sharing relationship with another object "
           --#TYPE      "Management Agent Event"
           --#SUMMARY   "Host %s : SCellName-TimeDate %s : EventCode %d : Description %s"
           --#ARGUMENTS {0,1,2,3,}
            --#SEVERITY  INFORMATIONAL
            --#TIMEINDEX 136
        ::= 136009017
 
   mngmtAgentTrap-9018 TRAP-TYPE
        ENTERPRISE compaq
        VARIABLES  { hostName,
                     scellNameDateTime,
                     agentEventCode,
                     agentEventDescription }
        DESCRIPTION
             "Operation on this Vdisk was rejected due to its degraded condition"
           --#TYPE      "Management Agent Event"
           --#SUMMARY   "Host %s : SCellName-TimeDate %s : EventCode %d : Description %s"
           --#ARGUMENTS {0,1,2,3,}
            --#SEVERITY  INFORMATIONAL
            --#TIMEINDEX 136
        ::= 136009018
 
   mngmtAgentTrap-9019 TRAP-TYPE
        ENTERPRISE compaq
        VARIABLES  { hostName,
                     scellNameDateTime,
                     agentEventCode,
                     agentEventDescription }
        DESCRIPTION
             "Operation on this Vdisk can only be performed if it is presented to a host"
           --#TYPE      "Management Agent Event"
           --#SUMMARY   "Host %s : SCellName-TimeDate %s : EventCode %d : Description %s"
           --#ARGUMENTS {0,1,2,3,}
            --#SEVERITY  INFORMATIONAL
            --#TIMEINDEX 136
        ::= 136009019
 
   mngmtAgentTrap-9020 TRAP-TYPE
        ENTERPRISE compaq
        VARIABLES  { hostName,
                     scellNameDateTime,
                     agentEventCode,
                     agentEventDescription }
        DESCRIPTION
             "Cache policies cannot be modified if Vdisk is presented to a host"
           --#TYPE      "Management Agent Event"
           --#SUMMARY   "Host %s : SCellName-TimeDate %s : EventCode %d : Description %s"
           --#ARGUMENTS {0,1,2,3,}
            --#SEVERITY  INFORMATIONAL
            --#TIMEINDEX 136
        ::= 136009020
 
   mngmtAgentTrap-9021 TRAP-TYPE
        ENTERPRISE compaq
        VARIABLES  { hostName,
                     scellNameDateTime,
                     agentEventCode,
                     agentEventDescription }
        DESCRIPTION
             "Allowed property changes successful. (Cache policy changes not allowed while Vdisk is presented to a host.)"
           --#TYPE      "Management Agent Event"
           --#SUMMARY   "Host %s : SCellName-TimeDate %s : EventCode %d : Description %s"
           --#ARGUMENTS {0,1,2,3,}
            --#SEVERITY  INFORMATIONAL
            --#TIMEINDEX 136
        ::= 136009021
 
   mngmtAgentTrap-9022 TRAP-TYPE
        ENTERPRISE compaq
        VARIABLES  { hostName,
                     scellNameDateTime,
                     agentEventCode,
                     agentEventDescription }
        DESCRIPTION
             "Requested redundancy type cannot be implemented with the current disk group condition."
           --#TYPE      "Management Agent Event"
           --#SUMMARY   "Host %s : SCellName-TimeDate %s : EventCode %d : Description %s"
           --#ARGUMENTS {0,1,2,3,}
            --#SEVERITY  INFORMATIONAL
            --#TIMEINDEX 136
        ::= 136009022
 
   mngmtAgentTrap-9023 TRAP-TYPE
        ENTERPRISE compaq
        VARIABLES  { hostName,
                     scellNameDateTime,
                     agentEventCode,
                     agentEventDescription }
        DESCRIPTION
             "Your Vdisk was created but cannot be presented at this time. It can be presented when it is fully allocated."
           --#TYPE      "Management Agent Event"
           --#SUMMARY   "Host %s : SCellName-TimeDate %s : EventCode %d : Description %s"
           --#ARGUMENTS {0,1,2,3,}
            --#SEVERITY  INFORMATIONAL
            --#TIMEINDEX 136
        ::= 136009023
 
   mngmtAgentTrap-9025 TRAP-TYPE
        ENTERPRISE compaq
        VARIABLES  { hostName,
                     scellNameDateTime,
                     agentEventCode,
                     agentEventDescription }
        DESCRIPTION
             "Vdisk device data lost error"
           --#TYPE      "Management Agent Event"
           --#SUMMARY   "Host %s : SCellName-TimeDate %s : EventCode %d : Description %s"
           --#ARGUMENTS {0,1,2,3,}
            --#SEVERITY  INFORMATIONAL
            --#TIMEINDEX 136
        ::= 136009025
 
   mngmtAgentTrap-9026 TRAP-TYPE
        ENTERPRISE compaq
        VARIABLES  { hostName,
                     scellNameDateTime,
                     agentEventCode,
                     agentEventDescription }
        DESCRIPTION
             "The most significant hex character in a World Wide LUN Name must be a 6."
           --#TYPE      "Management Agent Event"
           --#SUMMARY   "Host %s : SCellName-TimeDate %s : EventCode %d : Description %s"
           --#ARGUMENTS {0,1,2,3,}
            --#SEVERITY  INFORMATIONAL
            --#TIMEINDEX 136
        ::= 136009026
 
   mngmtAgentTrap-9027 TRAP-TYPE
        ENTERPRISE compaq
        VARIABLES  { hostName,
                     scellNameDateTime,
                     agentEventCode,
                     agentEventDescription }
        DESCRIPTION
             "Virtual disk cache and inoperative data lost error"
           --#TYPE      "Management Agent Event"
           --#SUMMARY   "Host %s : SCellName-TimeDate %s : EventCode %d : Description %s"
           --#ARGUMENTS {0,1,2,3,}
            --#SEVERITY  INFORMATIONAL
            --#TIMEINDEX 136
        ::= 136009027
 
   mngmtAgentTrap-9028 TRAP-TYPE
        ENTERPRISE compaq
        VARIABLES  { hostName,
                     scellNameDateTime,
                     agentEventCode,
                     agentEventDescription }
        DESCRIPTION
             "Virtual disk inoperative data lost error"
           --#TYPE      "Management Agent Event"
           --#SUMMARY   "Host %s : SCellName-TimeDate %s : EventCode %d : Description %s"
           --#ARGUMENTS {0,1,2,3,}
            --#SEVERITY  INFORMATIONAL
            --#TIMEINDEX 136
        ::= 136009028
 
   mngmtAgentTrap-9029 TRAP-TYPE
        ENTERPRISE compaq
        VARIABLES  { hostName,
                     scellNameDateTime,
                     agentEventCode,
                     agentEventDescription }
        DESCRIPTION
             "Virtual disk condition failed because of an inoperative data lost error."
           --#TYPE      "Management Agent Event"
           --#SUMMARY   "Host %s : SCellName-TimeDate %s : EventCode %d : Description %s"
           --#ARGUMENTS {0,1,2,3,}
            --#SEVERITY  INFORMATIONAL
            --#TIMEINDEX 136
        ::= 136009029
 
   mngmtAgentTrap-9030 TRAP-TYPE
        ENTERPRISE compaq
        VARIABLES  { hostName,
                     scellNameDateTime,
                     agentEventCode,
                     agentEventDescription }
        DESCRIPTION
             "Vdisk is a snapshot. The following properties cannot be changed: Preferred Path, Requested Size, Write-Back Cache Policy."
           --#TYPE      "Management Agent Event"
           --#SUMMARY   "Host %s : SCellName-TimeDate %s : EventCode %d : Description %s"
           --#ARGUMENTS {0,1,2,3,}
            --#SEVERITY  INFORMATIONAL
            --#TIMEINDEX 136
        ::= 136009030
 
   mngmtAgentTrap-9031 TRAP-TYPE
        ENTERPRISE compaq
        VARIABLES  { hostName,
                     scellNameDateTime,
                     agentEventCode,
                     agentEventDescription }
        DESCRIPTION
             "The World Wide LUN Name cannot be changed for a presented Vdisk Active member or snapshot."
           --#TYPE      "Management Agent Event"
           --#SUMMARY   "Host %s : SCellName-TimeDate %s : EventCode %d : Description %s"
           --#ARGUMENTS {0,1,2,3,}
            --#SEVERITY  INFORMATIONAL
            --#TIMEINDEX 136
        ::= 136009031
 
   mngmtAgentTrap-9032 TRAP-TYPE
        ENTERPRISE compaq
        VARIABLES  { hostName,
                     scellNameDateTime,
                     agentEventCode,
                     agentEventDescription }
        DESCRIPTION
             "Unknown property, request rejected"
           --#TYPE      "Management Agent Event"
           --#SUMMARY   "Host %s : SCellName-TimeDate %s : EventCode %d : Description %s"
           --#ARGUMENTS {0,1,2,3,}
            --#SEVERITY  INFORMATIONAL
            --#TIMEINDEX 136
        ::= 136009032
 
   mngmtAgentTrap-9033 TRAP-TYPE
        ENTERPRISE compaq
        VARIABLES  { hostName,
                     scellNameDateTime,
                     agentEventCode,
                     agentEventDescription }
        DESCRIPTION
             "This Vdisk was deleted as the indirect result of another user command."
           --#TYPE      "Management Agent Event"
           --#SUMMARY   "Host %s : SCellName-TimeDate %s : EventCode %d : Description %s"
           --#ARGUMENTS {0,1,2,3,}
            --#SEVERITY  INFORMATIONAL
            --#TIMEINDEX 136
        ::= 136009033
 
   mngmtAgentTrap-9034 TRAP-TYPE
        ENTERPRISE compaq
        VARIABLES  { hostName,
                     scellNameDateTime,
                     agentEventCode,
                     agentEventDescription }
        DESCRIPTION
             "The requested allocation policy cannot be satisfied. A different allocation policy is already in use by another snapshot in the same family."
           --#TYPE      "Management Agent Event"
           --#SUMMARY   "Host %s : SCellName-TimeDate %s : EventCode %d : Description %s"
           --#ARGUMENTS {0,1,2,3,}
            --#SEVERITY  INFORMATIONAL
            --#TIMEINDEX 136
        ::= 136009034
 
   mngmtAgentTrap-9035 TRAP-TYPE
        ENTERPRISE compaq
        VARIABLES  { hostName,
                     scellNameDateTime,
                     agentEventCode,
                     agentEventDescription }
        DESCRIPTION
             "The deletion of this Vdisk cannot take place.  The original Vdisk that this is being snapcloned from is in a VRaid1 Meltdown state which must first be resolved."
           --#TYPE      "Management Agent Event"
           --#SUMMARY   "Host %s : SCellName-TimeDate %s : EventCode %d : Description %s"
           --#ARGUMENTS {0,1,2,3,}
            --#SEVERITY  INFORMATIONAL
            --#TIMEINDEX 136
        ::= 136009035
 
   mngmtAgentTrap-9036 TRAP-TYPE
        ENTERPRISE compaq
        VARIABLES  { hostName,
                     scellNameDateTime,
                     agentEventCode,
                     agentEventDescription }
        DESCRIPTION
             "Synchronous creation of virtual disk has been aborted due to an internal error. Switching to asynchronous mode to complete the virtual disk creation."
           --#TYPE      "Management Agent Event"
           --#SUMMARY   "Host %s : SCellName-TimeDate %s : EventCode %d : Description %s"
           --#ARGUMENTS {0,1,2,3,}
            --#SEVERITY  INFORMATIONAL
            --#TIMEINDEX 136
        ::= 136009036
 
   mngmtAgentTrap-10001 TRAP-TYPE
        ENTERPRISE compaq
        VARIABLES  { hostName,
                     scellNameDateTime,
                     agentEventCode,
                     agentEventDescription }
        DESCRIPTION
             "Storage Object Broker Ready"
           --#TYPE      "Management Agent Event"
           --#SUMMARY   "Host %s : SCellName-TimeDate %s : EventCode %d : Description %s"
           --#ARGUMENTS {0,1,2,3,}
            --#SEVERITY  INFORMATIONAL
            --#TIMEINDEX 136
        ::= 136010001
 
   mngmtAgentTrap-10004 TRAP-TYPE
        ENTERPRISE compaq
        VARIABLES  { hostName,
                     scellNameDateTime,
                     agentEventCode,
                     agentEventDescription }
        DESCRIPTION
             "Storage system is not initialized"
           --#TYPE      "Management Agent Event"
           --#SUMMARY   "Host %s : SCellName-TimeDate %s : EventCode %d : Description %s"
           --#ARGUMENTS {0,1,2,3,}
            --#SEVERITY  INFORMATIONAL
            --#TIMEINDEX 136
        ::= 136010004
 
   mngmtAgentTrap-10006 TRAP-TYPE
        ENTERPRISE compaq
        VARIABLES  { hostName,
                     scellNameDateTime,
                     agentEventCode,
                     agentEventDescription }
        DESCRIPTION
             "SOB Memory Allocation Failure"
           --#TYPE      "Management Agent Event"
           --#SUMMARY   "Host %s : SCellName-TimeDate %s : EventCode %d : Description %s"
           --#ARGUMENTS {0,1,2,3,}
            --#SEVERITY  CRITICAL
            --#TIMEINDEX 136
        ::= 136010006
 
   mngmtAgentTrap-10010 TRAP-TYPE
        ENTERPRISE compaq
        VARIABLES  { hostName,
                     scellNameDateTime,
                     agentEventCode,
                     agentEventDescription }
        DESCRIPTION
             "Your initialized system must have at least one disk group"
           --#TYPE      "Management Agent Event"
           --#SUMMARY   "Host %s : SCellName-TimeDate %s : EventCode %d : Description %s"
           --#ARGUMENTS {0,1,2,3,}
            --#SEVERITY  INFORMATIONAL
            --#TIMEINDEX 136
        ::= 136010010
 
   mngmtAgentTrap-10011 TRAP-TYPE
        ENTERPRISE compaq
        VARIABLES  { hostName,
                     scellNameDateTime,
                     agentEventCode,
                     agentEventDescription }
        DESCRIPTION
             "Cannot talk to all available controllers"
           --#TYPE      "Management Agent Event"
           --#SUMMARY   "Host %s : SCellName-TimeDate %s : EventCode %d : Description %s"
           --#ARGUMENTS {0,1,2,3,}
            --#SEVERITY  INFORMATIONAL
            --#TIMEINDEX 136
        ::= 136010011
 
   mngmtAgentTrap-10012 TRAP-TYPE
        ENTERPRISE compaq
        VARIABLES  { hostName,
                     scellNameDateTime,
                     agentEventCode,
                     agentEventDescription }
        DESCRIPTION
             "Command rejected - Folder is not empty"
           --#TYPE      "Management Agent Event"
           --#SUMMARY   "Host %s : SCellName-TimeDate %s : EventCode %d : Description %s"
           --#ARGUMENTS {0,1,2,3,}
            --#SEVERITY  INFORMATIONAL
            --#TIMEINDEX 136
        ::= 136010012
 
   mngmtAgentTrap-10013 TRAP-TYPE
        ENTERPRISE compaq
        VARIABLES  { hostName,
                     scellNameDateTime,
                     agentEventCode,
                     agentEventDescription }
        DESCRIPTION
             "Command rejected - Vdisk(s) or a data replication log are contained in this disk group"
           --#TYPE      "Management Agent Event"
           --#SUMMARY   "Host %s : SCellName-TimeDate %s : EventCode %d : Description %s"
           --#ARGUMENTS {0,1,2,3,}
            --#SEVERITY  INFORMATIONAL
            --#TIMEINDEX 136
        ::= 136010013
 
   mngmtAgentTrap-10014 TRAP-TYPE
        ENTERPRISE compaq
        VARIABLES  { hostName,
                     scellNameDateTime,
                     agentEventCode,
                     agentEventDescription }
        DESCRIPTION
             "Command rejected - Vdisk(s) are presented to this host"
           --#TYPE      "Management Agent Event"
           --#SUMMARY   "Host %s : SCellName-TimeDate %s : EventCode %d : Description %s"
           --#ARGUMENTS {0,1,2,3,}
            --#SEVERITY  INFORMATIONAL
            --#TIMEINDEX 136
        ::= 136010014
 
   mngmtAgentTrap-10015 TRAP-TYPE
        ENTERPRISE compaq
        VARIABLES  { hostName,
                     scellNameDateTime,
                     agentEventCode,
                     agentEventDescription }
        DESCRIPTION
             "Command rejected - This Vdisk has a sharing relationship with another object "
           --#TYPE      "Management Agent Event"
           --#SUMMARY   "Host %s : SCellName-TimeDate %s : EventCode %d : Description %s"
           --#ARGUMENTS {0,1,2,3,}
            --#SEVERITY  INFORMATIONAL
            --#TIMEINDEX 136
        ::= 136010015
 
   mngmtAgentTrap-10017 TRAP-TYPE
        ENTERPRISE compaq
        VARIABLES  { hostName,
                     scellNameDateTime,
                     agentEventCode,
                     agentEventDescription }
        DESCRIPTION
             "Command rejected - Number of disk groups will exceed the maximum allowable number "
           --#TYPE      "Management Agent Event"
           --#SUMMARY   "Host %s : SCellName-TimeDate %s : EventCode %d : Description %s"
           --#ARGUMENTS {0,1,2,3,}
            --#SEVERITY  INFORMATIONAL
            --#TIMEINDEX 136
        ::= 136010017
 
   mngmtAgentTrap-10018 TRAP-TYPE
        ENTERPRISE compaq
        VARIABLES  { hostName,
                     scellNameDateTime,
                     agentEventCode,
                     agentEventDescription }
        DESCRIPTION
             "Cannot access the password file "
           --#TYPE      "Management Agent Event"
           --#SUMMARY   "Host %s : SCellName-TimeDate %s : EventCode %d : Description %s"
           --#ARGUMENTS {0,1,2,3,}
            --#SEVERITY  INFORMATIONAL
            --#TIMEINDEX 136
        ::= 136010018
 
   mngmtAgentTrap-10019 TRAP-TYPE
        ENTERPRISE compaq
        VARIABLES  { hostName,
                     scellNameDateTime,
                     agentEventCode,
                     agentEventDescription }
        DESCRIPTION
             "Enterprise Login - Complete"
           --#TYPE      "Management Agent Event"
           --#SUMMARY   "Host %s : SCellName-TimeDate %s : EventCode %d : Description %s"
           --#ARGUMENTS {0,1,2,3,}
            --#SEVERITY  INFORMATIONAL
            --#TIMEINDEX 136
        ::= 136010019
 
   mngmtAgentTrap-10020 TRAP-TYPE
        ENTERPRISE compaq
        VARIABLES  { hostName,
                     scellNameDateTime,
                     agentEventCode,
                     agentEventDescription }
        DESCRIPTION
             "Command rejected - Disks in the group would go below the minimum required number."
           --#TYPE      "Management Agent Event"
           --#SUMMARY   "Host %s : SCellName-TimeDate %s : EventCode %d : Description %s"
           --#ARGUMENTS {0,1,2,3,}
            --#SEVERITY  INFORMATIONAL
            --#TIMEINDEX 136
        ::= 136010020
 
   mngmtAgentTrap-10021 TRAP-TYPE
        ENTERPRISE compaq
        VARIABLES  { hostName,
                     scellNameDateTime,
                     agentEventCode,
                     agentEventDescription }
        DESCRIPTION
             "Rediscovery of controllers - Complete"
           --#TYPE      "Management Agent Event"
           --#SUMMARY   "Host %s : SCellName-TimeDate %s : EventCode %d : Description %s"
           --#ARGUMENTS {0,1,2,3,}
            --#SEVERITY  INFORMATIONAL
            --#TIMEINDEX 136
        ::= 136010021
 
   mngmtAgentTrap-10022 TRAP-TYPE
        ENTERPRISE compaq
        VARIABLES  { hostName,
                     scellNameDateTime,
                     agentEventCode,
                     agentEventDescription }
        DESCRIPTION
             "Unable to establish communication with controller, check all connections. "
           --#TYPE      "Management Agent Event"
           --#SUMMARY   "Host %s : SCellName-TimeDate %s : EventCode %d : Description %s"
           --#ARGUMENTS {0,1,2,3,}
            --#SEVERITY  INFORMATIONAL
            --#TIMEINDEX 136
        ::= 136010022
 
   mngmtAgentTrap-10023 TRAP-TYPE
        ENTERPRISE compaq
        VARIABLES  { hostName,
                     scellNameDateTime,
                     agentEventCode,
                     agentEventDescription }
        DESCRIPTION
             "Disk Group Data Lost Error Resolution Sequence 3 - Disk group resolved to normal"
           --#TYPE      "Management Agent Event"
           --#SUMMARY   "Host %s : SCellName-TimeDate %s : EventCode %d : Description %s"
           --#ARGUMENTS {0,1,2,3,}
            --#SEVERITY  INFORMATIONAL
            --#TIMEINDEX 136
        ::= 136010023
 
   mngmtAgentTrap-10024 TRAP-TYPE
        ENTERPRISE compaq
        VARIABLES  { hostName,
                     scellNameDateTime,
                     agentEventCode,
                     agentEventDescription }
        DESCRIPTION
             "Disk Group Data Lost Error Resolution Sequence 1 - Failed Vdisks marked for deletion"
           --#TYPE      "Management Agent Event"
           --#SUMMARY   "Host %s : SCellName-TimeDate %s : EventCode %d : Description %s"
           --#ARGUMENTS {0,1,2,3,}
            --#SEVERITY  INFORMATIONAL
            --#TIMEINDEX 136
        ::= 136010024
 
   mngmtAgentTrap-10025 TRAP-TYPE
        ENTERPRISE compaq
        VARIABLES  { hostName,
                     scellNameDateTime,
                     agentEventCode,
                     agentEventDescription }
        DESCRIPTION
             "Disk Group Data Lost Error Resolution Sequence 2 - Failed Vdisks deleted"
           --#TYPE      "Management Agent Event"
           --#SUMMARY   "Host %s : SCellName-TimeDate %s : EventCode %d : Description %s"
           --#ARGUMENTS {0,1,2,3,}
            --#SEVERITY  INFORMATIONAL
            --#TIMEINDEX 136
        ::= 136010025
 
   mngmtAgentTrap-10026 TRAP-TYPE
        ENTERPRISE compaq
        VARIABLES  { hostName,
                     scellNameDateTime,
                     agentEventCode,
                     agentEventDescription }
        DESCRIPTION
             "Disk Group Data Lost Error Resolution Sequence 3 - Disk group deleted"
           --#TYPE      "Management Agent Event"
           --#SUMMARY   "Host %s : SCellName-TimeDate %s : EventCode %d : Description %s"
           --#ARGUMENTS {0,1,2,3,}
            --#SEVERITY  INFORMATIONAL
            --#TIMEINDEX 136
        ::= 136010026
 
   mngmtAgentTrap-10027 TRAP-TYPE
        ENTERPRISE compaq
        VARIABLES  { hostName,
                     scellNameDateTime,
                     agentEventCode,
                     agentEventDescription }
        DESCRIPTION
             "Creating the Vdisk would exceed the maximum allowable Vdisk count"
           --#TYPE      "Management Agent Event"
           --#SUMMARY   "Host %s : SCellName-TimeDate %s : EventCode %d : Description %s"
           --#ARGUMENTS {0,1,2,3,}
            --#SEVERITY  INFORMATIONAL
            --#TIMEINDEX 136
        ::= 136010027
 
   mngmtAgentTrap-10028 TRAP-TYPE
        ENTERPRISE compaq
        VARIABLES  { hostName,
                     scellNameDateTime,
                     agentEventCode,
                     agentEventDescription }
        DESCRIPTION
             "Volume insufficient resources"
           --#TYPE      "Management Agent Event"
           --#SUMMARY   "Host %s : SCellName-TimeDate %s : EventCode %d : Description %s"
           --#ARGUMENTS {0,1,2,3,}
            --#SEVERITY  INFORMATIONAL
            --#TIMEINDEX 136
        ::= 136010028
 
   mngmtAgentTrap-10029 TRAP-TYPE
        ENTERPRISE compaq
        VARIABLES  { hostName,
                     scellNameDateTime,
                     agentEventCode,
                     agentEventDescription }
        DESCRIPTION
             "Process mutex is locked"
           --#TYPE      "Management Agent Event"
           --#SUMMARY   "Host %s : SCellName-TimeDate %s : EventCode %d : Description %s"
           --#ARGUMENTS {0,1,2,3,}
            --#SEVERITY  INFORMATIONAL
            --#TIMEINDEX 136
        ::= 136010029
 
   mngmtAgentTrap-10030 TRAP-TYPE
        ENTERPRISE compaq
        VARIABLES  { hostName,
                     scellNameDateTime,
                     agentEventCode,
                     agentEventDescription }
        DESCRIPTION
             "Invalid URL request type"
           --#TYPE      "Management Agent Event"
           --#SUMMARY   "Host %s : SCellName-TimeDate %s : EventCode %d : Description %s"
           --#ARGUMENTS {0,1,2,3,}
            --#SEVERITY  INFORMATIONAL
            --#TIMEINDEX 136
        ::= 136010030
 
   mngmtAgentTrap-10031 TRAP-TYPE
        ENTERPRISE compaq
        VARIABLES  { hostName,
                     scellNameDateTime,
                     agentEventCode,
                     agentEventDescription }
        DESCRIPTION
             "Invalid URL object type"
           --#TYPE      "Management Agent Event"
           --#SUMMARY   "Host %s : SCellName-TimeDate %s : EventCode %d : Description %s"
           --#ARGUMENTS {0,1,2,3,}
            --#SEVERITY  INFORMATIONAL
            --#TIMEINDEX 136
        ::= 136010031
 
   mngmtAgentTrap-10035 TRAP-TYPE
        ENTERPRISE compaq
        VARIABLES  { hostName,
                     scellNameDateTime,
                     agentEventCode,
                     agentEventDescription }
        DESCRIPTION
             "The snapshot/Snapclone license cannot be validated. Either the license key has not been entered, or there is a system communication failure."
           --#TYPE      "Management Agent Event"
           --#SUMMARY   "Host %s : SCellName-TimeDate %s : EventCode %d : Description %s"
           --#ARGUMENTS {0,1,2,3,}
            --#SEVERITY  INFORMATIONAL
            --#TIMEINDEX 136
        ::= 136010035
 
   mngmtAgentTrap-10036 TRAP-TYPE
        ENTERPRISE compaq
        VARIABLES  { hostName,
                     scellNameDateTime,
                     agentEventCode,
                     agentEventDescription }
        DESCRIPTION
             "A data replication license cannot be validated. Either the license key has not been entered, or there is a system communication failure."
           --#TYPE      "Management Agent Event"
           --#SUMMARY   "Host %s : SCellName-TimeDate %s : EventCode %d : Description %s"
           --#ARGUMENTS {0,1,2,3,}
            --#SEVERITY  INFORMATIONAL
            --#TIMEINDEX 136
        ::= 136010036
 
   mngmtAgentTrap-10037 TRAP-TYPE
        ENTERPRISE compaq
        VARIABLES  { hostName,
                     scellNameDateTime,
                     agentEventCode,
                     agentEventDescription }
        DESCRIPTION
             "Object name should not be empty or exceed its maximum length"
           --#TYPE      "Management Agent Event"
           --#SUMMARY   "Host %s : SCellName-TimeDate %s : EventCode %d : Description %s"
           --#ARGUMENTS {0,1,2,3,}
            --#SEVERITY  INFORMATIONAL
            --#TIMEINDEX 136
        ::= 136010037
 
   mngmtAgentTrap-10038 TRAP-TYPE
        ENTERPRISE compaq
        VARIABLES  { hostName,
                     scellNameDateTime,
                     agentEventCode,
                     agentEventDescription }
        DESCRIPTION
             "Object comments exceeds maximum length"
           --#TYPE      "Management Agent Event"
           --#SUMMARY   "Host %s : SCellName-TimeDate %s : EventCode %d : Description %s"
           --#ARGUMENTS {0,1,2,3,}
            --#SEVERITY  INFORMATIONAL
            --#TIMEINDEX 136
        ::= 136010038
 
   mngmtAgentTrap-10039 TRAP-TYPE
        ENTERPRISE compaq
        VARIABLES  { hostName,
                     scellNameDateTime,
                     agentEventCode,
                     agentEventDescription }
        DESCRIPTION
             "Vdisk does not meet the requirements to be part of a DR group."
           --#TYPE      "Management Agent Event"
           --#SUMMARY   "Host %s : SCellName-TimeDate %s : EventCode %d : Description %s"
           --#ARGUMENTS {0,1,2,3,}
            --#SEVERITY  INFORMATIONAL
            --#TIMEINDEX 136
        ::= 136010039
 
   mngmtAgentTrap-10040 TRAP-TYPE
        ENTERPRISE compaq
        VARIABLES  { hostName,
                     scellNameDateTime,
                     agentEventCode,
                     agentEventDescription }
        DESCRIPTION
             "The Eva selected as the Destination for the DR group is invalid. Either it has a DR relationship with another EVA or it is not the same EVA that the source EVA presently has a DR relationship with."
           --#TYPE      "Management Agent Event"
           --#SUMMARY   "Host %s : SCellName-TimeDate %s : EventCode %d : Description %s"
           --#ARGUMENTS {0,1,2,3,}
            --#SEVERITY  INFORMATIONAL
            --#TIMEINDEX 136
        ::= 136010040
 
   mngmtAgentTrap-10041 TRAP-TYPE
        ENTERPRISE compaq
        VARIABLES  { hostName,
                     scellNameDateTime,
                     agentEventCode,
                     agentEventDescription }
        DESCRIPTION
             "Cannot group the specified disk device because the disk is already in a disk group."
           --#TYPE      "Management Agent Event"
           --#SUMMARY   "Host %s : SCellName-TimeDate %s : EventCode %d : Description %s"
           --#ARGUMENTS {0,1,2,3,}
            --#SEVERITY  INFORMATIONAL
            --#TIMEINDEX 136
        ::= 136010041
 
   mngmtAgentTrap-10042 TRAP-TYPE
        ENTERPRISE compaq
        VARIABLES  { hostName,
                     scellNameDateTime,
                     agentEventCode,
                     agentEventDescription }
        DESCRIPTION
             "Cannot ungroup the specified disk device because the disk is not grouped."
           --#TYPE      "Management Agent Event"
           --#SUMMARY   "Host %s : SCellName-TimeDate %s : EventCode %d : Description %s"
           --#ARGUMENTS {0,1,2,3,}
            --#SEVERITY  INFORMATIONAL
            --#TIMEINDEX 136
        ::= 136010042
 
   mngmtAgentTrap-10043 TRAP-TYPE
        ENTERPRISE compaq
        VARIABLES  { hostName,
                     scellNameDateTime,
                     agentEventCode,
                     agentEventDescription }
        DESCRIPTION
             "Object ID provided, or object type, is invalid for the requested operation."
           --#TYPE      "Management Agent Event"
           --#SUMMARY   "Host %s : SCellName-TimeDate %s : EventCode %d : Description %s"
           --#ARGUMENTS {0,1,2,3,}
            --#SEVERITY  INFORMATIONAL
            --#TIMEINDEX 136
        ::= 136010043
 
   mngmtAgentTrap-10044 TRAP-TYPE
        ENTERPRISE compaq
        VARIABLES  { hostName,
                     scellNameDateTime,
                     agentEventCode,
                     agentEventDescription }
        DESCRIPTION
             "Specified remote disk group does not exist."
           --#TYPE      "Management Agent Event"
           --#SUMMARY   "Host %s : SCellName-TimeDate %s : EventCode %d : Description %s"
           --#ARGUMENTS {0,1,2,3,}
            --#SEVERITY  INFORMATIONAL
            --#TIMEINDEX 136
        ::= 136010044
 
   mngmtAgentTrap-11001 TRAP-TYPE
        ENTERPRISE compaq
        VARIABLES  { hostName,
                     scellNameDateTime,
                     agentEventCode,
                     agentEventDescription }
        DESCRIPTION
             "Agent startup complete"
           --#TYPE      "Management Agent Event"
           --#SUMMARY   "Host %s : SCellName-TimeDate %s : EventCode %d : Description %s"
           --#ARGUMENTS {0,1,2,3,}
            --#SEVERITY  INFORMATIONAL
            --#TIMEINDEX 136
        ::= 136011001
 
   mngmtAgentTrap-11002 TRAP-TYPE
        ENTERPRISE compaq
        VARIABLES  { hostName,
                     scellNameDateTime,
                     agentEventCode,
                     agentEventDescription }
        DESCRIPTION
             "Agent shutdown complete"
           --#TYPE      "Management Agent Event"
           --#SUMMARY   "Host %s : SCellName-TimeDate %s : EventCode %d : Description %s"
           --#ARGUMENTS {0,1,2,3,}
            --#SEVERITY  INFORMATIONAL
            --#TIMEINDEX 136
        ::= 136011002
 
   mngmtAgentTrap-11003 TRAP-TYPE
        ENTERPRISE compaq
        VARIABLES  { hostName,
                     scellNameDateTime,
                     agentEventCode,
                     agentEventDescription }
        DESCRIPTION
             "Insufficient memory to create a new object, Heap may be full!"
           --#TYPE      "Management Agent Event"
           --#SUMMARY   "Host %s : SCellName-TimeDate %s : EventCode %d : Description %s"
           --#ARGUMENTS {0,1,2,3,}
            --#SEVERITY  CRITICAL
            --#TIMEINDEX 136
        ::= 136011003
 
   mngmtAgentTrap-11004 TRAP-TYPE
        ENTERPRISE compaq
        VARIABLES  { hostName,
                     scellNameDateTime,
                     agentEventCode,
                     agentEventDescription }
        DESCRIPTION
             "Agent Startup Failed"
           --#TYPE      "Management Agent Event"
           --#SUMMARY   "Host %s : SCellName-TimeDate %s : EventCode %d : Description %s"
           --#ARGUMENTS {0,1,2,3,}
            --#SEVERITY  CRITICAL
            --#TIMEINDEX 136
        ::= 136011004
 
   mngmtAgentTrap-12001 TRAP-TYPE
        ENTERPRISE compaq
        VARIABLES  { hostName,
                     scellNameDateTime,
                     agentEventCode,
                     agentEventDescription }
        DESCRIPTION
             "Nsc Manager Interface No controllers Found"
           --#TYPE      "Management Agent Event"
           --#SUMMARY   "Host %s : SCellName-TimeDate %s : EventCode %d : Description %s"
           --#ARGUMENTS {0,1,2,3,}
            --#SEVERITY  INFORMATIONAL
            --#TIMEINDEX 136
        ::= 136012001
 
   mngmtAgentTrap-12002 TRAP-TYPE
        ENTERPRISE compaq
        VARIABLES  { hostName,
                     scellNameDateTime,
                     agentEventCode,
                     agentEventDescription }
        DESCRIPTION
             "Nsc Manager Interface Index Out Of Range"
           --#TYPE      "Management Agent Event"
           --#SUMMARY   "Host %s : SCellName-TimeDate %s : EventCode %d : Description %s"
           --#ARGUMENTS {0,1,2,3,}
            --#SEVERITY  INFORMATIONAL
            --#TIMEINDEX 136
        ::= 136012002
 
   mngmtAgentTrap-12003 TRAP-TYPE
        ENTERPRISE compaq
        VARIABLES  { hostName,
                     scellNameDateTime,
                     agentEventCode,
                     agentEventDescription }
        DESCRIPTION
             "Unable to process command at this time. Retry the command or check all connections. "
           --#TYPE      "Management Agent Event"
           --#SUMMARY   "Host %s : SCellName-TimeDate %s : EventCode %d : Description %s"
           --#ARGUMENTS {0,1,2,3,}
            --#SEVERITY  INFORMATIONAL
            --#TIMEINDEX 136
        ::= 136012003
 
   mngmtAgentTrap-12004 TRAP-TYPE
        ENTERPRISE compaq
        VARIABLES  { hostName,
                     scellNameDateTime,
                     agentEventCode,
                     agentEventDescription }
        DESCRIPTION
             "Nsc Manager Interface Initialization Complete"
           --#TYPE      "Management Agent Event"
           --#SUMMARY   "Host %s : SCellName-TimeDate %s : EventCode %d : Description %s"
           --#ARGUMENTS {0,1,2,3,}
            --#SEVERITY  INFORMATIONAL
            --#TIMEINDEX 136
        ::= 136012004
 
   mngmtAgentTrap-12005 TRAP-TYPE
        ENTERPRISE compaq
        VARIABLES  { hostName,
                     scellNameDateTime,
                     agentEventCode,
                     agentEventDescription }
        DESCRIPTION
             "Nsc Manager Interface Initialization Failed"
           --#TYPE      "Management Agent Event"
           --#SUMMARY   "Host %s : SCellName-TimeDate %s : EventCode %d : Description %s"
           --#ARGUMENTS {0,1,2,3,}
            --#SEVERITY  INFORMATIONAL
            --#TIMEINDEX 136
        ::= 136012005
 
   mngmtAgentTrap-12008 TRAP-TYPE
        ENTERPRISE compaq
        VARIABLES  { hostName,
                     scellNameDateTime,
                     agentEventCode,
                     agentEventDescription }
        DESCRIPTION
             "No Disk Groups Available For Access"
           --#TYPE      "Management Agent Event"
           --#SUMMARY   "Host %s : SCellName-TimeDate %s : EventCode %d : Description %s"
           --#ARGUMENTS {0,1,2,3,}
            --#SEVERITY  INFORMATIONAL
            --#TIMEINDEX 136
        ::= 136012008
 
   mngmtAgentTrap-13002 TRAP-TYPE
        ENTERPRISE compaq
        VARIABLES  { hostName,
                     scellNameDateTime,
                     agentEventCode,
                     agentEventDescription }
        DESCRIPTION
             "Notification Mngr Online"
           --#TYPE      "Management Agent Event"
           --#SUMMARY   "Host %s : SCellName-TimeDate %s : EventCode %d : Description %s"
           --#ARGUMENTS {0,1,2,3,}
            --#SEVERITY  INFORMATIONAL
            --#TIMEINDEX 136
        ::= 136013002
 
   mngmtAgentTrap-13003 TRAP-TYPE
        ENTERPRISE compaq
        VARIABLES  { hostName,
                     scellNameDateTime,
                     agentEventCode,
                     agentEventDescription }
        DESCRIPTION
             "Notification Mngr Offline"
           --#TYPE      "Management Agent Event"
           --#SUMMARY   "Host %s : SCellName-TimeDate %s : EventCode %d : Description %s"
           --#ARGUMENTS {0,1,2,3,}
            --#SEVERITY  INFORMATIONAL
            --#TIMEINDEX 136
        ::= 136013003
 
   mngmtAgentTrap-13004 TRAP-TYPE
        ENTERPRISE compaq
        VARIABLES  { hostName,
                     scellNameDateTime,
                     agentEventCode,
                     agentEventDescription }
        DESCRIPTION
             "NM Startup Complete"
           --#TYPE      "Management Agent Event"
           --#SUMMARY   "Host %s : SCellName-TimeDate %s : EventCode %d : Description %s"
           --#ARGUMENTS {0,1,2,3,}
            --#SEVERITY  INFORMATIONAL
            --#TIMEINDEX 136
        ::= 136013004
 
   mngmtAgentTrap-13007 TRAP-TYPE
        ENTERPRISE compaq
        VARIABLES  { hostName,
                     scellNameDateTime,
                     agentEventCode,
                     agentEventDescription }
        DESCRIPTION
             "Notification Failed"
           --#TYPE      "Management Agent Event"
           --#SUMMARY   "Host %s : SCellName-TimeDate %s : EventCode %d : Description %s"
           --#ARGUMENTS {0,1,2,3,}
            --#SEVERITY  CRITICAL
            --#TIMEINDEX 136
        ::= 136013007
 
   mngmtAgentTrap-13009 TRAP-TYPE
        ENTERPRISE compaq
        VARIABLES  { hostName,
                     scellNameDateTime,
                     agentEventCode,
                     agentEventDescription }
        DESCRIPTION
             "Notification Failed - Network Error"
           --#TYPE      "Management Agent Event"
           --#SUMMARY   "Host %s : SCellName-TimeDate %s : EventCode %d : Description %s"
           --#ARGUMENTS {0,1,2,3,}
            --#SEVERITY  CRITICAL
            --#TIMEINDEX 136
        ::= 136013009
 
   mngmtAgentTrap-13012 TRAP-TYPE
        ENTERPRISE compaq
        VARIABLES  { hostName,
                     scellNameDateTime,
                     agentEventCode,
                     agentEventDescription }
        DESCRIPTION
             "NM Prev Failed Notification Successfully Notified"
           --#TYPE      "Management Agent Event"
           --#SUMMARY   "Host %s : SCellName-TimeDate %s : EventCode %d : Description %s"
           --#ARGUMENTS {0,1,2,3,}
            --#SEVERITY  INFORMATIONAL
            --#TIMEINDEX 136
        ::= 136013012
 
   mngmtAgentTrap-13015 TRAP-TYPE
        ENTERPRISE compaq
        VARIABLES  { hostName,
                     scellNameDateTime,
                     agentEventCode,
                     agentEventDescription }
        DESCRIPTION
             "NM SNMP Packet Failed"
           --#TYPE      "Management Agent Event"
           --#SUMMARY   "Host %s : SCellName-TimeDate %s : EventCode %d : Description %s"
           --#ARGUMENTS {0,1,2,3,}
            --#SEVERITY  CRITICAL
            --#TIMEINDEX 136
        ::= 136013015
 
   mngmtAgentTrap-13017 TRAP-TYPE
        ENTERPRISE compaq
        VARIABLES  { hostName,
                     scellNameDateTime,
                     agentEventCode,
                     agentEventDescription }
        DESCRIPTION
             "NM Memory Allocation Error"
           --#TYPE      "Management Agent Event"
           --#SUMMARY   "Host %s : SCellName-TimeDate %s : EventCode %d : Description %s"
           --#ARGUMENTS {0,1,2,3,}
            --#SEVERITY  CRITICAL
            --#TIMEINDEX 136
        ::= 136013017
 
   mngmtAgentTrap-13018 TRAP-TYPE
        ENTERPRISE compaq
        VARIABLES  { hostName,
                     scellNameDateTime,
                     agentEventCode,
                     agentEventDescription }
        DESCRIPTION
             "NM StorageCell handle is NULL"
           --#TYPE      "Management Agent Event"
           --#SUMMARY   "Host %s : SCellName-TimeDate %s : EventCode %d : Description %s"
           --#ARGUMENTS {0,1,2,3,}
            --#SEVERITY  CRITICAL
            --#TIMEINDEX 136
        ::= 136013018
 
   mngmtAgentTrap-13019 TRAP-TYPE
        ENTERPRISE compaq
        VARIABLES  { hostName,
                     scellNameDateTime,
                     agentEventCode,
                     agentEventDescription }
        DESCRIPTION
             "NM User defined event state file is empty"
           --#TYPE      "Management Agent Event"
           --#SUMMARY   "Host %s : SCellName-TimeDate %s : EventCode %d : Description %s"
           --#ARGUMENTS {0,1,2,3,}
            --#SEVERITY  INFORMATIONAL
            --#TIMEINDEX 136
        ::= 136013019
 
   mngmtAgentTrap-13020 TRAP-TYPE
        ENTERPRISE compaq
        VARIABLES  { hostName,
                     scellNameDateTime,
                     agentEventCode,
                     agentEventDescription }
        DESCRIPTION
             "NM Notification Failed - Notification Matrix is NULL "
           --#TYPE      "Management Agent Event"
           --#SUMMARY   "Host %s : SCellName-TimeDate %s : EventCode %d : Description %s"
           --#ARGUMENTS {0,1,2,3,}
            --#SEVERITY  MINOR
            --#TIMEINDEX 136
        ::= 136013020
 
   mngmtAgentTrap-14001 TRAP-TYPE
        ENTERPRISE compaq
        VARIABLES  { hostName,
                     scellNameDateTime,
                     agentEventCode,
                     agentEventDescription }
        DESCRIPTION
             "View Already Exists"
           --#TYPE      "Management Agent Event"
           --#SUMMARY   "Host %s : SCellName-TimeDate %s : EventCode %d : Description %s"
           --#ARGUMENTS {0,1,2,3,}
            --#SEVERITY  INFORMATIONAL
            --#TIMEINDEX 136
        ::= 136014001
 
   mngmtAgentTrap-14002 TRAP-TYPE
        ENTERPRISE compaq
        VARIABLES  { hostName,
                     scellNameDateTime,
                     agentEventCode,
                     agentEventDescription }
        DESCRIPTION
             "View Is Not Set"
           --#TYPE      "Management Agent Event"
           --#SUMMARY   "Host %s : SCellName-TimeDate %s : EventCode %d : Description %s"
           --#ARGUMENTS {0,1,2,3,}
            --#SEVERITY  INFORMATIONAL
            --#TIMEINDEX 136
        ::= 136014002
 
   mngmtAgentTrap-14003 TRAP-TYPE
        ENTERPRISE compaq
        VARIABLES  { hostName,
                     scellNameDateTime,
                     agentEventCode,
                     agentEventDescription }
        DESCRIPTION
             "No View Object(s) Found"
           --#TYPE      "Management Agent Event"
           --#SUMMARY   "Host %s : SCellName-TimeDate %s : EventCode %d : Description %s"
           --#ARGUMENTS {0,1,2,3,}
            --#SEVERITY  INFORMATIONAL
            --#TIMEINDEX 136
        ::= 136014003
 
   mngmtAgentTrap-14004 TRAP-TYPE
        ENTERPRISE compaq
        VARIABLES  { hostName,
                     scellNameDateTime,
                     agentEventCode,
                     agentEventDescription }
        DESCRIPTION
             "View Index Is Out Of Range"
           --#TYPE      "Management Agent Event"
           --#SUMMARY   "Host %s : SCellName-TimeDate %s : EventCode %d : Description %s"
           --#ARGUMENTS {0,1,2,3,}
            --#SEVERITY  INFORMATIONAL
            --#TIMEINDEX 136
        ::= 136014004
 
   mngmtAgentTrap-14005 TRAP-TYPE
        ENTERPRISE compaq
        VARIABLES  { hostName,
                     scellNameDateTime,
                     agentEventCode,
                     agentEventDescription }
        DESCRIPTION
             "View Object - Invalid Object Condition"
           --#TYPE      "Management Agent Event"
           --#SUMMARY   "Host %s : SCellName-TimeDate %s : EventCode %d : Description %s"
           --#ARGUMENTS {0,1,2,3,}
            --#SEVERITY  INFORMATIONAL
            --#TIMEINDEX 136
        ::= 136014005
 
   mngmtAgentTrap-14006 TRAP-TYPE
        ENTERPRISE compaq
        VARIABLES  { hostName,
                     scellNameDateTime,
                     agentEventCode,
                     agentEventDescription }
        DESCRIPTION
             "View Object - Invalid Object Type"
           --#TYPE      "Management Agent Event"
           --#SUMMARY   "Host %s : SCellName-TimeDate %s : EventCode %d : Description %s"
           --#ARGUMENTS {0,1,2,3,}
            --#SEVERITY  INFORMATIONAL
            --#TIMEINDEX 136
        ::= 136014006
 
   mngmtAgentTrap-14007 TRAP-TYPE
        ENTERPRISE compaq
        VARIABLES  { hostName,
                     scellNameDateTime,
                     agentEventCode,
                     agentEventDescription }
        DESCRIPTION
             "View List Pointer is NULL"
           --#TYPE      "Management Agent Event"
           --#SUMMARY   "Host %s : SCellName-TimeDate %s : EventCode %d : Description %s"
           --#ARGUMENTS {0,1,2,3,}
            --#SEVERITY  MINOR
            --#TIMEINDEX 136
        ::= 136014007
 
   mngmtAgentTrap-14008 TRAP-TYPE
        ENTERPRISE compaq
        VARIABLES  { hostName,
                     scellNameDateTime,
                     agentEventCode,
                     agentEventDescription }
        DESCRIPTION
             "View Object Pointer is NULL"
           --#TYPE      "Management Agent Event"
           --#SUMMARY   "Host %s : SCellName-TimeDate %s : EventCode %d : Description %s"
           --#ARGUMENTS {0,1,2,3,}
            --#SEVERITY  MINOR
            --#TIMEINDEX 136
        ::= 136014008
 
   mngmtAgentTrap-14009 TRAP-TYPE
        ENTERPRISE compaq
        VARIABLES  { hostName,
                     scellNameDateTime,
                     agentEventCode,
                     agentEventDescription }
        DESCRIPTION
             "Building View List Object - Complete"
           --#TYPE      "Management Agent Event"
           --#SUMMARY   "Host %s : SCellName-TimeDate %s : EventCode %d : Description %s"
           --#ARGUMENTS {0,1,2,3,}
            --#SEVERITY  INFORMATIONAL
            --#TIMEINDEX 136
        ::= 136014009
 
   mngmtAgentTrap-14010 TRAP-TYPE
        ENTERPRISE compaq
        VARIABLES  { hostName,
                     scellNameDateTime,
                     agentEventCode,
                     agentEventDescription }
        DESCRIPTION
             "Building View List Object - Failed"
           --#TYPE      "Management Agent Event"
           --#SUMMARY   "Host %s : SCellName-TimeDate %s : EventCode %d : Description %s"
           --#ARGUMENTS {0,1,2,3,}
            --#SEVERITY  INFORMATIONAL
            --#TIMEINDEX 136
        ::= 136014010
 
   mngmtAgentTrap-14012 TRAP-TYPE
        ENTERPRISE compaq
        VARIABLES  { hostName,
                     scellNameDateTime,
                     agentEventCode,
                     agentEventDescription }
        DESCRIPTION
             "View Find by UID Failed"
           --#TYPE      "Management Agent Event"
           --#SUMMARY   "Host %s : SCellName-TimeDate %s : EventCode %d : Description %s"
           --#ARGUMENTS {0,1,2,3,}
            --#SEVERITY  INFORMATIONAL
            --#TIMEINDEX 136
        ::= 136014012
 
   mngmtAgentTrap-14013 TRAP-TYPE
        ENTERPRISE compaq
        VARIABLES  { hostName,
                     scellNameDateTime,
                     agentEventCode,
                     agentEventDescription }
        DESCRIPTION
             "View Find by Type Failed"
           --#TYPE      "Management Agent Event"
           --#SUMMARY   "Host %s : SCellName-TimeDate %s : EventCode %d : Description %s"
           --#ARGUMENTS {0,1,2,3,}
            --#SEVERITY  INFORMATIONAL
            --#TIMEINDEX 136
        ::= 136014013
 
   mngmtAgentTrap-14017 TRAP-TYPE
        ENTERPRISE compaq
        VARIABLES  { hostName,
                     scellNameDateTime,
                     agentEventCode,
                     agentEventDescription }
        DESCRIPTION
             "View Find by Type by Name Failed"
           --#TYPE      "Management Agent Event"
           --#SUMMARY   "Host %s : SCellName-TimeDate %s : EventCode %d : Description %s"
           --#ARGUMENTS {0,1,2,3,}
            --#SEVERITY  INFORMATIONAL
            --#TIMEINDEX 136
        ::= 136014017
 
   mngmtAgentTrap-15001 TRAP-TYPE
        ENTERPRISE compaq
        VARIABLES  { hostName,
                     scellNameDateTime,
                     agentEventCode,
                     agentEventDescription }
        DESCRIPTION
             "Tree View Symbol Not Found"
           --#TYPE      "Management Agent Event"
           --#SUMMARY   "Host %s : SCellName-TimeDate %s : EventCode %d : Description %s"
           --#ARGUMENTS {0,1,2,3,}
            --#SEVERITY  INFORMATIONAL
            --#TIMEINDEX 136
        ::= 136015001
 
   mngmtAgentTrap-15002 TRAP-TYPE
        ENTERPRISE compaq
        VARIABLES  { hostName,
                     scellNameDateTime,
                     agentEventCode,
                     agentEventDescription }
        DESCRIPTION
             "Tree View Id Symbol Not Found"
           --#TYPE      "Management Agent Event"
           --#SUMMARY   "Host %s : SCellName-TimeDate %s : EventCode %d : Description %s"
           --#ARGUMENTS {0,1,2,3,}
            --#SEVERITY  INFORMATIONAL
            --#TIMEINDEX 136
        ::= 136015002
 
   mngmtAgentTrap-15003 TRAP-TYPE
        ENTERPRISE compaq
        VARIABLES  { hostName,
                     scellNameDateTime,
                     agentEventCode,
                     agentEventDescription }
        DESCRIPTION
             "Tree Cursor Symbol Not Found"
           --#TYPE      "Management Agent Event"
           --#SUMMARY   "Host %s : SCellName-TimeDate %s : EventCode %d : Description %s"
           --#ARGUMENTS {0,1,2,3,}
            --#SEVERITY  INFORMATIONAL
            --#TIMEINDEX 136
        ::= 136015003
 
   mngmtAgentTrap-15004 TRAP-TYPE
        ENTERPRISE compaq
        VARIABLES  { hostName,
                     scellNameDateTime,
                     agentEventCode,
                     agentEventDescription }
        DESCRIPTION
             "Tree Cursor Id Symbol Not Found"
           --#TYPE      "Management Agent Event"
           --#SUMMARY   "Host %s : SCellName-TimeDate %s : EventCode %d : Description %s"
           --#ARGUMENTS {0,1,2,3,}
            --#SEVERITY  INFORMATIONAL
            --#TIMEINDEX 136
        ::= 136015004
 
   mngmtAgentTrap-15005 TRAP-TYPE
        ENTERPRISE compaq
        VARIABLES  { hostName,
                     scellNameDateTime,
                     agentEventCode,
                     agentEventDescription }
        DESCRIPTION
             "Tree Sibling Symbol Not Found"
           --#TYPE      "Management Agent Event"
           --#SUMMARY   "Host %s : SCellName-TimeDate %s : EventCode %d : Description %s"
           --#ARGUMENTS {0,1,2,3,}
            --#SEVERITY  INFORMATIONAL
            --#TIMEINDEX 136
        ::= 136015005
 
   mngmtAgentTrap-15006 TRAP-TYPE
        ENTERPRISE compaq
        VARIABLES  { hostName,
                     scellNameDateTime,
                     agentEventCode,
                     agentEventDescription }
        DESCRIPTION
             "Tree Total Children Symbol Not Found"
           --#TYPE      "Management Agent Event"
           --#SUMMARY   "Host %s : SCellName-TimeDate %s : EventCode %d : Description %s"
           --#ARGUMENTS {0,1,2,3,}
            --#SEVERITY  INFORMATIONAL
            --#TIMEINDEX 136
        ::= 136015006
 
   mngmtAgentTrap-15007 TRAP-TYPE
        ENTERPRISE compaq
        VARIABLES  { hostName,
                     scellNameDateTime,
                     agentEventCode,
                     agentEventDescription }
        DESCRIPTION
             "Tree Expansion Symbol Not Found"
           --#TYPE      "Management Agent Event"
           --#SUMMARY   "Host %s : SCellName-TimeDate %s : EventCode %d : Description %s"
           --#ARGUMENTS {0,1,2,3,}
            --#SEVERITY  INFORMATIONAL
            --#TIMEINDEX 136
        ::= 136015007
 
   mngmtAgentTrap-15008 TRAP-TYPE
        ENTERPRISE compaq
        VARIABLES  { hostName,
                     scellNameDateTime,
                     agentEventCode,
                     agentEventDescription }
        DESCRIPTION
             "Tree Contraction Symbol Not Found"
           --#TYPE      "Management Agent Event"
           --#SUMMARY   "Host %s : SCellName-TimeDate %s : EventCode %d : Description %s"
           --#ARGUMENTS {0,1,2,3,}
            --#SEVERITY  INFORMATIONAL
            --#TIMEINDEX 136
        ::= 136015008
 
   mngmtAgentTrap-15009 TRAP-TYPE
        ENTERPRISE compaq
        VARIABLES  { hostName,
                     scellNameDateTime,
                     agentEventCode,
                     agentEventDescription }
        DESCRIPTION
             "Tree Invalid Descriptor String"
           --#TYPE      "Management Agent Event"
           --#SUMMARY   "Host %s : SCellName-TimeDate %s : EventCode %d : Description %s"
           --#ARGUMENTS {0,1,2,3,}
            --#SEVERITY  INFORMATIONAL
            --#TIMEINDEX 136
        ::= 136015009
 
   mngmtAgentTrap-16001 TRAP-TYPE
        ENTERPRISE compaq
        VARIABLES  { hostName,
                     scellNameDateTime,
                     agentEventCode,
                     agentEventDescription }
        DESCRIPTION
             "Ema Short Status - Reissue Command"
           --#TYPE      "Management Agent Event"
           --#SUMMARY   "Host %s : SCellName-TimeDate %s : EventCode %d : Description %s"
           --#ARGUMENTS {0,1,2,3,}
            --#SEVERITY  INFORMATIONAL
            --#TIMEINDEX 136
        ::= 136016001
 
   mngmtAgentTrap-16004 TRAP-TYPE
        ENTERPRISE compaq
        VARIABLES  { hostName,
                     scellNameDateTime,
                     agentEventCode,
                     agentEventDescription }
        DESCRIPTION
             "Ema Invalid Handle Set In Request Packet"
           --#TYPE      "Management Agent Event"
           --#SUMMARY   "Host %s : SCellName-TimeDate %s : EventCode %d : Description %s"
           --#ARGUMENTS {0,1,2,3,}
            --#SEVERITY  INFORMATIONAL
            --#TIMEINDEX 136
        ::= 136016004
 
   mngmtAgentTrap-16005 TRAP-TYPE
        ENTERPRISE compaq
        VARIABLES  { hostName,
                     scellNameDateTime,
                     agentEventCode,
                     agentEventDescription }
        DESCRIPTION
             "Ema No Pstore At Referenced Location"
           --#TYPE      "Management Agent Event"
           --#SUMMARY   "Host %s : SCellName-TimeDate %s : EventCode %d : Description %s"
           --#ARGUMENTS {0,1,2,3,}
            --#SEVERITY  INFORMATIONAL
            --#TIMEINDEX 136
        ::= 136016005
 
   mngmtAgentTrap-16008 TRAP-TYPE
        ENTERPRISE compaq
        VARIABLES  { hostName,
                     scellNameDateTime,
                     agentEventCode,
                     agentEventDescription }
        DESCRIPTION
             "Ema No Device Found"
           --#TYPE      "Management Agent Event"
           --#SUMMARY   "Host %s : SCellName-TimeDate %s : EventCode %d : Description %s"
           --#ARGUMENTS {0,1,2,3,}
            --#SEVERITY  INFORMATIONAL
            --#TIMEINDEX 136
        ::= 136016008
 
   mngmtAgentTrap-16010 TRAP-TYPE
        ENTERPRISE compaq
        VARIABLES  { hostName,
                     scellNameDateTime,
                     agentEventCode,
                     agentEventDescription }
        DESCRIPTION
             "Ema Could Not Find SubEnclosure in Configuration List"
           --#TYPE      "Management Agent Event"
           --#SUMMARY   "Host %s : SCellName-TimeDate %s : EventCode %d : Description %s"
           --#ARGUMENTS {0,1,2,3,}
            --#SEVERITY  INFORMATIONAL
            --#TIMEINDEX 136
        ::= 136016010
 
   mngmtAgentTrap-16012 TRAP-TYPE
        ENTERPRISE compaq
        VARIABLES  { hostName,
                     scellNameDateTime,
                     agentEventCode,
                     agentEventDescription }
        DESCRIPTION
             "Ema Non-specific error occurred "
           --#TYPE      "Management Agent Event"
           --#SUMMARY   "Host %s : SCellName-TimeDate %s : EventCode %d : Description %s"
           --#ARGUMENTS {0,1,2,3,}
            --#SEVERITY  INFORMATIONAL
            --#TIMEINDEX 136
        ::= 136016012
 
   mngmtAgentTrap-16013 TRAP-TYPE
        ENTERPRISE compaq
        VARIABLES  { hostName,
                     scellNameDateTime,
                     agentEventCode,
                     agentEventDescription }
        DESCRIPTION
             "Ema Shelf WWN Could Not Be Accessed Through A Drive"
           --#TYPE      "Management Agent Event"
           --#SUMMARY   "Host %s : SCellName-TimeDate %s : EventCode %d : Description %s"
           --#ARGUMENTS {0,1,2,3,}
            --#SEVERITY  INFORMATIONAL
            --#TIMEINDEX 136
        ::= 136016013
 
   mngmtAgentTrap-16014 TRAP-TYPE
        ENTERPRISE compaq
        VARIABLES  { hostName,
                     scellNameDateTime,
                     agentEventCode,
                     agentEventDescription }
        DESCRIPTION
             "Ema EMU Failed To Enter Primary Mode"
           --#TYPE      "Management Agent Event"
           --#SUMMARY   "Host %s : SCellName-TimeDate %s : EventCode %d : Description %s"
           --#ARGUMENTS {0,1,2,3,}
            --#SEVERITY  INFORMATIONAL
            --#TIMEINDEX 136
        ::= 136016014
 
   mngmtAgentTrap-16015 TRAP-TYPE
        ENTERPRISE compaq
        VARIABLES  { hostName,
                     scellNameDateTime,
                     agentEventCode,
                     agentEventDescription }
        DESCRIPTION
             "Ema EMU Failed To Exit Primary Mode"
           --#TYPE      "Management Agent Event"
           --#SUMMARY   "Host %s : SCellName-TimeDate %s : EventCode %d : Description %s"
           --#ARGUMENTS {0,1,2,3,}
            --#SEVERITY  INFORMATIONAL
            --#TIMEINDEX 136
        ::= 136016015
 
   mngmtAgentTrap-16016 TRAP-TYPE
        ENTERPRISE compaq
        VARIABLES  { hostName,
                     scellNameDateTime,
                     agentEventCode,
                     agentEventDescription }
        DESCRIPTION
             "Ema Downloaded File Does Not Contain Valid Fibre Channel Loader [status:1]"
           --#TYPE      "Management Agent Event"
           --#SUMMARY   "Host %s : SCellName-TimeDate %s : EventCode %d : Description %s"
           --#ARGUMENTS {0,1,2,3,}
            --#SEVERITY  INFORMATIONAL
            --#TIMEINDEX 136
        ::= 136016016
 
   mngmtAgentTrap-16017 TRAP-TYPE
        ENTERPRISE compaq
        VARIABLES  { hostName,
                     scellNameDateTime,
                     agentEventCode,
                     agentEventDescription }
        DESCRIPTION
             "Ema Downloaded File Format Is Not Recognized [status:2]"
           --#TYPE      "Management Agent Event"
           --#SUMMARY   "Host %s : SCellName-TimeDate %s : EventCode %d : Description %s"
           --#ARGUMENTS {0,1,2,3,}
            --#SEVERITY  INFORMATIONAL
            --#TIMEINDEX 136
        ::= 136016017
 
   mngmtAgentTrap-16018 TRAP-TYPE
        ENTERPRISE compaq
        VARIABLES  { hostName,
                     scellNameDateTime,
                     agentEventCode,
                     agentEventDescription }
        DESCRIPTION
             "Ema Incorrect Firmware In Downloaded File [status:3]"
           --#TYPE      "Management Agent Event"
           --#SUMMARY   "Host %s : SCellName-TimeDate %s : EventCode %d : Description %s"
           --#ARGUMENTS {0,1,2,3,}
            --#SEVERITY  INFORMATIONAL
            --#TIMEINDEX 136
        ::= 136016018
 
   mngmtAgentTrap-16019 TRAP-TYPE
        ENTERPRISE compaq
        VARIABLES  { hostName,
                     scellNameDateTime,
                     agentEventCode,
                     agentEventDescription }
        DESCRIPTION
             "Ema Downloaded Loader is Too Large [status:4]"
           --#TYPE      "Management Agent Event"
           --#SUMMARY   "Host %s : SCellName-TimeDate %s : EventCode %d : Description %s"
           --#ARGUMENTS {0,1,2,3,}
            --#SEVERITY  INFORMATIONAL
            --#TIMEINDEX 136
        ::= 136016019
 
   mngmtAgentTrap-16020 TRAP-TYPE
        ENTERPRISE compaq
        VARIABLES  { hostName,
                     scellNameDateTime,
                     agentEventCode,
                     agentEventDescription }
        DESCRIPTION
             "Ema Invalid Checksum [status:5]"
           --#TYPE      "Management Agent Event"
           --#SUMMARY   "Host %s : SCellName-TimeDate %s : EventCode %d : Description %s"
           --#ARGUMENTS {0,1,2,3,}
            --#SEVERITY  INFORMATIONAL
            --#TIMEINDEX 136
        ::= 136016020
 
   mngmtAgentTrap-16021 TRAP-TYPE
        ENTERPRISE compaq
        VARIABLES  { hostName,
                     scellNameDateTime,
                     agentEventCode,
                     agentEventDescription }
        DESCRIPTION
             "Ema Previous Offset Plus Previous Length Not Equal To Current Offset [status:6]"
           --#TYPE      "Management Agent Event"
           --#SUMMARY   "Host %s : SCellName-TimeDate %s : EventCode %d : Description %s"
           --#ARGUMENTS {0,1,2,3,}
            --#SEVERITY  INFORMATIONAL
            --#TIMEINDEX 136
        ::= 136016021
 
   mngmtAgentTrap-16022 TRAP-TYPE
        ENTERPRISE compaq
        VARIABLES  { hostName,
                     scellNameDateTime,
                     agentEventCode,
                     agentEventDescription }
        DESCRIPTION
             "Ema Downloaded Loader Terminated Incorrectly [status:7]"
           --#TYPE      "Management Agent Event"
           --#SUMMARY   "Host %s : SCellName-TimeDate %s : EventCode %d : Description %s"
           --#ARGUMENTS {0,1,2,3,}
            --#SEVERITY  INFORMATIONAL
            --#TIMEINDEX 136
        ::= 136016022
 
   mngmtAgentTrap-16023 TRAP-TYPE
        ENTERPRISE compaq
        VARIABLES  { hostName,
                     scellNameDateTime,
                     agentEventCode,
                     agentEventDescription }
        DESCRIPTION
             "Ema EMU Out Of Memory [status:8]"
           --#TYPE      "Management Agent Event"
           --#SUMMARY   "Host %s : SCellName-TimeDate %s : EventCode %d : Description %s"
           --#ARGUMENTS {0,1,2,3,}
            --#SEVERITY  INFORMATIONAL
            --#TIMEINDEX 136
        ::= 136016023
 
   mngmtAgentTrap-16024 TRAP-TYPE
        ENTERPRISE compaq
        VARIABLES  { hostName,
                     scellNameDateTime,
                     agentEventCode,
                     agentEventDescription }
        DESCRIPTION
             "Ema EMU CDB Timeout -- Download Aborted [status:9]"
           --#TYPE      "Management Agent Event"
           --#SUMMARY   "Host %s : SCellName-TimeDate %s : EventCode %d : Description %s"
           --#ARGUMENTS {0,1,2,3,}
            --#SEVERITY  INFORMATIONAL
            --#TIMEINDEX 136
        ::= 136016024
 
   mngmtAgentTrap-16025 TRAP-TYPE
        ENTERPRISE compaq
        VARIABLES  { hostName,
                     scellNameDateTime,
                     agentEventCode,
                     agentEventDescription }
        DESCRIPTION
             "Ema EMU Internal State Machine Error [status:10]"
           --#TYPE      "Management Agent Event"
           --#SUMMARY   "Host %s : SCellName-TimeDate %s : EventCode %d : Description %s"
           --#ARGUMENTS {0,1,2,3,}
            --#SEVERITY  INFORMATIONAL
            --#TIMEINDEX 136
        ::= 136016025
 
   mngmtAgentTrap-16026 TRAP-TYPE
        ENTERPRISE compaq
        VARIABLES  { hostName,
                     scellNameDateTime,
                     agentEventCode,
                     agentEventDescription }
        DESCRIPTION
             "Ema EMU Flash Erasure Failure [status:11]"
           --#TYPE      "Management Agent Event"
           --#SUMMARY   "Host %s : SCellName-TimeDate %s : EventCode %d : Description %s"
           --#ARGUMENTS {0,1,2,3,}
            --#SEVERITY  INFORMATIONAL
            --#TIMEINDEX 136
        ::= 136016026
 
   mngmtAgentTrap-16027 TRAP-TYPE
        ENTERPRISE compaq
        VARIABLES  { hostName,
                     scellNameDateTime,
                     agentEventCode,
                     agentEventDescription }
        DESCRIPTION
             "Ema EMU In Primary Mode - Cannot Download To Primary EMU [status:12]"
           --#TYPE      "Management Agent Event"
           --#SUMMARY   "Host %s : SCellName-TimeDate %s : EventCode %d : Description %s"
           --#ARGUMENTS {0,1,2,3,}
            --#SEVERITY  INFORMATIONAL
            --#TIMEINDEX 136
        ::= 136016027
 
   mngmtAgentTrap-16028 TRAP-TYPE
        ENTERPRISE compaq
        VARIABLES  { hostName,
                     scellNameDateTime,
                     agentEventCode,
                     agentEventDescription }
        DESCRIPTION
             "Ema Previous Offset Plus Previous Length Greater Than Total Size [status:13]"
           --#TYPE      "Management Agent Event"
           --#SUMMARY   "Host %s : SCellName-TimeDate %s : EventCode %d : Description %s"
           --#ARGUMENTS {0,1,2,3,}
            --#SEVERITY  INFORMATIONAL
            --#TIMEINDEX 136
        ::= 136016028
 
   mngmtAgentTrap-16029 TRAP-TYPE
        ENTERPRISE compaq
        VARIABLES  { hostName,
                     scellNameDateTime,
                     agentEventCode,
                     agentEventDescription }
        DESCRIPTION
             "Ema Current Total Size Different From Previous Total Size [status:14]"
           --#TYPE      "Management Agent Event"
           --#SUMMARY   "Host %s : SCellName-TimeDate %s : EventCode %d : Description %s"
           --#ARGUMENTS {0,1,2,3,}
            --#SEVERITY  INFORMATIONAL
            --#TIMEINDEX 136
        ::= 136016029
 
   mngmtAgentTrap-16030 TRAP-TYPE
        ENTERPRISE compaq
        VARIABLES  { hostName,
                     scellNameDateTime,
                     agentEventCode,
                     agentEventDescription }
        DESCRIPTION
             "Ema Could Not Restore Reporting Group Number. Final Download Record Error"
           --#TYPE      "Management Agent Event"
           --#SUMMARY   "Host %s : SCellName-TimeDate %s : EventCode %d : Description %s"
           --#ARGUMENTS {0,1,2,3,}
            --#SEVERITY  INFORMATIONAL
            --#TIMEINDEX 136
        ::= 136016030
 
   mngmtAgentTrap-16031 TRAP-TYPE
        ENTERPRISE compaq
        VARIABLES  { hostName,
                     scellNameDateTime,
                     agentEventCode,
                     agentEventDescription }
        DESCRIPTION
             "Ema Could Not Recovery From Invop. Invop Retries Exhausted"
           --#TYPE      "Management Agent Event"
           --#SUMMARY   "Host %s : SCellName-TimeDate %s : EventCode %d : Description %s"
           --#ARGUMENTS {0,1,2,3,}
            --#SEVERITY  INFORMATIONAL
            --#TIMEINDEX 136
        ::= 136016031
 
   mngmtAgentTrap-16032 TRAP-TYPE
        ENTERPRISE compaq
        VARIABLES  { hostName,
                     scellNameDateTime,
                     agentEventCode,
                     agentEventDescription }
        DESCRIPTION
             "Ema Requested WWN Does Not Match Enclosure WWN"
           --#TYPE      "Management Agent Event"
           --#SUMMARY   "Host %s : SCellName-TimeDate %s : EventCode %d : Description %s"
           --#ARGUMENTS {0,1,2,3,}
            --#SEVERITY  INFORMATIONAL
            --#TIMEINDEX 136
        ::= 136016032
 
   mngmtAgentTrap-16033 TRAP-TYPE
        ENTERPRISE compaq
        VARIABLES  { hostName,
                     scellNameDateTime,
                     agentEventCode,
                     agentEventDescription }
        DESCRIPTION
             "Ema EMU Enclosure Services Error Occurred. EMU May Be Unavailable or Not Installed"
           --#TYPE      "Management Agent Event"
           --#SUMMARY   "Host %s : SCellName-TimeDate %s : EventCode %d : Description %s"
           --#ARGUMENTS {0,1,2,3,}
            --#SEVERITY  CRITICAL
            --#TIMEINDEX 136
        ::= 136016033
 
   mngmtAgentTrap-16034 TRAP-TYPE
        ENTERPRISE compaq
        VARIABLES  { hostName,
                     scellNameDateTime,
                     agentEventCode,
                     agentEventDescription }
        DESCRIPTION
             "Ema SCSI Error Occurred While Trying To Communicate With EMU"
           --#TYPE      "Management Agent Event"
           --#SUMMARY   "Host %s : SCellName-TimeDate %s : EventCode %d : Description %s"
           --#ARGUMENTS {0,1,2,3,}
            --#SEVERITY  INFORMATIONAL
            --#TIMEINDEX 136
        ::= 136016034
 
   mngmtAgentTrap-16035 TRAP-TYPE
        ENTERPRISE compaq
        VARIABLES  { hostName,
                     scellNameDateTime,
                     agentEventCode,
                     agentEventDescription }
        DESCRIPTION
             "Ema Could Not Open EMU Firmware File"
           --#TYPE      "Management Agent Event"
           --#SUMMARY   "Host %s : SCellName-TimeDate %s : EventCode %d : Description %s"
           --#ARGUMENTS {0,1,2,3,}
            --#SEVERITY  INFORMATIONAL
            --#TIMEINDEX 136
        ::= 136016035
 
   mngmtAgentTrap-16036 TRAP-TYPE
        ENTERPRISE compaq
        VARIABLES  { hostName,
                     scellNameDateTime,
                     agentEventCode,
                     agentEventDescription }
        DESCRIPTION
             "Ema EMU Firmware File Name Is Null"
           --#TYPE      "Management Agent Event"
           --#SUMMARY   "Host %s : SCellName-TimeDate %s : EventCode %d : Description %s"
           --#ARGUMENTS {0,1,2,3,}
            --#SEVERITY  INFORMATIONAL
            --#TIMEINDEX 136
        ::= 136016036
 
   mngmtAgentTrap-16037 TRAP-TYPE
        ENTERPRISE compaq
        VARIABLES  { hostName,
                     scellNameDateTime,
                     agentEventCode,
                     agentEventDescription }
        DESCRIPTION
             "Ema EMU Firmware Download Retries Exhausted. Manual Download May Be Required"
           --#TYPE      "Management Agent Event"
           --#SUMMARY   "Host %s : SCellName-TimeDate %s : EventCode %d : Description %s"
           --#ARGUMENTS {0,1,2,3,}
            --#SEVERITY  INFORMATIONAL
            --#TIMEINDEX 136
        ::= 136016037
 
   mngmtAgentTrap-16038 TRAP-TYPE
        ENTERPRISE compaq
        VARIABLES  { hostName,
                     scellNameDateTime,
                     agentEventCode,
                     agentEventDescription }
        DESCRIPTION
             "Ema EMU Current Firmware Version Matches Upgrade Firmware Version. No Upgrade Will Be Performed."
           --#TYPE      "Management Agent Event"
           --#SUMMARY   "Host %s : SCellName-TimeDate %s : EventCode %d : Description %s"
           --#ARGUMENTS {0,1,2,3,}
            --#SEVERITY  INFORMATIONAL
            --#TIMEINDEX 136
        ::= 136016038
 
   mngmtAgentTrap-16039 TRAP-TYPE
        ENTERPRISE compaq
        VARIABLES  { hostName,
                     scellNameDateTime,
                     agentEventCode,
                     agentEventDescription }
        DESCRIPTION
             "Ema EMU Firmware Upgrade Success"
           --#TYPE      "Management Agent Event"
           --#SUMMARY   "Host %s : SCellName-TimeDate %s : EventCode %d : Description %s"
           --#ARGUMENTS {0,1,2,3,}
            --#SEVERITY  INFORMATIONAL
            --#TIMEINDEX 136
        ::= 136016039
 
   mngmtAgentTrap-16040 TRAP-TYPE
        ENTERPRISE compaq
        VARIABLES  { hostName,
                     scellNameDateTime,
                     agentEventCode,
                     agentEventDescription }
        DESCRIPTION
             "Ema EMU In Load State. Do Not Power Off. Reload EMU Firmware "
           --#TYPE      "Management Agent Event"
           --#SUMMARY   "Host %s : SCellName-TimeDate %s : EventCode %d : Description %s"
           --#ARGUMENTS {0,1,2,3,}
            --#SEVERITY  INFORMATIONAL
            --#TIMEINDEX 136
        ::= 136016040
 
   mngmtAgentTrap-17001 TRAP-TYPE
        ENTERPRISE compaq
        VARIABLES  { hostName,
                     scellNameDateTime,
                     agentEventCode,
                     agentEventDescription }
        DESCRIPTION
             "Drive Code Load Descriptor File Open Error"
           --#TYPE      "Management Agent Event"
           --#SUMMARY   "Host %s : SCellName-TimeDate %s : EventCode %d : Description %s"
           --#ARGUMENTS {0,1,2,3,}
            --#SEVERITY  INFORMATIONAL
            --#TIMEINDEX 136
        ::= 136017001
 
   mngmtAgentTrap-17002 TRAP-TYPE
        ENTERPRISE compaq
        VARIABLES  { hostName,
                     scellNameDateTime,
                     agentEventCode,
                     agentEventDescription }
        DESCRIPTION
             "Drive Code Load Descriptor File Parsing Error - Invalid Line"
           --#TYPE      "Management Agent Event"
           --#SUMMARY   "Host %s : SCellName-TimeDate %s : EventCode %d : Description %s"
           --#ARGUMENTS {0,1,2,3,}
            --#SEVERITY  INFORMATIONAL
            --#TIMEINDEX 136
        ::= 136017002
 
   mngmtAgentTrap-17003 TRAP-TYPE
        ENTERPRISE compaq
        VARIABLES  { hostName,
                     scellNameDateTime,
                     agentEventCode,
                     agentEventDescription }
        DESCRIPTION
             "Drive Code Load Image File Open Error, "
           --#TYPE      "Management Agent Event"
           --#SUMMARY   "Host %s : SCellName-TimeDate %s : EventCode %d : Description %s"
           --#ARGUMENTS {0,1,2,3,}
            --#SEVERITY  INFORMATIONAL
            --#TIMEINDEX 136
        ::= 136017003
 
   mngmtAgentTrap-17004 TRAP-TYPE
        ENTERPRISE compaq
        VARIABLES  { hostName,
                     scellNameDateTime,
                     agentEventCode,
                     agentEventDescription }
        DESCRIPTION
             "Drive Code Load Image File Error Getting File Size"
           --#TYPE      "Management Agent Event"
           --#SUMMARY   "Host %s : SCellName-TimeDate %s : EventCode %d : Description %s"
           --#ARGUMENTS {0,1,2,3,}
            --#SEVERITY  INFORMATIONAL
            --#TIMEINDEX 136
        ::= 136017004
 
   mngmtAgentTrap-17005 TRAP-TYPE
        ENTERPRISE compaq
        VARIABLES  { hostName,
                     scellNameDateTime,
                     agentEventCode,
                     agentEventDescription }
        DESCRIPTION
             "Drive Code Load Image File Buffer Allocation Error"
           --#TYPE      "Management Agent Event"
           --#SUMMARY   "Host %s : SCellName-TimeDate %s : EventCode %d : Description %s"
           --#ARGUMENTS {0,1,2,3,}
            --#SEVERITY  INFORMATIONAL
            --#TIMEINDEX 136
        ::= 136017005
 
   mngmtAgentTrap-17006 TRAP-TYPE
        ENTERPRISE compaq
        VARIABLES  { hostName,
                     scellNameDateTime,
                     agentEventCode,
                     agentEventDescription }
        DESCRIPTION
             "Drive Code Load Image File Read Error"
           --#TYPE      "Management Agent Event"
           --#SUMMARY   "Host %s : SCellName-TimeDate %s : EventCode %d : Description %s"
           --#ARGUMENTS {0,1,2,3,}
            --#SEVERITY  INFORMATIONAL
            --#TIMEINDEX 136
        ::= 136017006
 
   mngmtAgentTrap-17007 TRAP-TYPE
        ENTERPRISE compaq
        VARIABLES  { hostName,
                     scellNameDateTime,
                     agentEventCode,
                     agentEventDescription }
        DESCRIPTION
             "Drive Code Load Drive Firmware Update Failed "
           --#TYPE      "Management Agent Event"
           --#SUMMARY   "Host %s : SCellName-TimeDate %s : EventCode %d : Description %s"
           --#ARGUMENTS {0,1,2,3,}
            --#SEVERITY  CRITICAL
            --#TIMEINDEX 136
        ::= 136017007
 
   mngmtAgentTrap-17008 TRAP-TYPE
        ENTERPRISE compaq
        VARIABLES  { hostName,
                     scellNameDateTime,
                     agentEventCode,
                     agentEventDescription }
        DESCRIPTION
             "Drive Code Load Drive Inquiry Failed"
           --#TYPE      "Management Agent Event"
           --#SUMMARY   "Host %s : SCellName-TimeDate %s : EventCode %d : Description %s"
           --#ARGUMENTS {0,1,2,3,}
            --#SEVERITY  MINOR
            --#TIMEINDEX 136
        ::= 136017008
 
   mngmtAgentTrap-17009 TRAP-TYPE
        ENTERPRISE compaq
        VARIABLES  { hostName,
                     scellNameDateTime,
                     agentEventCode,
                     agentEventDescription }
        DESCRIPTION
             "Drive Code Load Format Command Failed"
           --#TYPE      "Management Agent Event"
           --#SUMMARY   "Host %s : SCellName-TimeDate %s : EventCode %d : Description %s"
           --#ARGUMENTS {0,1,2,3,}
            --#SEVERITY  MINOR
            --#TIMEINDEX 136
        ::= 136017009
 
   mngmtAgentTrap-17012 TRAP-TYPE
        ENTERPRISE compaq
        VARIABLES  { hostName,
                     scellNameDateTime,
                     agentEventCode,
                     agentEventDescription }
        DESCRIPTION
             "Drive Code Load Get Physical Store Condition Failed"
           --#TYPE      "Management Agent Event"
           --#SUMMARY   "Host %s : SCellName-TimeDate %s : EventCode %d : Description %s"
           --#ARGUMENTS {0,1,2,3,}
            --#SEVERITY  INFORMATIONAL
            --#TIMEINDEX 136
        ::= 136017012
 
   mngmtAgentTrap-17013 TRAP-TYPE
        ENTERPRISE compaq
        VARIABLES  { hostName,
                     scellNameDateTime,
                     agentEventCode,
                     agentEventDescription }
        DESCRIPTION
             "Drive Code Load Get Volume Condition Failed"
           --#TYPE      "Management Agent Event"
           --#SUMMARY   "Host %s : SCellName-TimeDate %s : EventCode %d : Description %s"
           --#ARGUMENTS {0,1,2,3,}
            --#SEVERITY  INFORMATIONAL
            --#TIMEINDEX 136
        ::= 136017013
 
   mngmtAgentTrap-17014 TRAP-TYPE
        ENTERPRISE compaq
        VARIABLES  { hostName,
                     scellNameDateTime,
                     agentEventCode,
                     agentEventDescription }
        DESCRIPTION
             "Drive Code Load Drive Spin Up Error"
           --#TYPE      "Management Agent Event"
           --#SUMMARY   "Host %s : SCellName-TimeDate %s : EventCode %d : Description %s"
           --#ARGUMENTS {0,1,2,3,}
            --#SEVERITY  MINOR
            --#TIMEINDEX 136
        ::= 136017014
 
   mngmtAgentTrap-17015 TRAP-TYPE
        ENTERPRISE compaq
        VARIABLES  { hostName,
                     scellNameDateTime,
                     agentEventCode,
                     agentEventDescription }
        DESCRIPTION
             "Drive Code Load - Complete"
           --#TYPE      "Management Agent Event"
           --#SUMMARY   "Host %s : SCellName-TimeDate %s : EventCode %d : Description %s"
           --#ARGUMENTS {0,1,2,3,}
            --#SEVERITY  INFORMATIONAL
            --#TIMEINDEX 136
        ::= 136017015
 
   mngmtAgentTrap-17016 TRAP-TYPE
        ENTERPRISE compaq
        VARIABLES  { hostName,
                     scellNameDateTime,
                     agentEventCode,
                     agentEventDescription }
        DESCRIPTION
             "Drive Code Load Disk Group Migration In Progress"
           --#TYPE      "Management Agent Event"
           --#SUMMARY   "Host %s : SCellName-TimeDate %s : EventCode %d : Description %s"
           --#ARGUMENTS {0,1,2,3,}
            --#SEVERITY  INFORMATIONAL
            --#TIMEINDEX 136
        ::= 136017016
 
   mngmtAgentTrap-17017 TRAP-TYPE
        ENTERPRISE compaq
        VARIABLES  { hostName,
                     scellNameDateTime,
                     agentEventCode,
                     agentEventDescription }
        DESCRIPTION
             "Drive Code Load Unable To Code Load Disks Part Of A Group "
           --#TYPE      "Management Agent Event"
           --#SUMMARY   "Host %s : SCellName-TimeDate %s : EventCode %d : Description %s"
           --#ARGUMENTS {0,1,2,3,}
            --#SEVERITY  INFORMATIONAL
            --#TIMEINDEX 136
        ::= 136017017
 
   mngmtAgentTrap-18001 TRAP-TYPE
        ENTERPRISE compaq
        VARIABLES  { hostName,
                     scellNameDateTime,
                     agentEventCode,
                     agentEventDescription }
        DESCRIPTION
             "Api Created Element Success"
           --#TYPE      "Management Agent Event"
           --#SUMMARY   "Host %s : SCellName-TimeDate %s : EventCode %d : Description %s"
           --#ARGUMENTS {0,1,2,3,}
            --#SEVERITY  INFORMATIONAL
            --#TIMEINDEX 136
        ::= 136018001
 
   mngmtAgentTrap-18002 TRAP-TYPE
        ENTERPRISE compaq
        VARIABLES  { hostName,
                     scellNameDateTime,
                     agentEventCode,
                     agentEventDescription }
        DESCRIPTION
             "Api Created Storage Success"
           --#TYPE      "Management Agent Event"
           --#SUMMARY   "Host %s : SCellName-TimeDate %s : EventCode %d : Description %s"
           --#ARGUMENTS {0,1,2,3,}
            --#SEVERITY  INFORMATIONAL
            --#TIMEINDEX 136
        ::= 136018002
 
   mngmtAgentTrap-18003 TRAP-TYPE
        ENTERPRISE compaq
        VARIABLES  { hostName,
                     scellNameDateTime,
                     agentEventCode,
                     agentEventDescription }
        DESCRIPTION
             "Api Created Storage Client Success"
           --#TYPE      "Management Agent Event"
           --#SUMMARY   "Host %s : SCellName-TimeDate %s : EventCode %d : Description %s"
           --#ARGUMENTS {0,1,2,3,}
            --#SEVERITY  INFORMATIONAL
            --#TIMEINDEX 136
        ::= 136018003
 
   mngmtAgentTrap-18004 TRAP-TYPE
        ENTERPRISE compaq
        VARIABLES  { hostName,
                     scellNameDateTime,
                     agentEventCode,
                     agentEventDescription }
        DESCRIPTION
             "Api Set Storage Success"
           --#TYPE      "Management Agent Event"
           --#SUMMARY   "Host %s : SCellName-TimeDate %s : EventCode %d : Description %s"
           --#ARGUMENTS {0,1,2,3,}
            --#SEVERITY  INFORMATIONAL
            --#TIMEINDEX 136
        ::= 136018004
 
   mngmtAgentTrap-18005 TRAP-TYPE
        ENTERPRISE compaq
        VARIABLES  { hostName,
                     scellNameDateTime,
                     agentEventCode,
                     agentEventDescription }
        DESCRIPTION
             "Api Set Element Success"
           --#TYPE      "Management Agent Event"
           --#SUMMARY   "Host %s : SCellName-TimeDate %s : EventCode %d : Description %s"
           --#ARGUMENTS {0,1,2,3,}
            --#SEVERITY  INFORMATIONAL
            --#TIMEINDEX 136
        ::= 136018005
 
   mngmtAgentTrap-18006 TRAP-TYPE
        ENTERPRISE compaq
        VARIABLES  { hostName,
                     scellNameDateTime,
                     agentEventCode,
                     agentEventDescription }
        DESCRIPTION
             "Api Deleted Element Success"
           --#TYPE      "Management Agent Event"
           --#SUMMARY   "Host %s : SCellName-TimeDate %s : EventCode %d : Description %s"
           --#ARGUMENTS {0,1,2,3,}
            --#SEVERITY  INFORMATIONAL
            --#TIMEINDEX 136
        ::= 136018006
 
   mngmtAgentTrap-18007 TRAP-TYPE
        ENTERPRISE compaq
        VARIABLES  { hostName,
                     scellNameDateTime,
                     agentEventCode,
                     agentEventDescription }
        DESCRIPTION
             "Api Deleted Storage Success"
           --#TYPE      "Management Agent Event"
           --#SUMMARY   "Host %s : SCellName-TimeDate %s : EventCode %d : Description %s"
           --#ARGUMENTS {0,1,2,3,}
            --#SEVERITY  INFORMATIONAL
            --#TIMEINDEX 136
        ::= 136018007
 
   mngmtAgentTrap-18008 TRAP-TYPE
        ENTERPRISE compaq
        VARIABLES  { hostName,
                     scellNameDateTime,
                     agentEventCode,
                     agentEventDescription }
        DESCRIPTION
             "Api Deleted Storage Client Success"
           --#TYPE      "Management Agent Event"
           --#SUMMARY   "Host %s : SCellName-TimeDate %s : EventCode %d : Description %s"
           --#ARGUMENTS {0,1,2,3,}
            --#SEVERITY  INFORMATIONAL
            --#TIMEINDEX 136
        ::= 136018008
 
   mngmtAgentTrap-18009 TRAP-TYPE
        ENTERPRISE compaq
        VARIABLES  { hostName,
                     scellNameDateTime,
                     agentEventCode,
                     agentEventDescription }
        DESCRIPTION
             "Api Created Snapshot Success	"
           --#TYPE      "Management Agent Event"
           --#SUMMARY   "Host %s : SCellName-TimeDate %s : EventCode %d : Description %s"
           --#ARGUMENTS {0,1,2,3,}
            --#SEVERITY  INFORMATIONAL
            --#TIMEINDEX 136
        ::= 136018009
 
   mngmtAgentTrap-18010 TRAP-TYPE
        ENTERPRISE compaq
        VARIABLES  { hostName,
                     scellNameDateTime,
                     agentEventCode,
                     agentEventDescription }
        DESCRIPTION
             "Api Created Clone Success"
           --#TYPE      "Management Agent Event"
           --#SUMMARY   "Host %s : SCellName-TimeDate %s : EventCode %d : Description %s"
           --#ARGUMENTS {0,1,2,3,}
            --#SEVERITY  INFORMATIONAL
            --#TIMEINDEX 136
        ::= 136018010
 
   mngmtAgentTrap-18018 TRAP-TYPE
        ENTERPRISE compaq
        VARIABLES  { hostName,
                     scellNameDateTime,
                     agentEventCode,
                     agentEventDescription }
        DESCRIPTION
             "Api Unable To Get The Lock"
           --#TYPE      "Management Agent Event"
           --#SUMMARY   "Host %s : SCellName-TimeDate %s : EventCode %d : Description %s"
           --#ARGUMENTS {0,1,2,3,}
            --#SEVERITY  INFORMATIONAL
            --#TIMEINDEX 136
        ::= 136018018
 
   mngmtAgentTrap-18019 TRAP-TYPE
        ENTERPRISE compaq
        VARIABLES  { hostName,
                     scellNameDateTime,
                     agentEventCode,
                     agentEventDescription }
        DESCRIPTION
             "Api Created PresentedUnit Success"
           --#TYPE      "Management Agent Event"
           --#SUMMARY   "Host %s : SCellName-TimeDate %s : EventCode %d : Description %s"
           --#ARGUMENTS {0,1,2,3,}
            --#SEVERITY  INFORMATIONAL
            --#TIMEINDEX 136
        ::= 136018019
 
   mngmtAgentTrap-18022 TRAP-TYPE
        ENTERPRISE compaq
        VARIABLES  { hostName,
                     scellNameDateTime,
                     agentEventCode,
                     agentEventDescription }
        DESCRIPTION
             "Api Create DiskGroup Success"
           --#TYPE      "Management Agent Event"
           --#SUMMARY   "Host %s : SCellName-TimeDate %s : EventCode %d : Description %s"
           --#ARGUMENTS {0,1,2,3,}
            --#SEVERITY  INFORMATIONAL
            --#TIMEINDEX 136
        ::= 136018022
 
   mngmtAgentTrap-18024 TRAP-TYPE
        ENTERPRISE compaq
        VARIABLES  { hostName,
                     scellNameDateTime,
                     agentEventCode,
                     agentEventDescription }
        DESCRIPTION
             "Api Create Folder Success"
           --#TYPE      "Management Agent Event"
           --#SUMMARY   "Host %s : SCellName-TimeDate %s : EventCode %d : Description %s"
           --#ARGUMENTS {0,1,2,3,}
            --#SEVERITY  INFORMATIONAL
            --#TIMEINDEX 136
        ::= 136018024
 
   mngmtAgentTrap-18025 TRAP-TYPE
        ENTERPRISE compaq
        VARIABLES  { hostName,
                     scellNameDateTime,
                     agentEventCode,
                     agentEventDescription }
        DESCRIPTION
             "Api Delete Folder Success"
           --#TYPE      "Management Agent Event"
           --#SUMMARY   "Host %s : SCellName-TimeDate %s : EventCode %d : Description %s"
           --#ARGUMENTS {0,1,2,3,}
            --#SEVERITY  INFORMATIONAL
            --#TIMEINDEX 136
        ::= 136018025
 
   mngmtAgentTrap-18028 TRAP-TYPE
        ENTERPRISE compaq
        VARIABLES  { hostName,
                     scellNameDateTime,
                     agentEventCode,
                     agentEventDescription }
        DESCRIPTION
             "Api Set Folder Success"
           --#TYPE      "Management Agent Event"
           --#SUMMARY   "Host %s : SCellName-TimeDate %s : EventCode %d : Description %s"
           --#ARGUMENTS {0,1,2,3,}
            --#SEVERITY  INFORMATIONAL
            --#TIMEINDEX 136
        ::= 136018028
 
   mngmtAgentTrap-18034 TRAP-TYPE
        ENTERPRISE compaq
        VARIABLES  { hostName,
                     scellNameDateTime,
                     agentEventCode,
                     agentEventDescription }
        DESCRIPTION
             "Api Invalid User Name Or Password Error"
           --#TYPE      "Management Agent Event"
           --#SUMMARY   "Host %s : SCellName-TimeDate %s : EventCode %d : Description %s"
           --#ARGUMENTS {0,1,2,3,}
            --#SEVERITY  INFORMATIONAL
            --#TIMEINDEX 136
        ::= 136018034
 
   mngmtAgentTrap-18036 TRAP-TYPE
        ENTERPRISE compaq
        VARIABLES  { hostName,
                     scellNameDateTime,
                     agentEventCode,
                     agentEventDescription }
        DESCRIPTION
             "Api Delete Presented Unit Success"
           --#TYPE      "Management Agent Event"
           --#SUMMARY   "Host %s : SCellName-TimeDate %s : EventCode %d : Description %s"
           --#ARGUMENTS {0,1,2,3,}
            --#SEVERITY  INFORMATIONAL
            --#TIMEINDEX 136
        ::= 136018036
 
   mngmtAgentTrap-18038 TRAP-TYPE
        ENTERPRISE compaq
        VARIABLES  { hostName,
                     scellNameDateTime,
                     agentEventCode,
                     agentEventDescription }
        DESCRIPTION
             "Api Set Diskgroup Success                         "
           --#TYPE      "Management Agent Event"
           --#SUMMARY   "Host %s : SCellName-TimeDate %s : EventCode %d : Description %s"
           --#ARGUMENTS {0,1,2,3,}
            --#SEVERITY  INFORMATIONAL
            --#TIMEINDEX 136
        ::= 136018038
 
   mngmtAgentTrap-18039 TRAP-TYPE
        ENTERPRISE compaq
        VARIABLES  { hostName,
                     scellNameDateTime,
                     agentEventCode,
                     agentEventDescription }
        DESCRIPTION
             "Api Set Disk Success"
           --#TYPE      "Management Agent Event"
           --#SUMMARY   "Host %s : SCellName-TimeDate %s : EventCode %d : Description %s"
           --#ARGUMENTS {0,1,2,3,}
            --#SEVERITY  INFORMATIONAL
            --#TIMEINDEX 136
        ::= 136018039
 
   mngmtAgentTrap-18040 TRAP-TYPE
        ENTERPRISE compaq
        VARIABLES  { hostName,
                     scellNameDateTime,
                     agentEventCode,
                     agentEventDescription }
        DESCRIPTION
             "Api Delete Storage Family Success "
           --#TYPE      "Management Agent Event"
           --#SUMMARY   "Host %s : SCellName-TimeDate %s : EventCode %d : Description %s"
           --#ARGUMENTS {0,1,2,3,}
            --#SEVERITY  INFORMATIONAL
            --#TIMEINDEX 136
        ::= 136018040
 
   mngmtAgentTrap-18041 TRAP-TYPE
        ENTERPRISE compaq
        VARIABLES  { hostName,
                     scellNameDateTime,
                     agentEventCode,
                     agentEventDescription }
        DESCRIPTION
             "Api Set Storage Family Success"
           --#TYPE      "Management Agent Event"
           --#SUMMARY   "Host %s : SCellName-TimeDate %s : EventCode %d : Description %s"
           --#ARGUMENTS {0,1,2,3,}
            --#SEVERITY  INFORMATIONAL
            --#TIMEINDEX 136
        ::= 136018041
 
   mngmtAgentTrap-18042 TRAP-TYPE
        ENTERPRISE compaq
        VARIABLES  { hostName,
                     scellNameDateTime,
                     agentEventCode,
                     agentEventDescription }
        DESCRIPTION
             "Api Control Memory Allocation Failure"
           --#TYPE      "Management Agent Event"
           --#SUMMARY   "Host %s : SCellName-TimeDate %s : EventCode %d : Description %s"
           --#ARGUMENTS {0,1,2,3,}
            --#SEVERITY  INFORMATIONAL
            --#TIMEINDEX 136
        ::= 136018042
 
   mngmtAgentTrap-18045 TRAP-TYPE
        ENTERPRISE compaq
        VARIABLES  { hostName,
                     scellNameDateTime,
                     agentEventCode,
                     agentEventDescription }
        DESCRIPTION
             "Api Element Codeload Success   "
           --#TYPE      "Management Agent Event"
           --#SUMMARY   "Host %s : SCellName-TimeDate %s : EventCode %d : Description %s"
           --#ARGUMENTS {0,1,2,3,}
            --#SEVERITY  INFORMATIONAL
            --#TIMEINDEX 136
        ::= 136018045
 
   mngmtAgentTrap-18047 TRAP-TYPE
        ENTERPRISE compaq
        VARIABLES  { hostName,
                     scellNameDateTime,
                     agentEventCode,
                     agentEventDescription }
        DESCRIPTION
             "Api Disk Codeload Success"
           --#TYPE      "Management Agent Event"
           --#SUMMARY   "Host %s : SCellName-TimeDate %s : EventCode %d : Description %s"
           --#ARGUMENTS {0,1,2,3,}
            --#SEVERITY  INFORMATIONAL
            --#TIMEINDEX 136
        ::= 136018047
 
   mngmtAgentTrap-18048 TRAP-TYPE
        ENTERPRISE compaq
        VARIABLES  { hostName,
                     scellNameDateTime,
                     agentEventCode,
                     agentEventDescription }
        DESCRIPTION
             "Api Monitor Codeload Success"
           --#TYPE      "Management Agent Event"
           --#SUMMARY   "Host %s : SCellName-TimeDate %s : EventCode %d : Description %s"
           --#ARGUMENTS {0,1,2,3,}
            --#SEVERITY  INFORMATIONAL
            --#TIMEINDEX 136
        ::= 136018048
 
   mngmtAgentTrap-18049 TRAP-TYPE
        ENTERPRISE compaq
        VARIABLES  { hostName,
                     scellNameDateTime,
                     agentEventCode,
                     agentEventDescription }
        DESCRIPTION
             "Api Added Port WWID Success"
           --#TYPE      "Management Agent Event"
           --#SUMMARY   "Host %s : SCellName-TimeDate %s : EventCode %d : Description %s"
           --#ARGUMENTS {0,1,2,3,}
            --#SEVERITY  INFORMATIONAL
            --#TIMEINDEX 136
        ::= 136018049
 
   mngmtAgentTrap-18050 TRAP-TYPE
        ENTERPRISE compaq
        VARIABLES  { hostName,
                     scellNameDateTime,
                     agentEventCode,
                     agentEventDescription }
        DESCRIPTION
             "Api Set Storage Client Success"
           --#TYPE      "Management Agent Event"
           --#SUMMARY   "Host %s : SCellName-TimeDate %s : EventCode %d : Description %s"
           --#ARGUMENTS {0,1,2,3,}
            --#SEVERITY  INFORMATIONAL
            --#TIMEINDEX 136
        ::= 136018050
 
   mngmtAgentTrap-18051 TRAP-TYPE
        ENTERPRISE compaq
        VARIABLES  { hostName,
                     scellNameDateTime,
                     agentEventCode,
                     agentEventDescription }
        DESCRIPTION
             "Api Invalid Operation"
           --#TYPE      "Management Agent Event"
           --#SUMMARY   "Host %s : SCellName-TimeDate %s : EventCode %d : Description %s"
           --#ARGUMENTS {0,1,2,3,}
            --#SEVERITY  INFORMATIONAL
            --#TIMEINDEX 136
        ::= 136018051
 
   mngmtAgentTrap-18052 TRAP-TYPE
        ENTERPRISE compaq
        VARIABLES  { hostName,
                     scellNameDateTime,
                     agentEventCode,
                     agentEventDescription }
        DESCRIPTION
             "Api Deleted Port WWID Success"
           --#TYPE      "Management Agent Event"
           --#SUMMARY   "Host %s : SCellName-TimeDate %s : EventCode %d : Description %s"
           --#ARGUMENTS {0,1,2,3,}
            --#SEVERITY  INFORMATIONAL
            --#TIMEINDEX 136
        ::= 136018052
 
   mngmtAgentTrap-18059 TRAP-TYPE
        ENTERPRISE compaq
        VARIABLES  { hostName,
                     scellNameDateTime,
                     agentEventCode,
                     agentEventDescription }
        DESCRIPTION
             "Api Set Power Success"
           --#TYPE      "Management Agent Event"
           --#SUMMARY   "Host %s : SCellName-TimeDate %s : EventCode %d : Description %s"
           --#ARGUMENTS {0,1,2,3,}
            --#SEVERITY  INFORMATIONAL
            --#TIMEINDEX 136
        ::= 136018059
 
   mngmtAgentTrap-18060 TRAP-TYPE
        ENTERPRISE compaq
        VARIABLES  { hostName,
                     scellNameDateTime,
                     agentEventCode,
                     agentEventDescription }
        DESCRIPTION
             "Api Element Is Not Initialized"
           --#TYPE      "Management Agent Event"
           --#SUMMARY   "Host %s : SCellName-TimeDate %s : EventCode %d : Description %s"
           --#ARGUMENTS {0,1,2,3,}
            --#SEVERITY  INFORMATIONAL
            --#TIMEINDEX 136
        ::= 136018060
 
   mngmtAgentTrap-18063 TRAP-TYPE
        ENTERPRISE compaq
        VARIABLES  { hostName,
                     scellNameDateTime,
                     agentEventCode,
                     agentEventDescription }
        DESCRIPTION
             "Api Error trying to delete a disk group"
           --#TYPE      "Management Agent Event"
           --#SUMMARY   "Host %s : SCellName-TimeDate %s : EventCode %d : Description %s"
           --#ARGUMENTS {0,1,2,3,}
            --#SEVERITY  INFORMATIONAL
            --#TIMEINDEX 136
        ::= 136018063
 
   mngmtAgentTrap-18065 TRAP-TYPE
        ENTERPRISE compaq
        VARIABLES  { hostName,
                     scellNameDateTime,
                     agentEventCode,
                     agentEventDescription }
        DESCRIPTION
             "Api A storage (Vdisk) operation is in progress. Try again later."
           --#TYPE      "Management Agent Event"
           --#SUMMARY   "Host %s : SCellName-TimeDate %s : EventCode %d : Description %s"
           --#ARGUMENTS {0,1,2,3,}
            --#SEVERITY  INFORMATIONAL
            --#TIMEINDEX 136
        ::= 136018065
 
   mngmtAgentTrap-18066 TRAP-TYPE
        ENTERPRISE compaq
        VARIABLES  { hostName,
                     scellNameDateTime,
                     agentEventCode,
                     agentEventDescription }
        DESCRIPTION
             "Api The storage (Vdisk) condition is invalid. The storage may be in error. Try again later."
           --#TYPE      "Management Agent Event"
           --#SUMMARY   "Host %s : SCellName-TimeDate %s : EventCode %d : Description %s"
           --#ARGUMENTS {0,1,2,3,}
            --#SEVERITY  INFORMATIONAL
            --#TIMEINDEX 136
        ::= 136018066
 
   mngmtAgentTrap-18067 TRAP-TYPE
        ENTERPRISE compaq
        VARIABLES  { hostName,
                     scellNameDateTime,
                     agentEventCode,
                     agentEventDescription }
        DESCRIPTION
             "Api Error calling get Vdisk condition. Vdisk may be deleted. Try again later."
           --#TYPE      "Management Agent Event"
           --#SUMMARY   "Host %s : SCellName-TimeDate %s : EventCode %d : Description %s"
           --#ARGUMENTS {0,1,2,3,}
            --#SEVERITY  INFORMATIONAL
            --#TIMEINDEX 136
        ::= 136018067
 
   mngmtAgentTrap-18068 TRAP-TYPE
        ENTERPRISE compaq
        VARIABLES  { hostName,
                     scellNameDateTime,
                     agentEventCode,
                     agentEventDescription }
        DESCRIPTION
             "Api Invalid initialization of the API. Cannot start monitoring process. Storage system management limited."
           --#TYPE      "Management Agent Event"
           --#SUMMARY   "Host %s : SCellName-TimeDate %s : EventCode %d : Description %s"
           --#ARGUMENTS {0,1,2,3,}
            --#SEVERITY  INFORMATIONAL
            --#TIMEINDEX 136
        ::= 136018068
 
   mngmtAgentTrap-18070 TRAP-TYPE
        ENTERPRISE compaq
        VARIABLES  { hostName,
                     scellNameDateTime,
                     agentEventCode,
                     agentEventDescription }
        DESCRIPTION
             "Api A command is currently under execution from another API call. Try again later."
           --#TYPE      "Management Agent Event"
           --#SUMMARY   "Host %s : SCellName-TimeDate %s : EventCode %d : Description %s"
           --#ARGUMENTS {0,1,2,3,}
            --#SEVERITY  INFORMATIONAL
            --#TIMEINDEX 136
        ::= 136018070
 
   mngmtAgentTrap-18071 TRAP-TYPE
        ENTERPRISE compaq
        VARIABLES  { hostName,
                     scellNameDateTime,
                     agentEventCode,
                     agentEventDescription }
        DESCRIPTION
             "Api The server has not completed initialization, cannot process the request."
           --#TYPE      "Management Agent Event"
           --#SUMMARY   "Host %s : SCellName-TimeDate %s : EventCode %d : Description %s"
           --#ARGUMENTS {0,1,2,3,}
            --#SEVERITY  INFORMATIONAL
            --#TIMEINDEX 136
        ::= 136018071
 
   mngmtAgentTrap-18073 TRAP-TYPE
        ENTERPRISE compaq
        VARIABLES  { hostName,
                     scellNameDateTime,
                     agentEventCode,
                     agentEventDescription }
        DESCRIPTION
             "Api Removal of disk from disk group successful"
           --#TYPE      "Management Agent Event"
           --#SUMMARY   "Host %s : SCellName-TimeDate %s : EventCode %d : Description %s"
           --#ARGUMENTS {0,1,2,3,}
            --#SEVERITY  INFORMATIONAL
            --#TIMEINDEX 136
        ::= 136018073
 
   mngmtAgentTrap-18074 TRAP-TYPE
        ENTERPRISE compaq
        VARIABLES  { hostName,
                     scellNameDateTime,
                     agentEventCode,
                     agentEventDescription }
        DESCRIPTION
             "Api Disk(s) added to disk group successfully"
           --#TYPE      "Management Agent Event"
           --#SUMMARY   "Host %s : SCellName-TimeDate %s : EventCode %d : Description %s"
           --#ARGUMENTS {0,1,2,3,}
            --#SEVERITY  INFORMATIONAL
            --#TIMEINDEX 136
        ::= 136018074
 
   mngmtAgentTrap-18075 TRAP-TYPE
        ENTERPRISE compaq
        VARIABLES  { hostName,
                     scellNameDateTime,
                     agentEventCode,
                     agentEventDescription }
        DESCRIPTION
             "Api Modify monitor properties successful"
           --#TYPE      "Management Agent Event"
           --#SUMMARY   "Host %s : SCellName-TimeDate %s : EventCode %d : Description %s"
           --#ARGUMENTS {0,1,2,3,}
            --#SEVERITY  INFORMATIONAL
            --#TIMEINDEX 136
        ::= 136018075
 
   mngmtAgentTrap-18076 TRAP-TYPE
        ENTERPRISE compaq
        VARIABLES  { hostName,
                     scellNameDateTime,
                     agentEventCode,
                     agentEventDescription }
        DESCRIPTION
             "Api Element name too long. Maximum is 20 characters."
           --#TYPE      "Management Agent Event"
           --#SUMMARY   "Host %s : SCellName-TimeDate %s : EventCode %d : Description %s"
           --#ARGUMENTS {0,1,2,3,}
            --#SEVERITY  INFORMATIONAL
            --#TIMEINDEX 136
        ::= 136018076
 
   mngmtAgentTrap-18080 TRAP-TYPE
        ENTERPRISE compaq
        VARIABLES  { hostName,
                     scellNameDateTime,
                     agentEventCode,
                     agentEventDescription }
        DESCRIPTION
             "Api The snapshot/Snapclone license cannot be validated. Either the license key has not been entered, or there is a system communication failure."
           --#TYPE      "Management Agent Event"
           --#SUMMARY   "Host %s : SCellName-TimeDate %s : EventCode %d : Description %s"
           --#ARGUMENTS {0,1,2,3,}
            --#SEVERITY  INFORMATIONAL
            --#TIMEINDEX 136
        ::= 136018080
 
   mngmtAgentTrap-18081 TRAP-TYPE
        ENTERPRISE compaq
        VARIABLES  { hostName,
                     scellNameDateTime,
                     agentEventCode,
                     agentEventDescription }
        DESCRIPTION
             "Api The folder operation is not valid for the specified folder. Either the folder is a root folder and cannot be modified, or it is a disk group folder for which you should use 'Set Group' command."
           --#TYPE      "Management Agent Event"
           --#SUMMARY   "Host %s : SCellName-TimeDate %s : EventCode %d : Description %s"
           --#ARGUMENTS {0,1,2,3,}
            --#SEVERITY  INFORMATIONAL
            --#TIMEINDEX 136
        ::= 136018081
 
   mngmtAgentTrap-20001 TRAP-TYPE
        ENTERPRISE compaq
        VARIABLES  { hostName,
                     scellNameDateTime,
                     agentEventCode,
                     agentEventDescription }
        DESCRIPTION
             "LicMngr Memory Allocation Failure"
           --#TYPE      "Management Agent Event"
           --#SUMMARY   "Host %s : SCellName-TimeDate %s : EventCode %d : Description %s"
           --#ARGUMENTS {0,1,2,3,}
            --#SEVERITY  CRITICAL
            --#TIMEINDEX 136
        ::= 136020001
 
   mngmtAgentTrap-20002 TRAP-TYPE
        ENTERPRISE compaq
        VARIABLES  { hostName,
                     scellNameDateTime,
                     agentEventCode,
                     agentEventDescription }
        DESCRIPTION
             "LicMngr Startup Complete"
           --#TYPE      "Management Agent Event"
           --#SUMMARY   "Host %s : SCellName-TimeDate %s : EventCode %d : Description %s"
           --#ARGUMENTS {0,1,2,3,}
            --#SEVERITY  INFORMATIONAL
            --#TIMEINDEX 136
        ::= 136020002
 
   mngmtAgentTrap-20003 TRAP-TYPE
        ENTERPRISE compaq
        VARIABLES  { hostName,
                     scellNameDateTime,
                     agentEventCode,
                     agentEventDescription }
        DESCRIPTION
             "LicMngr Startup Failed"
           --#TYPE      "Management Agent Event"
           --#SUMMARY   "Host %s : SCellName-TimeDate %s : EventCode %d : Description %s"
           --#ARGUMENTS {0,1,2,3,}
            --#SEVERITY  CRITICAL
            --#TIMEINDEX 136
        ::= 136020003
 
   mngmtAgentTrap-20004 TRAP-TYPE
        ENTERPRISE compaq
        VARIABLES  { hostName,
                     scellNameDateTime,
                     agentEventCode,
                     agentEventDescription }
        DESCRIPTION
             "License successfully checked out"
           --#TYPE      "Management Agent Event"
           --#SUMMARY   "Host %s : SCellName-TimeDate %s : EventCode %d : Description %s"
           --#ARGUMENTS {0,1,2,3,}
            --#SEVERITY  INFORMATIONAL
            --#TIMEINDEX 136
        ::= 136020004
 
   mngmtAgentTrap-20005 TRAP-TYPE
        ENTERPRISE compaq
        VARIABLES  { hostName,
                     scellNameDateTime,
                     agentEventCode,
                     agentEventDescription }
        DESCRIPTION
             "License checkout failed"
           --#TYPE      "Management Agent Event"
           --#SUMMARY   "Host %s : SCellName-TimeDate %s : EventCode %d : Description %s"
           --#ARGUMENTS {0,1,2,3,}
            --#SEVERITY  MINOR
            --#TIMEINDEX 136
        ::= 136020005
 
   mngmtAgentTrap-20011 TRAP-TYPE
        ENTERPRISE compaq
        VARIABLES  { hostName,
                     scellNameDateTime,
                     agentEventCode,
                     agentEventDescription }
        DESCRIPTION
             "License Line has an incorrect format"
           --#TYPE      "Management Agent Event"
           --#SUMMARY   "Host %s : SCellName-TimeDate %s : EventCode %d : Description %s"
           --#ARGUMENTS {0,1,2,3,}
            --#SEVERITY  MINOR
            --#TIMEINDEX 136
        ::= 136020011
 
   mngmtAgentTrap-20013 TRAP-TYPE
        ENTERPRISE compaq
        VARIABLES  { hostName,
                     scellNameDateTime,
                     agentEventCode,
                     agentEventDescription }
        DESCRIPTION
             "License Library runtime error"
           --#TYPE      "Management Agent Event"
           --#SUMMARY   "Host %s : SCellName-TimeDate %s : EventCode %d : Description %s"
           --#ARGUMENTS {0,1,2,3,}
            --#SEVERITY  CRITICAL
            --#TIMEINDEX 136
        ::= 136020013
 
   mngmtAgentTrap-20015 TRAP-TYPE
        ENTERPRISE compaq
        VARIABLES  { hostName,
                     scellNameDateTime,
                     agentEventCode,
                     agentEventDescription }
        DESCRIPTION
             "Failed to retrieve Node WWN from storage system"
           --#TYPE      "Management Agent Event"
           --#SUMMARY   "Host %s : SCellName-TimeDate %s : EventCode %d : Description %s"
           --#ARGUMENTS {0,1,2,3,}
            --#SEVERITY  MINOR
            --#TIMEINDEX 136
        ::= 136020015
 
   mngmtAgentTrap-20016 TRAP-TYPE
        ENTERPRISE compaq
        VARIABLES  { hostName,
                     scellNameDateTime,
                     agentEventCode,
                     agentEventDescription }
        DESCRIPTION
             "Failed to retrieve license list from MLD"
           --#TYPE      "Management Agent Event"
           --#SUMMARY   "Host %s : SCellName-TimeDate %s : EventCode %d : Description %s"
           --#ARGUMENTS {0,1,2,3,}
            --#SEVERITY  MINOR
            --#TIMEINDEX 136
        ::= 136020016
 
   mngmtAgentTrap-20017 TRAP-TYPE
        ENTERPRISE compaq
        VARIABLES  { hostName,
                     scellNameDateTime,
                     agentEventCode,
                     agentEventDescription }
        DESCRIPTION
             "Failed to write license list to MLD"
           --#TYPE      "Management Agent Event"
           --#SUMMARY   "Host %s : SCellName-TimeDate %s : EventCode %d : Description %s"
           --#ARGUMENTS {0,1,2,3,}
            --#SEVERITY  MINOR
            --#TIMEINDEX 136
        ::= 136020017
 
   mngmtAgentTrap-20018 TRAP-TYPE
        ENTERPRISE compaq
        VARIABLES  { hostName,
                     scellNameDateTime,
                     agentEventCode,
                     agentEventDescription }
        DESCRIPTION
             "This license line appears to be invalid"
           --#TYPE      "Management Agent Event"
           --#SUMMARY   "Host %s : SCellName-TimeDate %s : EventCode %d : Description %s"
           --#ARGUMENTS {0,1,2,3,}
            --#SEVERITY  MINOR
            --#TIMEINDEX 136
        ::= 136020018
 
   mngmtAgentTrap-20019 TRAP-TYPE
        ENTERPRISE compaq
        VARIABLES  { hostName,
                     scellNameDateTime,
                     agentEventCode,
                     agentEventDescription }
        DESCRIPTION
             "MLD Manager Handle is NULL - unable to update MLD License List"
           --#TYPE      "Management Agent Event"
           --#SUMMARY   "Host %s : SCellName-TimeDate %s : EventCode %d : Description %s"
           --#ARGUMENTS {0,1,2,3,}
            --#SEVERITY  MINOR
            --#TIMEINDEX 136
        ::= 136020019
 
   mngmtAgentTrap-20020 TRAP-TYPE
        ENTERPRISE compaq
        VARIABLES  { hostName,
                     scellNameDateTime,
                     agentEventCode,
                     agentEventDescription }
        DESCRIPTION
             "LicMngr: Storage system handle is NULL"
           --#TYPE      "Management Agent Event"
           --#SUMMARY   "Host %s : SCellName-TimeDate %s : EventCode %d : Description %s"
           --#ARGUMENTS {0,1,2,3,}
            --#SEVERITY  CRITICAL
            --#TIMEINDEX 136
        ::= 136020020
 
   mngmtAgentTrap-20021 TRAP-TYPE
        ENTERPRISE compaq
        VARIABLES  { hostName,
                     scellNameDateTime,
                     agentEventCode,
                     agentEventDescription }
        DESCRIPTION
             "The license you entered is a valid license but not for the Node WWN and/or firmware version on this controller pair"
           --#TYPE      "Management Agent Event"
           --#SUMMARY   "Host %s : SCellName-TimeDate %s : EventCode %d : Description %s"
           --#ARGUMENTS {0,1,2,3,}
            --#SEVERITY  INFORMATIONAL
            --#TIMEINDEX 136
        ::= 136020021
 
   mngmtAgentTrap-20022 TRAP-TYPE
        ENTERPRISE compaq
        VARIABLES  { hostName,
                     scellNameDateTime,
                     agentEventCode,
                     agentEventDescription }
        DESCRIPTION
             "Function name string is null or in an incorrect format"
           --#TYPE      "Management Agent Event"
           --#SUMMARY   "Host %s : SCellName-TimeDate %s : EventCode %d : Description %s"
           --#ARGUMENTS {0,1,2,3,}
            --#SEVERITY  INFORMATIONAL
            --#TIMEINDEX 136
        ::= 136020022
 
   mngmtAgentTrap-20023 TRAP-TYPE
        ENTERPRISE compaq
        VARIABLES  { hostName,
                     scellNameDateTime,
                     agentEventCode,
                     agentEventDescription }
        DESCRIPTION
             "Version string is null or in an incorrect format"
           --#TYPE      "Management Agent Event"
           --#SUMMARY   "Host %s : SCellName-TimeDate %s : EventCode %d : Description %s"
           --#ARGUMENTS {0,1,2,3,}
            --#SEVERITY  INFORMATIONAL
            --#TIMEINDEX 136
        ::= 136020023
 
   mngmtAgentTrap-21001 TRAP-TYPE
        ENTERPRISE compaq
        VARIABLES  { hostName,
                     scellNameDateTime,
                     agentEventCode,
                     agentEventDescription }
        DESCRIPTION
             "HSV Upgrade Manager Image File Open Error"
           --#TYPE      "Management Agent Event"
           --#SUMMARY   "Host %s : SCellName-TimeDate %s : EventCode %d : Description %s"
           --#ARGUMENTS {0,1,2,3,}
            --#SEVERITY  INFORMATIONAL
            --#TIMEINDEX 136
        ::= 136021001
 
   mngmtAgentTrap-21002 TRAP-TYPE
        ENTERPRISE compaq
        VARIABLES  { hostName,
                     scellNameDateTime,
                     agentEventCode,
                     agentEventDescription }
        DESCRIPTION
             "HSV Upgrade Manager Image File Buffer Allocation Error"
           --#TYPE      "Management Agent Event"
           --#SUMMARY   "Host %s : SCellName-TimeDate %s : EventCode %d : Description %s"
           --#ARGUMENTS {0,1,2,3,}
            --#SEVERITY  INFORMATIONAL
            --#TIMEINDEX 136
        ::= 136021002
 
   mngmtAgentTrap-21003 TRAP-TYPE
        ENTERPRISE compaq
        VARIABLES  { hostName,
                     scellNameDateTime,
                     agentEventCode,
                     agentEventDescription }
        DESCRIPTION
             "HSV Upgrade Manager Image File Read Error"
           --#TYPE      "Management Agent Event"
           --#SUMMARY   "Host %s : SCellName-TimeDate %s : EventCode %d : Description %s"
           --#ARGUMENTS {0,1,2,3,}
            --#SEVERITY  INFORMATIONAL
            --#TIMEINDEX 136
        ::= 136021003
 
   mngmtAgentTrap-21004 TRAP-TYPE
        ENTERPRISE compaq
        VARIABLES  { hostName,
                     scellNameDateTime,
                     agentEventCode,
                     agentEventDescription }
        DESCRIPTION
             "HSV Upgrade Manager Event File Write Error"
           --#TYPE      "Management Agent Event"
           --#SUMMARY   "Host %s : SCellName-TimeDate %s : EventCode %d : Description %s"
           --#ARGUMENTS {0,1,2,3,}
            --#SEVERITY  INFORMATIONAL
            --#TIMEINDEX 136
        ::= 136021004
 
   mngmtAgentTrap-21006 TRAP-TYPE
        ENTERPRISE compaq
        VARIABLES  { hostName,
                     scellNameDateTime,
                     agentEventCode,
                     agentEventDescription }
        DESCRIPTION
             "HSV Upgrade Manager Global Header Edc Compute Error"
           --#TYPE      "Management Agent Event"
           --#SUMMARY   "Host %s : SCellName-TimeDate %s : EventCode %d : Description %s"
           --#ARGUMENTS {0,1,2,3,}
            --#SEVERITY  INFORMATIONAL
            --#TIMEINDEX 136
        ::= 136021006
 
   mngmtAgentTrap-21007 TRAP-TYPE
        ENTERPRISE compaq
        VARIABLES  { hostName,
                     scellNameDateTime,
                     agentEventCode,
                     agentEventDescription }
        DESCRIPTION
             "HSV Upgrade Manager Image Header Edc Compute Error"
           --#TYPE      "Management Agent Event"
           --#SUMMARY   "Host %s : SCellName-TimeDate %s : EventCode %d : Description %s"
           --#ARGUMENTS {0,1,2,3,}
            --#SEVERITY  INFORMATIONAL
            --#TIMEINDEX 136
        ::= 136021007
 
   mngmtAgentTrap-21008 TRAP-TYPE
        ENTERPRISE compaq
        VARIABLES  { hostName,
                     scellNameDateTime,
                     agentEventCode,
                     agentEventDescription }
        DESCRIPTION
             "HSV Upgrade Manager Image Type Exceeds Max Image Count"
           --#TYPE      "Management Agent Event"
           --#SUMMARY   "Host %s : SCellName-TimeDate %s : EventCode %d : Description %s"
           --#ARGUMENTS {0,1,2,3,}
            --#SEVERITY  INFORMATIONAL
            --#TIMEINDEX 136
        ::= 136021008
 
   mngmtAgentTrap-21009 TRAP-TYPE
        ENTERPRISE compaq
        VARIABLES  { hostName,
                     scellNameDateTime,
                     agentEventCode,
                     agentEventDescription }
        DESCRIPTION
             "HSV Upgrade Manager Image Type Not Controller Image"
           --#TYPE      "Management Agent Event"
           --#SUMMARY   "Host %s : SCellName-TimeDate %s : EventCode %d : Description %s"
           --#ARGUMENTS {0,1,2,3,}
            --#SEVERITY  INFORMATIONAL
            --#TIMEINDEX 136
        ::= 136021009
 
   mngmtAgentTrap-21010 TRAP-TYPE
        ENTERPRISE compaq
        VARIABLES  { hostName,
                     scellNameDateTime,
                     agentEventCode,
                     agentEventDescription }
        DESCRIPTION
             "HSV Upgrade Manager Image Size Exceeded"
           --#TYPE      "Management Agent Event"
           --#SUMMARY   "Host %s : SCellName-TimeDate %s : EventCode %d : Description %s"
           --#ARGUMENTS {0,1,2,3,}
            --#SEVERITY  INFORMATIONAL
            --#TIMEINDEX 136
        ::= 136021010
 
   mngmtAgentTrap-21011 TRAP-TYPE
        ENTERPRISE compaq
        VARIABLES  { hostName,
                     scellNameDateTime,
                     agentEventCode,
                     agentEventDescription }
        DESCRIPTION
             "HSV Upgrade Manager Event File Open Error"
           --#TYPE      "Management Agent Event"
           --#SUMMARY   "Host %s : SCellName-TimeDate %s : EventCode %d : Description %s"
           --#ARGUMENTS {0,1,2,3,}
            --#SEVERITY  INFORMATIONAL
            --#TIMEINDEX 136
        ::= 136021011
 
   mngmtAgentTrap-21012 TRAP-TYPE
        ENTERPRISE compaq
        VARIABLES  { hostName,
                     scellNameDateTime,
                     agentEventCode,
                     agentEventDescription }
        DESCRIPTION
             "HSV Upgrade Manager Image Edc Compute Error"
           --#TYPE      "Management Agent Event"
           --#SUMMARY   "Host %s : SCellName-TimeDate %s : EventCode %d : Description %s"
           --#ARGUMENTS {0,1,2,3,}
            --#SEVERITY  INFORMATIONAL
            --#TIMEINDEX 136
        ::= 136021012
 
   mngmtAgentTrap-21013 TRAP-TYPE
        ENTERPRISE compaq
        VARIABLES  { hostName,
                     scellNameDateTime,
                     agentEventCode,
                     agentEventDescription }
        DESCRIPTION
             "HSV Upgrade Manager Begin Text Not Found"
           --#TYPE      "Management Agent Event"
           --#SUMMARY   "Host %s : SCellName-TimeDate %s : EventCode %d : Description %s"
           --#ARGUMENTS {0,1,2,3,}
            --#SEVERITY  INFORMATIONAL
            --#TIMEINDEX 136
        ::= 136021013
 
   mngmtAgentTrap-21014 TRAP-TYPE
        ENTERPRISE compaq
        VARIABLES  { hostName,
                     scellNameDateTime,
                     agentEventCode,
                     agentEventDescription }
        DESCRIPTION
             "HSV Upgrade Manager After Text Not Found"
           --#TYPE      "Management Agent Event"
           --#SUMMARY   "Host %s : SCellName-TimeDate %s : EventCode %d : Description %s"
           --#ARGUMENTS {0,1,2,3,}
            --#SEVERITY  INFORMATIONAL
            --#TIMEINDEX 136
        ::= 136021014
 
   mngmtAgentTrap-21015 TRAP-TYPE
        ENTERPRISE compaq
        VARIABLES  { hostName,
                     scellNameDateTime,
                     agentEventCode,
                     agentEventDescription }
        DESCRIPTION
             "HSV Upgrade Manager File Format Version Mismatch"
           --#TYPE      "Management Agent Event"
           --#SUMMARY   "Host %s : SCellName-TimeDate %s : EventCode %d : Description %s"
           --#ARGUMENTS {0,1,2,3,}
            --#SEVERITY  INFORMATIONAL
            --#TIMEINDEX 136
        ::= 136021015
 
   mngmtAgentTrap-21016 TRAP-TYPE
        ENTERPRISE compaq
        VARIABLES  { hostName,
                     scellNameDateTime,
                     agentEventCode,
                     agentEventDescription }
        DESCRIPTION
             "HSV Upgrade Manager Global Header Format Version Mismatch"
           --#TYPE      "Management Agent Event"
           --#SUMMARY   "Host %s : SCellName-TimeDate %s : EventCode %d : Description %s"
           --#ARGUMENTS {0,1,2,3,}
            --#SEVERITY  INFORMATIONAL
            --#TIMEINDEX 136
        ::= 136021016
 
   mngmtAgentTrap-21017 TRAP-TYPE
        ENTERPRISE compaq
        VARIABLES  { hostName,
                     scellNameDateTime,
                     agentEventCode,
                     agentEventDescription }
        DESCRIPTION
             "HSV Upgrade Manager Product Information Was Not Found"
           --#TYPE      "Management Agent Event"
           --#SUMMARY   "Host %s : SCellName-TimeDate %s : EventCode %d : Description %s"
           --#ARGUMENTS {0,1,2,3,}
            --#SEVERITY  INFORMATIONAL
            --#TIMEINDEX 136
        ::= 136021017
 
   mngmtAgentTrap-21018 TRAP-TYPE
        ENTERPRISE compaq
        VARIABLES  { hostName,
                     scellNameDateTime,
                     agentEventCode,
                     agentEventDescription }
        DESCRIPTION
             "HSV Upgrade Manager Event File Was Not Found"
           --#TYPE      "Management Agent Event"
           --#SUMMARY   "Host %s : SCellName-TimeDate %s : EventCode %d : Description %s"
           --#ARGUMENTS {0,1,2,3,}
            --#SEVERITY  INFORMATIONAL
            --#TIMEINDEX 136
        ::= 136021018
 
   mngmtAgentTrap-21019 TRAP-TYPE
        ENTERPRISE compaq
        VARIABLES  { hostName,
                     scellNameDateTime,
                     agentEventCode,
                     agentEventDescription }
        DESCRIPTION
             "HSV Upgrade Manager All Images Match Versions Already Loaded"
           --#TYPE      "Management Agent Event"
           --#SUMMARY   "Host %s : SCellName-TimeDate %s : EventCode %d : Description %s"
           --#ARGUMENTS {0,1,2,3,}
            --#SEVERITY  INFORMATIONAL
            --#TIMEINDEX 136
        ::= 136021019
 
   mngmtAgentTrap-22001 TRAP-TYPE
        ENTERPRISE compaq
        VARIABLES  { hostName,
                     scellNameDateTime,
                     agentEventCode,
                     agentEventDescription }
        DESCRIPTION
             "Trace: Unable to write management agent trace file"
           --#TYPE      "Management Agent Event"
           --#SUMMARY   "Host %s : SCellName-TimeDate %s : EventCode %d : Description %s"
           --#ARGUMENTS {0,1,2,3,}
            --#SEVERITY  MINOR
            --#TIMEINDEX 136
        ::= 136022001
 
   mngmtAgentTrap-22002 TRAP-TYPE
        ENTERPRISE compaq
        VARIABLES  { hostName,
                     scellNameDateTime,
                     agentEventCode,
                     agentEventDescription }
        DESCRIPTION
             "Trace: file write succeeded"
           --#TYPE      "Management Agent Event"
           --#SUMMARY   "Host %s : SCellName-TimeDate %s : EventCode %d : Description %s"
           --#ARGUMENTS {0,1,2,3,}
            --#SEVERITY  INFORMATIONAL
            --#TIMEINDEX 136
        ::= 136022002
 
   mngmtAgentTrap-23002 TRAP-TYPE
        ENTERPRISE compaq
        VARIABLES  { hostName,
                     scellNameDateTime,
                     agentEventCode,
                     agentEventDescription }
        DESCRIPTION
             "Diagnostic The view list has errors"
           --#TYPE      "Management Agent Event"
           --#SUMMARY   "Host %s : SCellName-TimeDate %s : EventCode %d : Description %s"
           --#ARGUMENTS {0,1,2,3,}
            --#SEVERITY  MINOR
            --#TIMEINDEX 136
        ::= 136023002
 
   mngmtAgentTrap-23003 TRAP-TYPE
        ENTERPRISE compaq
        VARIABLES  { hostName,
                     scellNameDateTime,
                     agentEventCode,
                     agentEventDescription }
        DESCRIPTION
             "Diagnostic Memory allocation failure"
           --#TYPE      "Management Agent Event"
           --#SUMMARY   "Host %s : SCellName-TimeDate %s : EventCode %d : Description %s"
           --#ARGUMENTS {0,1,2,3,}
            --#SEVERITY  CRITICAL
            --#TIMEINDEX 136
        ::= 136023003
 
   mngmtAgentTrap-24001 TRAP-TYPE
        ENTERPRISE compaq
        VARIABLES  { hostName,
                     scellNameDateTime,
                     agentEventCode,
                     agentEventDescription }
        DESCRIPTION
             "Windows system error"
           --#TYPE      "Management Agent Event"
           --#SUMMARY   "Host %s : SCellName-TimeDate %s : EventCode %d : Description %s"
           --#ARGUMENTS {0,1,2,3,}
            --#SEVERITY  INFORMATIONAL
            --#TIMEINDEX 136
        ::= 136024001
 
   mngmtAgentTrap-24002 TRAP-TYPE
        ENTERPRISE compaq
        VARIABLES  { hostName,
                     scellNameDateTime,
                     agentEventCode,
                     agentEventDescription }
        DESCRIPTION
             "Lock is already taken"
           --#TYPE      "Management Agent Event"
           --#SUMMARY   "Host %s : SCellName-TimeDate %s : EventCode %d : Description %s"
           --#ARGUMENTS {0,1,2,3,}
            --#SEVERITY  INFORMATIONAL
            --#TIMEINDEX 136
        ::= 136024002
 
   mngmtAgentTrap-24003 TRAP-TYPE
        ENTERPRISE compaq
        VARIABLES  { hostName,
                     scellNameDateTime,
                     agentEventCode,
                     agentEventDescription }
        DESCRIPTION
             "Lock is not taken"
           --#TYPE      "Management Agent Event"
           --#SUMMARY   "Host %s : SCellName-TimeDate %s : EventCode %d : Description %s"
           --#ARGUMENTS {0,1,2,3,}
            --#SEVERITY  INFORMATIONAL
            --#TIMEINDEX 136
        ::= 136024003
 
   mngmtAgentTrap-24004 TRAP-TYPE
        ENTERPRISE compaq
        VARIABLES  { hostName,
                     scellNameDateTime,
                     agentEventCode,
                     agentEventDescription }
        DESCRIPTION
             "Request timed out"
           --#TYPE      "Management Agent Event"
           --#SUMMARY   "Host %s : SCellName-TimeDate %s : EventCode %d : Description %s"
           --#ARGUMENTS {0,1,2,3,}
            --#SEVERITY  INFORMATIONAL
            --#TIMEINDEX 136
        ::= 136024004
 
   mngmtAgentTrap-25001 TRAP-TYPE
        ENTERPRISE compaq
        VARIABLES  { hostName,
                     scellNameDateTime,
                     agentEventCode,
                     agentEventDescription }
        DESCRIPTION
             "No path to controller"
           --#TYPE      "Management Agent Event"
           --#SUMMARY   "Host %s : SCellName-TimeDate %s : EventCode %d : Description %s"
           --#ARGUMENTS {0,1,2,3,}
            --#SEVERITY  INFORMATIONAL
            --#TIMEINDEX 136
        ::= 136025001
 
   mngmtAgentTrap-25002 TRAP-TYPE
        ENTERPRISE compaq
        VARIABLES  { hostName,
                     scellNameDateTime,
                     agentEventCode,
                     agentEventDescription }
        DESCRIPTION
             "Thread is not running"
           --#TYPE      "Management Agent Event"
           --#SUMMARY   "Host %s : SCellName-TimeDate %s : EventCode %d : Description %s"
           --#ARGUMENTS {0,1,2,3,}
            --#SEVERITY  INFORMATIONAL
            --#TIMEINDEX 136
        ::= 136025002
 
   mngmtAgentTrap-25003 TRAP-TYPE
        ENTERPRISE compaq
        VARIABLES  { hostName,
                     scellNameDateTime,
                     agentEventCode,
                     agentEventDescription }
        DESCRIPTION
             "No physical stores"
           --#TYPE      "Management Agent Event"
           --#SUMMARY   "Host %s : SCellName-TimeDate %s : EventCode %d : Description %s"
           --#ARGUMENTS {0,1,2,3,}
            --#SEVERITY  INFORMATIONAL
            --#TIMEINDEX 136
        ::= 136025003
 
   mngmtAgentTrap-25004 TRAP-TYPE
        ENTERPRISE compaq
        VARIABLES  { hostName,
                     scellNameDateTime,
                     agentEventCode,
                     agentEventDescription }
        DESCRIPTION
             "Loop context ID changed"
           --#TYPE      "Management Agent Event"
           --#SUMMARY   "Host %s : SCellName-TimeDate %s : EventCode %d : Description %s"
           --#ARGUMENTS {0,1,2,3,}
            --#SEVERITY  INFORMATIONAL
            --#TIMEINDEX 136
        ::= 136025004
 
   mngmtAgentTrap-25005 TRAP-TYPE
        ENTERPRISE compaq
        VARIABLES  { hostName,
                     scellNameDateTime,
                     agentEventCode,
                     agentEventDescription }
        DESCRIPTION
             "Storage Cell context ID changed"
           --#TYPE      "Management Agent Event"
           --#SUMMARY   "Host %s : SCellName-TimeDate %s : EventCode %d : Description %s"
           --#ARGUMENTS {0,1,2,3,}
            --#SEVERITY  INFORMATIONAL
            --#TIMEINDEX 136
        ::= 136025005
 
   mngmtAgentTrap-25006 TRAP-TYPE
        ENTERPRISE compaq
        VARIABLES  { hostName,
                     scellNameDateTime,
                     agentEventCode,
                     agentEventDescription }
        DESCRIPTION
             "Cache Write Failure"
           --#TYPE      "Management Agent Event"
           --#SUMMARY   "Host %s : SCellName-TimeDate %s : EventCode %d : Description %s"
           --#ARGUMENTS {0,1,2,3,}
            --#SEVERITY  INFORMATIONAL
            --#TIMEINDEX 136
        ::= 136025006
 
   mngmtAgentTrap-25007 TRAP-TYPE
        ENTERPRISE compaq
        VARIABLES  { hostName,
                     scellNameDateTime,
                     agentEventCode,
                     agentEventDescription }
        DESCRIPTION
             "Battery Disable Failure"
           --#TYPE      "Management Agent Event"
           --#SUMMARY   "Host %s : SCellName-TimeDate %s : EventCode %d : Description %s"
           --#ARGUMENTS {0,1,2,3,}
            --#SEVERITY  INFORMATIONAL
            --#TIMEINDEX 136
        ::= 136025007
 
   mngmtAgentTrap-25008 TRAP-TYPE
        ENTERPRISE compaq
        VARIABLES  { hostName,
                     scellNameDateTime,
                     agentEventCode,
                     agentEventDescription }
        DESCRIPTION
             "Drive Shelf Disable Failure"
           --#TYPE      "Management Agent Event"
           --#SUMMARY   "Host %s : SCellName-TimeDate %s : EventCode %d : Description %s"
           --#ARGUMENTS {0,1,2,3,}
            --#SEVERITY  INFORMATIONAL
            --#TIMEINDEX 136
        ::= 136025008
 
   mngmtAgentTrap-25009 TRAP-TYPE
        ENTERPRISE compaq
        VARIABLES  { hostName,
                     scellNameDateTime,
                     agentEventCode,
                     agentEventDescription }
        DESCRIPTION
             "Shutdown Both Restart And Power Off Requested"
           --#TYPE      "Management Agent Event"
           --#SUMMARY   "Host %s : SCellName-TimeDate %s : EventCode %d : Description %s"
           --#ARGUMENTS {0,1,2,3,}
            --#SEVERITY  INFORMATIONAL
            --#TIMEINDEX 136
        ::= 136025009
 
   mngmtAgentTrap-25010 TRAP-TYPE
        ENTERPRISE compaq
        VARIABLES  { hostName,
                     scellNameDateTime,
                     agentEventCode,
                     agentEventDescription }
        DESCRIPTION
             "Shutdown Drive Shelf Power Off But No Enclosure Power Off Requested"
           --#TYPE      "Management Agent Event"
           --#SUMMARY   "Host %s : SCellName-TimeDate %s : EventCode %d : Description %s"
           --#ARGUMENTS {0,1,2,3,}
            --#SEVERITY  INFORMATIONAL
            --#TIMEINDEX 136
        ::= 136025010
 
   mngmtAgentTrap-25011 TRAP-TYPE
        ENTERPRISE compaq
        VARIABLES  { hostName,
                     scellNameDateTime,
                     agentEventCode,
                     agentEventDescription }
        DESCRIPTION
             "Shutdown Disable Battery But No Enclosure Power Off Requested"
           --#TYPE      "Management Agent Event"
           --#SUMMARY   "Host %s : SCellName-TimeDate %s : EventCode %d : Description %s"
           --#ARGUMENTS {0,1,2,3,}
            --#SEVERITY  INFORMATIONAL
            --#TIMEINDEX 136
        ::= 136025011
 
   mngmtAgentTrap-25012 TRAP-TYPE
        ENTERPRISE compaq
        VARIABLES  { hostName,
                     scellNameDateTime,
                     agentEventCode,
                     agentEventDescription }
        DESCRIPTION
             "Shutdown Disable Battery But Shutdown Unconditional Requested"
           --#TYPE      "Management Agent Event"
           --#SUMMARY   "Host %s : SCellName-TimeDate %s : EventCode %d : Description %s"
           --#ARGUMENTS {0,1,2,3,}
            --#SEVERITY  INFORMATIONAL
            --#TIMEINDEX 136
        ::= 136025012
 
   mngmtAgentTrap-25013 TRAP-TYPE
        ENTERPRISE compaq
        VARIABLES  { hostName,
                     scellNameDateTime,
                     agentEventCode,
                     agentEventDescription }
        DESCRIPTION
             "Shutdown Delay Out Of Range"
           --#TYPE      "Management Agent Event"
           --#SUMMARY   "Host %s : SCellName-TimeDate %s : EventCode %d : Description %s"
           --#ARGUMENTS {0,1,2,3,}
            --#SEVERITY  INFORMATIONAL
            --#TIMEINDEX 136
        ::= 136025013
 
   mngmtAgentTrap-25014 TRAP-TYPE
        ENTERPRISE compaq
        VARIABLES  { hostName,
                     scellNameDateTime,
                     agentEventCode,
                     agentEventDescription }
        DESCRIPTION
             "Invalid Storage Cell name"
           --#TYPE      "Management Agent Event"
           --#SUMMARY   "Host %s : SCellName-TimeDate %s : EventCode %d : Description %s"
           --#ARGUMENTS {0,1,2,3,}
            --#SEVERITY  INFORMATIONAL
            --#TIMEINDEX 136
        ::= 136025014
 
   mngmtAgentTrap-25015 TRAP-TYPE
        ENTERPRISE compaq
        VARIABLES  { hostName,
                     scellNameDateTime,
                     agentEventCode,
                     agentEventDescription }
        DESCRIPTION
             "Requested spares goal cannot be satisfied"
           --#TYPE      "Management Agent Event"
           --#SUMMARY   "Host %s : SCellName-TimeDate %s : EventCode %d : Description %s"
           --#ARGUMENTS {0,1,2,3,}
            --#SEVERITY  INFORMATIONAL
            --#TIMEINDEX 136
        ::= 136025015
 
   mngmtAgentTrap-25016 TRAP-TYPE
        ENTERPRISE compaq
        VARIABLES  { hostName,
                     scellNameDateTime,
                     agentEventCode,
                     agentEventDescription }
        DESCRIPTION
             "No valid LDAD found"
           --#TYPE      "Management Agent Event"
           --#SUMMARY   "Host %s : SCellName-TimeDate %s : EventCode %d : Description %s"
           --#ARGUMENTS {0,1,2,3,}
            --#SEVERITY  INFORMATIONAL
            --#TIMEINDEX 136
        ::= 136025016
 
   mngmtAgentTrap-25017 TRAP-TYPE
        ENTERPRISE compaq
        VARIABLES  { hostName,
                     scellNameDateTime,
                     agentEventCode,
                     agentEventDescription }
        DESCRIPTION
             "Mismatched MLD size"
           --#TYPE      "Management Agent Event"
           --#SUMMARY   "Host %s : SCellName-TimeDate %s : EventCode %d : Description %s"
           --#ARGUMENTS {0,1,2,3,}
            --#SEVERITY  INFORMATIONAL
            --#TIMEINDEX 136
        ::= 136025017
 
   mngmtAgentTrap-25018 TRAP-TYPE
        ENTERPRISE compaq
        VARIABLES  { hostName,
                     scellNameDateTime,
                     agentEventCode,
                     agentEventDescription }
        DESCRIPTION
             "Codeload image file error"
           --#TYPE      "Management Agent Event"
           --#SUMMARY   "Host %s : SCellName-TimeDate %s : EventCode %d : Description %s"
           --#ARGUMENTS {0,1,2,3,}
            --#SEVERITY  INFORMATIONAL
            --#TIMEINDEX 136
        ::= 136025018
 
   mngmtAgentTrap-25019 TRAP-TYPE
        ENTERPRISE compaq
        VARIABLES  { hostName,
                     scellNameDateTime,
                     agentEventCode,
                     agentEventDescription }
        DESCRIPTION
             "Storage System is not initialized"
           --#TYPE      "Management Agent Event"
           --#SUMMARY   "Host %s : SCellName-TimeDate %s : EventCode %d : Description %s"
           --#ARGUMENTS {0,1,2,3,}
            --#SEVERITY  INFORMATIONAL
            --#TIMEINDEX 136
        ::= 136025019
 
   mngmtAgentTrap-26002 TRAP-TYPE
        ENTERPRISE compaq
        VARIABLES  { hostName,
                     scellNameDateTime,
                     agentEventCode,
                     agentEventDescription }
        DESCRIPTION
             "Invalid data replication operation"
           --#TYPE      "Management Agent Event"
           --#SUMMARY   "Host %s : SCellName-TimeDate %s : EventCode %d : Description %s"
           --#ARGUMENTS {0,1,2,3,}
            --#SEVERITY  INFORMATIONAL
            --#TIMEINDEX 136
        ::= 136026002
 
   mngmtAgentTrap-26005 TRAP-TYPE
        ENTERPRISE compaq
        VARIABLES  { hostName,
                     scellNameDateTime,
                     agentEventCode,
                     agentEventDescription }
        DESCRIPTION
             "DR group name exceeds maximum length"
           --#TYPE      "Management Agent Event"
           --#SUMMARY   "Host %s : SCellName-TimeDate %s : EventCode %d : Description %s"
           --#ARGUMENTS {0,1,2,3,}
            --#SEVERITY  INFORMATIONAL
            --#TIMEINDEX 136
        ::= 136026005
 
   mngmtAgentTrap-26006 TRAP-TYPE
        ENTERPRISE compaq
        VARIABLES  { hostName,
                     scellNameDateTime,
                     agentEventCode,
                     agentEventDescription }
        DESCRIPTION
             "DR group created successfully"
           --#TYPE      "Management Agent Event"
           --#SUMMARY   "Host %s : SCellName-TimeDate %s : EventCode %d : Description %s"
           --#ARGUMENTS {0,1,2,3,}
            --#SEVERITY  INFORMATIONAL
            --#TIMEINDEX 136
        ::= 136026006
 
   mngmtAgentTrap-26007 TRAP-TYPE
        ENTERPRISE compaq
        VARIABLES  { hostName,
                     scellNameDateTime,
                     agentEventCode,
                     agentEventDescription }
        DESCRIPTION
             "Data replication invalid mode for DR Group create "
           --#TYPE      "Management Agent Event"
           --#SUMMARY   "Host %s : SCellName-TimeDate %s : EventCode %d : Description %s"
           --#ARGUMENTS {0,1,2,3,}
            --#SEVERITY  INFORMATIONAL
            --#TIMEINDEX 136
        ::= 136026007
 
   mngmtAgentTrap-26008 TRAP-TYPE
        ENTERPRISE compaq
        VARIABLES  { hostName,
                     scellNameDateTime,
                     agentEventCode,
                     agentEventDescription }
        DESCRIPTION
             "A duplicate DR group name exists in the specified source or destination DR group."
           --#TYPE      "Management Agent Event"
           --#SUMMARY   "Host %s : SCellName-TimeDate %s : EventCode %d : Description %s"
           --#ARGUMENTS {0,1,2,3,}
            --#SEVERITY  INFORMATIONAL
            --#TIMEINDEX 136
        ::= 136026008
 
   mngmtAgentTrap-26009 TRAP-TYPE
        ENTERPRISE compaq
        VARIABLES  { hostName,
                     scellNameDateTime,
                     agentEventCode,
                     agentEventDescription }
        DESCRIPTION
             "Data replication invalid operation while DR Groups exist"
           --#TYPE      "Management Agent Event"
           --#SUMMARY   "Host %s : SCellName-TimeDate %s : EventCode %d : Description %s"
           --#ARGUMENTS {0,1,2,3,}
            --#SEVERITY  INFORMATIONAL
            --#TIMEINDEX 136
        ::= 136026009
 
   mngmtAgentTrap-26010 TRAP-TYPE
        ENTERPRISE compaq
        VARIABLES  { hostName,
                     scellNameDateTime,
                     agentEventCode,
                     agentEventDescription }
        DESCRIPTION
             "Data replication root folder does not exist"
           --#TYPE      "Management Agent Event"
           --#SUMMARY   "Host %s : SCellName-TimeDate %s : EventCode %d : Description %s"
           --#ARGUMENTS {0,1,2,3,}
            --#SEVERITY  INFORMATIONAL
            --#TIMEINDEX 136
        ::= 136026010
 
   mngmtAgentTrap-26011 TRAP-TYPE
        ENTERPRISE compaq
        VARIABLES  { hostName,
                     scellNameDateTime,
                     agentEventCode,
                     agentEventDescription }
        DESCRIPTION
             "DR group discarded"
           --#TYPE      "Management Agent Event"
           --#SUMMARY   "Host %s : SCellName-TimeDate %s : EventCode %d : Description %s"
           --#ARGUMENTS {0,1,2,3,}
            --#SEVERITY  INFORMATIONAL
            --#TIMEINDEX 136
        ::= 136026011
 
   mngmtAgentTrap-26012 TRAP-TYPE
        ENTERPRISE compaq
        VARIABLES  { hostName,
                     scellNameDateTime,
                     agentEventCode,
                     agentEventDescription }
        DESCRIPTION
             "Data replication unknown remote storage system"
           --#TYPE      "Management Agent Event"
           --#SUMMARY   "Host %s : SCellName-TimeDate %s : EventCode %d : Description %s"
           --#ARGUMENTS {0,1,2,3,}
            --#SEVERITY  INFORMATIONAL
            --#TIMEINDEX 136
        ::= 136026012
 
   mngmtAgentTrap-26013 TRAP-TYPE
        ENTERPRISE compaq
        VARIABLES  { hostName,
                     scellNameDateTime,
                     agentEventCode,
                     agentEventDescription }
        DESCRIPTION
             "Data replication Error. A conflicting Vdisk name exists on the remote storage system."
           --#TYPE      "Management Agent Event"
           --#SUMMARY   "Host %s : SCellName-TimeDate %s : EventCode %d : Description %s"
           --#ARGUMENTS {0,1,2,3,}
            --#SEVERITY  INFORMATIONAL
            --#TIMEINDEX 136
        ::= 136026013
 
   mngmtAgentTrap-26014 TRAP-TYPE
        ENTERPRISE compaq
        VARIABLES  { hostName,
                     scellNameDateTime,
                     agentEventCode,
                     agentEventDescription }
        DESCRIPTION
             "Data Replication Error. Invalid Remote Vdisk Name specified."
           --#TYPE      "Management Agent Event"
           --#SUMMARY   "Host %s : SCellName-TimeDate %s : EventCode %d : Description %s"
           --#ARGUMENTS {0,1,2,3,}
            --#SEVERITY  INFORMATIONAL
            --#TIMEINDEX 136
        ::= 136026014
 
   mngmtAgentTrap-26015 TRAP-TYPE
        ENTERPRISE compaq
        VARIABLES  { hostName,
                     scellNameDateTime,
                     agentEventCode,
                     agentEventDescription }
        DESCRIPTION
             "Data Replication Error. Remote Vdisk size cannot be modified."
           --#TYPE      "Management Agent Event"
           --#SUMMARY   "Host %s : SCellName-TimeDate %s : EventCode %d : Description %s"
           --#ARGUMENTS {0,1,2,3,}
            --#SEVERITY  INFORMATIONAL
            --#TIMEINDEX 136
        ::= 136026015
 
   mngmtAgentTrap-26016 TRAP-TYPE
        ENTERPRISE compaq
        VARIABLES  { hostName,
                     scellNameDateTime,
                     agentEventCode,
                     agentEventDescription }
        DESCRIPTION
             "Data Replication Error. Remote Vdisk should be unpresented to proceed with the discard/detach operation."
           --#TYPE      "Management Agent Event"
           --#SUMMARY   "Host %s : SCellName-TimeDate %s : EventCode %d : Description %s"
           --#ARGUMENTS {0,1,2,3,}
            --#SEVERITY  INFORMATIONAL
            --#TIMEINDEX 136
        ::= 136026016
 
   mngmtAgentTrap-27001 TRAP-TYPE
        ENTERPRISE compaq
        VARIABLES  { hostName,
                     scellNameDateTime,
                     agentEventCode,
                     agentEventDescription }
        DESCRIPTION
             "The element manager has successfully initialized storage system. Command issued through XML Interface."
           --#TYPE      "Management Agent Event"
           --#SUMMARY   "Host %s : SCellName-TimeDate %s : EventCode %d : Description %s"
           --#ARGUMENTS {0,1,2,3,}
            --#SEVERITY  INFORMATIONAL
            --#TIMEINDEX 136
        ::= 136027001
 
   mngmtAgentTrap-27002 TRAP-TYPE
        ENTERPRISE compaq
        VARIABLES  { hostName,
                     scellNameDateTime,
                     agentEventCode,
                     agentEventDescription }
        DESCRIPTION
             "The element manager has successfully created a virtual disk. Command issued through the XML Interface."
           --#TYPE      "Management Agent Event"
           --#SUMMARY   "Host %s : SCellName-TimeDate %s : EventCode %d : Description %s"
           --#ARGUMENTS {0,1,2,3,}
            --#SEVERITY  INFORMATIONAL
            --#TIMEINDEX 136
        ::= 136027002
 
   mngmtAgentTrap-27003 TRAP-TYPE
        ENTERPRISE compaq
        VARIABLES  { hostName,
                     scellNameDateTime,
                     agentEventCode,
                     agentEventDescription }
        DESCRIPTION
             "The element manager has successfully created a disk group. Command issued through the XML Interface."
           --#TYPE      "Management Agent Event"
           --#SUMMARY   "Host %s : SCellName-TimeDate %s : EventCode %d : Description %s"
           --#ARGUMENTS {0,1,2,3,}
            --#SEVERITY  INFORMATIONAL
            --#TIMEINDEX 136
        ::= 136027003
 
   mngmtAgentTrap-27004 TRAP-TYPE
        ENTERPRISE compaq
        VARIABLES  { hostName,
                     scellNameDateTime,
                     agentEventCode,
                     agentEventDescription }
        DESCRIPTION
             "The element manager has successfully created a DRM group. Command issued through the XML Interface."
           --#TYPE      "Management Agent Event"
           --#SUMMARY   "Host %s : SCellName-TimeDate %s : EventCode %d : Description %s"
           --#ARGUMENTS {0,1,2,3,}
            --#SEVERITY  INFORMATIONAL
            --#TIMEINDEX 136
        ::= 136027004
 
   mngmtAgentTrap-27005 TRAP-TYPE
        ENTERPRISE compaq
        VARIABLES  { hostName,
                     scellNameDateTime,
                     agentEventCode,
                     agentEventDescription }
        DESCRIPTION
             "The element manager has successfully created a host. Command issued through the XML Interface."
           --#TYPE      "Management Agent Event"
           --#SUMMARY   "Host %s : SCellName-TimeDate %s : EventCode %d : Description %s"
           --#ARGUMENTS {0,1,2,3,}
            --#SEVERITY  INFORMATIONAL
            --#TIMEINDEX 136
        ::= 136027005
 
   mngmtAgentTrap-27006 TRAP-TYPE
        ENTERPRISE compaq
        VARIABLES  { hostName,
                     scellNameDateTime,
                     agentEventCode,
                     agentEventDescription }
        DESCRIPTION
             "The element manager has successfully created a presented unit. Command issued through the XML Interface."
           --#TYPE      "Management Agent Event"
           --#SUMMARY   "Host %s : SCellName-TimeDate %s : EventCode %d : Description %s"
           --#ARGUMENTS {0,1,2,3,}
            --#SEVERITY  INFORMATIONAL
            --#TIMEINDEX 136
        ::= 136027006
 
   mngmtAgentTrap-27007 TRAP-TYPE
        ENTERPRISE compaq
        VARIABLES  { hostName,
                     scellNameDateTime,
                     agentEventCode,
                     agentEventDescription }
        DESCRIPTION
             "The element manager has successfully created a virtual disk folder. Command issued through the XML Interface."
           --#TYPE      "Management Agent Event"
           --#SUMMARY   "Host %s : SCellName-TimeDate %s : EventCode %d : Description %s"
           --#ARGUMENTS {0,1,2,3,}
            --#SEVERITY  INFORMATIONAL
            --#TIMEINDEX 136
        ::= 136027007
 
   mngmtAgentTrap-27008 TRAP-TYPE
        ENTERPRISE compaq
        VARIABLES  { hostName,
                     scellNameDateTime,
                     agentEventCode,
                     agentEventDescription }
        DESCRIPTION
             "The element manager has successfully created a host folder. Command issued through the XML Interface."
           --#TYPE      "Management Agent Event"
           --#SUMMARY   "Host %s : SCellName-TimeDate %s : EventCode %d : Description %s"
           --#ARGUMENTS {0,1,2,3,}
            --#SEVERITY  INFORMATIONAL
            --#TIMEINDEX 136
        ::= 136027008
 
   mngmtAgentTrap-27009 TRAP-TYPE
        ENTERPRISE compaq
        VARIABLES  { hostName,
                     scellNameDateTime,
                     agentEventCode,
                     agentEventDescription }
        DESCRIPTION
             "The element manager has successfully created a disk group folder. Command issued through the XML Interface."
           --#TYPE      "Management Agent Event"
           --#SUMMARY   "Host %s : SCellName-TimeDate %s : EventCode %d : Description %s"
           --#ARGUMENTS {0,1,2,3,}
            --#SEVERITY  INFORMATIONAL
            --#TIMEINDEX 136
        ::= 136027009
 
   mngmtAgentTrap-27010 TRAP-TYPE
        ENTERPRISE compaq
        VARIABLES  { hostName,
                     scellNameDateTime,
                     agentEventCode,
                     agentEventDescription }
        DESCRIPTION
             "The element manager has successfully created a DRM group folder. Command issued through the XML Interface."
           --#TYPE      "Management Agent Event"
           --#SUMMARY   "Host %s : SCellName-TimeDate %s : EventCode %d : Description %s"
           --#ARGUMENTS {0,1,2,3,}
            --#SEVERITY  INFORMATIONAL
            --#TIMEINDEX 136
        ::= 136027010
 
   mngmtAgentTrap-27011 TRAP-TYPE
        ENTERPRISE compaq
        VARIABLES  { hostName,
                     scellNameDateTime,
                     agentEventCode,
                     agentEventDescription }
        DESCRIPTION
             "The element manager has successfully created a folder. Command issued through the XML Interface."
           --#TYPE      "Management Agent Event"
           --#SUMMARY   "Host %s : SCellName-TimeDate %s : EventCode %d : Description %s"
           --#ARGUMENTS {0,1,2,3,}
            --#SEVERITY  INFORMATIONAL
            --#TIMEINDEX 136
        ::= 136027011
 
   mngmtAgentTrap-27012 TRAP-TYPE
        ENTERPRISE compaq
        VARIABLES  { hostName,
                     scellNameDateTime,
                     agentEventCode,
                     agentEventDescription }
        DESCRIPTION
             "The element manager has successfully created a snapshot. Command issued through the XML Interface."
           --#TYPE      "Management Agent Event"
           --#SUMMARY   "Host %s : SCellName-TimeDate %s : EventCode %d : Description %s"
           --#ARGUMENTS {0,1,2,3,}
            --#SEVERITY  INFORMATIONAL
            --#TIMEINDEX 136
        ::= 136027012
 
   mngmtAgentTrap-27013 TRAP-TYPE
        ENTERPRISE compaq
        VARIABLES  { hostName,
                     scellNameDateTime,
                     agentEventCode,
                     agentEventDescription }
        DESCRIPTION
             "The element manager has successfully created a snapclone. Command issued through the XML Interface."
           --#TYPE      "Management Agent Event"
           --#SUMMARY   "Host %s : SCellName-TimeDate %s : EventCode %d : Description %s"
           --#ARGUMENTS {0,1,2,3,}
            --#SEVERITY  INFORMATIONAL
            --#TIMEINDEX 136
        ::= 136027013
 
   mngmtAgentTrap-27014 TRAP-TYPE
        ENTERPRISE compaq
        VARIABLES  { hostName,
                     scellNameDateTime,
                     agentEventCode,
                     agentEventDescription }
        DESCRIPTION
             "The element manager has successfully uninitialized the storage system. Command issued through the XML Interface."
           --#TYPE      "Management Agent Event"
           --#SUMMARY   "Host %s : SCellName-TimeDate %s : EventCode %d : Description %s"
           --#ARGUMENTS {0,1,2,3,}
            --#SEVERITY  INFORMATIONAL
            --#TIMEINDEX 136
        ::= 136027014
 
   mngmtAgentTrap-27015 TRAP-TYPE
        ENTERPRISE compaq
        VARIABLES  { hostName,
                     scellNameDateTime,
                     agentEventCode,
                     agentEventDescription }
        DESCRIPTION
             "The element manager has successfully deleted a virtual disk. Command issued through the XML Interface."
           --#TYPE      "Management Agent Event"
           --#SUMMARY   "Host %s : SCellName-TimeDate %s : EventCode %d : Description %s"
           --#ARGUMENTS {0,1,2,3,}
            --#SEVERITY  INFORMATIONAL
            --#TIMEINDEX 136
        ::= 136027015
 
   mngmtAgentTrap-27016 TRAP-TYPE
        ENTERPRISE compaq
        VARIABLES  { hostName,
                     scellNameDateTime,
                     agentEventCode,
                     agentEventDescription }
        DESCRIPTION
             "The element manager has successfully deleted a disk group. Command issued through the XML Interface."
           --#TYPE      "Management Agent Event"
           --#SUMMARY   "Host %s : SCellName-TimeDate %s : EventCode %d : Description %s"
           --#ARGUMENTS {0,1,2,3,}
            --#SEVERITY  INFORMATIONAL
            --#TIMEINDEX 136
        ::= 136027016
 
   mngmtAgentTrap-27017 TRAP-TYPE
        ENTERPRISE compaq
        VARIABLES  { hostName,
                     scellNameDateTime,
                     agentEventCode,
                     agentEventDescription }
        DESCRIPTION
             "The element manager has successfully deleted a DRM group. Command issued through the XML Interface."
           --#TYPE      "Management Agent Event"
           --#SUMMARY   "Host %s : SCellName-TimeDate %s : EventCode %d : Description %s"
           --#ARGUMENTS {0,1,2,3,}
            --#SEVERITY  INFORMATIONAL
            --#TIMEINDEX 136
        ::= 136027017
 
   mngmtAgentTrap-27018 TRAP-TYPE
        ENTERPRISE compaq
        VARIABLES  { hostName,
                     scellNameDateTime,
                     agentEventCode,
                     agentEventDescription }
        DESCRIPTION
             "The element manager has successfully deleted a host. Command issued through the XML Interface."
           --#TYPE      "Management Agent Event"
           --#SUMMARY   "Host %s : SCellName-TimeDate %s : EventCode %d : Description %s"
           --#ARGUMENTS {0,1,2,3,}
            --#SEVERITY  INFORMATIONAL
            --#TIMEINDEX 136
        ::= 136027018
 
   mngmtAgentTrap-27019 TRAP-TYPE
        ENTERPRISE compaq
        VARIABLES  { hostName,
                     scellNameDateTime,
                     agentEventCode,
                     agentEventDescription }
        DESCRIPTION
             "The element manager has successfully deleted a presented unit. Command issued through the XML Interface."
           --#TYPE      "Management Agent Event"
           --#SUMMARY   "Host %s : SCellName-TimeDate %s : EventCode %d : Description %s"
           --#ARGUMENTS {0,1,2,3,}
            --#SEVERITY  INFORMATIONAL
            --#TIMEINDEX 136
        ::= 136027019
 
   mngmtAgentTrap-27020 TRAP-TYPE
        ENTERPRISE compaq
        VARIABLES  { hostName,
                     scellNameDateTime,
                     agentEventCode,
                     agentEventDescription }
        DESCRIPTION
             "The element manager has successfully deleted a virtual disk folder. Command issued through the XML Interface."
           --#TYPE      "Management Agent Event"
           --#SUMMARY   "Host %s : SCellName-TimeDate %s : EventCode %d : Description %s"
           --#ARGUMENTS {0,1,2,3,}
            --#SEVERITY  INFORMATIONAL
            --#TIMEINDEX 136
        ::= 136027020
 
   mngmtAgentTrap-27021 TRAP-TYPE
        ENTERPRISE compaq
        VARIABLES  { hostName,
                     scellNameDateTime,
                     agentEventCode,
                     agentEventDescription }
        DESCRIPTION
             "The element manager has successfully deleted a host folder. Command issued through the XML Interface."
           --#TYPE      "Management Agent Event"
           --#SUMMARY   "Host %s : SCellName-TimeDate %s : EventCode %d : Description %s"
           --#ARGUMENTS {0,1,2,3,}
            --#SEVERITY  INFORMATIONAL
            --#TIMEINDEX 136
        ::= 136027021
 
   mngmtAgentTrap-27022 TRAP-TYPE
        ENTERPRISE compaq
        VARIABLES  { hostName,
                     scellNameDateTime,
                     agentEventCode,
                     agentEventDescription }
        DESCRIPTION
             "The element manager has successfully deleted a disk group folder. Command issued through the XML Interface."
           --#TYPE      "Management Agent Event"
           --#SUMMARY   "Host %s : SCellName-TimeDate %s : EventCode %d : Description %s"
           --#ARGUMENTS {0,1,2,3,}
            --#SEVERITY  INFORMATIONAL
            --#TIMEINDEX 136
        ::= 136027022
 
   mngmtAgentTrap-27023 TRAP-TYPE
        ENTERPRISE compaq
        VARIABLES  { hostName,
                     scellNameDateTime,
                     agentEventCode,
                     agentEventDescription }
        DESCRIPTION
             "The element manager has successfully deleted a DRM group folder. Command issued through the XML Interface."
           --#TYPE      "Management Agent Event"
           --#SUMMARY   "Host %s : SCellName-TimeDate %s : EventCode %d : Description %s"
           --#ARGUMENTS {0,1,2,3,}
            --#SEVERITY  INFORMATIONAL
            --#TIMEINDEX 136
        ::= 136027023
 
   mngmtAgentTrap-27024 TRAP-TYPE
        ENTERPRISE compaq
        VARIABLES  { hostName,
                     scellNameDateTime,
                     agentEventCode,
                     agentEventDescription }
        DESCRIPTION
             "The element manager has successfully deleted a folder. Command issued through the XML Interface."
           --#TYPE      "Management Agent Event"
           --#SUMMARY   "Host %s : SCellName-TimeDate %s : EventCode %d : Description %s"
           --#ARGUMENTS {0,1,2,3,}
            --#SEVERITY  INFORMATIONAL
            --#TIMEINDEX 136
        ::= 136027024
 
   mngmtAgentTrap-27025 TRAP-TYPE
        ENTERPRISE compaq
        VARIABLES  { hostName,
                     scellNameDateTime,
                     agentEventCode,
                     agentEventDescription }
        DESCRIPTION
             "The element manager has successfully deleted a snapshot. Command issued through the XML Interface."
           --#TYPE      "Management Agent Event"
           --#SUMMARY   "Host %s : SCellName-TimeDate %s : EventCode %d : Description %s"
           --#ARGUMENTS {0,1,2,3,}
            --#SEVERITY  INFORMATIONAL
            --#TIMEINDEX 136
        ::= 136027025
 
   mngmtAgentTrap-27026 TRAP-TYPE
        ENTERPRISE compaq
        VARIABLES  { hostName,
                     scellNameDateTime,
                     agentEventCode,
                     agentEventDescription }
        DESCRIPTION
             "The element manager has successfully modified the properties of a storage system. Command issued through the XML Interface."
           --#TYPE      "Management Agent Event"
           --#SUMMARY   "Host %s : SCellName-TimeDate %s : EventCode %d : Description %s"
           --#ARGUMENTS {0,1,2,3,}
            --#SEVERITY  INFORMATIONAL
            --#TIMEINDEX 136
        ::= 136027026
 
   mngmtAgentTrap-27027 TRAP-TYPE
        ENTERPRISE compaq
        VARIABLES  { hostName,
                     scellNameDateTime,
                     agentEventCode,
                     agentEventDescription }
        DESCRIPTION
             "The element manager has successfully modified the properties of a virtual disk. Command issued through the XML Interface."
           --#TYPE      "Management Agent Event"
           --#SUMMARY   "Host %s : SCellName-TimeDate %s : EventCode %d : Description %s"
           --#ARGUMENTS {0,1,2,3,}
            --#SEVERITY  INFORMATIONAL
            --#TIMEINDEX 136
        ::= 136027027
 
   mngmtAgentTrap-27028 TRAP-TYPE
        ENTERPRISE compaq
        VARIABLES  { hostName,
                     scellNameDateTime,
                     agentEventCode,
                     agentEventDescription }
        DESCRIPTION
             "The element manager has successfully modified the properties of a disk group. Command issued through the XML Interface."
           --#TYPE      "Management Agent Event"
           --#SUMMARY   "Host %s : SCellName-TimeDate %s : EventCode %d : Description %s"
           --#ARGUMENTS {0,1,2,3,}
            --#SEVERITY  INFORMATIONAL
            --#TIMEINDEX 136
        ::= 136027028
 
   mngmtAgentTrap-27029 TRAP-TYPE
        ENTERPRISE compaq
        VARIABLES  { hostName,
                     scellNameDateTime,
                     agentEventCode,
                     agentEventDescription }
        DESCRIPTION
             "The element manager has successfully modified the properties of a DRM group. Command issued through the XML Interface."
           --#TYPE      "Management Agent Event"
           --#SUMMARY   "Host %s : SCellName-TimeDate %s : EventCode %d : Description %s"
           --#ARGUMENTS {0,1,2,3,}
            --#SEVERITY  INFORMATIONAL
            --#TIMEINDEX 136
        ::= 136027029
 
   mngmtAgentTrap-27030 TRAP-TYPE
        ENTERPRISE compaq
        VARIABLES  { hostName,
                     scellNameDateTime,
                     agentEventCode,
                     agentEventDescription }
        DESCRIPTION
             "The element manager has successfully modified the properties of a host. Command issued through the XML Interface."
           --#TYPE      "Management Agent Event"
           --#SUMMARY   "Host %s : SCellName-TimeDate %s : EventCode %d : Description %s"
           --#ARGUMENTS {0,1,2,3,}
            --#SEVERITY  INFORMATIONAL
            --#TIMEINDEX 136
        ::= 136027030
 
   mngmtAgentTrap-27031 TRAP-TYPE
        ENTERPRISE compaq
        VARIABLES  { hostName,
                     scellNameDateTime,
                     agentEventCode,
                     agentEventDescription }
        DESCRIPTION
             "The element manager has successfully modified the properties of a presented unit. Command issued through the XML Interface."
           --#TYPE      "Management Agent Event"
           --#SUMMARY   "Host %s : SCellName-TimeDate %s : EventCode %d : Description %s"
           --#ARGUMENTS {0,1,2,3,}
            --#SEVERITY  INFORMATIONAL
            --#TIMEINDEX 136
        ::= 136027031
 
   mngmtAgentTrap-27032 TRAP-TYPE
        ENTERPRISE compaq
        VARIABLES  { hostName,
                     scellNameDateTime,
                     agentEventCode,
                     agentEventDescription }
        DESCRIPTION
             "The element manager has successfully modified the properties of a virtual disk folder. Command issued through the XML Interface."
           --#TYPE      "Management Agent Event"
           --#SUMMARY   "Host %s : SCellName-TimeDate %s : EventCode %d : Description %s"
           --#ARGUMENTS {0,1,2,3,}
            --#SEVERITY  INFORMATIONAL
            --#TIMEINDEX 136
        ::= 136027032
 
   mngmtAgentTrap-27033 TRAP-TYPE
        ENTERPRISE compaq
        VARIABLES  { hostName,
                     scellNameDateTime,
                     agentEventCode,
                     agentEventDescription }
        DESCRIPTION
             "The element manager has successfully modified the properties of a host folder. Command issued through the XML Interface."
           --#TYPE      "Management Agent Event"
           --#SUMMARY   "Host %s : SCellName-TimeDate %s : EventCode %d : Description %s"
           --#ARGUMENTS {0,1,2,3,}
            --#SEVERITY  INFORMATIONAL
            --#TIMEINDEX 136
        ::= 136027033
 
   mngmtAgentTrap-27034 TRAP-TYPE
        ENTERPRISE compaq
        VARIABLES  { hostName,
                     scellNameDateTime,
                     agentEventCode,
                     agentEventDescription }
        DESCRIPTION
             "The element manager has successfully modified the properties of a hardware root folder. Command issued through the XML Interface."
           --#TYPE      "Management Agent Event"
           --#SUMMARY   "Host %s : SCellName-TimeDate %s : EventCode %d : Description %s"
           --#ARGUMENTS {0,1,2,3,}
            --#SEVERITY  INFORMATIONAL
            --#TIMEINDEX 136
        ::= 136027034
 
   mngmtAgentTrap-27035 TRAP-TYPE
        ENTERPRISE compaq
        VARIABLES  { hostName,
                     scellNameDateTime,
                     agentEventCode,
                     agentEventDescription }
        DESCRIPTION
             "The element manager has successfully modified the properties of a disk group folder. Command issued through the XML Interface."
           --#TYPE      "Management Agent Event"
           --#SUMMARY   "Host %s : SCellName-TimeDate %s : EventCode %d : Description %s"
           --#ARGUMENTS {0,1,2,3,}
            --#SEVERITY  INFORMATIONAL
            --#TIMEINDEX 136
        ::= 136027035
 
   mngmtAgentTrap-27036 TRAP-TYPE
        ENTERPRISE compaq
        VARIABLES  { hostName,
                     scellNameDateTime,
                     agentEventCode,
                     agentEventDescription }
        DESCRIPTION
             "The element manager has successfully modified the properties of a DRM group folder. Command issued through the XML Interface."
           --#TYPE      "Management Agent Event"
           --#SUMMARY   "Host %s : SCellName-TimeDate %s : EventCode %d : Description %s"
           --#ARGUMENTS {0,1,2,3,}
            --#SEVERITY  INFORMATIONAL
            --#TIMEINDEX 136
        ::= 136027036
 
   mngmtAgentTrap-27037 TRAP-TYPE
        ENTERPRISE compaq
        VARIABLES  { hostName,
                     scellNameDateTime,
                     agentEventCode,
                     agentEventDescription }
        DESCRIPTION
             "The element manager has successfully modified the properties of a DRM group root folder. Command issued through the XML Interface."
           --#TYPE      "Management Agent Event"
           --#SUMMARY   "Host %s : SCellName-TimeDate %s : EventCode %d : Description %s"
           --#ARGUMENTS {0,1,2,3,}
            --#SEVERITY  INFORMATIONAL
            --#TIMEINDEX 136
        ::= 136027037
 
   mngmtAgentTrap-27038 TRAP-TYPE
        ENTERPRISE compaq
        VARIABLES  { hostName,
                     scellNameDateTime,
                     agentEventCode,
                     agentEventDescription }
        DESCRIPTION
             "The element manager has successfully modified the properties of a folder. Command issued through the XML Interface."
           --#TYPE      "Management Agent Event"
           --#SUMMARY   "Host %s : SCellName-TimeDate %s : EventCode %d : Description %s"
           --#ARGUMENTS {0,1,2,3,}
            --#SEVERITY  INFORMATIONAL
            --#TIMEINDEX 136
        ::= 136027038
 
   mngmtAgentTrap-27039 TRAP-TYPE
        ENTERPRISE compaq
        VARIABLES  { hostName,
                     scellNameDateTime,
                     agentEventCode,
                     agentEventDescription }
        DESCRIPTION
             "The element manager has successfully modified the properties of a snapshot. Command issued through the XML Interface."
           --#TYPE      "Management Agent Event"
           --#SUMMARY   "Host %s : SCellName-TimeDate %s : EventCode %d : Description %s"
           --#ARGUMENTS {0,1,2,3,}
            --#SEVERITY  INFORMATIONAL
            --#TIMEINDEX 136
        ::= 136027039
 
   mngmtAgentTrap-27040 TRAP-TYPE
        ENTERPRISE compaq
        VARIABLES  { hostName,
                     scellNameDateTime,
                     agentEventCode,
                     agentEventDescription }
        DESCRIPTION
             "The element manager has successfully modified the properties of a disk. Command issued through the XML Interface."
           --#TYPE      "Management Agent Event"
           --#SUMMARY   "Host %s : SCellName-TimeDate %s : EventCode %d : Description %s"
           --#ARGUMENTS {0,1,2,3,}
            --#SEVERITY  INFORMATIONAL
            --#TIMEINDEX 136
        ::= 136027040
 
   mngmtAgentTrap-27041 TRAP-TYPE
        ENTERPRISE compaq
        VARIABLES  { hostName,
                     scellNameDateTime,
                     agentEventCode,
                     agentEventDescription }
        DESCRIPTION
             "The element manager has successfully modified the properties of a disk shelf. Command issued through the XML Interface."
           --#TYPE      "Management Agent Event"
           --#SUMMARY   "Host %s : SCellName-TimeDate %s : EventCode %d : Description %s"
           --#ARGUMENTS {0,1,2,3,}
            --#SEVERITY  INFORMATIONAL
            --#TIMEINDEX 136
        ::= 136027041
 
   mngmtAgentTrap-27042 TRAP-TYPE
        ENTERPRISE compaq
        VARIABLES  { hostName,
                     scellNameDateTime,
                     agentEventCode,
                     agentEventDescription }
        DESCRIPTION
             "The element manager has successfully modified the properties of a controller. Command issued through the XML Interface."
           --#TYPE      "Management Agent Event"
           --#SUMMARY   "Host %s : SCellName-TimeDate %s : EventCode %d : Description %s"
           --#ARGUMENTS {0,1,2,3,}
            --#SEVERITY  INFORMATIONAL
            --#TIMEINDEX 136
        ::= 136027042
 
   mngmtAgentTrap-27043 TRAP-TYPE
        ENTERPRISE compaq
        VARIABLES  { hostName,
                     scellNameDateTime,
                     agentEventCode,
                     agentEventDescription }
        DESCRIPTION
             "The element manager has successfully modified the properties of a controller shelf. Command issued through the XML Interface."
           --#TYPE      "Management Agent Event"
           --#SUMMARY   "Host %s : SCellName-TimeDate %s : EventCode %d : Description %s"
           --#ARGUMENTS {0,1,2,3,}
            --#SEVERITY  INFORMATIONAL
            --#TIMEINDEX 136
        ::= 136027043
 
   mngmtAgentTrap-27044 TRAP-TYPE
        ENTERPRISE compaq
        VARIABLES  { hostName,
                     scellNameDateTime,
                     agentEventCode,
                     agentEventDescription }
        DESCRIPTION
             "The element manager has successfully modified the properties of a cabinet. Command issued through the XML Interface."
           --#TYPE      "Management Agent Event"
           --#SUMMARY   "Host %s : SCellName-TimeDate %s : EventCode %d : Description %s"
           --#ARGUMENTS {0,1,2,3,}
            --#SEVERITY  INFORMATIONAL
            --#TIMEINDEX 136
        ::= 136027044
 
   mngmtAgentTrap-27045 TRAP-TYPE
        ENTERPRISE compaq
        VARIABLES  { hostName,
                     scellNameDateTime,
                     agentEventCode,
                     agentEventDescription }
        DESCRIPTION
             "The element manager has successfully reserved an object. Command issued through the XML Interface."
           --#TYPE      "Management Agent Event"
           --#SUMMARY   "Host %s : SCellName-TimeDate %s : EventCode %d : Description %s"
           --#ARGUMENTS {0,1,2,3,}
            --#SEVERITY  INFORMATIONAL
            --#TIMEINDEX 136
        ::= 136027045
 
   mngmtAgentTrap-27046 TRAP-TYPE
        ENTERPRISE compaq
        VARIABLES  { hostName,
                     scellNameDateTime,
                     agentEventCode,
                     agentEventDescription }
        DESCRIPTION
             "The element manager has successfully released an object. Command issued through the XML Interface."
           --#TYPE      "Management Agent Event"
           --#SUMMARY   "Host %s : SCellName-TimeDate %s : EventCode %d : Description %s"
           --#ARGUMENTS {0,1,2,3,}
            --#SEVERITY  INFORMATIONAL
            --#TIMEINDEX 136
        ::= 136027046
 
   mngmtAgentTrap-27047 TRAP-TYPE
        ENTERPRISE compaq
        VARIABLES  { hostName,
                     scellNameDateTime,
                     agentEventCode,
                     agentEventDescription }
        DESCRIPTION
             "XML cache mutex timeout."
           --#TYPE      "Management Agent Event"
           --#SUMMARY   "Host %s : SCellName-TimeDate %s : EventCode %d : Description %s"
           --#ARGUMENTS {0,1,2,3,}
            --#SEVERITY  INFORMATIONAL
            --#TIMEINDEX 136
        ::= 136027047
 
   mngmtAgentTrap-27048 TRAP-TYPE
        ENTERPRISE compaq
        VARIABLES  { hostName,
                     scellNameDateTime,
                     agentEventCode,
                     agentEventDescription }
        DESCRIPTION
             "XML cache memory allocation error."
           --#TYPE      "Management Agent Event"
           --#SUMMARY   "Host %s : SCellName-TimeDate %s : EventCode %d : Description %s"
           --#ARGUMENTS {0,1,2,3,}
            --#SEVERITY  INFORMATIONAL
            --#TIMEINDEX 136
        ::= 136027048
 
   mngmtAgentTrap-27049 TRAP-TYPE
        ENTERPRISE compaq
        VARIABLES  { hostName,
                     scellNameDateTime,
                     agentEventCode,
                     agentEventDescription }
        DESCRIPTION
             "XML subsystem unknown error."
           --#TYPE      "Management Agent Event"
           --#SUMMARY   "Host %s : SCellName-TimeDate %s : EventCode %d : Description %s"
           --#ARGUMENTS {0,1,2,3,}
            --#SEVERITY  INFORMATIONAL
            --#TIMEINDEX 136
        ::= 136027049
 
	END
