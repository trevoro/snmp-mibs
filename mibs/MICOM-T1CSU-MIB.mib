-- Based on T1 CSU/DSU Requirements document (Rev 1.0, dated 7/8/97).
-- 
-- MIB Revision : 1.0 dated 7-8-97
-- Change Desc. : Initial submittal - R. Carmona. 
-- 
-- MIB Revision : 1.1 dated 8-15-97
-- Change Desc. : Add enumeration to T1 Line Speed, and add
--		  Line Status object. - R. Carmona. 
--
-- MIB Revision : 1.2 dated 10-7-97
-- Change Desc. : Replaced MPA with 4400, and other minor changes - B. Jafari. 
-- 
-- ** RELEASE 3.0 **
-- MIB Revision : 1.3 dated 6-1-98
-- Change Desc. : Deprecated group mcmT1CsuCfgGroup and replaced it with 
--                   table mcmT1E1CsuCfgTable.
--                Obsoleted group nvmT1CsuCfgGroup.
--                Deprecated mcmT1CsuStatusT1LineSpeed and relocated functionality
--                  into table mcmT1E1CsuCfgTable.
--                Deprecated group mcmT1CsuCntlRegStatusGroup and replaced it with 
--                  table mcmT1E1CsuCntlRegStatusTable.
--                Deprecated group mcmT1CsuGenStatusGroup and replaced it with 
--                  table mcmT1CsuGenStatusTable.
--                All T1 CSU replacement tables reside in MIB module: mcmcsu.mib.
--                - R. Carmona, A. Llanes, S. Gaur


MICOM-T1CSU-MIB DEFINITIONS ::= BEGIN

IMPORTS
	OBJECT-TYPE
		FROM RFC-1212
	DisplayString 
		FROM SNMPv2-TC
	micom-oscar 
		FROM MICOM-OSCAR-MIB;


-- group OBJECT IDENTIFIERs

	micom-t1csu			OBJECT IDENTIFIER ::= {micom-oscar 26}
	t1csu-configuration		OBJECT IDENTIFIER ::= {micom-t1csu 1}
	t1csu-status			OBJECT IDENTIFIER ::= {micom-t1csu 2}


--  THE OBJECTS IN THE FOLLOWING GROUP (mcmT1CsuCfgGroup) 
--  HAVE BEEN DEPRECATED (beginning with Release 3.0) AND REPLACED
--  BY THE TABLE mcmT1E1CsuCfgTable (see mcmcsu.mib MIB module).

--  the T1 CSU Configuration Group 
--  (Standard/Operational Parameters)

--  This group provides the T1 CSU configuration parameters.

mcmT1CsuCfgGroup  OBJECT IDENTIFIER ::= { t1csu-configuration 1 }

mcmT1CsuCfgLineBuildOut OBJECT-TYPE
	SYNTAX	INTEGER {
		dist-0-133-feet (1),
		dist-133-266-feet (2),
		dist-266-399-feet (3),
		dist-399-533-feet (4),
		dist-533-655-feet (5),
		neg-7pt5-db (6),
		neg-15-db (7),
		neg-22pt5-db (8)
		}
	ACCESS	read-write
	STATUS	deprecated
	DESCRIPTION
	  "NAME = ;
	   DESC = The value of this object selects the T1 CSU \
		  line build out. (Operational);
	   HELP = ;
	   CAPABILITIES = NET_CFG, VPN_CFG;"
	DEFVAL { neg-7pt5-db }
	::= { mcmT1CsuCfgGroup 1 }

mcmT1CsuCfgFrameFmt OBJECT-TYPE
	SYNTAX	INTEGER {
		d4FramingMode (1),
		esfFramingMode (2)
		}
	ACCESS	read-write
	STATUS	deprecated
	DESCRIPTION
	  "NAME = ;
	   DESC = The value of this object selects the T1 CSU \
		  frame format. (Operational);
	   HELP = ;
	   CAPABILITIES = NET_CFG, VPN_CFG;"
	DEFVAL { esfFramingMode }
	::= { mcmT1CsuCfgGroup 2 }

mcmT1CsuCfgTxIdleCode OBJECT-TYPE
	SYNTAX	INTEGER (0..255)
	ACCESS	read-write
	STATUS	deprecated
	DESCRIPTION
	  "NAME = ;
	   DESC = The value of this object selects the T1 CSU \
		  transmit idle code. (Operational);
	   HELP = ;
	   CAPABILITIES = NET_CFG, VPN_CFG;"
	DEFVAL { 127 }
	::= { mcmT1CsuCfgGroup 3 }

mcmT1CsuCfgTxRx0CodeSuppress OBJECT-TYPE
	SYNTAX	INTEGER {
		b8zsDisable (1),
		b8zsEnable (2)
		}
	ACCESS	read-write
	STATUS	deprecated
	DESCRIPTION
	  "NAME = ;
	   DESC = The value of this object selects zero \
		  code suppression. (Operational);
	   HELP = ;
	   CAPABILITIES = NET_CFG, VPN_CFG;"
	DEFVAL { b8zsEnable }
	::= { mcmT1CsuCfgGroup 4 }

mcmT1CsuCfgTxB7ZeroSuppress OBJECT-TYPE
	SYNTAX	INTEGER {
		b7zsDisable (1),
		b7zsEnable (2)
		}
	ACCESS	read-write
	STATUS	deprecated
	DESCRIPTION
	  "NAME = ;
	   DESC = The value of this object selects bit 7 \
		  zero suppression.  Selects stuffing bit 7 \
		  to 1 if 8 consecutive zeros occurred. \
		  (Operational);
	   HELP = b7zsDisable (1): no stuffing occurred. \
		  b7zsEnable (2): bit 7 forced to a one in \
		  channels with all zeros.;
	   CAPABILITIES = NET_CFG, VPN_CFG;"
	DEFVAL { b7zsDisable }
	::= { mcmT1CsuCfgGroup 5 }

mcmT1CsuCfgTxRxClkSource OBJECT-TYPE
	SYNTAX	INTEGER {
		internalClockingSource (1),
		externalClockingSource (2)
		}
	ACCESS	read-write
	STATUS	deprecated
	DESCRIPTION
	  "NAME = ;
	   DESC = The value of this object selects the T1 CSU \
		  line clocking source. (Operational);
	   HELP = ;
	   CAPABILITIES = NET_CFG, VPN_CFG;"
	DEFVAL { externalClockingSource }
	::= { mcmT1CsuCfgGroup 6 }

mcmT1CsuCfgDS0BasicRate OBJECT-TYPE
	SYNTAX	INTEGER {
		basicRate-64K (1),
		basicRate-56K (2)
		}
	ACCESS	read-write
	STATUS	deprecated
	DESCRIPTION
	  "NAME = ;
	   DESC = The value of this object selects the T1 CSU \
		  line speed to be a multiple of the specified \
		  basic rate.  E.g., Line Speed 256K = 4 x 64K. \
		  (Operational);
	   HELP = ;
	   CAPABILITIES = NET_CFG, VPN_CFG;"
	DEFVAL { basicRate-64K }
	::= { mcmT1CsuCfgGroup 7 }

mcmT1CsuCfgDS0Connection OBJECT-TYPE
	SYNTAX	DisplayString (SIZE (0..73))
	ACCESS	read-write
	STATUS	deprecated
	DESCRIPTION
	  "NAME = ;
	   DESC = The value of this object selects the DS0 \
		  channels for the T1 CSU line connection. \
		  Valid characters are decimal digits, comma \
		  (','), and hyphen ('-'). (Operational);
	   HELP = Comma (',') is used as a delimiter between \
		  individual channel selections. \
		  e.g., 13,16 means DS0 channels 13 and 16. \
		  Hyphen ('-') is used only in Set operations \
		  to indicate a range of DS0 channels. \
		  e.g., 2,5-8 means DS0 channels 2,5,6,7, and 8.;
	   CAPABILITIES = NET_CFG, VPN_CFG;"
	DEFVAL { "" }
	::= { mcmT1CsuCfgGroup 8 }

mcmT1CsuCfgLocalLoopback OBJECT-TYPE
	SYNTAX	INTEGER {
		disable (1),
		enable (2)
		}
	ACCESS	read-write
	STATUS	deprecated
	DESCRIPTION
	  "NAME = ;
	   DESC = The value of this object selects the T1 CSU \
		  local loopback. (Operational);
	   HELP = ;
	   CAPABILITIES = NET_CFG, VPN_CFG;"
	DEFVAL { disable }
	::= { mcmT1CsuCfgGroup 9 }

mcmT1CsuCfgRemoteLoopback OBJECT-TYPE
	SYNTAX	INTEGER {
		disable (1),
		enable (2)
		}
	ACCESS	read-write
	STATUS	deprecated
	DESCRIPTION
	  "NAME = ;
	   DESC = The value of this object selects the T1 CSU \
		  remote loopback. (Operational);
	   HELP = ;
	   CAPABILITIES = NET_CFG, VPN_CFG;"
	DEFVAL { disable }
	::= { mcmT1CsuCfgGroup 10 }

mcmT1CsuCfgPayloadLoopback OBJECT-TYPE
	SYNTAX	INTEGER {
		disable (1),
		enable (2)
		}
	ACCESS	read-write
	STATUS	deprecated
	DESCRIPTION
	  "NAME = ;
	   DESC = The value of this object selects the T1 CSU \
		  payload loopback. (Operational);
	   HELP = ;
	   CAPABILITIES = NET_CFG, VPN_CFG;"
	DEFVAL { disable }
	::= { mcmT1CsuCfgGroup 11 }

mcmT1CsuCfgFramerLoopback OBJECT-TYPE
	SYNTAX	INTEGER {
		disable (1),
		enable (2)
		}
	ACCESS	read-write
	STATUS	deprecated
	DESCRIPTION
	  "NAME = ;
	   DESC = The value of this object selects the T1 CSU \
		  framer loopback. (Operational);
	   HELP = ;
	   CAPABILITIES = NET_CFG, VPN_CFG;"
	DEFVAL { disable }
	::= { mcmT1CsuCfgGroup 12 }

mcmT1CsuCfgTransmitLoopUp OBJECT-TYPE
	SYNTAX	INTEGER {
		disable (1),
		enable (2)
		}
	ACCESS	read-write
	STATUS	deprecated
	DESCRIPTION
	  "NAME = ;
	   DESC = The value of this object selects the T1 CSU \
		  transmit loop up. (Operational);
	   HELP = ;
	   CAPABILITIES = NET_CFG, VPN_CFG;"
	DEFVAL { disable }
	::= { mcmT1CsuCfgGroup 13 }

mcmT1CsuCfgTransmitLoopDown OBJECT-TYPE
	SYNTAX	INTEGER {
		disable (1),
		enable (2)
		}
	ACCESS	read-write
	STATUS	deprecated
	DESCRIPTION
	  "NAME = ;
	   DESC = The value of this object selects the T1 CSU \
		  transmit loop down. (Operational);
	   HELP = ;
	   CAPABILITIES = NET_CFG, VPN_CFG;"
	DEFVAL { disable }
	::= { mcmT1CsuCfgGroup 14 }


--  THE OBJECTS IN THE FOLLOWING GROUP (nvmT1CsuCfgGroup) 
--  HAVE BEEN OBSOLETED (beginning with Release 3.0). 

--  the T1 CSU Configuration Group 
--  (Configuration Parameters)

nvmT1CsuCfgGroup  OBJECT IDENTIFIER ::= { t1csu-configuration 2 }

nvmT1CsuCfgLineBuildOut OBJECT-TYPE
	SYNTAX	INTEGER {
		dist-0-133-feet (1),
		dist-133-266-feet (2),
		dist-266-399-feet (3),
		dist-399-533-feet (4),
		dist-533-655-feet (5),
		neg-7pt5-db (6),
		neg-15-db (7),
		neg-22pt5-db (8)
		}
	ACCESS	read-only
	STATUS	obsolete
	DESCRIPTION
	  "NAME = ;
	   DESC = The value of this object selects the T1 CSU \
		  line build out. (Configuration);
	   HELP = ;
	   CAPABILITIES = NET_CFG, VPN_CFG;"
	DEFVAL { neg-7pt5-db }
	::= { nvmT1CsuCfgGroup 1 }

nvmT1CsuCfgFrameFmt OBJECT-TYPE
	SYNTAX	INTEGER {
		d4FramingMode (1),
		esfFramingMode (2)
		}
	ACCESS	read-only
	STATUS	obsolete
	DESCRIPTION
	  "NAME = ;
	   DESC = The value of this object selects the T1 CSU \
		  frame format. (Configuration);
	   HELP = ;
	   CAPABILITIES = NET_CFG, VPN_CFG;"
	DEFVAL { esfFramingMode }
	::= { nvmT1CsuCfgGroup 2 }

nvmT1CsuCfgTxIdleCode OBJECT-TYPE
	SYNTAX	INTEGER (0..255)
	ACCESS	read-only
	STATUS	obsolete
	DESCRIPTION
	  "NAME = ;
	   DESC = The value of this object selects the T1 CSU \
		  transmit idle code. (Configuration);
	   HELP = ;
	   CAPABILITIES = NET_CFG, VPN_CFG;"
	DEFVAL { 127 }
	::= { nvmT1CsuCfgGroup 3 }

nvmT1CsuCfgTxRx0CodeSuppress OBJECT-TYPE
	SYNTAX	INTEGER {
		b8zsDisable (1),
		b8zsEnable (2)
		}
	ACCESS	read-only
	STATUS	obsolete
	DESCRIPTION
	  "NAME = ;
	   DESC = The value of this object selects zero \
		  code suppression. (Configuration);
	   HELP = ;
	   CAPABILITIES = NET_CFG, VPN_CFG;"
	DEFVAL { b8zsEnable }
	::= { nvmT1CsuCfgGroup 4 }

nvmT1CsuCfgTxB7ZeroSuppress OBJECT-TYPE
	SYNTAX	INTEGER {
		b7zsDisable (1),
		b7zsEnable (2)
		}
	ACCESS	read-only
	STATUS	obsolete
	DESCRIPTION
	  "NAME = ;
	   DESC = The value of this object selects bit 7 \
		  zero suppression.  Selects stuffing bit 7 \
		  to 1 if 8 consecutive zeros occurred. \
		  (Configuration);
	   HELP = b7zsDisable (1): no stuffing occurred. \
		  b7zsEnable (2): bit 7 forced to a one in \
		  channels with all zeros.;
	   CAPABILITIES = NET_CFG, VPN_CFG;"
	DEFVAL { b7zsDisable }
	::= { nvmT1CsuCfgGroup 5 }

nvmT1CsuCfgTxRxClkSource OBJECT-TYPE
	SYNTAX	INTEGER {
		internalClockingSource (1),
		externalClockingSource (2)
		}
	ACCESS	read-only
	STATUS	obsolete
	DESCRIPTION
	  "NAME = ;
	   DESC = The value of this object selects the T1 CSU \
		  line clocking source. (Configuration);
	   HELP = ;
	   CAPABILITIES = NET_CFG, VPN_CFG;"
	DEFVAL { externalClockingSource }
	::= { nvmT1CsuCfgGroup 6 }

nvmT1CsuCfgDS0BasicRate OBJECT-TYPE
	SYNTAX	INTEGER {
		basicRate-64K (1),
		basicRate-56K (2)
		}
	ACCESS	read-only
	STATUS	obsolete
	DESCRIPTION
	  "NAME = ;
	   DESC = The value of this object selects the T1 CSU \
		  line speed to be a multiple of the specified \
		  basic rate.  E.g., Line Speed 256K = 4 x 64K. \
		  (Configuration);
	   HELP = ;
	   CAPABILITIES = NET_CFG, VPN_CFG;"
	DEFVAL { basicRate-64K }
	::= { nvmT1CsuCfgGroup 7 }

nvmT1CsuCfgDS0Connection OBJECT-TYPE
	SYNTAX	DisplayString (SIZE (0..73))
	ACCESS	read-only
	STATUS	obsolete
	DESCRIPTION
	  "NAME = ;
	   DESC = The value of this object selects the DS0 \
		  channels for the T1 CSU line connection. \
		  Valid characters are decimal digits and \
		  comma (','). (Configuration);
	   HELP = Comma (',') is used as a delimiter between \
		  individual channel selections. \
		  e.g., 13,16 means DS0 channels 13 and 16.;
	   CAPABILITIES = NET_CFG, VPN_CFG;"
	DEFVAL { "" }
	::= { nvmT1CsuCfgGroup 8 }

nvmT1CsuCfgLocalLoopback OBJECT-TYPE
	SYNTAX	INTEGER {
		disable (1),
		enable (2)
		}
	ACCESS	read-only
	STATUS	obsolete
	DESCRIPTION
	  "NAME = ;
	   DESC = The value of this object selects the T1 CSU \
		  local loopback. (Configuration);
	   HELP = ;
	   CAPABILITIES = NET_CFG, VPN_CFG;"
	DEFVAL { disable }
	::= { nvmT1CsuCfgGroup 9 }

nvmT1CsuCfgRemoteLoopback OBJECT-TYPE
	SYNTAX	INTEGER {
		disable (1),
		enable (2)
		}
	ACCESS	read-only
	STATUS	obsolete
	DESCRIPTION
	  "NAME = ;
	   DESC = The value of this object selects the T1 CSU \
		  remote loopback. (Configuration);
	   HELP = ;
	   CAPABILITIES = NET_CFG, VPN_CFG;"
	DEFVAL { disable }
	::= { nvmT1CsuCfgGroup 10 }

nvmT1CsuCfgPayloadLoopback OBJECT-TYPE
	SYNTAX	INTEGER {
		disable (1),
		enable (2)
		}
	ACCESS	read-only
	STATUS	obsolete
	DESCRIPTION
	  "NAME = ;
	   DESC = The value of this object selects the T1 CSU \
		  payload loopback. (Configuration);
	   HELP = ;
	   CAPABILITIES = NET_CFG, VPN_CFG;"
	DEFVAL { disable }
	::= { nvmT1CsuCfgGroup 11 }

nvmT1CsuCfgFramerLoopback OBJECT-TYPE
	SYNTAX	INTEGER {
		disable (1),
		enable (2)
		}
	ACCESS	read-only
	STATUS	obsolete
	DESCRIPTION
	  "NAME = ;
	   DESC = The value of this object selects the T1 CSU \
		  framer loopback. (Configuration);
	   HELP = ;
	   CAPABILITIES = NET_CFG, VPN_CFG;"
	DEFVAL { disable }
	::= { nvmT1CsuCfgGroup 12 }

nvmT1CsuCfgTransmitLoopUp OBJECT-TYPE
	SYNTAX	INTEGER {
		disable (1),
		enable (2)
		}
	ACCESS	read-only
	STATUS	obsolete
	DESCRIPTION
	  "NAME = ;
	   DESC = The value of this object selects the T1 CSU \
		  transmit loop up. (Configuration);
	   HELP = ;
	   CAPABILITIES = NET_CFG, VPN_CFG;"
	DEFVAL { disable }
	::= { nvmT1CsuCfgGroup 13 }

nvmT1CsuCfgTransmitLoopDown OBJECT-TYPE
	SYNTAX	INTEGER {
		disable (1),
		enable (2)
		}
	ACCESS	read-only
	STATUS	obsolete
	DESCRIPTION
	  "NAME = ;
	   DESC = The value of this object selects the T1 CSU \
		  transmit loop down. (Configuration);
	   HELP = ;
	   CAPABILITIES = NET_CFG, VPN_CFG;"
	DEFVAL { disable }
	::= { nvmT1CsuCfgGroup 14 }


--  THE FOLLOWING GROUP/OBJECT (mcmT1CsuStatusT1LineSpeed) 
--  HAS BEEN DEPRECATED (beginning with Release 3.0); ITS FUNCTIONALITY
--  HAS BEEN RELOCATED IN THE TABLE mcmT1E1CsuCfgTable
--  (see mcmcsu.mib MIB module).

--  the T1 CSU Configured Line Speed Status Group

--  This 'group' provides the T1 CSU total configured DS0 line speed status object.

mcmT1CsuStatusT1LineSpeed OBJECT-TYPE
	SYNTAX	INTEGER {
		ls-1ds0Times64K-64K (1),
		ls-2ds0Times64K-128K (2),
		ls-3ds0Times64K-192K (3),
		ls-4ds0Times64K-256K (4),
		ls-5ds0Times64K-320K (5),
		ls-6ds0Times64K-384K (6),
		ls-7ds0Times64K-448K (7),
		ls-8ds0Times64K-512K (8),
		ls-9ds0Times64K-576K (9),
		ls-10ds0Times64K-640K (10),
		ls-11ds0Times64K-704K (11),
		ls-12ds0Times64K-768K (12),
		ls-13ds0Times64K-832K (13),
		ls-14ds0Times64K-896K (14),
		ls-15ds0Times64K-960K (15),
		ls-16ds0Times64K-1024K (16),
		ls-17ds0Times64K-1088K (17),
		ls-18ds0Times64K-1152K (18),
		ls-19ds0Times64K-1216K (19),
		ls-20ds0Times64K-1280K (20),
		ls-21ds0Times64K-1344K (21),
		ls-22ds0Times64K-1408K (22),
		ls-23ds0Times64K-1472K (23),
		ls-24ds0Times64K-1536K (24),
		ls-1ds0Times56K-56K (25),
		ls-2ds0Times56K-112K (26),
		ls-3ds0Times56K-168K (27),
		ls-4ds0Times56K-224K (28),
		ls-5ds0Times56K-280K (29),
		ls-6ds0Times56K-336K (30),
		ls-7ds0Times56K-392K (31),
		ls-8ds0Times56K-448K (32),
		ls-9ds0Times56K-504K (33),
		ls-10ds0Times56K-560K (34),
		ls-11ds0Times56K-616K (35),
		ls-12ds0Times56K-672K (36),
		ls-13ds0Times56K-728K (37),
		ls-14ds0Times56K-784K (38),
		ls-15ds0Times56K-840K (39),
		ls-16ds0Times56K-896K (40),
		ls-17ds0Times56K-952K (41),
		ls-18ds0Times56K-1008K (42),
		ls-19ds0Times56K-1064K (43),
		ls-20ds0Times56K-1120K (44),
		ls-21ds0Times56K-1176K (45),
		ls-22ds0Times56K-1232K (46),
		ls-23ds0Times56K-1288K (47),
		ls-24ds0Times56K-1344K (48),
		idle (49)
		}
	ACCESS	read-only
	STATUS	deprecated	
	DESCRIPTION
	  "NAME = ;
	   DESC = The value of this object indicates the T1 CSU \
		  total configured DS0 line speed.;
	   HELP = ;
	   CAPABILITIES = NET_CFG, VPN_CFG ;"
	::= { t1csu-status 1 }


--  THE OBJECTS IN THE FOLLOWING GROUP (mcmT1CsuCntlRegStatusGroup) 
--  HAVE BEEN DEPRECATED (beginning with Release 3.0) AND REPLACED
--  BY THE TABLE mcmT1E1CsuCntlRegStatusTable (see mcmcsu.mib MIB module).

--  the T1 CSU Control Register Status Group 

--  This group provides the T1 CSU Control Register status parameters. 

mcmT1CsuCntlRegStatusGroup  OBJECT IDENTIFIER ::= { t1csu-status 2 }

mcmT1CsuStatusCntlReg1 OBJECT-TYPE
	SYNTAX	INTEGER (0..255)
	ACCESS	read-only
	STATUS	deprecated
	DESCRIPTION
	  "NAME = ;
	   DESC = The value of this object indicates RCR1, the \
		  value of Receive Control Register 1.;
	   HELP = ;
	   CAPABILITIES = NET_CFG, VPN_CFG ;"
	::= { mcmT1CsuCntlRegStatusGroup 1 }

mcmT1CsuStatusCntlReg2 OBJECT-TYPE
	SYNTAX	INTEGER (0..255)
	ACCESS	read-only
	STATUS	deprecated
	DESCRIPTION
	  "NAME = ;
	   DESC = The value of this object indicates RCR2, the \
		  value of Receive Control Register 2.;
	   HELP = ;
	   CAPABILITIES = NET_CFG, VPN_CFG ;"
	::= { mcmT1CsuCntlRegStatusGroup 2 }

mcmT1CsuStatusCntlReg3 OBJECT-TYPE
	SYNTAX	INTEGER (0..255)
	ACCESS	read-only
	STATUS	deprecated
	DESCRIPTION
	  "NAME = ;
	   DESC = The value of this object indicates TCR1, the \
		  value of Transmit Control Register 1.;
	   HELP = ;
	   CAPABILITIES = NET_CFG, VPN_CFG ;"
	::= { mcmT1CsuCntlRegStatusGroup 3 }

mcmT1CsuStatusCntlReg4 OBJECT-TYPE
	SYNTAX	INTEGER (0..255)
	ACCESS	read-only
	STATUS	deprecated
	DESCRIPTION
	  "NAME = ;
	   DESC = The value of this object indicates TCR2, the \
		  value of Transmit Control Register 2.;
	   HELP = ;
	   CAPABILITIES = NET_CFG, VPN_CFG ;"
	::= { mcmT1CsuCntlRegStatusGroup 4 }

mcmT1CsuStatusCntlReg5 OBJECT-TYPE
	SYNTAX	INTEGER (0..255)
	ACCESS	read-only
	STATUS	deprecated
	DESCRIPTION
	  "NAME = ;
	   DESC = The value of this object indicates CCR1, the \
		  value of Common Control Register 1.;
	   HELP = ;
	   CAPABILITIES = NET_CFG, VPN_CFG ;"
	::= { mcmT1CsuCntlRegStatusGroup 5 }

mcmT1CsuStatusCntlReg6 OBJECT-TYPE
	SYNTAX	INTEGER (0..255)
	ACCESS	read-only
	STATUS	deprecated
	DESCRIPTION
	  "NAME = ;
	   DESC = The value of this object indicates CCR2, the \
		  value of Common Control Register 2.;
	   HELP = ;
	   CAPABILITIES = NET_CFG, VPN_CFG ;"
	::= { mcmT1CsuCntlRegStatusGroup 6 }

mcmT1CsuStatusCntlReg7 OBJECT-TYPE
	SYNTAX	INTEGER (0..255)
	ACCESS	read-only
	STATUS	deprecated
	DESCRIPTION
	  "NAME = ;
	   DESC = The value of this object indicates CCR3, the \
		  value of Common Control Register 3.;
	   HELP = ;
	   CAPABILITIES = NET_CFG, VPN_CFG ;"
	::= { mcmT1CsuCntlRegStatusGroup 7 }

mcmT1CsuStatusCntlReg8 OBJECT-TYPE
	SYNTAX	INTEGER (0..255)
	ACCESS	read-only
	STATUS	deprecated
	DESCRIPTION
	  "NAME = ;
	   DESC = The value of this object indicates LICR, the \
		  value of the Line Interface Control Register.;
	   HELP = ;
	   CAPABILITIES = NET_CFG, VPN_CFG ;"
	::= { mcmT1CsuCntlRegStatusGroup 8 }


--  THE OBJECTS IN THE FOLLOWING GROUP (mcmT1CsuGenStatusGroup) 
--  HAVE BEEN DEPRECATED (beginning with Release 3.0) AND REPLACED
--  BY THE TABLE mcmT1CsuGenStatusTable (see mcmcsu.mib MIB module).

--  the T1 CSU General Status Group 

--  This group provides the T1 CSU general status parameters. 

mcmT1CsuGenStatusGroup  OBJECT IDENTIFIER ::= { t1csu-status 3 }

mcmT1CsuGenStatusLineStatus OBJECT-TYPE
	SYNTAX	INTEGER {
		operational (1),
		alarmMode (2),
		testMode (3)
		}
	ACCESS	read-only
	STATUS	deprecated
	DESCRIPTION
	  "NAME = ;
	   DESC = The value of this object indicates the \
		  T1 CSU line status.;
	   HELP = ;
	   CAPABILITIES = NET_CFG, VPN_CFG ;"
	::= { mcmT1CsuGenStatusGroup 1 }

mcmT1CsuGenStatusRedAlarm OBJECT-TYPE
	SYNTAX	INTEGER {
		redAlarm (1),
		noRedAlarm (2)
		}
	ACCESS	read-only
	STATUS	deprecated
	DESCRIPTION
	  "NAME = ;
	   DESC = The value of this object indicates the \
		  T1 CSU red alarm status.;
	   HELP = ;
	   CAPABILITIES = NET_CFG, VPN_CFG ;"
	::= { mcmT1CsuGenStatusGroup 2 }

mcmT1CsuGenStatusYellowAlarm OBJECT-TYPE
	SYNTAX	INTEGER {
		yellowAlarm (1),
		noYellowAlarm (2)
		}
	ACCESS	read-only
	STATUS	deprecated
	DESCRIPTION
	  "NAME = ;
	   DESC = The value of this object indicates the \
		  T1 CSU yellow alarm status.;
	   HELP = ;
	   CAPABILITIES = NET_CFG, VPN_CFG ;"
	::= { mcmT1CsuGenStatusGroup 3 }

mcmT1CsuGenStatusBlueAlarm OBJECT-TYPE
	SYNTAX	INTEGER {
		blueAlarm (1),
		noBlueAlarm (2)
		}
	ACCESS	read-only
	STATUS	deprecated
	DESCRIPTION
	  "NAME = ;
	   DESC = The value of this object indicates the \
		  T1 CSU blue alarm status.;
	   HELP = ;
	   CAPABILITIES = NET_CFG, VPN_CFG ;"
	::= { mcmT1CsuGenStatusGroup 4 }

mcmT1CsuGenStatusRxLevel OBJECT-TYPE
	SYNTAX	INTEGER {
		plus2db-to-neg7pt5db (1),
		neg7pt5db-to-neg15db (2),
		neg15db-to-neg22pt5db (3),
		lessThan-neg22pt5db (4)
		}
	ACCESS	read-only
	STATUS	deprecated
	DESCRIPTION
	  "NAME = ;
	   DESC = The value of this object indicates the T1 \
		  CSU line receive level status.;
	   HELP = ;
	   CAPABILITIES = NET_CFG, VPN_CFG ;"
	::= { mcmT1CsuGenStatusGroup 5 }

mcmT1CsuGenStatusRxElasStrFull OBJECT-TYPE
	SYNTAX	INTEGER {
		yes (1),
		no (2)
		}
	ACCESS	read-only
	STATUS	deprecated
	DESCRIPTION
	  "NAME = ;
	   DESC = The value of this object indicates the T1 \
		  CSU receive elastic store full status.;
	   HELP = ;
	   CAPABILITIES = NET_CFG, VPN_CFG ;"
	::= { mcmT1CsuGenStatusGroup 6 }

mcmT1CsuGenStatusRxElasStrEmpty OBJECT-TYPE
	SYNTAX	INTEGER {
		yes (1),
		no (2)
		}
	ACCESS	read-only
	STATUS	deprecated
	DESCRIPTION
	  "NAME = ;
	   DESC = The value of this object indicates the T1 \
		  CSU receive elastic store empty status.;
	   HELP = ;
	   CAPABILITIES = NET_CFG, VPN_CFG ;"
	::= { mcmT1CsuGenStatusGroup 7 }

mcmT1CsuGenStatusRxPlsDensViolate OBJECT-TYPE
	SYNTAX	INTEGER {
		yes (1),
		no (2)
		}
	ACCESS	read-only
	STATUS	deprecated
	DESCRIPTION
	  "NAME = ;
	   DESC = The value of this object indicates the T1 \
		  CSU receive pulse density violation status.;
	   HELP = ;
	   CAPABILITIES = NET_CFG, VPN_CFG ;"
	::= { mcmT1CsuGenStatusGroup 8 }

mcmT1CsuGenStatusTxPlsDensViolate OBJECT-TYPE
	SYNTAX	INTEGER {
		yes (1),
		no (2)
		}
	ACCESS	read-only
	STATUS	deprecated
	DESCRIPTION
	  "NAME = ;
	   DESC = The value of this object indicates the T1 \
		  CSU transmit pulse density violation status.;
	   HELP = ;
	   CAPABILITIES = NET_CFG, VPN_CFG ;"
	::= { mcmT1CsuGenStatusGroup 9 }

mcmT1CsuGenStatusRxCarrierLoss OBJECT-TYPE
	SYNTAX	INTEGER {
		yes (1),
		no (2)
		}
	ACCESS	read-only
	STATUS	deprecated
	DESCRIPTION
	  "NAME = ;
	   DESC = The value of this object indicates the T1 \
		  CSU receive carrier loss status.;
	   HELP = ;
	   CAPABILITIES = NET_CFG, VPN_CFG ;"
	::= { mcmT1CsuGenStatusGroup 10 }

mcmT1CsuGenStatusRxSyncLoss OBJECT-TYPE
	SYNTAX	INTEGER {
		yes (1),
		no (2)
		}
	ACCESS	read-only
	STATUS	deprecated
	DESCRIPTION
	  "NAME = ;
	   DESC = The value of this object indicates the T1 \
		  CSU receive loss of sync status.;
	   HELP = ;
	   CAPABILITIES = NET_CFG, VPN_CFG ;"
	::= { mcmT1CsuGenStatusGroup 11 }

mcmT1CsuGenStatusLnCdViolHighByte OBJECT-TYPE
	SYNTAX	INTEGER (0..255)
	ACCESS	read-only
	STATUS	deprecated
	DESCRIPTION
	  "NAME = ;
	   DESC = The value of this object indicates the T1 \
		  CSU line code violation high byte.;
	   HELP = ;
	   CAPABILITIES = NET_CFG, VPN_CFG ;"
	::= { mcmT1CsuGenStatusGroup 12 }

mcmT1CsuGenStatusLnCdViolLowByte OBJECT-TYPE
	SYNTAX	INTEGER (0..255)
	ACCESS	read-only
	STATUS	deprecated
	DESCRIPTION
	  "NAME = ;
	   DESC = The value of this object indicates the T1 \
		  CSU line code violation low byte.;
	   HELP = ;
	   CAPABILITIES = NET_CFG, VPN_CFG ;"
	::= { mcmT1CsuGenStatusGroup 13 }

mcmT1CsuGenStatusRxLoopUpCdDetect OBJECT-TYPE
	SYNTAX	INTEGER {
		yes (1),
		no (2)
		}
	ACCESS	read-only
	STATUS	deprecated
	DESCRIPTION
	  "NAME = ;
	   DESC = The value of this object indicates the T1 \
		  CSU receive loop up code status.;
	   HELP = ;
	   CAPABILITIES = NET_CFG, VPN_CFG ;"
	::= { mcmT1CsuGenStatusGroup 14 }

mcmT1CsuGenStatusRxLoopDnCdDetect OBJECT-TYPE
	SYNTAX	INTEGER {
		yes (1),
		no (2)
		}
	ACCESS	read-only
	STATUS	deprecated
	DESCRIPTION
	  "NAME = ;
	   DESC = The value of this object indicates the T1 \
		  CSU receive loop down code status.;
	   HELP = ;
	   CAPABILITIES = NET_CFG, VPN_CFG ;"
	::= { mcmT1CsuGenStatusGroup 15 }


END
