-- 
-- Copyright 1999 by Fore Systems, Inc. 
-- Converted to SMIv2 rfc 2578,2579,2580 - STD 58
--
-- Copyright 1993-1995 by Fore Systems, Inc.

Fore-CES-MIB DEFINITIONS ::= BEGIN

IMPORTS
	OBJECT-TYPE,
	MODULE-IDENTITY,
        Integer32                  FROM SNMPv2-SMI
	TimeInterval,
        TestAndIncr                FROM SNMPv2-TC
	asxd			   FROM Fore-Common-MIB
        ifIndex                    FROM IF-MIB;
	
------------------------------------------------------------------------
-- MIB Groups

cesExtGroup MODULE-IDENTITY
          LAST-UPDATED         "9911050000Z"
          ORGANIZATION         "FORE"
          CONTACT-INFO         
               "      Postal:   FORE Systems Inc.
                                1000 FORE Drive
                                Warrendale, PA 15086-7502
                      Tel:      +1 724 742 6900
                      Email:    nm_mibs@fore.com
                      Web:      http://www.fore.com"
          DESCRIPTION "Fore Systems CES MIB Definitions"
    ::= { asxd 16 }

cesExtTable OBJECT-TYPE
        SYNTAX  TestAndIncr
        MAX-ACCESS read-only
        STATUS current
        DESCRIPTION
                "This indicates the value of the next available index
                to be used for CES creation"
        ::= { cesExtGroup 1 }

cbrctConfTable OBJECT-TYPE
        SYNTAX  SEQUENCE OF CbrctConfEntry
        MAX-ACCESS not-accessible
        STATUS current
        DESCRIPTION
                "A table of CBR Cut-through configuration information."
        ::= { cesExtGroup 2 }

cbrctConfEntry OBJECT-TYPE
        SYNTAX  CbrctConfEntry
        MAX-ACCESS  not-accessible
        STATUS  current
        DESCRIPTION
                "A table entry containing CBR Cut-through configuration
                information for each CES connection. "
        INDEX   { ifIndex }
        ::= { cbrctConfTable 1 }

CbrctConfEntry ::=
        SEQUENCE {
                cbrctState              INTEGER,
                cbrctIdleDetection      INTEGER,
                cbrctIdleMask           Integer32,
                cbrctNoOfIdlePatterns   Integer32,
                cbrctIdlePatterns       Integer32,
                cbrctIdleIntPeriod      TimeInterval,
                cbrctActiveIntPeriod    TimeInterval
        }

cbrctState OBJECT-TYPE
        SYNTAX  INTEGER {
                enabled(1),
                disabled(2)
        }
        MAX-ACCESS  read-write
        STATUS  current
        DESCRIPTION
                "This variable indicates whether the CBR Cut-through
                feature is enabled or disabled on the ingress connection
.
                The values mean:
                enabled         CBR Cut-through enabled
                disabled        CBR Cut-through disabled"
        DEFVAL { disabled }
        ::= { cbrctConfEntry 1 }

cbrctIdleDetection OBJECT-TYPE
        SYNTAX  INTEGER {
                idlePattern(1),
                cas(2)
        }
        MAX-ACCESS  read-write
        STATUS  current
        DESCRIPTION
                "This variable identifies the idle detection
                mechanism used on this connection.
                The different values are:
                idlePattern(1)          detection is based on idle
                                        pattern detection
                cas(2)                  detection is based on CAS
                                        signalling"
        DEFVAL { idlePattern }
        ::= { cbrctConfEntry 2 }

cbrctIdleMask OBJECT-TYPE
        SYNTAX  Integer32
        MAX-ACCESS  read-write
        STATUS  current
        DESCRIPTION
                "This contains the mask pattern for idle detection."
        DEFVAL { 'ff'h }
        ::= { cbrctConfEntry 3 }

cbrctNoOfIdlePatterns OBJECT-TYPE
        SYNTAX  Integer32
        MAX-ACCESS  read-write
        STATUS  current
        DESCRIPTION
                "This variable contains the number of idle patterns
                configured for detection."
        DEFVAL { 2 }
        ::= { cbrctConfEntry 4 }

cbrctIdlePatterns OBJECT-TYPE
        SYNTAX  Integer32
        MAX-ACCESS  read-write
        STATUS  current
        DESCRIPTION
                "This contains the patterns for idle detection.
                For detection based on both idle and mask patterns
                it contains the idle octet patterns. For detection
                based on signalling it contains the octet value
                of AB signalling bits (eg. 00000010 (02H), the bit
                0 is B bit and bit 1 is A bit). Maximum of 4 idle patter
ns
                are used. The idle patterns get filled from the
                least significant byte. The cbrctNoOfIdlePatterns gives
                the number of idle patterns."
        DEFVAL { '00007fff'h }
        ::= { cbrctConfEntry 5 }

cbrctIdleIntPeriod OBJECT-TYPE
        SYNTAX  TimeInterval
        MAX-ACCESS  read-write
        STATUS  current
        DESCRIPTION
                "This contains the integration period for idle
                detection."
        DEFVAL { 6 }
        ::= { cbrctConfEntry 6 }

cbrctActiveIntPeriod OBJECT-TYPE
        SYNTAX  TimeInterval
        MAX-ACCESS  read-write
        STATUS  current
        DESCRIPTION
                "This contains the integration period for active
                detection."
        DEFVAL { 6 }
        ::= { cbrctConfEntry 7 }
 
END
------------------------------------------------------------------------
