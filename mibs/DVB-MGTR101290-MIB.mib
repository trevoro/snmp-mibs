--
-- DVB-MGTR101290-MIB.my
-- MIB generated by MG-SOFT Visual MIB Builder Version 2.5 Build 225
-- Friday, November 09, 2001 at 15:03:43
--

	DVB-MGTR101290-MIB DEFINITIONS ::= BEGIN

		IMPORTS 
			OBJECT-GROUP, MODULE-COMPLIANCE, NOTIFICATION-GROUP			
				FROM SNMPv2-CONF			
			enterprises, Integer32, Unsigned32, Counter32, OBJECT-TYPE, 
			MODULE-IDENTITY, NOTIFICATION-TYPE			
				FROM SNMPv2-SMI			
			TruthValue, DateAndTime, DisplayString, RowStatus, TEXTUAL-CONVENTION			
				FROM SNMPv2-TC;
	
	
		tr101290 MODULE-IDENTITY
			LAST-UPDATED "200111071400Z"
			ORGANIZATION
				"DVB"
			CONTACT-INFO
				"DVB project
				European Broadcasting Union
				CH-1218 GRAND SACONNEX (Geneva)
				Switzerland
				Tel: +41 22 717 21 11
				Fax: +41 22 717 24 81"
			DESCRIPTION
				"DVB Measurement Group MIB to support TR 101 290.
				This tr101290 module contains measurements defined in TR 101 290."
			::= { mg 2 }
		
	
--
-- Textual conventions
--
	
		ActiveTime ::= TEXTUAL-CONVENTION
			DISPLAY-HINT
				"d"
			STATUS current
			DESCRIPTION
				"This is a monotonically increasing value in units of seconds
				that represents the total amount of time for which the
				instrument has been able to perform a particular test or
				measurement. The instrument might not be performing the test
				because some other error condition prevented it, because it
				was operating in a polled mode where it looked at one input
				at a time or because it had been placed in an inactive state
				for a while. 'Able to perform the test' corresponds to the
				TestState being either 'pass' or 'fail'.
				
				The existence of this attribute allows a management system to
				calculate a realistic errors per second value for any test."
			SYNTAX Unsigned32
			
		Availability ::= TEXTUAL-CONVENTION
			STATUS current
			DESCRIPTION
				"Availability is used in the capabilities branch of the MIB
				to indicate whether the instrument is equipped to provide a
				specific test and/or measurement."
			SYNTAX INTEGER
				{
				notAvailable(1),
				testAvailable(2),
				measurementAvailable(3),
				measurementAndTestAvailable(4)
				}
			
		BERMeasurementMethod ::= TEXTUAL-CONVENTION
			STATUS current
			DESCRIPTION
				"Indicates the method used for measuring BER before
				Viterbi decoding"
			SYNTAX INTEGER
				{
				iqSeparate(1),
				iqCombined(2)
				}
			
		BitRateElement ::= TEXTUAL-CONVENTION
			STATUS current
			DESCRIPTION
				"The fundamental data unit that is being counted by the bit
				rate measurement algorithm."
			REFERENCE
				"TR 101 290 5.3.3.1"
			SYNTAX INTEGER
				{
				bit(1),
				byte(2),
				packet(3),
				other(4)
				}
			
		DeliverySystemType ::= TEXTUAL-CONVENTION
			STATUS current
			DESCRIPTION
				"Specifies the physical delivery system used for a
				Transport Stream."
			SYNTAX INTEGER
				{
				unknown(1),
				cable(2),
				satellite(3),
				terrestrial(4)
				}
			
		Enable ::= TEXTUAL-CONVENTION
			STATUS current
			DESCRIPTION
				"This type is used for the '...Enable' objects of tests and
				measurements. It determines whether the test is enabled and
				also which traps can be generated by this test/measurement.
				If the testEnable bit is zero, the test will not be performed
				and the failTrapEnable bit is ignored.  If the testEnable bit
				is one, the test will be performed. Additionally, a
				testFailTrap or measurementFailTrap will be sent when the
				test state becomes 'fail'.
				The 'unknownTrapEnable' bit is only relevant to measurements.
				If it is set to one, a 'measurementUnknownTrap' will be sent
				when the '...MeasurementState' object becomes 'unknown'."
			SYNTAX BITS
				{
				testEnable(0),
				failTrapEnable(1),
				unknownTrapEnable(2)
				}
			
		FloatingPoint ::= TEXTUAL-CONVENTION
			DISPLAY-HINT
				"63a"
			STATUS current
			DESCRIPTION
				"FloatingPoint provides a way of representing non-integer
				numbers in SNMP. Numbers are represented as a string of
				ASCII characters in the natural way. So for example, '3',
				'3.142' and '0.3142E1' are all valid numbers.
				
				The syntax for the string is as follows.  [] enclose an
				optional element, | is the separator for a set of
				alternatives.  () enclose syntax which is to be viewed
				as a unit.
				
				FloatingPoint ::= [Sign]
				                  (Float1 | Float2 | DigitSequence)
				                  [ExponentPart]
				
				Float1        ::= DigitSequence '.' [DigitSequence]
				Float2        ::= '.' DigitSequence
				DigitSequence ::= Digit [DigitSequence]
				
				ExponentPart  ::= ('e' | 'E') [Sign] DigitSequence
				
				Digit         ::= '0'..'9'
				Sign          ::= '+' | '-'"
			SYNTAX OCTET STRING (SIZE (1..63))
			
		GroupAvailability ::= TEXTUAL-CONVENTION
			STATUS current
			DESCRIPTION
				"This is used in the tr101290Capability branch of the MIB to
				specify an agent's degree of support for a whole branch of
				the MIB. The individual values mean:
				
				noSupport         no objects in this branch are available
				selectiveSupport  some but not all objects are available,
				                  refer to the test table for further details
				completeSupport   all objects defined in the stated revision
				                  of the MIB are available"
			SYNTAX INTEGER
				{
				noSupport(1),
				selectiveSupport(2),
				completeSupport(3)
				}
			
		GuardInterval ::= TEXTUAL-CONVENTION
			STATUS current
			DESCRIPTION
				"Guard intervals as specified for DVB-T transmissions.
				interval1d4 means a guard interval of 1/4."
			REFERENCE
				"EN 300 744 section 4.1"
			SYNTAX INTEGER
				{
				interval1d4(1),
				interval1d8(2),
				interval1d16(3),
				interval1d32(4)
				}
			
		Hierarchy ::= TEXTUAL-CONVENTION
			STATUS current
			DESCRIPTION
				"In DVB-T systems this is used to specify whether the
				transmission is hierarchical, and if so, the value of
				alpha."
			SYNTAX INTEGER
				{
				nonHierarchical(1),
				hierarchicalAlphaOne(2),
				hierarchicalAphaTwo(3),
				hierarchicalAlphaFour(4)
				}
			
		IndexConsistencyTest ::= TEXTUAL-CONVENTION
			STATUS current
			DESCRIPTION
				"Index of consistency check tests"
			REFERENCE
				"TR 101 290 section 5.3.4"
			SYNTAX INTEGER { tsIdCheck(1) }
			
		IndexMIPSyntaxTest ::= TEXTUAL-CONVENTION
			STATUS current
			DESCRIPTION
				"This assigns numbers to the MIP syntax tests. These numbers
				are then used as indexes into the MIP syntax table."
			REFERENCE
				"TR 101 290 section 9.20"
			SYNTAX INTEGER
				{
				mipTimingError(1),
				mipStructureError(2),
				mipPresenceError(3),
				mipPointerError(4),
				mipPeriodicityError(5),
				mipTsRateError(6)
				}
			
		IndexPCRMeasurement ::= TEXTUAL-CONVENTION
			STATUS current
			DESCRIPTION
				"This assigns numbers to the PCR measurements. These numbers
				are then used as indexes into the PCR measurement table."
			REFERENCE
				"TR 101 290 section 5.3.2"
			SYNTAX INTEGER
				{
				pcrFO(1),
				pcrDR(2),
				pcrOJ(3),
				pcrAC(4)
				}
			
		IndexServicePerformance ::= TEXTUAL-CONVENTION
			STATUS current
			DESCRIPTION
				"This assigns numbers to the Service Performance measurements.
				These numbers are then used as indexes into the Service
				Performance measurement table."
			REFERENCE
				"TR 101 290 section 5.5"
			SYNTAX INTEGER
				{
				serviceAvailability(1),
				serviceDegradation(2),
				serviceImpairments(3)
				}
			
		IndexTransportStreamTest ::= TEXTUAL-CONVENTION
			STATUS current
			DESCRIPTION
				"IndexTransportStreamTest assigns a unique numerical
				value to each of the TR 101 290 Transport Stream tests
				in section 5.2. The number allocated is:
				
				  priority * 1000 + test number * 10 + subtest
				
				Subtest is zero if there is no subtest.  Subtest 'a'
				is numbered 1, 'b' is numbered 2 etc. The enumeration
				names are derived directly from the test names in
				TR 101 290 taking into account the syntax requirements
				of the MIB."
			REFERENCE
				"TR 101 290 section 5.2"
			SYNTAX INTEGER
				{
				tsSyncLoss(1010),
				syncByteError(1020),
				patError2(1031),
				continuityCountError(1040),
				pmtError2(1051),
				pidError(1060),
				transportError(2010),
				crcError(2020),
				pcrRepetitionError(2031),
				pcrDiscontinuityError(2032),
				pcrAccuracyError(2040),
				ptsError(2050),
				catError(2060),
				nitActualError(3011),
				nitOtherError(3012),
				siRepetitionError(3020),
				bufferError(3030),
				unreferencedPID(3041),
				sdtActualError(3051),
				sdtOtherError(3052),
				eitActualError(3061),
				eitOtherError(3062),
				eitPfError(3063),
				rstError(3070),
				tdtError(3080),
				emptyBufferError(3090),
				dataDelayError(3100)
				}
			
		InputNumber ::= TEXTUAL-CONVENTION
			DISPLAY-HINT
				"d"
			STATUS current
			DESCRIPTION
				"InputNumber objects are used to select a specific Transport
				Stream input on a multi-input monitoring/measurement device.
				On a single input monitoring/measuring device, InputNumber
				objects will always have the value one."
			SYNTAX INTEGER (1..2147483647)
			
		MeasurementState ::= TEXTUAL-CONVENTION
			STATUS current
			DESCRIPTION
				"MeasurementState is used to represent the state of a single
				measurement.
				
				'disabled' means that the measurement has been disabled by
				setting the 'testEnable' bit in its ...Enable object to zero.
				
				'unknown' means that the equipment cannot provide a value
				because of temporary circumstances, for example some other
				signal condition makes this measurement impossible.
				
				'abnormal' means that the measurement value is incorrect for
				reasons connected with that measurement itself. For example
				the measurement may be out of range. A measurement value is
				still provided and users or managers with knowledge of the
				behaviour of this specific measuring equipment may be able
				to interpret the value.
				
				'normal' means that the measurement is enabled and has been
				evaluated."
			SYNTAX INTEGER
				{
				disabled(1),
				unknown(2),
				normal(3),
				abnormal(4)
				}
			
		Modulation ::= TEXTUAL-CONVENTION
			STATUS current
			DESCRIPTION
				"Modulation systems used in RF transmissions"
			REFERENCE
				"TR 101 198 (BPSK)
				EN 300 421 (QPSK)
				EN 301 210 (8PSK, 16QAM)
				EN 300 429 (16QAM, 32QAM, 64QAM, 128QAM, 256QAM)
				EN 300 744 (QPSK, 16QAM, 64QAM, 16QAM/alpha=2, 64QAM/alpha=2,
				            16QAM/alpha=4, 64QAM/alpha=4)
				"
			SYNTAX INTEGER
				{
				bpsk(1),
				qpsk(2),
				psk8(3),
				qam16(4),
				qam32(5),
				qam64(6),
				qam128(7),
				qam256(8),
				qam16Alpha2(9),
				qam64Alpha2(10),
				qam16Alpha4(11),
				qam64Alpha4(12)
				}
			
		PIDPlusOne ::= TEXTUAL-CONVENTION
			DISPLAY-HINT
				"x"
			STATUS current
			DESCRIPTION
				"An object of type PIDPlusOne represents an MPEG-2 PID number.
				The numeric value of the object is the PID + 1, to allow for
				its use as a table index."
			REFERENCE
				"ISO 13818-1 2.1.32"
			SYNTAX INTEGER (1..8192)
			
		PollingInterval ::= TEXTUAL-CONVENTION
			STATUS current
			DESCRIPTION
				"Objects of this type are used by the agent to indicate how
				often it internally updates the information related to a
				particular test or measurement. The manager can then adjust
				its polling behaviour accordingly. The polling interval
				should be interpreted by the manager as approximate. In
				practice the agent may update the information faster or
				slower than indicated depending on the circumstances.
				
				The meaning of the value is:
				    positive - represents a normal value in milliseconds
				    zero     - the value is updated continuously
				    negative - unknown or not applicable "
			SYNTAX Integer32
			
		RateStatus ::= TEXTUAL-CONVENTION
			STATUS current
			DESCRIPTION
				"RateStatus is used in trap control"
			SYNTAX INTEGER
				{
				disabled(1),
				enabled(2),
				enabledThrottled(3)
				}
			
		ServiceId ::= TEXTUAL-CONVENTION
			DISPLAY-HINT
				"x"
			STATUS current
			DESCRIPTION
				"Allowed values of program_number/service_id.  Note that zero
				is used in the PAT to represent the NIT PID and so will never
				occur as a service_id."
			SYNTAX INTEGER (1..65535)
			
		TerrestrialTransmissionMode ::= TEXTUAL-CONVENTION
			STATUS current
			DESCRIPTION
				"Transmission mode for DVB-T transmissions, specifies whether
				there are 2k or 8k carriers."
			REFERENCE
				"EN 300 744 section 4.1"
			SYNTAX INTEGER
				{
				mode2k(1),
				mode8k(2)
				}
			
		TestState ::= TEXTUAL-CONVENTION
			STATUS current
			DESCRIPTION
				"TestState is used to represent the state of a single test.
				
				'disabled' means that the test has been disabled by setting
				the 'testEnable' bit of its ...Enable variable to zero.
				
				'unknown' means that the equipment cannot provide a value
				for the state because of temporary circumstances (for example
				some other error makes this test impossible to evaluate).
				
				'pass' means that the test is enabled, can be evaluated and
				is not failing.
				
				For a 'Status error', 'fail' means that the state of the
				input is currently in error.  For an 'Event error', 'fail'
				means that an error event has occurred within the most recent
				persistence interval as defined by the
				'controlEventPersistence' object."
			SYNTAX INTEGER
				{
				disabled(1),
				unknown(2),
				pass(3),
				fail(4)
				}
			
		TestSummary ::= TEXTUAL-CONVENTION
			STATUS current
			DESCRIPTION
				"Bit String providing a status summary for all the tests
				defined in this MIB module. A bit is set to one if the
				state of that test is 'fail'.
				
				In several cases, a single bit summarises the results of
				a set of tests. In that case, if the state of any of the
				tests is 'fail', the bit is set to one. An example of
				this is 'bitratePID' where the single bit summarises
				whether all the PID bitrates are within range.
				
				To aid identification, the bits are numbered in the order
				in which the associated tests appear in the MIB. Other
				than this, there is no connection between the bit number
				and the OID of the test."
			SYNTAX BITS
				{
				tsTsSyncLoss(0),
				tsSyncByteError(1),
				tsPatError2(2),
				tsContinuityCountError(3),
				tsPmtError2(4),
				tsPidError(5),
				tsTransportError(6),
				tsCrcError(7),
				tsPcrRepetitionError(8),
				tsPcrDiscontinuityError(9),
				tsPcrAccuracyError(10),
				tsPtsError(11),
				tsCatError(12),
				tsNitActualError(13),
				tsNitOtherError(14),
				tsSiRepetitionError(15),
				tsBufferError(16),
				tsUnreferencedPID(17),
				tsSdtActualError(18),
				tsSdtOtherError(19),
				tsEitActualError(20),
				tsEitOtherError(21),
				tsEitPfError(22),
				tsRstError(23),
				tsTdtError(24),
				tsEmptyBufferError(25),
				tsDataDelayError(26),
				pcrPcrFO(27),
				pcrPcrDR(28),
				pcrPcrOJ(29),
				pcrPcrAC(30),
				bitrateTransportStream(31),
				bitrateService(32),
				bitratePID(33),
				tsTsConsistency(34),
				performanceServiceAvailability(35),
				performanceServiceDegradation(36),
				performanceServiceImpairments(37),
				csSysAvailability(38),
				csLinkAvailability(39),
				csBerRS(40),
				csRFIFSignalPower(41),
				csNoisePower(42),
				csMer(43),
				csSteMean(44),
				csSteDeviation(45),
				csCS(46),
				csAI(47),
				csQE(48),
				csRTE(49),
				csCI(50),
				csPJ(51),
				csSNR(52),
				cNoiseMargin(53),
				cEstNoiseMargin(54),
				cSignQualMarT(55),
				cEND(56),
				cOutBandEmiss(57),
				sBerViterbi(58),
				sIfSpectrum(59),
				tRFAccuracy(60),
				tRFChannelWidth(61),
				tSymbolLength(62),
				tRFIFPower(63),
				tRFIFSpectrum(64),
				tEND(65),
				tENF(66),
				tENDLP(67),
				tENFLP(68),
				tLinearity(69),
				tBerViterbi(70),
				tBerViterbiLP(71),
				tBerRS(72),
				tBerRSLP(73),
				tMER(74),
				tSteMean(75),
				tSteDeviation(76),
				tCS(77),
				tAI(78),
				tQE(79),
				tPJ(80),
				tMipTimingError(81),
				tMipStructureError(82),
				tMipPresenceError(83),
				tMipPointerError(84),
				tMipPeriodicityError(85),
				tMipTsRateError(86),
				tSepEti(87),
				tSepSeti(88)
				}
			
		TransportStreamID ::= TEXTUAL-CONVENTION
			DISPLAY-HINT
				"x"
			STATUS current
			DESCRIPTION
				"Range of possible values for a transport_stream_id
				as found in the PAT."
			SYNTAX INTEGER (0..65535)
			
		UATMode ::= TEXTUAL-CONVENTION
			STATUS current
			DESCRIPTION
				"Method of determining the start and end of a period of
				Unavailable Time."
			REFERENCE
				"TR 101 290 section 5.4.5"
			SYNTAX INTEGER
				{
				nConsecutive(1),
				rollingWindow(2)
				}
			
	
--
-- Node definitions
--
	
		dvb OBJECT IDENTIFIER ::= { enterprises 2696 }
		
		mg OBJECT IDENTIFIER ::= { dvb 3 }
		
		tr101290Objects OBJECT IDENTIFIER ::= { tr101290 1 }
		
-- The tr101290Control branch contains objects that provide
-- general control of and general information about the
-- measurements and tests in the rest of the MIB.
		tr101290Control OBJECT IDENTIFIER ::= { tr101290Objects 1 }
		
		controlNow OBJECT-TYPE
			SYNTAX DateAndTime
			MAX-ACCESS read-write
			STATUS current
			DESCRIPTION
				"The current date and time at the location of the measurement
				equipment. It is highly desirable that the offset from UTC
				should be included.
				
				It is possible to set the time and date through this object,
				but it is expected that most systems will incorporate a more
				accurate method for doing this."
			::= { tr101290Control 1 }
		
		controlEventPersistence OBJECT-TYPE
			SYNTAX FloatingPoint
			UNITS "second"
			MAX-ACCESS read-write
			STATUS current
			DESCRIPTION
				"The persistence timer used with Event errors.  An Event error
				test remains in the 'fail' state for this length of time
				after the occurrence of the Event."
			DEFVAL { "2" }
			::= { tr101290Control 2 }
		
		controlRFSystemTable OBJECT-TYPE
			SYNTAX SEQUENCE OF ControlRFSystemEntry
			MAX-ACCESS not-accessible
			STATUS current
			DESCRIPTION
				"Table which controls the RF modulation expected to
				be received on each input."
			::= { tr101290Control 3 }
		
		controlRFSystemEntry OBJECT-TYPE
			SYNTAX ControlRFSystemEntry
			MAX-ACCESS not-accessible
			STATUS current
			DESCRIPTION
				"Row specification"
			INDEX { rfSystemInputNumber }
			::= { controlRFSystemTable 1 }
		
		ControlRFSystemEntry ::=
			SEQUENCE { 
				rfSystemInputNumber
					InputNumber,
				rfSystemDelivery
					DeliverySystemType
			 }

		rfSystemInputNumber OBJECT-TYPE
			SYNTAX InputNumber
			MAX-ACCESS not-accessible
			STATUS current
			DESCRIPTION
				"RF input whose mode of operation is to be set"
			::= { controlRFSystemEntry 1 }
		
		rfSystemDelivery OBJECT-TYPE
			SYNTAX DeliverySystemType
			MAX-ACCESS read-write
			STATUS current
			DESCRIPTION
				"The type of signal the instrument should expect at its input."
			::= { controlRFSystemEntry 2 }
		
		controlSynchronizationTable OBJECT-TYPE
			SYNTAX SEQUENCE OF ControlSynchronizationEntry
			MAX-ACCESS not-accessible
			STATUS current
			DESCRIPTION
				"Table reserved for future specification of synchronized
				timing."
			::= { tr101290Control 4 }
		
		controlSynchronizationEntry OBJECT-TYPE
			SYNTAX ControlSynchronizationEntry
			MAX-ACCESS not-accessible
			STATUS current
			DESCRIPTION
				"Row specification"
			INDEX { controlSynchronizationInputNumber }
			::= { controlSynchronizationTable 1 }
		
		ControlSynchronizationEntry ::=
			SEQUENCE { 
				controlSynchronizationInputNumber
					InputNumber,
				controlSynchronizedTime
					FloatingPoint
			 }

		controlSynchronizationInputNumber OBJECT-TYPE
			SYNTAX InputNumber
			MAX-ACCESS not-accessible
			STATUS current
			DESCRIPTION
				"Transport Stream number to which the objects in this row apply."
			::= { controlSynchronizationEntry 1 }
		
		controlSynchronizedTime OBJECT-TYPE
			SYNTAX FloatingPoint
			MAX-ACCESS read-write
			STATUS current
			DESCRIPTION
				"This object is reserved pending future standardisation of
				timestamping of Transport Streams. "
			::= { controlSynchronizationEntry 2 }
		
-- This branch of the MIB contains all the traps and their
-- associated control information.
		tr101290Trap OBJECT IDENTIFIER ::= { tr101290Objects 2 }
		
-- This prefix is necessary to satisfy the requirement of RFC 2578
-- section 8.5 that 'the next to last sub-identifier in the name of
-- any newly-defined notification must have the value zero'.
		trapPrefix OBJECT IDENTIFIER ::= { tr101290Trap 0 }
		
		testFailTrap NOTIFICATION-TYPE
			OBJECTS { trapControlOID, trapControlGenerationTime, trapControlFailureSummary, trapInput }
			STATUS current
			DESCRIPTION
				"This trap is sent when a test which is not associated with a
				measurement fails. This trap is triggered by the transition of
				the '...State' or '...TestState' object associated with the
				test to the 'fail' state from any other state.
				
				Transmission of the trap is subject to rate control and to the
				enable status of each test."
			::= { trapPrefix 1 }
		
		measurementFailTrap NOTIFICATION-TYPE
			OBJECTS { trapControlOID, trapControlGenerationTime, trapControlMeasurementValue, trapControlFailureSummary, trapInput
				 }
			STATUS current
			DESCRIPTION
				"Trap which is sent when a test which is associated with a
				measurement fails. This trap is triggered by the transition
				of the '...State' or '...TestState' object associated with
				the test to the 'fail' state from any other state.
				
				Transmission of the trap is subject to rate control and to
				the enable status of each test."
			::= { trapPrefix 2 }
		
		measurementUnknownTrap NOTIFICATION-TYPE
			OBJECTS { trapControlOID, trapControlGenerationTime, trapControlFailureSummary, trapInput }
			STATUS current
			DESCRIPTION
				"Trap which is sent when a measurement value becomes
				unavailable. This trap is triggered by the transition of
				the '...MeasurementState' object associated with the
				measurement to the 'unknown' state from any other state.
				
				Transmission of the trap is subject to rate control."
			::= { trapPrefix 3 }
		
		trapControlTable OBJECT-TYPE
			SYNTAX SEQUENCE OF TrapControlEntry
			MAX-ACCESS not-accessible
			STATUS current
			DESCRIPTION
				"Table of trap control information for each input"
			::= { tr101290Trap 1 }
		
		trapControlEntry OBJECT-TYPE
			SYNTAX TrapControlEntry
			MAX-ACCESS not-accessible
			STATUS current
			DESCRIPTION
				"Row specification"
			INDEX { trapControlInputNumber }
			::= { trapControlTable 1 }
		
		TrapControlEntry ::=
			SEQUENCE { 
				trapControlInputNumber
					InputNumber,
				trapControlOID
					OBJECT IDENTIFIER,
				trapControlGenerationTime
					DateAndTime,
				trapControlMeasurementValue
					FloatingPoint,
				trapControlRateStatus
					RateStatus,
				trapControlPeriod 
					Unsigned32,
				trapControlFailureSummary
					TestSummary
			 }

		trapControlInputNumber OBJECT-TYPE
			SYNTAX InputNumber
			MAX-ACCESS not-accessible
			STATUS current
			DESCRIPTION
				"Each Transport Stream input has separate trap control
				parameters. This object identifies the Transport Stream
				input to which the trap control parameters apply"
			::= { trapControlEntry 1 }
		
		trapControlOID OBJECT-TYPE
			SYNTAX OBJECT IDENTIFIER
			MAX-ACCESS accessible-for-notify
			STATUS current
			DESCRIPTION
				"In the case of a testFailTrap or a measurementFailTrap, this
				object holds the OID of the '...State' or '...TestState' object
				whose transition to 'fail' has triggered the trap.
				
				In the case of a measurementUnknownTrap, this object holds the
				OID of the '...MeasurementState' object whose transition to
				'unknown' has triggered the trap.
				
				This object is present for the formal purpose of defining the
				variable bindings returned with the traps. It is not accessible
				for normal reading."
			::= { trapControlEntry 2 }
		
		trapControlGenerationTime OBJECT-TYPE
			SYNTAX DateAndTime
			MAX-ACCESS accessible-for-notify
			STATUS current
			DESCRIPTION
				"In the case of a testFailTrap or a measurementFailTrap,
				at the moment when the trap is generated, the value of
				the '...LatestError' object associated with the test which
				caused the trap is copied here. In the case of a
				measurementUnknownTrap, the time at which the measurement
				became unknown is copied here.
				
				This object is present for the formal purpose of defining
				the variable bindings returned with the traps. It is not
				accessible for normal reading."
			::= { trapControlEntry 3 }
		
		trapControlMeasurementValue OBJECT-TYPE
			SYNTAX FloatingPoint
			MAX-ACCESS accessible-for-notify
			STATUS current
			DESCRIPTION
				"At the moment when a measurementFailTrap is generated,
				the value of this object is set from the '...Value' object
				associated with the measurement which caused the trap.
				Where a measurement returns multiple values, the value
				which is copied here is the one which is compared with the
				threshold(s) to generate the test result. The measurement
				units are the same as those of the source object.
				
				This object is present for the formal purpose of defining
				the variable bindings returned with the traps. It is not
				accessible for normal reading."
			::= { trapControlEntry 4 }
		
		trapControlRateStatus OBJECT-TYPE
			SYNTAX RateStatus
			MAX-ACCESS read-write
			STATUS current
			DESCRIPTION
				"This object is used for rate control of traps, preventing
				overload of the management network by transmission of an
				excessive number of traps. The value 'disabled' means that
				traps are never sent. The value 'enabled' means that a trap
				will be sent when triggered.
				
				When a trap is sent, the agent changes the value of this
				object to 'enabledThrottled'. In this state the agent will
				not send any more traps. The agent automatically changes
				the value back to 'enabled' when the time specified by
				trapControlPeriod expires. A management application may
				set the value to 'enabled' at any time, but must never set
				the value to 'enabledThrottled'.
				
				This single status applies to all the trap types, so for
				example if an agent sends a testFailTrap it will not send
				a measurementFailTrap until the trapControlPeriod expires."
			::= { trapControlEntry 5 }
		
		trapControlPeriod  OBJECT-TYPE
			SYNTAX Unsigned32 (0..3600000)
			UNITS "millisecond"
			MAX-ACCESS read-write
			STATUS current
			DESCRIPTION
				"An agent will ensure that the interval between sending traps is
				no shorter than this time period. The management system can
				override this by setting trapControlRateStatus back to 'enabled'
				within the time period."
			::= { trapControlEntry 6 }
		
		trapControlFailureSummary OBJECT-TYPE
			SYNTAX TestSummary
			MAX-ACCESS read-only
			STATUS current
			DESCRIPTION
				"This bit string contains a summary of all the test failures.
				If the bit for the test is set to one, that test is in a
				fail state.
				
				When a trap is being generated, the agent should ensure that
				this information is as up to date as possible, without
				causing undue delay in sending the trap."
			::= { trapControlEntry 7 }
		
		trapInput OBJECT-TYPE
			SYNTAX InputNumber
			MAX-ACCESS accessible-for-notify
			STATUS current
			DESCRIPTION
				"The Transport Stream input whose change triggered the
				current trap.  This information can also be obtained by
				analysing the trapControlOID, but trapInput provides the
				information directly.
				
				This object is present for the formal purpose of defining
				the variable bindings returned with the traps. It is not
				accessible for normal reading."
			::= { tr101290Trap 2 }
		
-- From this branch of the MIB, a manager can read the
-- capabilities of each agent. The capabilities say which tests
-- and measurements are supported by that agent.
-- 
-- The capabilities are defined relative to a specific revision
-- of this MIB module (defined by the capabilityMIBRevision
-- object).
-- 
-- For each group of capabilities, at least one of the following
-- must be true:
-- 
-- 1) the capabilityXXXGroup object has the value 'noSupport'
-- 2) the capabilityXXXGroup object has the value 'completeSupport'
-- 3) there is a row in the capabilityXXXTable for every object
--    defined in the supported revision of the MIB.
		tr101290Capability OBJECT IDENTIFIER ::= { tr101290Objects 3 }
		
		capabilityMIBRevision OBJECT-TYPE
			SYNTAX DateAndTime
			MAX-ACCESS read-only
			STATUS current
			DESCRIPTION
				"The capabilities of the agent are expressed in relation to a
				specific revision of the tr101290 MIB module. The date and time
				here must exactly match one of the revision dates in the
				MODULE-IDENTITY section of the MIB."
			::= { tr101290Capability 1 }
		
-- Capabilities for the tr101290TS branch of the MIB
		capabilityTS OBJECT IDENTIFIER ::= { tr101290Capability 5 }
		
		capabilityTSGroup OBJECT-TYPE
			SYNTAX GroupAvailability
			MAX-ACCESS read-only
			STATUS current
			DESCRIPTION
				"Specifies the overall availability of the Transport Stream
				group of tests and measurements, tr101290TS."
			::= { capabilityTS 1 }
		
		capabilityTSTable OBJECT-TYPE
			SYNTAX SEQUENCE OF CapabilityTSEntry
			MAX-ACCESS not-accessible
			STATUS current
			DESCRIPTION
				"Specifies the individual availability of the Transport Stream
				group of tests and measurements, tr101290TS."
			::= { capabilityTS 2 }
		
		capabilityTSEntry OBJECT-TYPE
			SYNTAX CapabilityTSEntry
			MAX-ACCESS not-accessible
			STATUS current
			DESCRIPTION
				"Row specification"
			INDEX { capabilityTSOID }
			::= { capabilityTSTable 1 }
		
		CapabilityTSEntry ::=
			SEQUENCE { 
				capabilityTSOID
					OBJECT IDENTIFIER,
				capabilityTSAvailability
					Availability,
				capabilityTSPollInterval
					PollingInterval
			 }

		capabilityTSOID OBJECT-TYPE
			SYNTAX OBJECT IDENTIFIER
			MAX-ACCESS not-accessible
			STATUS current
			DESCRIPTION
				"The object identifier of a specific test/measurement. The object
				identifier of the object within the table whose SYNTAX is
				'TestState' is used to identify the test/measurement. Table
				index components of the object identifier are set to zero,
				except for those which identify specific tests/measurements.
				Such index objects always have a syntax which begins 'Index...'
				in this MIB."
			::= { capabilityTSEntry 1 }
		
		capabilityTSAvailability OBJECT-TYPE
			SYNTAX Availability
			MAX-ACCESS read-only
			STATUS current
			DESCRIPTION
				"The availability of a specific test or measurement"
			::= { capabilityTSEntry 2 }
		
		capabilityTSPollInterval OBJECT-TYPE
			SYNTAX PollingInterval
			UNITS "millisecond"
			MAX-ACCESS read-only
			STATUS current
			DESCRIPTION
				"Indicates the interval between updates of the information
				supplied by this object."
			::= { capabilityTSEntry 3 }
		
-- Capabilities for the tr101290CableSat branch of the MIB
		capabilityCableSat OBJECT IDENTIFIER ::= { tr101290Capability 6 }
		
		capabilityCableSatGroup OBJECT-TYPE
			SYNTAX GroupAvailability
			MAX-ACCESS read-only
			STATUS current
			DESCRIPTION
				"Specifies the overall availability of the cable and satellite
				group of tests and measurements, tr101290CableSat."
			::= { capabilityCableSat 1 }
		
		capabilityCableSatTable OBJECT-TYPE
			SYNTAX SEQUENCE OF CapabilityCableSatEntry
			MAX-ACCESS not-accessible
			STATUS current
			DESCRIPTION
				"Specifies the individual availability of the cable and satellite
				group of tests and measurements, tr101290CableSat."
			::= { capabilityCableSat 2 }
		
		capabilityCableSatEntry OBJECT-TYPE
			SYNTAX CapabilityCableSatEntry
			MAX-ACCESS not-accessible
			STATUS current
			DESCRIPTION
				"Row specification"
			INDEX { capabilityCableSatOID }
			::= { capabilityCableSatTable 1 }
		
		CapabilityCableSatEntry ::=
			SEQUENCE { 
				capabilityCableSatOID
					OBJECT IDENTIFIER,
				capabilityCableSatAvailability
					Availability,
				capabilityCableSatPollInterval
					PollingInterval
			 }

		capabilityCableSatOID OBJECT-TYPE
			SYNTAX OBJECT IDENTIFIER
			MAX-ACCESS not-accessible
			STATUS current
			DESCRIPTION
				"The object identifier of a specific test/measurement. The object
				identifier of the object within the table whose SYNTAX is
				'TestState' is used to identify the test/measurement. Table
				index components of the object identifier are set to zero,
				except for those which identify specific tests/measurements.
				Such index objects always have a syntax which begins 'Index...'
				in this MIB."
			::= { capabilityCableSatEntry 1 }
		
		capabilityCableSatAvailability OBJECT-TYPE
			SYNTAX Availability
			MAX-ACCESS read-only
			STATUS current
			DESCRIPTION
				"The availability of a specific test or measurement"
			::= { capabilityCableSatEntry 2 }
		
		capabilityCableSatPollInterval OBJECT-TYPE
			SYNTAX PollingInterval
			UNITS "millisecond"
			MAX-ACCESS read-only
			STATUS current
			DESCRIPTION
				"Indicates the interval between updates of the information
				supplied by this object."
			::= { capabilityCableSatEntry 3 }
		
-- Capabilities for the tr101290Cable branch of the MIB
		capabilityCable OBJECT IDENTIFIER ::= { tr101290Capability 7 }
		
		capabilityCableGroup OBJECT-TYPE
			SYNTAX GroupAvailability
			MAX-ACCESS read-only
			STATUS current
			DESCRIPTION
				"Specifies the overall availability of the cable group of
				tests and measurements, tr101290Cable."
			::= { capabilityCable 1 }
		
		capabilityCableTable OBJECT-TYPE
			SYNTAX SEQUENCE OF CapabilityCableEntry
			MAX-ACCESS not-accessible
			STATUS current
			DESCRIPTION
				"Specifies the individual availability of the cable group of
				tests and measurements, tr101290Cable."
			::= { capabilityCable 2 }
		
		capabilityCableEntry OBJECT-TYPE
			SYNTAX CapabilityCableEntry
			MAX-ACCESS not-accessible
			STATUS current
			DESCRIPTION
				"Row specification"
			INDEX { capabilityCableOID }
			::= { capabilityCableTable 1 }
		
		CapabilityCableEntry ::=
			SEQUENCE { 
				capabilityCableOID
					OBJECT IDENTIFIER,
				capabilityCableAvailability
					Availability,
				capabilityCablePollInterval
					PollingInterval
			 }

		capabilityCableOID OBJECT-TYPE
			SYNTAX OBJECT IDENTIFIER
			MAX-ACCESS not-accessible
			STATUS current
			DESCRIPTION
				"The object identifier of a specific test/measurement. The object
				identifier of the object within the table whose SYNTAX is
				'TestState' is used to identify the test/measurement. Table
				index components of the object identifier are set to zero,
				except for those which identify specific tests/measurements.
				Such index objects always have a syntax which begins 'Index...'
				in this MIB."
			::= { capabilityCableEntry 1 }
		
		capabilityCableAvailability OBJECT-TYPE
			SYNTAX Availability
			MAX-ACCESS read-only
			STATUS current
			DESCRIPTION
				"The availability of a specific test or measurement"
			::= { capabilityCableEntry 2 }
		
		capabilityCablePollInterval OBJECT-TYPE
			SYNTAX PollingInterval
			UNITS "millisecond"
			MAX-ACCESS read-only
			STATUS current
			DESCRIPTION
				"Indicates the interval between updates of the information
				supplied by this object."
			::= { capabilityCableEntry 3 }
		
-- Capabilities for the tr101290Satellite branch of the MIB
		capabilitySatellite OBJECT IDENTIFIER ::= { tr101290Capability 8 }
		
		capabilitySatelliteGroup OBJECT-TYPE
			SYNTAX GroupAvailability
			MAX-ACCESS read-only
			STATUS current
			DESCRIPTION
				"Specifies the overall availability of the satellite group of
				tests and measurements, tr101290Satellite."
			::= { capabilitySatellite 1 }
		
		capabilitySatelliteTable OBJECT-TYPE
			SYNTAX SEQUENCE OF CapabilitySatelliteEntry
			MAX-ACCESS not-accessible
			STATUS current
			DESCRIPTION
				"Specifies the individual availability of the satellite group of
				tests and measurements, tr101290Satellite."
			::= { capabilitySatellite 2 }
		
		capabilitySatelliteEntry OBJECT-TYPE
			SYNTAX CapabilitySatelliteEntry
			MAX-ACCESS not-accessible
			STATUS current
			DESCRIPTION
				"Row specification"
			INDEX { capabilitySatelliteOID }
			::= { capabilitySatelliteTable 1 }
		
		CapabilitySatelliteEntry ::=
			SEQUENCE { 
				capabilitySatelliteOID
					OBJECT IDENTIFIER,
				capabilitySatelliteAvailability
					Availability,
				capabilitySatellitePollInterval
					PollingInterval
			 }

		capabilitySatelliteOID OBJECT-TYPE
			SYNTAX OBJECT IDENTIFIER
			MAX-ACCESS not-accessible
			STATUS current
			DESCRIPTION
				"The object identifier of a specific test/measurement. The object
				identifier of the object within the table whose SYNTAX is
				'TestState' is used to identify the test/measurement. Table
				index components of the object identifier are set to zero,
				except for those which identify specific tests/measurements.
				Such index objects always have a syntax which begins 'Index...'
				in this MIB."
			::= { capabilitySatelliteEntry 1 }
		
		capabilitySatelliteAvailability OBJECT-TYPE
			SYNTAX Availability
			MAX-ACCESS read-only
			STATUS current
			DESCRIPTION
				"The availability of a specific test or measurement"
			::= { capabilitySatelliteEntry 2 }
		
		capabilitySatellitePollInterval OBJECT-TYPE
			SYNTAX PollingInterval
			UNITS "millisecond"
			MAX-ACCESS read-only
			STATUS current
			DESCRIPTION
				"Indicates the interval between updates of the information
				supplied by this object."
			::= { capabilitySatelliteEntry 3 }
		
-- Capabilities for the tr101290Terrestrial branch of the MIB
		capabilityTerrestrial OBJECT IDENTIFIER ::= { tr101290Capability 9 }
		
		capabilityTerrestrialGroup OBJECT-TYPE
			SYNTAX GroupAvailability
			MAX-ACCESS read-only
			STATUS current
			DESCRIPTION
				"Specifies the overall availability of the terrestrial
				group of tests and measurements, tr101290Terrestrial."
			::= { capabilityTerrestrial 1 }
		
		capabilityTerrestrialTable OBJECT-TYPE
			SYNTAX SEQUENCE OF CapabilityTerrestrialEntry
			MAX-ACCESS not-accessible
			STATUS current
			DESCRIPTION
				"Specifies the individual availability of the terrestrial
				group of tests and measurements, tr101290Terrestrial."
			::= { capabilityTerrestrial 2 }
		
		capabilityTerrestrialEntry OBJECT-TYPE
			SYNTAX CapabilityTerrestrialEntry
			MAX-ACCESS not-accessible
			STATUS current
			DESCRIPTION
				"Row specification"
			INDEX { capabilityTerrestrialOID }
			::= { capabilityTerrestrialTable 1 }
		
		CapabilityTerrestrialEntry ::=
			SEQUENCE { 
				capabilityTerrestrialOID
					OBJECT IDENTIFIER,
				capabilityTerrestrialAvailability
					Availability,
				capabilityTerrestrialPollInterval
					PollingInterval
			 }

		capabilityTerrestrialOID OBJECT-TYPE
			SYNTAX OBJECT IDENTIFIER
			MAX-ACCESS not-accessible
			STATUS current
			DESCRIPTION
				"The object identifier of a specific test/measurement. The object
				identifier of the object within the table whose SYNTAX is
				'TestState' is used to identify the test/measurement. Table
				index components of the object identifier are set to zero,
				except for those which identify specific tests/measurements.
				Such index objects always have a syntax which begins 'Index...'
				in this MIB."
			::= { capabilityTerrestrialEntry 1 }
		
		capabilityTerrestrialAvailability OBJECT-TYPE
			SYNTAX Availability
			MAX-ACCESS read-only
			STATUS current
			DESCRIPTION
				"The availability of a specific test or measurement"
			::= { capabilityTerrestrialEntry 2 }
		
		capabilityTerrestrialPollInterval OBJECT-TYPE
			SYNTAX PollingInterval
			UNITS "millisecond"
			MAX-ACCESS read-only
			STATUS current
			DESCRIPTION
				"Indicates the interval between updates of the information
				supplied by this object."
			::= { capabilityTerrestrialEntry 3 }
		
-- Transport Stream measurements and tests from
-- section 5 of TR 101 290.
		tr101290TS OBJECT IDENTIFIER ::= { tr101290Objects 5 }
		
		tsTests OBJECT IDENTIFIER ::= { tr101290TS 2 }
		
		tsTestsSummaryTable OBJECT-TYPE
			SYNTAX SEQUENCE OF TsTestsSummaryEntry
			MAX-ACCESS not-accessible
			STATUS current
			DESCRIPTION
				"The tsTestsSummaryTable provides access to the state of all of
				the Transport Stream tests enumerated in IndexTransportStreamTest.
				The status relates to the whole Transport Stream.  In the case
				of tests which have a status per PID, the tsTestsSummaryTable
				gives the 'worst' status across all the PIDs and the status for
				each PID is available in tsTestsPIDTable."
			REFERENCE
				"TR 101 290 section 5.2"
			::= { tsTests 2 }
		
		tsTestsSummaryEntry OBJECT-TYPE
			SYNTAX TsTestsSummaryEntry
			MAX-ACCESS not-accessible
			STATUS current
			DESCRIPTION
				"Row specification"
			INDEX { tsTestsSummaryTestNumber, tsTestsSummaryInputNumber }
			::= { tsTestsSummaryTable 1 }
		
		TsTestsSummaryEntry ::=
			SEQUENCE { 
				tsTestsSummaryInputNumber
					InputNumber,
				tsTestsSummaryTestNumber
					IndexTransportStreamTest,
				tsTestsSummaryState
					TestState,
				tsTestsSummaryEnable
					Enable,
				tsTestsSummaryCounter
					Counter32,
				tsTestsSummaryCounterDiscontinuity
					DateAndTime,
				tsTestsSummaryCounterReset
					TruthValue,
				tsTestsSummaryLatestError
					DateAndTime,
				tsTestsSummaryActiveTime
					ActiveTime
			 }

		tsTestsSummaryInputNumber OBJECT-TYPE
			SYNTAX InputNumber
			MAX-ACCESS not-accessible
			STATUS current
			DESCRIPTION
				"Transport Stream on which the test is made"
			::= { tsTestsSummaryEntry 1 }
		
		tsTestsSummaryTestNumber OBJECT-TYPE
			SYNTAX IndexTransportStreamTest
			MAX-ACCESS not-accessible
			STATUS current
			DESCRIPTION
				"Specifies the test, see definition of IndexTransportStreamTest.
				
				Rows in the table exist only for tests which are actually
				implemented by the measuring equipment."
			::= { tsTestsSummaryEntry 2 }
		
		tsTestsSummaryState OBJECT-TYPE
			SYNTAX TestState
			MAX-ACCESS read-only
			STATUS current
			DESCRIPTION
				"This gives the overall pass/fail state of the test. For tests
				which have a state per PID, tsTestsSummaryState contains the
				highest numeric value of all the tsTestsPIDState objects for
				the test."
			::= { tsTestsSummaryEntry 3 }
		
		tsTestsSummaryEnable OBJECT-TYPE
			SYNTAX Enable
			MAX-ACCESS read-write
			STATUS current
			DESCRIPTION
				"Determines whether this test and associated traps are enabled.
				
				Setting tsTestsSummaryEnable affects tsTestsPIDEnable in
				tsTestsPIDTable. When tsTestsSummaryEnable is set, all existing
				instances of tsTestsPIDEnable are set to the same value. Any
				new rows in tsTestsPIDTable which are created will also have
				this value for tsTestsPIDEnable (unless the row is created by
				explicitly setting the value of tsTestsPIDEnable)."
			DEFVAL { { testEnable } }
			::= { tsTestsSummaryEntry 4 }
		
		tsTestsSummaryCounter OBJECT-TYPE
			SYNTAX Counter32
			MAX-ACCESS read-only
			STATUS current
			DESCRIPTION
				"Count of the number of times this error has occurred.
				For Status errors this is the number of times the
				TestState has entered the fail state from some other
				state.  For Error events this is the total number of
				events; the persistence timer is not taken into
				account by the counter."
			::= { tsTestsSummaryEntry 5 }
		
		tsTestsSummaryCounterDiscontinuity OBJECT-TYPE
			SYNTAX DateAndTime
			MAX-ACCESS read-only
			STATUS current
			DESCRIPTION
				"Provides the last time at which there was a discontinuity
				in the tsTestsSummaryCounter object."
			::= { tsTestsSummaryEntry 6 }
		
		tsTestsSummaryCounterReset OBJECT-TYPE
			SYNTAX TruthValue
			MAX-ACCESS read-write
			STATUS current
			DESCRIPTION
				"tsTestsSummaryCounter is reset to zero and
				tsTestsSummaryCounterDiscontinuity is set to the current
				time if this object is set to 'true'.
				
				This object has no effect on the tsTestsPIDCounter objects."
			::= { tsTestsSummaryEntry 7 }
		
		tsTestsSummaryLatestError OBJECT-TYPE
			SYNTAX DateAndTime
			MAX-ACCESS read-only
			STATUS current
			DESCRIPTION
				"The timestamp at the most recent occurrence of the error.
				For Status errors this is the most recent time the
				TestState entered the fail state from some other state.
				For Error events this is the most recent occurrence;
				the persistence timer is not taken into account."
			::= { tsTestsSummaryEntry 8 }
		
		tsTestsSummaryActiveTime OBJECT-TYPE
			SYNTAX ActiveTime
			UNITS "second"
			MAX-ACCESS read-only
			STATUS current
			DESCRIPTION
				"The total time when it has been possible to evaluate this test."
			::= { tsTestsSummaryEntry 9 }
		
		tsTestsPIDTable OBJECT-TYPE
			SYNTAX SEQUENCE OF TsTestsPIDEntry
			MAX-ACCESS not-accessible
			STATUS current
			DESCRIPTION
				"The tsTestsPIDTable provides access to the state of those
				Transport Stream tests enumerated in IndexTransportStreamTest
				which relate to individual PIDs. These tests are:
				
				1.4   Continuity_count_error
				1.5.a PMT_error_2
				1.6   PID_error
				2.3.a PCR_repetition_error
				2.3.b PCR_discontinuity_indicator_error
				2.4   PCR_accuracy_error
				2.5   PTS_error
				3.3   Buffer_error
				3.4.a Unreferenced_PID"
			REFERENCE
				"TR 101 290 section 5.2"
			::= { tsTests 3 }
		
		tsTestsPIDEntry OBJECT-TYPE
			SYNTAX TsTestsPIDEntry
			MAX-ACCESS not-accessible
			STATUS current
			DESCRIPTION
				"Row specification"
			INDEX { tsTestsPIDPID, tsTestsPIDTestNumber, tsTestsPIDInputNumber }
			::= { tsTestsPIDTable 1 }
		
		TsTestsPIDEntry ::=
			SEQUENCE { 
				tsTestsPIDInputNumber
					InputNumber,
				tsTestsPIDPID
					PIDPlusOne,
				tsTestsPIDTestNumber
					IndexTransportStreamTest,
				tsTestsPIDRowStatus
					RowStatus,
				tsTestsPIDState
					TestState,
				tsTestsPIDEnable
					Enable,
				tsTestsPIDCounter
					Counter32,
				tsTestsPIDCounterDiscontinuity
					DateAndTime,
				tsTestsPIDCounterReset
					TruthValue,
				tsTestsPIDLatestError
					DateAndTime,
				tsTestsPIDActiveTime
					ActiveTime
			 }

		tsTestsPIDInputNumber OBJECT-TYPE
			SYNTAX InputNumber
			MAX-ACCESS not-accessible
			STATUS current
			DESCRIPTION
				"Transport Stream on which the test is made"
			::= { tsTestsPIDEntry 1 }
		
		tsTestsPIDPID OBJECT-TYPE
			SYNTAX PIDPlusOne
			MAX-ACCESS not-accessible
			STATUS current
			DESCRIPTION
				"PID (plus one) on which the test is made"
			::= { tsTestsPIDEntry 2 }
		
		tsTestsPIDTestNumber OBJECT-TYPE
			SYNTAX IndexTransportStreamTest
			MAX-ACCESS not-accessible
			STATUS current
			DESCRIPTION
				"Specifies the test, see definition of IndexTransportStreamTest.
				
				Rows in the table exist only for tests which are actually
				implemented by the measuring equipment."
			::= { tsTestsPIDEntry 3 }
		
		tsTestsPIDRowStatus OBJECT-TYPE
			SYNTAX RowStatus
			MAX-ACCESS read-create
			STATUS current
			DESCRIPTION
				"This is used by the manager to create and delete rows in
				tsTestsPIDTable. The agent automatically creates rows for
				PID/test combinations where there are errors to report."
			REFERENCE
				"RFC 2579"
			DEFVAL { active }
			::= { tsTestsPIDEntry 4 }
		
		tsTestsPIDState OBJECT-TYPE
			SYNTAX TestState
			MAX-ACCESS read-only
			STATUS current
			DESCRIPTION
				"This gives the overall pass/fail state of the test"
			::= { tsTestsPIDEntry 5 }
		
		tsTestsPIDEnable OBJECT-TYPE
			SYNTAX Enable
			MAX-ACCESS read-create
			STATUS current
			DESCRIPTION
				"Determines whether this test and associated traps are enabled.
				
				When a trap triggering condition arises for a per PID test,
				this object alone is used to determine whether a trap will be
				generated, without any reference to tsTestsSummaryEnable."
			DEFVAL { { testEnable } }
			::= { tsTestsPIDEntry 6 }
		
		tsTestsPIDCounter OBJECT-TYPE
			SYNTAX Counter32
			MAX-ACCESS read-only
			STATUS current
			DESCRIPTION
				"Count of the number of times this error has occurred.
				For Status errors this is the number of times the
				TestState has entered the fail state from some other
				state.  For Error events this is the total number of
				events; the persistence timer is not taken into
				account by the counter."
			::= { tsTestsPIDEntry 7 }
		
		tsTestsPIDCounterDiscontinuity OBJECT-TYPE
			SYNTAX DateAndTime
			MAX-ACCESS read-only
			STATUS current
			DESCRIPTION
				"Provides the last time at which there was a discontinuity
				in the tsTestsSummaryCounter object."
			::= { tsTestsPIDEntry 8 }
		
		tsTestsPIDCounterReset OBJECT-TYPE
			SYNTAX TruthValue
			MAX-ACCESS read-create
			STATUS current
			DESCRIPTION
				"tsTestsPIDCounter is reset to zero and
				tsTestsPIDCounterDiscontinuity is set to the current
				time if 'true' is written to this variable.
				
				When read, the value of this object is always 'false'."
			DEFVAL { false }
			::= { tsTestsPIDEntry 9 }
		
		tsTestsPIDLatestError OBJECT-TYPE
			SYNTAX DateAndTime
			MAX-ACCESS read-only
			STATUS current
			DESCRIPTION
				"The timestamp at the most recent occurrence of the error.
				For Status errors this is the most recent time the
				TestState entered the fail state from some other state.
				For Error events this is the most recent occurrence;
				the persistence timer is not taken into account."
			::= { tsTestsPIDEntry 10 }
		
		tsTestsPIDActiveTime OBJECT-TYPE
			SYNTAX ActiveTime
			UNITS "second"
			MAX-ACCESS read-only
			STATUS current
			DESCRIPTION
				"The total time when it has been possible to evaluate this test."
			::= { tsTestsPIDEntry 11 }
		
		tsTestsPreferences OBJECT IDENTIFIER ::= { tsTests 100 }
		
		tsTestsPreferencesTable OBJECT-TYPE
			SYNTAX SEQUENCE OF TsTestsPreferencesEntry
			MAX-ACCESS not-accessible
			STATUS current
			DESCRIPTION
				"This table contains measurement thresholds and other
				configuration information that is applied on a per
				Transport Stream basis."
			::= { tsTestsPreferences 1 }
		
		tsTestsPreferencesEntry OBJECT-TYPE
			SYNTAX TsTestsPreferencesEntry
			MAX-ACCESS not-accessible
			STATUS current
			DESCRIPTION
				"Row specification"
			INDEX { tsTestsPrefInputNumber }
			::= { tsTestsPreferencesTable 1 }
		
		TsTestsPreferencesEntry ::=
			SEQUENCE { 
				tsTestsPrefInputNumber
					InputNumber,
				tsTestsPrefTransitionDuration
					FloatingPoint,
				tsTestsPrefPATSectionIntervalMax
					FloatingPoint,
				tsTestsPrefPMTSectionIntervalMax
					FloatingPoint,
				tsTestsPrefReferredIntervalMax
					FloatingPoint,
				tsTestsPrefPCRIntervalMax
					FloatingPoint,
				tsTestsPrefPCRDiscontinuityMax
					FloatingPoint,
				tsTestsPrefPCRInaccuracyMax
					FloatingPoint,
				tsTestsPrefPTSIntervalMax
					FloatingPoint,
				tsTestsPrefNITActualIntervalMax
					FloatingPoint,
				tsTestsPrefNITActualIntervalMin
					FloatingPoint,
				tsTestsPrefNITOtherIntervalMax
					FloatingPoint,
				tsTestsPrefSIGapMin
					FloatingPoint,
				tsTestsPrefNITTableIntervalMax
					FloatingPoint,
				tsTestsPrefBATTableIntervalMax
					FloatingPoint,
				tsTestsPrefSDTActualTableIntervalMax
					FloatingPoint,
				tsTestsPrefSDTOtherTableIntervalMax
					FloatingPoint,
				tsTestsPrefEITPFActualTableIntervalMax
					FloatingPoint,
				tsTestsPrefEITPFOtherTableIntervalMax
					FloatingPoint,
				tsTestsPrefEITSActualNearTableIntervalMax
					FloatingPoint,
				tsTestsPrefEITSActualFarTableIntervalMax
					FloatingPoint,
				tsTestsPrefEITSOtherNearTableIntervalMax
					FloatingPoint,
				tsTestsPrefEITSOtherFarTableIntervalMax
					FloatingPoint,
				tsTestsPrefTxTTableIntervalMax
					FloatingPoint,
				tsTestsPrefSDTActualIntervalMax
					FloatingPoint,
				tsTestsPrefSDTActualIntervalMin
					FloatingPoint,
				tsTestsPrefSDTOtherIntervalMax
					FloatingPoint,
				tsTestsPrefEITActualIntervalMax
					FloatingPoint,
				tsTestsPrefEITActualIntervalMin
					FloatingPoint,
				tsTestsPrefEITOtherIntervalMax
					FloatingPoint,
				tsTestsPrefRSTIntervalMin
					FloatingPoint,
				tsTestsPrefTDTIntervalMax
					FloatingPoint,
				tsTestsPrefTDTIntervalMin
					FloatingPoint
			 }

		tsTestsPrefInputNumber OBJECT-TYPE
			SYNTAX InputNumber
			MAX-ACCESS not-accessible
			STATUS current
			DESCRIPTION
				"Transport Stream input to which the preferences apply"
			::= { tsTestsPreferencesEntry 1 }
		
		tsTestsPrefTransitionDuration OBJECT-TYPE
			SYNTAX FloatingPoint
			UNITS "second"
			MAX-ACCESS read-write
			STATUS current
			DESCRIPTION
				"Various tests, including CAT_error (2.6) and Unreferenced_PID
				(3.4) must take into account that short transition periods can
				exist where the state of the SI and PSI information is
				inconsistent with the state of the stream. These transitions
				should not cause error indications. This parameter specifies
				the period which must be allowed for transition states."
			REFERENCE
				"TR 101 290 section 5.2.3 NOTE 1"
			DEFVAL { "0.5" }
			::= { tsTestsPreferencesEntry 2 }
		
		tsTestsPrefPATSectionIntervalMax OBJECT-TYPE
			SYNTAX FloatingPoint
			UNITS "second"
			MAX-ACCESS read-write
			STATUS current
			DESCRIPTION
				"Maximum repetition interval for PAT sections."
			REFERENCE
				"TR 101 290 section 5.2.1 (PAT_error_2 1.3.a)"
			DEFVAL { "0.5" }
			::= { tsTestsPreferencesEntry 3 }
		
		tsTestsPrefPMTSectionIntervalMax OBJECT-TYPE
			SYNTAX FloatingPoint
			UNITS "second"
			MAX-ACCESS read-write
			STATUS current
			DESCRIPTION
				"Maximum repetition interval for PMT sections."
			REFERENCE
				"TR 101 290 section 5.2.1 (PMT_error_2 1.5.a)"
			DEFVAL { "0.5" }
			::= { tsTestsPreferencesEntry 4 }
		
		tsTestsPrefReferredIntervalMax OBJECT-TYPE
			SYNTAX FloatingPoint
			UNITS "s"
			MAX-ACCESS read-write
			STATUS current
			DESCRIPTION
				"Maximum permitted interval between the arrival of consecutive
				packets for all PIDs. When the value of this object is set, the
				value of tsTestsPrefPIDReferredIntervalMax is changed for every PID.
				The value of this object is also used as a default for
				tsTestsPrefPIDReferredIntervalMax when a new row is created in
				tsTestsPreferencesPIDTable."
			REFERENCE
				"TR 101 290 section 5.2.1 (PID_error 1.6)"
			DEFVAL { "5" }
			::= { tsTestsPreferencesEntry 5 }
		
		tsTestsPrefPCRIntervalMax OBJECT-TYPE
			SYNTAX FloatingPoint
			UNITS "second"
			MAX-ACCESS read-write
			STATUS current
			DESCRIPTION
				"Maximum permitted interval between PCR arrival times
				on each PCR PID."
			REFERENCE
				"TR 101 290 section 5.2.2 (PCR_repetition_error 2.3.a)"
			DEFVAL { "0.04" }
			::= { tsTestsPreferencesEntry 6 }
		
		tsTestsPrefPCRDiscontinuityMax OBJECT-TYPE
			SYNTAX FloatingPoint
			UNITS "second"
			MAX-ACCESS read-write
			STATUS current
			DESCRIPTION
				"Maximum permitted difference between two consecutive
				PCR values."
			REFERENCE
				"TR 101 290 section 5.2.2 (PCR_discontinuity_indication_error 2.3.b)"
			DEFVAL { "0.1" }
			::= { tsTestsPreferencesEntry 7 }
		
		tsTestsPrefPCRInaccuracyMax OBJECT-TYPE
			SYNTAX FloatingPoint
			UNITS "second"
			MAX-ACCESS read-write
			STATUS current
			DESCRIPTION
				"Maximum permitted PCR inaccuracy. An error is indicated
				if the PCR inaccuracy is outside the range:
				
				[-tsTestsPrefPCRInaccuracyMax .. +tsTestsPrefPCRInaccuracyMax]."
			REFERENCE
				"TR 101 290 section 5.2.2 (PCR_accuracy_error 2.4)"
			DEFVAL { "500E-9" }
			::= { tsTestsPreferencesEntry 8 }
		
		tsTestsPrefPTSIntervalMax OBJECT-TYPE
			SYNTAX FloatingPoint
			UNITS "second"
			MAX-ACCESS read-write
			STATUS current
			DESCRIPTION
				"Maximum permitted PTS repetition interval"
			REFERENCE
				"TR 101 290 section 5.2.2 (PTS_error 2.5)"
			DEFVAL { "0.7" }
			::= { tsTestsPreferencesEntry 9 }
		
		tsTestsPrefNITActualIntervalMax OBJECT-TYPE
			SYNTAX FloatingPoint
			UNITS "second"
			MAX-ACCESS read-write
			STATUS current
			DESCRIPTION
				"Maximum permitted NIT_actual section repetition interval"
			REFERENCE
				"TR 101 290 section 5.2.3 test 3.1.a"
			DEFVAL { "10" }
			::= { tsTestsPreferencesEntry 10 }
		
		tsTestsPrefNITActualIntervalMin OBJECT-TYPE
			SYNTAX FloatingPoint
			UNITS "second"
			MAX-ACCESS read-write
			STATUS current
			DESCRIPTION
				"Minimum permitted NIT_actual section repetition interval"
			REFERENCE
				"TR 101 290 section 5.2.3 test 3.1.a"
			DEFVAL { "0.025" }
			::= { tsTestsPreferencesEntry 11 }
		
		tsTestsPrefNITOtherIntervalMax OBJECT-TYPE
			SYNTAX FloatingPoint
			UNITS "second"
			MAX-ACCESS read-write
			STATUS current
			DESCRIPTION
				"Maximum permitted NIT_other section repetition interval"
			REFERENCE
				"TR 101 290 section 5.2.3 test 3.1.b"
			DEFVAL { "10" }
			::= { tsTestsPreferencesEntry 12 }
		
		tsTestsPrefSIGapMin OBJECT-TYPE
			SYNTAX FloatingPoint
			UNITS "second"
			MAX-ACCESS read-write
			STATUS current
			DESCRIPTION
				"Minimum permitted gap between packets containing sections."
			REFERENCE
				"TR 101 290 section 5.2.3 test 3.2
				EN 300 468 section 5.1.4"
			DEFVAL { "0.025" }
			::= { tsTestsPreferencesEntry 13 }
		
		tsTestsPrefNITTableIntervalMax OBJECT-TYPE
			SYNTAX FloatingPoint
			UNITS "second"
			MAX-ACCESS read-write
			STATUS current
			DESCRIPTION
				"Maximum permitted NIT table repetition interval"
			REFERENCE
				"TR 101 290 section 5.2.3 test 3.2
				TR 101 211 section 4.4.1 a) and 4.4.2 a)"
			DEFVAL { "10" }
			::= { tsTestsPreferencesEntry 14 }
		
		tsTestsPrefBATTableIntervalMax OBJECT-TYPE
			SYNTAX FloatingPoint
			UNITS "second"
			MAX-ACCESS read-write
			STATUS current
			DESCRIPTION
				"Maximum permitted BAT table repetition interval"
			REFERENCE
				"TR 101 290 section 5.2.3 test 3.2
				TR 101 211 section 4.4.1 b) and 4.4.2 b)"
			DEFVAL { "10" }
			::= { tsTestsPreferencesEntry 15 }
		
		tsTestsPrefSDTActualTableIntervalMax OBJECT-TYPE
			SYNTAX FloatingPoint
			UNITS "second"
			MAX-ACCESS read-write
			STATUS current
			DESCRIPTION
				"Maximum permitted SDT actual transport stream table
				repetition interval"
			REFERENCE
				"TR 101 290 section 5.2.3 test 3.2
				TR 101 211 section 4.4.1 c) and 4.4.2 c)"
			DEFVAL { "2" }
			::= { tsTestsPreferencesEntry 16 }
		
		tsTestsPrefSDTOtherTableIntervalMax OBJECT-TYPE
			SYNTAX FloatingPoint
			UNITS "second"
			MAX-ACCESS read-write
			STATUS current
			DESCRIPTION
				"Maximum permitted SDT other transport stream table
				repetition interval"
			REFERENCE
				"TR 101 290 section 5.2.3 test 3.2
				TR 101 211 section 4.4.1 d) and 4.4.2 d)"
			DEFVAL { "10" }
			::= { tsTestsPreferencesEntry 17 }
		
		tsTestsPrefEITPFActualTableIntervalMax OBJECT-TYPE
			SYNTAX FloatingPoint
			UNITS "second"
			MAX-ACCESS read-write
			STATUS current
			DESCRIPTION
				"Maximum permitted EIT Present/Following actual transport
				stream table repetition interval"
			REFERENCE
				"TR 101 290 section 5.2.3 test 3.2
				TR 101 211 section 4.4.1 e) and 4.4.2 e:"
			DEFVAL { "2" }
			::= { tsTestsPreferencesEntry 18 }
		
		tsTestsPrefEITPFOtherTableIntervalMax OBJECT-TYPE
			SYNTAX FloatingPoint
			UNITS "second"
			MAX-ACCESS read-write
			STATUS current
			DESCRIPTION
				"Maximum permitted EIT Present/Following other transport
				stream table repetition interval"
			REFERENCE
				"TR 101 290 section 5.2.3 test 3.2
				TR 101 211 section 4.4.1 f) and 4.4.2 f)"
			DEFVAL { "10" }
			::= { tsTestsPreferencesEntry 19 }
		
		tsTestsPrefEITSActualNearTableIntervalMax OBJECT-TYPE
			SYNTAX FloatingPoint
			UNITS "second"
			MAX-ACCESS read-write
			STATUS current
			DESCRIPTION
				"Maximum permitted EIT Schedule actual transport stream table
				repetition interval for the near future (the next 8 days for
				satellite and cable, the next day for terrestrial)."
			REFERENCE
				"TR 101 290 section 5.2.3 test 3.2
				TR 101 211 section 4.4.1 g) and 4.4.2 second a)"
			DEFVAL { "10" }
			::= { tsTestsPreferencesEntry 20 }
		
		tsTestsPrefEITSActualFarTableIntervalMax OBJECT-TYPE
			SYNTAX FloatingPoint
			UNITS "second"
			MAX-ACCESS read-write
			STATUS current
			DESCRIPTION
				"Maximum permitted EIT Schedule actual transport stream table
				repetition interval for the far future (beyond the next 8 days
				for satellite and cable, beyond the next day for terrestrial)."
			REFERENCE
				"TR 101 290 section 5.2.3 test 3.2
				TR 101 211 section 4.4.1 h) and 4.4.2 second c)"
			DEFVAL { "10" }
			::= { tsTestsPreferencesEntry 21 }
		
		tsTestsPrefEITSOtherNearTableIntervalMax OBJECT-TYPE
			SYNTAX FloatingPoint
			UNITS "second"
			MAX-ACCESS read-write
			STATUS current
			DESCRIPTION
				"Maximum permitted EIT Schedule other transport stream table
				repetition interval for the near future (the next 8 days for
				satellite and cable, the next day for terrestrial)."
			REFERENCE
				"TR 101 290 section 5.2.3 test 3.2
				TR 101 211 section 4.4.1 g) and 4.4.2 second b)"
			DEFVAL { "10" }
			::= { tsTestsPreferencesEntry 22 }
		
		tsTestsPrefEITSOtherFarTableIntervalMax OBJECT-TYPE
			SYNTAX FloatingPoint
			UNITS "second"
			MAX-ACCESS read-write
			STATUS current
			DESCRIPTION
				"Maximum permitted EIT Schedule other transport stream table
				repetition interval for the far future (beyond the next 8 days
				for satellite and cable, beyond the next day for terrestrial)."
			REFERENCE
				"TR 101 290 section 5.2.3 test 3.2
				TR 101 211 section 4.4.1 h) and 4.4.2 second d)"
			DEFVAL { "30" }
			::= { tsTestsPreferencesEntry 23 }
		
		tsTestsPrefTxTTableIntervalMax OBJECT-TYPE
			SYNTAX FloatingPoint
			UNITS "second"
			MAX-ACCESS read-write
			STATUS current
			DESCRIPTION
				"Maximum permitted TDT and TOT table repetition intervals"
			REFERENCE
				"TR 101 290 section 5.2.3 test 3.2
				TR 101 211 section 4.4.1 i) and 4.4.2 second e)"
			DEFVAL { "30" }
			::= { tsTestsPreferencesEntry 24 }
		
		tsTestsPrefSDTActualIntervalMax OBJECT-TYPE
			SYNTAX FloatingPoint
			UNITS "second"
			MAX-ACCESS read-write
			STATUS current
			DESCRIPTION
				"Maximum permitted SDT_actual section repetition interval"
			REFERENCE
				"TR 101 290 section 5.2.3 test 3.5.a"
			DEFVAL { "2" }
			::= { tsTestsPreferencesEntry 25 }
		
		tsTestsPrefSDTActualIntervalMin OBJECT-TYPE
			SYNTAX FloatingPoint
			UNITS "second"
			MAX-ACCESS read-write
			STATUS current
			DESCRIPTION
				"Minimum permitted SDT_actual section repetition interval"
			REFERENCE
				"TR 101 290 section 5.2.3 test 3.5.a"
			DEFVAL { "0.025" }
			::= { tsTestsPreferencesEntry 26 }
		
		tsTestsPrefSDTOtherIntervalMax OBJECT-TYPE
			SYNTAX FloatingPoint
			UNITS "second"
			MAX-ACCESS read-write
			STATUS current
			DESCRIPTION
				"Maximum permitted SDT_other section repetition interval"
			REFERENCE
				"TR 101 290 section 5.2.3 test 3.5.b"
			DEFVAL { "10" }
			::= { tsTestsPreferencesEntry 27 }
		
		tsTestsPrefEITActualIntervalMax OBJECT-TYPE
			SYNTAX FloatingPoint
			UNITS "second"
			MAX-ACCESS read-write
			STATUS current
			DESCRIPTION
				"Maximum permitted EIT_actual section repetition interval (applies to
				both present and following sections)."
			REFERENCE
				"TR 101 290 section 5.2.3 test 3.6.a"
			DEFVAL { "2" }
			::= { tsTestsPreferencesEntry 28 }
		
		tsTestsPrefEITActualIntervalMin OBJECT-TYPE
			SYNTAX FloatingPoint
			UNITS "second"
			MAX-ACCESS read-write
			STATUS current
			DESCRIPTION
				"Minimum permitted EIT_actual section repetition interval"
			REFERENCE
				"TR 101 290 section 5.2.3 test 3.5.a"
			DEFVAL { "0.025" }
			::= { tsTestsPreferencesEntry 29 }
		
		tsTestsPrefEITOtherIntervalMax OBJECT-TYPE
			SYNTAX FloatingPoint
			UNITS "second"
			MAX-ACCESS read-write
			STATUS current
			DESCRIPTION
				"Maximum permitted EIT_other section repetition interval (applies to
				both present and following sections)."
			REFERENCE
				"TR 101 290 section 5.2.3 test 3.6.b"
			DEFVAL { "10" }
			::= { tsTestsPreferencesEntry 30 }
		
		tsTestsPrefRSTIntervalMin OBJECT-TYPE
			SYNTAX FloatingPoint
			UNITS "second"
			MAX-ACCESS read-write
			STATUS current
			DESCRIPTION
				"Minimum permitted RST section repetition interval"
			REFERENCE
				"TR 101 290 section 5.2.3 test 3.7"
			DEFVAL { "0.025" }
			::= { tsTestsPreferencesEntry 31 }
		
		tsTestsPrefTDTIntervalMax OBJECT-TYPE
			SYNTAX FloatingPoint
			UNITS "second"
			MAX-ACCESS read-write
			STATUS current
			DESCRIPTION
				"Maximum permitted TDT section repetition interval"
			REFERENCE
				"TR 101 290 section 5.2.3 test 3.8"
			DEFVAL { "10" }
			::= { tsTestsPreferencesEntry 32 }
		
		tsTestsPrefTDTIntervalMin OBJECT-TYPE
			SYNTAX FloatingPoint
			UNITS "second"
			MAX-ACCESS read-write
			STATUS current
			DESCRIPTION
				"Minimum permitted TDT section repetition interval"
			REFERENCE
				"TR 101 290 section 5.2.3 test 3.8"
			DEFVAL { "0.025" }
			::= { tsTestsPreferencesEntry 33 }
		
		tsTestsPreferencesPIDTable OBJECT-TYPE
			SYNTAX SEQUENCE OF TsTestsPreferencesPIDEntry
			MAX-ACCESS not-accessible
			STATUS current
			DESCRIPTION
				"This table contains measurement thresholds and other
				configuration information that is applied on a per
				PID per Transport Stream basis."
			::= { tsTestsPreferences 2 }
		
		tsTestsPreferencesPIDEntry OBJECT-TYPE
			SYNTAX TsTestsPreferencesPIDEntry
			MAX-ACCESS not-accessible
			STATUS current
			DESCRIPTION
				"Description."
			INDEX { tsTestsPrefPIDInputNumber, tsTestsPrefPIDPID }
			::= { tsTestsPreferencesPIDTable 1 }
		
		TsTestsPreferencesPIDEntry ::=
			SEQUENCE { 
				tsTestsPrefPIDInputNumber
					InputNumber,
				tsTestsPrefPIDPID
					PIDPlusOne,
				tsTestsPrefPIDRowStatus
					RowStatus,
				tsTestsPrefPIDReferredIntervalMax
					FloatingPoint
			 }

		tsTestsPrefPIDInputNumber OBJECT-TYPE
			SYNTAX InputNumber
			MAX-ACCESS not-accessible
			STATUS current
			DESCRIPTION
				"Transport Stream input to which the preferences apply"
			::= { tsTestsPreferencesPIDEntry 1 }
		
		tsTestsPrefPIDPID OBJECT-TYPE
			SYNTAX PIDPlusOne
			MAX-ACCESS not-accessible
			STATUS current
			DESCRIPTION
				"PID to which these preferences apply"
			::= { tsTestsPreferencesPIDEntry 2 }
		
		tsTestsPrefPIDRowStatus OBJECT-TYPE
			SYNTAX RowStatus
			MAX-ACCESS read-create
			STATUS current
			DESCRIPTION
				"This object is used to manage the rows in this table."
			::= { tsTestsPreferencesPIDEntry 3 }
		
		tsTestsPrefPIDReferredIntervalMax OBJECT-TYPE
			SYNTAX FloatingPoint
			UNITS "second"
			MAX-ACCESS read-write
			STATUS current
			DESCRIPTION
				"Maximum permitted interval between the arrival of consecutive
				packets of this PID.
				The default value for this object is the current value of
				tsTestsPrefReferredIntervalMax for the same input."
			REFERENCE
				"TR 101 290 section 5.2.1 (PID_error 1.6)"
			::= { tsTestsPreferencesPIDEntry 4 }
		
		tsMeasurements OBJECT IDENTIFIER ::= { tr101290TS 4 }
		
		tsPcrMeasurementTable OBJECT-TYPE
			SYNTAX SEQUENCE OF TsPcrMeasurementEntry
			MAX-ACCESS not-accessible
			STATUS current
			DESCRIPTION
				"This table makes available the PCR_FO, PCR_DR, PCR_OJ
				and PCR_AC measurements."
			REFERENCE
				"TR 101 290 section 5.3.2"
			::= { tsMeasurements 1 }
		
		tsPcrMeasurementEntry OBJECT-TYPE
			SYNTAX TsPcrMeasurementEntry
			MAX-ACCESS not-accessible
			STATUS current
			DESCRIPTION
				"Row specification"
			INDEX { tsPcrMeasurementPID, tsPcrMeasurementNumber, tsPcrMeasurementInputNumber }
			::= { tsPcrMeasurementTable 1 }
		
		TsPcrMeasurementEntry ::=
			SEQUENCE { 
				tsPcrMeasurementInputNumber
					InputNumber,
				tsPcrMeasurementPID
					PIDPlusOne,
				tsPcrMeasurementNumber
					IndexPCRMeasurement,
				tsPcrMeasurementRowStatus
					RowStatus,
				tsPcrMeasurementState
					TestState,
				tsPcrMeasurementEnable
					Enable,
				tsPcrMeasurementCounter
					Counter32,
				tsPcrMeasurementCounterDiscontinuity
					DateAndTime,
				tsPcrMeasurementCounterReset
					TruthValue,
				tsPcrMeasurementLatestError
					DateAndTime,
				tsPcrMeasurementActiveTime
					ActiveTime,
				tsPcrMeasurementMeasurementState
					MeasurementState,
				tsPcrMeasurementValue
					FloatingPoint
			 }

		tsPcrMeasurementInputNumber OBJECT-TYPE
			SYNTAX InputNumber
			MAX-ACCESS not-accessible
			STATUS current
			DESCRIPTION
				"Input on which the measurement is made"
			::= { tsPcrMeasurementEntry 1 }
		
		tsPcrMeasurementPID OBJECT-TYPE
			SYNTAX PIDPlusOne
			MAX-ACCESS not-accessible
			STATUS current
			DESCRIPTION
				"PID (plus one) in the Transport Stream carrying (or expected
				to carry) PCRs."
			::= { tsPcrMeasurementEntry 2 }
		
		tsPcrMeasurementNumber OBJECT-TYPE
			SYNTAX IndexPCRMeasurement
			MAX-ACCESS not-accessible
			STATUS current
			DESCRIPTION
				"This selects one of the four PCR measurements"
			::= { tsPcrMeasurementEntry 3 }
		
		tsPcrMeasurementRowStatus OBJECT-TYPE
			SYNTAX RowStatus
			MAX-ACCESS read-create
			STATUS current
			DESCRIPTION
				"This object is used by the manager to create and delete
				rows in the table. The agent automatically creates rows
				for PIDs where it detects the presence of a PCR."
			REFERENCE
				"RFC 2579"
			DEFVAL { active }
			::= { tsPcrMeasurementEntry 4 }
		
		tsPcrMeasurementState OBJECT-TYPE
			SYNTAX TestState
			MAX-ACCESS read-only
			STATUS current
			DESCRIPTION
				"This gives the overall pass/fail state of the threshold
				test on this measurement"
			::= { tsPcrMeasurementEntry 5 }
		
		tsPcrMeasurementEnable OBJECT-TYPE
			SYNTAX Enable
			MAX-ACCESS read-create
			STATUS current
			DESCRIPTION
				"Determines whether this test and associated traps are enabled."
			DEFVAL { { testEnable } }
			::= { tsPcrMeasurementEntry 6 }
		
		tsPcrMeasurementCounter OBJECT-TYPE
			SYNTAX Counter32
			MAX-ACCESS read-only
			STATUS current
			DESCRIPTION
				"Count of the number of times a threshold error has
				occurred for this measurement."
			::= { tsPcrMeasurementEntry 7 }
		
		tsPcrMeasurementCounterDiscontinuity OBJECT-TYPE
			SYNTAX DateAndTime
			MAX-ACCESS read-only
			STATUS current
			DESCRIPTION
				"Provides the last time at which there was a discontinuity
				in the tsPcrMeasurementCounter object."
			::= { tsPcrMeasurementEntry 8 }
		
		tsPcrMeasurementCounterReset OBJECT-TYPE
			SYNTAX TruthValue
			MAX-ACCESS read-create
			STATUS current
			DESCRIPTION
				"tsPcrMeasurementCounter is reset to zero and
				tsPcrMeasurementCounterDiscontinuity is set to the
				current time if 'true' is written to this variable.
				
				When read, the value of this object is always 'false'."
			DEFVAL { false }
			::= { tsPcrMeasurementEntry 9 }
		
		tsPcrMeasurementLatestError OBJECT-TYPE
			SYNTAX DateAndTime
			MAX-ACCESS read-only
			STATUS current
			DESCRIPTION
				"The timestamp at the most recent occurrence of a
				threshold error on this measurement."
			::= { tsPcrMeasurementEntry 10 }
		
		tsPcrMeasurementActiveTime OBJECT-TYPE
			SYNTAX ActiveTime
			UNITS "second"
			MAX-ACCESS read-only
			STATUS current
			DESCRIPTION
				"The total time when it has been possible to make this measurement"
			::= { tsPcrMeasurementEntry 11 }
		
		tsPcrMeasurementMeasurementState OBJECT-TYPE
			SYNTAX MeasurementState
			MAX-ACCESS read-only
			STATUS current
			DESCRIPTION
				"Indicates the validity of the measurement"
			::= { tsPcrMeasurementEntry 12 }
		
		tsPcrMeasurementValue OBJECT-TYPE
			SYNTAX FloatingPoint
			MAX-ACCESS read-only
			STATUS current
			DESCRIPTION
				"The units for the measured value depend on the measurement:
				
				PCR_FO      Hz
				PCR_DR      Hz/s
				
				Values for PCR_OJ and PCR_AC are not provided as they occur
				too quickly to be usefully retrieved via SNMP.  For these
				measurements, the MeasurementState is always 'unknown'.
				However, the threshold tests are expected to work correctly
				for these measurements."
			::= { tsPcrMeasurementEntry 13 }
		
		bitRate OBJECT IDENTIFIER ::= { tsMeasurements 2 }
		
		tsTransportStreamBitRateTable OBJECT-TYPE
			SYNTAX SEQUENCE OF TsTransportStreamBitRateEntry
			MAX-ACCESS not-accessible
			STATUS current
			DESCRIPTION
				"Bit rates for each complete Transport Stream"
			REFERENCE
				"TR 101 290 section 5.3.3"
			::= { bitRate 1 }
		
		tsTransportStreamBitRateEntry OBJECT-TYPE
			SYNTAX TsTransportStreamBitRateEntry
			MAX-ACCESS not-accessible
			STATUS current
			DESCRIPTION
				"Row specification"
			INDEX { tsTransportStreamBitRateInputNumber }
			::= { tsTransportStreamBitRateTable 1 }
		
		TsTransportStreamBitRateEntry ::=
			SEQUENCE { 
				tsTransportStreamBitRateInputNumber
					InputNumber,
				tsTransportStreamBitRateState
					TestState,
				tsTransportStreamBitRateEnable
					Enable,
				tsTransportStreamBitRateCounter
					Counter32,
				tsTransportStreamBitRateCounterDiscontinuity
					DateAndTime,
				tsTransportStreamBitRateCounterReset
					TruthValue,
				tsTransportStreamBitRateLatestError
					DateAndTime,
				tsTransportStreamBitRateActiveTime
					ActiveTime,
				tsTransportStreamBitRateMeasurementState
					MeasurementState,
				tsTransportStreamBitRateValue
					FloatingPoint,
				tsTransportStreamBitRateNomenclature
					DisplayString
			 }

		tsTransportStreamBitRateInputNumber OBJECT-TYPE
			SYNTAX InputNumber
			MAX-ACCESS not-accessible
			STATUS current
			DESCRIPTION
				"Transport Stream on which the measurement is made"
			::= { tsTransportStreamBitRateEntry 1 }
		
		tsTransportStreamBitRateState OBJECT-TYPE
			SYNTAX TestState
			MAX-ACCESS read-only
			STATUS current
			DESCRIPTION
				"This gives the overall pass/fail state of the
				threshold test on this measurement"
			::= { tsTransportStreamBitRateEntry 2 }
		
		tsTransportStreamBitRateEnable OBJECT-TYPE
			SYNTAX Enable
			MAX-ACCESS read-write
			STATUS current
			DESCRIPTION
				"Determines whether the threshold test and associated traps
				for this measurement are enabled."
			::= { tsTransportStreamBitRateEntry 3 }
		
		tsTransportStreamBitRateCounter OBJECT-TYPE
			SYNTAX Counter32
			MAX-ACCESS read-only
			STATUS current
			DESCRIPTION
				"Count of the number of times a threshold error has
				occurred for this measurement."
			::= { tsTransportStreamBitRateEntry 4 }
		
		tsTransportStreamBitRateCounterDiscontinuity OBJECT-TYPE
			SYNTAX DateAndTime
			MAX-ACCESS read-only
			STATUS current
			DESCRIPTION
				"Provides the last time at which there was a discontinuity
				in the tsTransportStreamBitRateCounterobject."
			::= { tsTransportStreamBitRateEntry 5 }
		
		tsTransportStreamBitRateCounterReset OBJECT-TYPE
			SYNTAX TruthValue
			MAX-ACCESS read-write
			STATUS current
			DESCRIPTION
				"tsTransportStreamBitRateCounteris reset to zero and
				tsTransportStreamBitRateCounterDiscontinuity is set to
				the current time if 'true' is written to this variable.
				
				When read, the value of this object is always 'false'."
			DEFVAL { false }
			::= { tsTransportStreamBitRateEntry 6 }
		
		tsTransportStreamBitRateLatestError OBJECT-TYPE
			SYNTAX DateAndTime
			MAX-ACCESS read-only
			STATUS current
			DESCRIPTION
				"The timestamp at the most recent occurrence of a threshold
				error on this measurement."
			::= { tsTransportStreamBitRateEntry 7 }
		
		tsTransportStreamBitRateActiveTime OBJECT-TYPE
			SYNTAX ActiveTime
			UNITS "second"
			MAX-ACCESS read-only
			STATUS current
			DESCRIPTION
				"The total time when it has been possible to perform this measurement"
			::= { tsTransportStreamBitRateEntry 8 }
		
		tsTransportStreamBitRateMeasurementState OBJECT-TYPE
			SYNTAX MeasurementState
			MAX-ACCESS read-only
			STATUS current
			DESCRIPTION
				"Indicates the validity of the measurement"
			::= { tsTransportStreamBitRateEntry 9 }
		
		tsTransportStreamBitRateValue OBJECT-TYPE
			SYNTAX FloatingPoint
			UNITS "bit/s"
			MAX-ACCESS read-only
			STATUS current
			DESCRIPTION
				"The overall Transport Stream bit rate"
			::= { tsTransportStreamBitRateEntry 10 }
		
		tsTransportStreamBitRateNomenclature OBJECT-TYPE
			SYNTAX DisplayString
			MAX-ACCESS read-only
			STATUS current
			DESCRIPTION
				"Standardised description of the method of measurement
				of the bitrate, for example 'bit/s @MGB2'"
			REFERENCE
				"TR 101 290 5.3.3.3"
			::= { tsTransportStreamBitRateEntry 11 }
		
		tsServiceBitRateTable OBJECT-TYPE
			SYNTAX SEQUENCE OF TsServiceBitRateEntry
			MAX-ACCESS not-accessible
			STATUS current
			DESCRIPTION
				"Bit rates for each service/program within each Transport
				Stream. The table is sparse, in that only services
				mentioned in the PMT will be present.
				
				The bit rate of a service is the sum of the bit rates of
				the elementary_PID's in its PMT and the CA_PID's in any
				CA_descriptors in its PMT (ECMs).  The bit rate of the
				PMT itself is excluded.  The bit rate of the PCR_PID is
				excluded unless the PCR_PID is also one of the
				elementary_PID's in the PMT."
			REFERENCE
				"TR 101 290 section 5.3.3"
			::= { bitRate 2 }
		
		tsServiceBitRateEntry OBJECT-TYPE
			SYNTAX TsServiceBitRateEntry
			MAX-ACCESS not-accessible
			STATUS current
			DESCRIPTION
				"Row specification"
			INDEX { tsServiceBitRateService, tsServiceBitRateInputNumber }
			::= { tsServiceBitRateTable 1 }
		
		TsServiceBitRateEntry ::=
			SEQUENCE { 
				tsServiceBitRateInputNumber
					InputNumber,
				tsServiceBitRateService
					ServiceId,
				tsServiceBitRateRowStatus
					RowStatus,
				tsServiceBitRateState
					TestState,
				tsServiceBitRateEnable
					Enable,
				tsServiceBitRateCounter
					Counter32,
				tsServiceBitRateCounterDiscontinuity
					DateAndTime,
				tsServiceBitRateCounterReset
					TruthValue,
				tsServiceBitRateLatestError
					DateAndTime,
				tsServiceBitRateActiveTime
					ActiveTime,
				tsServiceBitRateMeasurementState
					MeasurementState,
				tsServiceBitRateValue
					FloatingPoint,
				tsServiceBitRateNomenclature
					DisplayString
			 }

		tsServiceBitRateInputNumber OBJECT-TYPE
			SYNTAX InputNumber
			MAX-ACCESS not-accessible
			STATUS current
			DESCRIPTION
				"Transport Stream on which the measurement is made"
			::= { tsServiceBitRateEntry 1 }
		
		tsServiceBitRateService OBJECT-TYPE
			SYNTAX ServiceId
			MAX-ACCESS not-accessible
			STATUS current
			DESCRIPTION
				"The program_number/service_id to which the information
				in the rest of the row applies."
			::= { tsServiceBitRateEntry 2 }
		
		tsServiceBitRateRowStatus OBJECT-TYPE
			SYNTAX RowStatus
			MAX-ACCESS read-create
			STATUS current
			DESCRIPTION
				"This is used by the manager to create and delete rows
				in the table. The agent will automatically create rows
				for services it finds in the PMT."
			REFERENCE
				"RFC 2579"
			DEFVAL { active }
			::= { tsServiceBitRateEntry 3 }
		
		tsServiceBitRateState OBJECT-TYPE
			SYNTAX TestState
			MAX-ACCESS read-only
			STATUS current
			DESCRIPTION
				"This gives the overall pass/fail state of the threshold
				test on this measurement"
			::= { tsServiceBitRateEntry 4 }
		
		tsServiceBitRateEnable OBJECT-TYPE
			SYNTAX Enable
			MAX-ACCESS read-create
			STATUS current
			DESCRIPTION
				"Determines whether the threshold test and associated traps
				for this measurement are enabled."
			DEFVAL { { testEnable } }
			::= { tsServiceBitRateEntry 5 }
		
		tsServiceBitRateCounter OBJECT-TYPE
			SYNTAX Counter32
			MAX-ACCESS read-only
			STATUS current
			DESCRIPTION
				"Count of the number of times a threshold error has
				occurred for this measurement."
			::= { tsServiceBitRateEntry 6 }
		
		tsServiceBitRateCounterDiscontinuity OBJECT-TYPE
			SYNTAX DateAndTime
			MAX-ACCESS read-only
			STATUS current
			DESCRIPTION
				"Provides the last time at which there was a discontinuity
				in the tsServiceBitRateCounter object."
			::= { tsServiceBitRateEntry 7 }
		
		tsServiceBitRateCounterReset OBJECT-TYPE
			SYNTAX TruthValue
			MAX-ACCESS read-create
			STATUS current
			DESCRIPTION
				"tsServiceBitRateCounter is reset to zero and
				tsServiceBitRateCounterDiscontinuity is set to the
				current time if 'true' is written to this variable.
				
				When read, the value of this object is always 'false'."
			DEFVAL { false }
			::= { tsServiceBitRateEntry 8 }
		
		tsServiceBitRateLatestError OBJECT-TYPE
			SYNTAX DateAndTime
			MAX-ACCESS read-only
			STATUS current
			DESCRIPTION
				"The timestamp at the most recent occurrence of a
				threshold error on this measurement."
			::= { tsServiceBitRateEntry 9 }
		
		tsServiceBitRateActiveTime OBJECT-TYPE
			SYNTAX ActiveTime
			UNITS "second"
			MAX-ACCESS read-only
			STATUS current
			DESCRIPTION
				"The total time when it has been possible to perform this measurement"
			::= { tsServiceBitRateEntry 10 }
		
		tsServiceBitRateMeasurementState OBJECT-TYPE
			SYNTAX MeasurementState
			MAX-ACCESS read-only
			STATUS current
			DESCRIPTION
				"Indicates the validity of the measurement"
			::= { tsServiceBitRateEntry 11 }
		
		tsServiceBitRateValue OBJECT-TYPE
			SYNTAX FloatingPoint
			UNITS "bit/s"
			MAX-ACCESS read-only
			STATUS current
			DESCRIPTION
				"Overall bit rate for the service"
			::= { tsServiceBitRateEntry 12 }
		
		tsServiceBitRateNomenclature OBJECT-TYPE
			SYNTAX DisplayString
			MAX-ACCESS read-only
			STATUS current
			DESCRIPTION
				"Standardised description of the method of measurement
				of the bitrate, for example 'bit/s @MGB2'"
			REFERENCE
				"TR 101 290 5.3.3.3"
			::= { tsServiceBitRateEntry 13 }
		
		tsPIDBitRateTable OBJECT-TYPE
			SYNTAX SEQUENCE OF TsPIDBitRateEntry
			MAX-ACCESS not-accessible
			STATUS current
			DESCRIPTION
				"Bit rates for each PID within each Transport Stream.
				The table is sparse, in that only PIDs whose bit rate
				is currently greater than zero will be present in the
				table. This allows for faster traversal of the table
				to build up a list of PID bit rates."
			REFERENCE
				"TR 101 290 section 5.3.3"
			::= { bitRate 3 }
		
		tsPIDBitRateEntry OBJECT-TYPE
			SYNTAX TsPIDBitRateEntry
			MAX-ACCESS not-accessible
			STATUS current
			DESCRIPTION
				"Row specification"
			INDEX { tsPIDBitRateInputNumber, tsPIDBitRatePID }
			::= { tsPIDBitRateTable 1 }
		
		TsPIDBitRateEntry ::=
			SEQUENCE { 
				tsPIDBitRateInputNumber
					InputNumber,
				tsPIDBitRatePID
					PIDPlusOne,
				tsPIDBitRateRowStatus
					RowStatus,
				tsPIDBitRateState
					TestState,
				tsPIDBitRateEnable
					Enable,
				tsPIDBitRateCounter
					Counter32,
				tsPIDBitRateCounterDiscontinuity
					DateAndTime,
				tsPIDBitRateCounterReset
					TruthValue,
				tsPIDBitRateLatestError
					DateAndTime,
				tsPIDBitRateActiveTime
					ActiveTime,
				tsPIDBitRateMeasurementState
					MeasurementState,
				tsPIDBitRateValue
					FloatingPoint,
				tsPIDBitRateNomenclature
					DisplayString
			 }

		tsPIDBitRateInputNumber OBJECT-TYPE
			SYNTAX InputNumber
			MAX-ACCESS not-accessible
			STATUS current
			DESCRIPTION
				"Transport Stream on which the measurement is made"
			::= { tsPIDBitRateEntry 1 }
		
		tsPIDBitRatePID OBJECT-TYPE
			SYNTAX PIDPlusOne
			MAX-ACCESS not-accessible
			STATUS current
			DESCRIPTION
				"PID whose bit rate is being measured (plus one)"
			::= { tsPIDBitRateEntry 2 }
		
		tsPIDBitRateRowStatus OBJECT-TYPE
			SYNTAX RowStatus
			MAX-ACCESS read-create
			STATUS current
			DESCRIPTION
				"This is used by the manager to create and delete rows
				in the table. The agent will automatically create rows
				for PIDs whose bit rate is non-zero."
			DEFVAL { active }
			::= { tsPIDBitRateEntry 3 }
		
		tsPIDBitRateState OBJECT-TYPE
			SYNTAX TestState
			MAX-ACCESS read-only
			STATUS current
			DESCRIPTION
				"This gives the overall pass/fail state of the threshold
				test on this measurement"
			::= { tsPIDBitRateEntry 4 }
		
		tsPIDBitRateEnable OBJECT-TYPE
			SYNTAX Enable
			MAX-ACCESS read-create
			STATUS current
			DESCRIPTION
				"Determines whether the threshold test and associated traps
				for this measurement are enabled."
			DEFVAL { { testEnable } }
			::= { tsPIDBitRateEntry 5 }
		
		tsPIDBitRateCounter OBJECT-TYPE
			SYNTAX Counter32
			MAX-ACCESS read-only
			STATUS current
			DESCRIPTION
				"Count of the number of times a threshold error has
				occurred for this measurement."
			::= { tsPIDBitRateEntry 6 }
		
		tsPIDBitRateCounterDiscontinuity OBJECT-TYPE
			SYNTAX DateAndTime
			MAX-ACCESS read-only
			STATUS current
			DESCRIPTION
				"Provides the last time at which there was a discontinuity
				in the tsPIDBitRateCounter object."
			::= { tsPIDBitRateEntry 7 }
		
		tsPIDBitRateCounterReset OBJECT-TYPE
			SYNTAX TruthValue
			MAX-ACCESS read-create
			STATUS current
			DESCRIPTION
				"tsPIDBitRateCounter is reset to zero and
				tsPIDBitRateCounterDiscontinuity is set to the current
				time if 'true' is written to this variable.
				
				When read, the value of this object is always 'false'."
			DEFVAL { false }
			::= { tsPIDBitRateEntry 8 }
		
		tsPIDBitRateLatestError OBJECT-TYPE
			SYNTAX DateAndTime
			MAX-ACCESS read-only
			STATUS current
			DESCRIPTION
				"The timestamp at the most recent occurrence of a
				threshold error on this measurement."
			::= { tsPIDBitRateEntry 9 }
		
		tsPIDBitRateActiveTime OBJECT-TYPE
			SYNTAX ActiveTime
			UNITS "second"
			MAX-ACCESS read-only
			STATUS current
			DESCRIPTION
				"The total time when it has been possible to perform
				this measurement"
			::= { tsPIDBitRateEntry 10 }
		
		tsPIDBitRateMeasurementState OBJECT-TYPE
			SYNTAX MeasurementState
			MAX-ACCESS read-only
			STATUS current
			DESCRIPTION
				"Indicates the validity of the measurement"
			::= { tsPIDBitRateEntry 11 }
		
		tsPIDBitRateValue OBJECT-TYPE
			SYNTAX FloatingPoint
			UNITS "bit/s"
			MAX-ACCESS read-only
			STATUS current
			DESCRIPTION
				"Bit rate for the PID."
			::= { tsPIDBitRateEntry 12 }
		
		tsPIDBitRateNomenclature OBJECT-TYPE
			SYNTAX DisplayString
			MAX-ACCESS read-only
			STATUS current
			DESCRIPTION
				"Standardised description of the method of measurement
				of the bitrate, for example 'bit/s @MGB2'"
			REFERENCE
				"TR 101 290 5.3.3.3"
			::= { tsPIDBitRateEntry 13 }
		
		tsConsistencyTable OBJECT-TYPE
			SYNTAX SEQUENCE OF TsConsistencyEntry
			MAX-ACCESS not-accessible
			STATUS current
			DESCRIPTION
				"This table provides the result of the Transport Stream
				consistency test for each input."
			REFERENCE
				"TR 101 290 section 5.3.4"
			::= { tsMeasurements 3 }
		
		tsConsistencyEntry OBJECT-TYPE
			SYNTAX TsConsistencyEntry
			MAX-ACCESS not-accessible
			STATUS current
			DESCRIPTION
				"Row specification"
			INDEX { tsConsistencyInputNumber, tsConsistencyTestNumber }
			::= { tsConsistencyTable 1 }
		
		TsConsistencyEntry ::=
			SEQUENCE { 
				tsConsistencyInputNumber
					InputNumber,
				tsConsistencyTestNumber
					IndexConsistencyTest,
				tsConsistencyState
					TestState,
				tsConsistencyEnable
					Enable,
				tsConsistencyCounter
					Counter32,
				tsConsistencyCounterDiscontinuity
					DateAndTime,
				tsConsistencyCounterReset
					TruthValue,
				tsConsistencyLatestError
					DateAndTime,
				tsConsistencyActiveTime
					ActiveTime
			 }

		tsConsistencyInputNumber OBJECT-TYPE
			SYNTAX InputNumber
			MAX-ACCESS not-accessible
			STATUS current
			DESCRIPTION
				"Input (Transport Stream) on which the consistency check is made."
			::= { tsConsistencyEntry 1 }
		
		tsConsistencyTestNumber OBJECT-TYPE
			SYNTAX IndexConsistencyTest
			MAX-ACCESS not-accessible
			STATUS current
			DESCRIPTION
				"Specifies the consistency check test"
			::= { tsConsistencyEntry 2 }
		
		tsConsistencyState OBJECT-TYPE
			SYNTAX TestState
			MAX-ACCESS read-only
			STATUS current
			DESCRIPTION
				"This gives the overall pass/fail state of the consistency check."
			::= { tsConsistencyEntry 3 }
		
		tsConsistencyEnable OBJECT-TYPE
			SYNTAX Enable
			MAX-ACCESS read-write
			STATUS current
			DESCRIPTION
				"Determines whether this test and associated traps are enabled."
			DEFVAL { { testEnable } }
			::= { tsConsistencyEntry 4 }
		
		tsConsistencyCounter OBJECT-TYPE
			SYNTAX Counter32
			MAX-ACCESS read-only
			STATUS current
			DESCRIPTION
				"Count of the number of times the consistency check has failed."
			::= { tsConsistencyEntry 5 }
		
		tsConsistencyCounterDiscontinuity OBJECT-TYPE
			SYNTAX DateAndTime
			MAX-ACCESS read-only
			STATUS current
			DESCRIPTION
				"Provides the last time at which there was a discontinuity
				in the tsConsistencyCounter object."
			::= { tsConsistencyEntry 6 }
		
		tsConsistencyCounterReset OBJECT-TYPE
			SYNTAX TruthValue
			MAX-ACCESS read-write
			STATUS current
			DESCRIPTION
				"tsConsistencyCounter is reset to zero and
				tsConsistencyCounterDiscontinuity is set to the current
				time if 'true' is written to this variable.
				
				When read, the value of this object is always 'false'."
			::= { tsConsistencyEntry 7 }
		
		tsConsistencyLatestError OBJECT-TYPE
			SYNTAX DateAndTime
			MAX-ACCESS read-only
			STATUS current
			DESCRIPTION
				"The timestamp at the most recent failure of the consistency check."
			::= { tsConsistencyEntry 8 }
		
		tsConsistencyActiveTime OBJECT-TYPE
			SYNTAX ActiveTime
			UNITS "second"
			MAX-ACCESS read-only
			STATUS current
			DESCRIPTION
				"The total time when it has been possible to perform this test"
			::= { tsConsistencyEntry 9 }
		
		tsMeasurePreferences OBJECT IDENTIFIER ::= { tsMeasurements 100 }
		
		tsMeasurePreferencesTable OBJECT-TYPE
			SYNTAX SEQUENCE OF TsMeasurePreferencesEntry
			MAX-ACCESS not-accessible
			STATUS current
			DESCRIPTION
				"This table contains configuration information for the
				tsMeasurements branch of the MIB. Configuration related
				to the whole Transport Stream is found here."
			::= { tsMeasurePreferences 1 }
		
		tsMeasurePreferencesEntry OBJECT-TYPE
			SYNTAX TsMeasurePreferencesEntry
			MAX-ACCESS not-accessible
			STATUS current
			DESCRIPTION
				"Row specification"
			INDEX { tsMeasurePrefInputNumber }
			::= { tsMeasurePreferencesTable 1 }
		
		TsMeasurePreferencesEntry ::=
			SEQUENCE { 
				tsMeasurePrefInputNumber
					InputNumber,
				tsMeasurePrefPCRDemarcationFrequency
					FloatingPoint,
				tsMeasurePrefPCRFOMax
					FloatingPoint,
				tsMeasurePrefPCRDRMax
					FloatingPoint,
				tsMeasurePrefPCROJMax
					FloatingPoint,
				tsMeasurePrefTSBitRateTau
					FloatingPoint,
				tsMeasurePrefTSBitRateN
					Unsigned32,
				tsMeasurePrefTSBitRateElement
					BitRateElement,
				tsMeasurePrefTSBitRateMin
					FloatingPoint,
				tsMeasurePrefTSBitRateMax
					FloatingPoint,
				tsMeasurePrefAllServiceBitRateTau
					FloatingPoint,
				tsMeasurePrefAllServiceBitRateN
					Unsigned32,
				tsMeasurePrefAllServiceBitRateElement
					BitRateElement,
				tsMeasurePrefAllPIDBitRateTau
					FloatingPoint,
				tsMeasurePrefAllPIDBitRateN
					Unsigned32,
				tsMeasurePrefAllPIDBitRateElement
					BitRateElement,
				tsMeasurePrefExpectedTSID
					TransportStreamID
			 }

		tsMeasurePrefInputNumber OBJECT-TYPE
			SYNTAX InputNumber
			MAX-ACCESS not-accessible
			STATUS current
			DESCRIPTION
				"Transport Stream input to which the preferences apply"
			::= { tsMeasurePreferencesEntry 1 }
		
		tsMeasurePrefPCRDemarcationFrequency OBJECT-TYPE
			SYNTAX FloatingPoint
			MAX-ACCESS read-write
			STATUS current
			DESCRIPTION
				"This is the demarcation frequency used by the PCR measurement
				system to distinguish between inaccuracy/jitter and drift."
			REFERENCE
				"TR 101 290 section 5.3.2.2"
			DEFVAL { "0.01" }
			::= { tsMeasurePreferencesEntry 2 }
		
		tsMeasurePrefPCRFOMax OBJECT-TYPE
			SYNTAX FloatingPoint
			UNITS "Hz"
			MAX-ACCESS read-write
			STATUS current
			DESCRIPTION
				"Maximum permitted PCR_FO (frequency offset). An error is
				indicated if the measured PCR_FO is outside the range
				
				[-tsMeasurePrefPCRFOMax .. +tsMeasurePrefPCRFOMax]."
			REFERENCE
				"ISO/IEC 13818-1 section 2.4.2.1"
			DEFVAL { "810" }
			::= { tsMeasurePreferencesEntry 3 }
		
		tsMeasurePrefPCRDRMax OBJECT-TYPE
			SYNTAX FloatingPoint
			UNITS "Hz/s"
			MAX-ACCESS read-write
			STATUS current
			DESCRIPTION
				"Maximum permitted PCR_DR (drift rate). An error is
				indicated if the measured PCR_DR is outside the range
				
				[-tsMeasurePrefPCRDRMax .. +tsMeasurePrefPCRDRMax]"
			REFERENCE
				"ISO/IEC 13818-1 section 2.4.2.1"
			DEFVAL { "0.075" }
			::= { tsMeasurePreferencesEntry 4 }
		
		tsMeasurePrefPCROJMax OBJECT-TYPE
			SYNTAX FloatingPoint
			UNITS "second"
			MAX-ACCESS read-write
			STATUS current
			DESCRIPTION
				"Maximum permitted PCR_OJ (overall jitter). An error is
				indicated if the measured PCR_OJ is outside the range
				
				[-tsMeasurePrefPCROJMax .. +tsMeasurePrefPCROJMax]"
			REFERENCE
				"ISO/IEC 13818-9 section 3.3"
			DEFVAL { "25E-06" }
			::= { tsMeasurePreferencesEntry 5 }
-- 
-- The limit value for PCR_AC is defined by tsTestsPrefPCRInaccuracyMax.
		
		tsMeasurePrefTSBitRateTau OBJECT-TYPE
			SYNTAX FloatingPoint
			UNITS "second"
			MAX-ACCESS read-write
			STATUS current
			DESCRIPTION
				"'tau' value for Transport Stream bit rate measurement.
				
				The MIB provides very flexible ways of setting the bit rate
				measurement parameters tau, N and element for the Transport
				Stream, services, PIDs and for individual services and PIDs.
				Real measurement equipment can be expected to provide much
				less flexibility. Management software should anticipate this by
				either being statically aware of the capabilities of the agent
				or by checking that preference settings have been accepted by
				reading them back after each attempt to set them."
			REFERENCE
				"TR 101 290 section 5.3.3.1"
			DEFVAL { "0.1" }
			::= { tsMeasurePreferencesEntry 6 }
		
		tsMeasurePrefTSBitRateN OBJECT-TYPE
			SYNTAX Unsigned32
			MAX-ACCESS read-write
			STATUS current
			DESCRIPTION
				"'N' value for Transport Stream bit rate measurement.
				
				See note in description for tsMeasurePrefTSBitRateTau."
			REFERENCE
				"TR 101 290 section 5.3.3.1"
			DEFVAL { 10 }
			::= { tsMeasurePreferencesEntry 7 }
		
		tsMeasurePrefTSBitRateElement OBJECT-TYPE
			SYNTAX BitRateElement
			MAX-ACCESS read-write
			STATUS current
			DESCRIPTION
				"Data unit which is counted by the bit rate measurement algorithm.
				
				See note in description for tsMeasurePrefTSBitRateTau."
			REFERENCE
				"TR 101 290 section 5.3.3.1"
			DEFVAL { packet }
			::= { tsMeasurePreferencesEntry 8 }
		
		tsMeasurePrefTSBitRateMin OBJECT-TYPE
			SYNTAX FloatingPoint
			UNITS "bit/s"
			MAX-ACCESS read-write
			STATUS current
			DESCRIPTION
				"An error is generated if the Transport Stream bit rate
				is below this value."
			::= { tsMeasurePreferencesEntry 9 }
		
		tsMeasurePrefTSBitRateMax OBJECT-TYPE
			SYNTAX FloatingPoint
			UNITS "bit/s"
			MAX-ACCESS read-write
			STATUS current
			DESCRIPTION
				"An error is generated if the Transport Stream bit rate
				exceeds this value."
			::= { tsMeasurePreferencesEntry 10 }
		
		tsMeasurePrefAllServiceBitRateTau OBJECT-TYPE
			SYNTAX FloatingPoint
			UNITS "second"
			MAX-ACCESS read-write
			STATUS current
			DESCRIPTION
				"'tau' value for Service bit rate measurement. When a manager
				sets the value of this object, the values of the
				tsMeasurePrefServiceBitRateTau columns in all the rows of the
				tsMeasurePreferencesServiceTable are set to this same value.
				This also becomes the default value for any new rows created
				subsequently.
				
				See note in description for tsMeasurePrefTSBitRateTau."
			REFERENCE
				"TR 101 290 section 5.3.3.1"
			DEFVAL { "0.1" }
			::= { tsMeasurePreferencesEntry 11 }
		
		tsMeasurePrefAllServiceBitRateN OBJECT-TYPE
			SYNTAX Unsigned32
			MAX-ACCESS read-write
			STATUS current
			DESCRIPTION
				"'N' value for Service bit rate measurement.  When a
				manager sets the value of this object, the values of
				the tsMeasurePrefServiceBitRateN columns in all the
				rows of the tsMeasurePreferencesServiceTable are set
				to this same value. This also becomes the default value
				for any new rows created subsequently.
				
				See note in description for tsMeasurePrefTSBitRateTau."
			REFERENCE
				"TR 101 290 section 5.3.3.1"
			DEFVAL { 10 }
			::= { tsMeasurePreferencesEntry 12 }
		
		tsMeasurePrefAllServiceBitRateElement OBJECT-TYPE
			SYNTAX BitRateElement
			MAX-ACCESS read-write
			STATUS current
			DESCRIPTION
				"Data unit which is counted by the bit rate measurement
				algorithm for services. When a manager sets the value
				of this object, the values of the
				tsMeasurePrefServiceBitRateElement columns in all the
				rows of the tsMeasurePreferencesServiceTable are set to
				this same value. This also becomes the default value
				for any new rows created subsequently.
				
				See note in description for tsMeasurePrefTSBitRateTau."
			REFERENCE
				"TR 101 290 section 5.3.3.1"
			DEFVAL { packet }
			::= { tsMeasurePreferencesEntry 13 }
		
		tsMeasurePrefAllPIDBitRateTau OBJECT-TYPE
			SYNTAX FloatingPoint
			UNITS "second"
			MAX-ACCESS read-write
			STATUS current
			DESCRIPTION
				"'tau' value for Service bit rate measurement. When a
				manager sets the value of this object, the values of
				the tsMeasurePrefPIDBitRateTau columns in all the rows
				of the tsMeasurePreferencesPIDTable are set to this
				same value. This also becomes the default value
				for any new rows created subsequently.
				
				See note in description for tsMeasurePrefTSBitRateTau."
			REFERENCE
				"TR 101 290 section 5.3.3.1"
			DEFVAL { "0.1" }
			::= { tsMeasurePreferencesEntry 14 }
		
		tsMeasurePrefAllPIDBitRateN OBJECT-TYPE
			SYNTAX Unsigned32
			MAX-ACCESS read-write
			STATUS current
			DESCRIPTION
				"'N' value for PID bit rate measurement.  When a
				manager sets the value of this object, the values of
				the tsMeasurePrefPIDBitRateN columns in all the rows
				of the tsMeasurePreferencesPIDTable are set to this
				same value. This also becomes the default value
				for any new rows created subsequently.
				
				See note in description for tsMeasurePrefTSBitRateTau."
			REFERENCE
				"TR 101 290 section 5.3.3.1"
			DEFVAL { 10 }
			::= { tsMeasurePreferencesEntry 15 }
		
		tsMeasurePrefAllPIDBitRateElement OBJECT-TYPE
			SYNTAX BitRateElement
			MAX-ACCESS read-write
			STATUS current
			DESCRIPTION
				"Data unit which is counted by the bit rate measurement
				algorithm for PIDs. When a manager sets the value of
				this object, the values of the tsMeasurePrefPIDBitRateElement
				columns in all the rows of the tsMeasurePreferencesPIDTable
				are set to this same value. This also becomes the default value
				for any new rows created subsequently.
				
				See note in description for tsMeasurePrefTSBitRateTau."
			REFERENCE
				"TR 101 290 section 5.3.3.1"
			DEFVAL { packet }
			::= { tsMeasurePreferencesEntry 16 }
		
		tsMeasurePrefExpectedTSID OBJECT-TYPE
			SYNTAX TransportStreamID
			MAX-ACCESS read-write
			STATUS current
			DESCRIPTION
				"This object defines the expected Transport Stream ID that
				is compared with the actual ID to perform the consistency
				of information check."
			REFERENCE
				"TR 101 290 5.3.4"
			::= { tsMeasurePreferencesEntry 17 }
		
		tsMeasurePreferencesServiceTable OBJECT-TYPE
			SYNTAX SEQUENCE OF TsMeasurePreferencesServiceEntry
			MAX-ACCESS not-accessible
			STATUS current
			DESCRIPTION
				"This table contains configuration information for the
				tsMeasurements branch of the MIB. Configuration related
				to individual services is found here."
			::= { tsMeasurePreferences 2 }
		
		tsMeasurePreferencesServiceEntry OBJECT-TYPE
			SYNTAX TsMeasurePreferencesServiceEntry
			MAX-ACCESS not-accessible
			STATUS current
			DESCRIPTION
				"Row specification"
			INDEX { tsMeasurePrefServiceInputNumber, tsMeasurePrefServiceService }
			::= { tsMeasurePreferencesServiceTable 1 }
		
		TsMeasurePreferencesServiceEntry ::=
			SEQUENCE { 
				tsMeasurePrefServiceInputNumber
					InputNumber,
				tsMeasurePrefServiceService
					ServiceId,
				tsMeasurePrefServiceRowStatus
					RowStatus,
				tsMeasurePrefServiceBitRateTau
					FloatingPoint,
				tsMeasurePrefServiceBitRateN
					Unsigned32,
				tsMeasurePrefServiceBitRateElement
					BitRateElement,
				tsMeasurePrefServiceBitRateMin
					FloatingPoint,
				tsMeasurePrefServiceBitRateMax
					FloatingPoint
			 }

		tsMeasurePrefServiceInputNumber OBJECT-TYPE
			SYNTAX InputNumber
			MAX-ACCESS not-accessible
			STATUS current
			DESCRIPTION
				"Transport Stream input to which the preferences apply"
			::= { tsMeasurePreferencesServiceEntry 1 }
		
		tsMeasurePrefServiceService OBJECT-TYPE
			SYNTAX ServiceId
			MAX-ACCESS not-accessible
			STATUS current
			DESCRIPTION
				"Service to which the preferences apply."
			::= { tsMeasurePreferencesServiceEntry 2 }
		
		tsMeasurePrefServiceRowStatus OBJECT-TYPE
			SYNTAX RowStatus
			MAX-ACCESS read-create
			STATUS current
			DESCRIPTION
				"This is used by the manager to create and delete rows
				in the table. The agent will automatically create rows
				for services it finds in the PMT."
			DEFVAL { active }
			::= { tsMeasurePreferencesServiceEntry 3 }
		
		tsMeasurePrefServiceBitRateTau OBJECT-TYPE
			SYNTAX FloatingPoint
			UNITS "second"
			MAX-ACCESS read-create
			STATUS current
			DESCRIPTION
				"'tau' value for bit rate measurement for this service.
				
				See note in description for tsMeasurePrefTSBitRateTau.
				
				If an agent does not support per service tau settings, it shall
				ignore attempts to change the setting by writing to this object."
			REFERENCE
				"TR 101 290 section 5.3.3.1"
			DEFVAL { "0.1" }
			::= { tsMeasurePreferencesServiceEntry 4 }
		
		tsMeasurePrefServiceBitRateN OBJECT-TYPE
			SYNTAX Unsigned32
			MAX-ACCESS read-create
			STATUS current
			DESCRIPTION
				"'N' value for rate measurement for this service.
				
				See note in description for tsMeasurePrefTSBitRateTau.
				
				If an agent does not support per service 'N' settings, it shall
				ignore attempts to change the setting by writing to this object."
			REFERENCE
				"TR 101 290 section 5.3.3.1"
			DEFVAL { 10 }
			::= { tsMeasurePreferencesServiceEntry 5 }
		
		tsMeasurePrefServiceBitRateElement OBJECT-TYPE
			SYNTAX BitRateElement
			MAX-ACCESS read-create
			STATUS current
			DESCRIPTION
				"Data unit which is counted by the bit rate measurement
				algorithm for this service.
				
				See note in description for tsMeasurePrefTSBitRateTau.
				
				If an agent does not support per service element settings, it
				shall ignore attempts to change the setting by writing to this
				object."
			REFERENCE
				"TR 101 290 section 5.3.3.1"
			DEFVAL { packet }
			::= { tsMeasurePreferencesServiceEntry 6 }
		
		tsMeasurePrefServiceBitRateMin OBJECT-TYPE
			SYNTAX FloatingPoint
			UNITS "bit/s"
			MAX-ACCESS read-create
			STATUS current
			DESCRIPTION
				"An error is generated if the Service bit rate
				is below this value."
			::= { tsMeasurePreferencesServiceEntry 7 }
		
		tsMeasurePrefServiceBitRateMax OBJECT-TYPE
			SYNTAX FloatingPoint
			UNITS "bit/s"
			MAX-ACCESS read-create
			STATUS current
			DESCRIPTION
				"An error is generated if the Transport Stream bit rate
				exceeds this value."
			::= { tsMeasurePreferencesServiceEntry 8 }
		
		tsMeasurePreferencesPIDTable OBJECT-TYPE
			SYNTAX SEQUENCE OF TsMeasurePreferencesPIDEntry
			MAX-ACCESS not-accessible
			STATUS current
			DESCRIPTION
				"This table contains configuration information for the
				tsMeasurements branch of the MIB. Configuration related
				to individual PIDs is found here."
			::= { tsMeasurePreferences 3 }
		
		tsMeasurePreferencesPIDEntry OBJECT-TYPE
			SYNTAX TsMeasurePreferencesPIDEntry
			MAX-ACCESS not-accessible
			STATUS current
			DESCRIPTION
				"Row specification"
			INDEX { tsMeasurePrefPIDInputNumber, tsMeasurePrefPIDPID }
			::= { tsMeasurePreferencesPIDTable 1 }
		
		TsMeasurePreferencesPIDEntry ::=
			SEQUENCE { 
				tsMeasurePrefPIDInputNumber
					InputNumber,
				tsMeasurePrefPIDPID
					PIDPlusOne,
				tsMeasurePrefPIDRowStatus
					RowStatus,
				tsMeasurePrefPIDBitRateTau
					FloatingPoint,
				tsMeasurePrefPIDBitRateN
					Unsigned32,
				tsMeasurePrefPIDBitRateElement
					BitRateElement,
				tsMeasurePrefPIDBitRateMin
					FloatingPoint,
				tsMeasurePrefPIDBitRateMax
					FloatingPoint
			 }

		tsMeasurePrefPIDInputNumber OBJECT-TYPE
			SYNTAX InputNumber
			MAX-ACCESS not-accessible
			STATUS current
			DESCRIPTION
				"Transport Stream input to which the preferences apply"
			::= { tsMeasurePreferencesPIDEntry 1 }
		
		tsMeasurePrefPIDPID OBJECT-TYPE
			SYNTAX PIDPlusOne
			MAX-ACCESS not-accessible
			STATUS current
			DESCRIPTION
				"PID (plus one) to which the preferences apply."
			::= { tsMeasurePreferencesPIDEntry 2 }
		
		tsMeasurePrefPIDRowStatus OBJECT-TYPE
			SYNTAX RowStatus
			MAX-ACCESS read-create
			STATUS current
			DESCRIPTION
				"This is used by the manager to create and delete rows
				in the table. The agent will automatically create rows
				for PIDs which have a non-zero bit rate."
			DEFVAL { active }
			::= { tsMeasurePreferencesPIDEntry 3 }
		
		tsMeasurePrefPIDBitRateTau OBJECT-TYPE
			SYNTAX FloatingPoint
			UNITS "second"
			MAX-ACCESS read-create
			STATUS current
			DESCRIPTION
				"'tau' value for bit rate measurement for this PID.
				
				See note in description for tsMeasurePrefTSBitRateTau.
				
				If an agent does not support per PID tau settings, it shall
				ignore attempts to change the setting by writing to this object."
			REFERENCE
				"TR 101 290 section 5.3.3.1"
			DEFVAL { "0.1" }
			::= { tsMeasurePreferencesPIDEntry 4 }
		
		tsMeasurePrefPIDBitRateN OBJECT-TYPE
			SYNTAX Unsigned32
			MAX-ACCESS read-create
			STATUS current
			DESCRIPTION
				"'N' value for bit rate measurement for this PID.
				
				See note in description for tsMeasurePrefTSBitRateTau.
				
				If an agent does not support per PID 'N' settings, it shall
				ignore attempts to change the setting by writing to this object."
			REFERENCE
				"TR 101 290 section 5.3.3.1"
			DEFVAL { 10 }
			::= { tsMeasurePreferencesPIDEntry 5 }
		
		tsMeasurePrefPIDBitRateElement OBJECT-TYPE
			SYNTAX BitRateElement
			MAX-ACCESS read-create
			STATUS current
			DESCRIPTION
				"Data unit which is counted by the bit rate measurement
				algorithm for this PID.
				
				See note in description for tsMeasurePrefTSBitRateTau.
				
				If an agent does not support per PID element settings, it shall
				ignore attempts to change the setting by writing to this object."
			REFERENCE
				"TR 101 290 section 5.3.3.1"
			DEFVAL { packet }
			::= { tsMeasurePreferencesPIDEntry 6 }
		
		tsMeasurePrefPIDBitRateMin OBJECT-TYPE
			SYNTAX FloatingPoint
			UNITS "bit/s"
			MAX-ACCESS read-create
			STATUS current
			DESCRIPTION
				"An error is generated if the PID bit rate is below this value."
			::= { tsMeasurePreferencesPIDEntry 7 }
		
		tsMeasurePrefPIDBitRateMax OBJECT-TYPE
			SYNTAX FloatingPoint
			UNITS "bit/s"
			MAX-ACCESS read-create
			STATUS current
			DESCRIPTION
				"An error is generated if the PID bit rate exceeds this value."
			::= { tsMeasurePreferencesPIDEntry 8 }
		
		tsServicePerformance OBJECT IDENTIFIER ::= { tr101290TS 5 }
		
		tsServicePerformanceTable OBJECT-TYPE
			SYNTAX SEQUENCE OF TsServicePerformanceEntry
			MAX-ACCESS not-accessible
			STATUS current
			DESCRIPTION
				"This table gives access to the Service Performance
				measurements and tests"
			REFERENCE
				"TR 101 290 section 5.5"
			::= { tsServicePerformance 2 }
		
		tsServicePerformanceEntry OBJECT-TYPE
			SYNTAX TsServicePerformanceEntry
			MAX-ACCESS not-accessible
			STATUS current
			DESCRIPTION
				"Row specification"
			INDEX { tsServicePerformanceNumber, tsServicePerformanceInputNumber }
			::= { tsServicePerformanceTable 1 }
		
		TsServicePerformanceEntry ::=
			SEQUENCE { 
				tsServicePerformanceInputNumber
					InputNumber,
				tsServicePerformanceNumber
					IndexServicePerformance,
				tsServicePerformanceState
					TestState,
				tsServicePerformanceEnable
					Enable,
				tsServicePerformanceCounter
					Counter32,
				tsServicePerformanceCounterDiscontinuity
					DateAndTime,
				tsServicePerformanceCounterReset
					TruthValue,
				tsServicePerformanceLatestError
					DateAndTime,
				tsServicePerformanceActiveTime
					ActiveTime,
				tsServicePerformanceMeasurementState
					MeasurementState,
				tsServicePerformanceError
					Unsigned32,
				tsServicePerformanceErrorRatio
					FloatingPoint
			 }

		tsServicePerformanceInputNumber OBJECT-TYPE
			SYNTAX InputNumber
			MAX-ACCESS not-accessible
			STATUS current
			DESCRIPTION
				"Transport Stream on which the measurement is made"
			::= { tsServicePerformanceEntry 1 }
		
		tsServicePerformanceNumber OBJECT-TYPE
			SYNTAX IndexServicePerformance
			MAX-ACCESS not-accessible
			STATUS current
			DESCRIPTION
				"The Service Performance measurement which this row
				applies to."
			::= { tsServicePerformanceEntry 2 }
		
		tsServicePerformanceState OBJECT-TYPE
			SYNTAX TestState
			MAX-ACCESS read-only
			STATUS current
			DESCRIPTION
				"This gives the overall pass/fail state of the threshold
				test on this measurement. The threshold test fails if
				the value of tsServicePerformanceErrorRatio exceeds
				the value given in the preferences."
			::= { tsServicePerformanceEntry 3 }
		
		tsServicePerformanceEnable OBJECT-TYPE
			SYNTAX Enable
			MAX-ACCESS read-write
			STATUS current
			DESCRIPTION
				"Determines whether the threshold test and associated traps
				for this measurement are enabled."
			DEFVAL { { testEnable } }
			::= { tsServicePerformanceEntry 4 }
		
		tsServicePerformanceCounter OBJECT-TYPE
			SYNTAX Counter32
			MAX-ACCESS read-only
			STATUS current
			DESCRIPTION
				"Count of the number of times a threshold error has
				occurred for this measurement."
			::= { tsServicePerformanceEntry 5 }
		
		tsServicePerformanceCounterDiscontinuity OBJECT-TYPE
			SYNTAX DateAndTime
			MAX-ACCESS read-only
			STATUS current
			DESCRIPTION
				"Provides the last time at which there was a discontinuity
				in the tsServicePerformanceCounter object."
			::= { tsServicePerformanceEntry 6 }
		
		tsServicePerformanceCounterReset OBJECT-TYPE
			SYNTAX TruthValue
			MAX-ACCESS read-write
			STATUS current
			DESCRIPTION
				"tsServicePerformanceCounter is reset to zero and
				tsServicePerformanceCounterDiscontinuity is set to
				the current time if 'true' is written to this variable.
				
				The value read from this object is always 'false'."
			DEFVAL { false }
			::= { tsServicePerformanceEntry 7 }
		
		tsServicePerformanceLatestError OBJECT-TYPE
			SYNTAX DateAndTime
			MAX-ACCESS read-only
			STATUS current
			DESCRIPTION
				"The timestamp at the most recent occurrence of a threshold
				error on this measurement."
			::= { tsServicePerformanceEntry 8 }
		
		tsServicePerformanceActiveTime OBJECT-TYPE
			SYNTAX ActiveTime
			UNITS "second"
			MAX-ACCESS read-only
			STATUS current
			DESCRIPTION
				"The total time when it has been possible to perform this measurement"
			::= { tsServicePerformanceEntry 9 }
		
		tsServicePerformanceMeasurementState OBJECT-TYPE
			SYNTAX MeasurementState
			MAX-ACCESS read-only
			STATUS current
			DESCRIPTION
				"Indicates the validity of the measurement"
			::= { tsServicePerformanceEntry 10 }
		
		tsServicePerformanceError OBJECT-TYPE
			SYNTAX Unsigned32
			MAX-ACCESS read-only
			STATUS current
			DESCRIPTION
				"The calculated xxx_Error parameter as measured at the
				end of the most recently completed DeltaT period."
			::= { tsServicePerformanceEntry 11 }
		
		tsServicePerformanceErrorRatio OBJECT-TYPE
			SYNTAX FloatingPoint
			MAX-ACCESS read-only
			STATUS current
			DESCRIPTION
				"This is the calculated xxx_Error_Ratio as a percentage
				(e.g. '1.32'). The value is for the most recently
				completed evaluation time (e.g. 10 minutes)."
			::= { tsServicePerformanceEntry 12 }
		
		tsServicePerformancePreferencesTable OBJECT-TYPE
			SYNTAX SEQUENCE OF TsServicePerformancePreferencesEntry
			MAX-ACCESS not-accessible
			STATUS current
			DESCRIPTION
				"Parameters controlling the Service Performance measurements"
			::= { tsServicePerformance 100 }
		
		tsServicePerformancePreferencesEntry OBJECT-TYPE
			SYNTAX TsServicePerformancePreferencesEntry
			MAX-ACCESS not-accessible
			STATUS current
			DESCRIPTION
				"Row specification"
			INDEX { tsSPPrefInputNumber, tsSPPrefNumber }
			::= { tsServicePerformancePreferencesTable 1 }
		
		TsServicePerformancePreferencesEntry ::=
			SEQUENCE { 
				tsSPPrefInputNumber
					InputNumber,
				tsSPPrefNumber
					IndexServicePerformance,
				tsSPPrefDeltaT
					FloatingPoint,
				tsSPPrefEvaluationTime
					FloatingPoint,
				tsSPPrefThreshold
					FloatingPoint
			 }

		tsSPPrefInputNumber OBJECT-TYPE
			SYNTAX InputNumber
			MAX-ACCESS not-accessible
			STATUS current
			DESCRIPTION
				"Transport Stream input to which the preferences apply"
			::= { tsServicePerformancePreferencesEntry 1 }
		
		tsSPPrefNumber OBJECT-TYPE
			SYNTAX IndexServicePerformance
			MAX-ACCESS not-accessible
			STATUS current
			DESCRIPTION
				"The service performance parameter to which these
				preferences apply."
			::= { tsServicePerformancePreferencesEntry 2 }
		
		tsSPPrefDeltaT OBJECT-TYPE
			SYNTAX FloatingPoint
			UNITS "second"
			MAX-ACCESS read-write
			STATUS current
			DESCRIPTION
				"The defined time interval over which errors are counted"
			REFERENCE
				"TR 101 290 section 5.5"
			::= { tsServicePerformancePreferencesEntry 3 }
		
		tsSPPrefEvaluationTime OBJECT-TYPE
			SYNTAX FloatingPoint
			UNITS "second"
			MAX-ACCESS read-write
			STATUS current
			DESCRIPTION
				"The period over which the ...Error_Ratio is calculated"
			REFERENCE
				"TR 101 290 section 5.5"
			::= { tsServicePerformancePreferencesEntry 4 }
		
		tsSPPrefThreshold OBJECT-TYPE
			SYNTAX FloatingPoint
			MAX-ACCESS read-write
			STATUS current
			DESCRIPTION
				"The threshold value used in calculating the ..._Error_Ratio."
			REFERENCE
				"TR 101 290 section 5.5"
			::= { tsServicePerformancePreferencesEntry 5 }
		
-- Measurements and tests from section 6 of TR 101 290.
-- These apply to both cable and satellite systems.
		tr101290CableSat OBJECT IDENTIFIER ::= { tr101290Objects 6 }
		
		sysAvailabilityTable OBJECT-TYPE
			SYNTAX SEQUENCE OF SysAvailabilityEntry
			MAX-ACCESS not-accessible
			STATUS current
			DESCRIPTION
				"System availability measurement"
			REFERENCE
				"TR 101 290 section 6.1
				TR 101 290 section 5.4"
			::= { tr101290CableSat 1 }
		
		sysAvailabilityEntry OBJECT-TYPE
			SYNTAX SysAvailabilityEntry
			MAX-ACCESS not-accessible
			STATUS current
			DESCRIPTION
				"Row specification"
			INDEX { sysAvailabilityInputNumber }
			::= { sysAvailabilityTable 1 }
		
		SysAvailabilityEntry ::=
			SEQUENCE { 
				sysAvailabilityInputNumber
					InputNumber,
				sysAvailabilityTestState
					TestState,
				sysAvailabilityEnable
					Enable,
				sysAvailabilityCounter
					Counter32,
				sysAvailabilityCounterDiscontinuity
					DateAndTime,
				sysAvailabilityCounterReset
					TruthValue,
				sysAvailabilityLatestError
					DateAndTime,
				sysAvailabilityActiveTime
					ActiveTime,
				sysAvailabilityMeasurementState
					MeasurementState,
				sysAvailabilityUnavailableTime
					Unsigned32,
				sysAvailabilityRatio
					FloatingPoint,
				sysAvailabilityInSETI
					TruthValue
			 }

		sysAvailabilityInputNumber OBJECT-TYPE
			SYNTAX InputNumber
			MAX-ACCESS not-accessible
			STATUS current
			DESCRIPTION
				"Transport Stream on which the measurement is made"
			::= { sysAvailabilityEntry 1 }
		
		sysAvailabilityTestState OBJECT-TYPE
			SYNTAX TestState
			MAX-ACCESS read-only
			STATUS current
			DESCRIPTION
				"A 'fail' is an approximate indication that the system
				is in a period of unavailable time (UAT).  'fail' is
				indicated as soon as a trigger period for unavailable
				time completes.  'pass' is indicated as soon as a trigger
				period for available time completes.  This necessarily
				differs from the strict definition of UAT because the
				measuring equipment is unable to look into the future."
			::= { sysAvailabilityEntry 2 }
		
		sysAvailabilityEnable OBJECT-TYPE
			SYNTAX Enable
			MAX-ACCESS read-write
			STATUS current
			DESCRIPTION
				"Determines whether system availability testing is
				performed and whether the associated traps are generated."
			DEFVAL { { testEnable } }
			::= { sysAvailabilityEntry 3 }
		
		sysAvailabilityCounter OBJECT-TYPE
			SYNTAX Counter32
			MAX-ACCESS read-only
			STATUS current
			DESCRIPTION
				"Count of the number of times the system has become unavailable"
			::= { sysAvailabilityEntry 4 }
		
		sysAvailabilityCounterDiscontinuity OBJECT-TYPE
			SYNTAX DateAndTime
			MAX-ACCESS read-only
			STATUS current
			DESCRIPTION
				"Provides the last time at which there was a discontinuity
				in the sysAvailabilityCounter object."
			::= { sysAvailabilityEntry 5 }
		
		sysAvailabilityCounterReset OBJECT-TYPE
			SYNTAX TruthValue
			MAX-ACCESS read-write
			STATUS current
			DESCRIPTION
				"sysAvailabilityCounter is reset to zero and
				sysAvailabilityCounterDiscontinuity is set to the
				current time if 'true' is written to this variable.
				
				When read, the value of this object is always 'false'."
			::= { sysAvailabilityEntry 6 }
		
		sysAvailabilityLatestError OBJECT-TYPE
			SYNTAX DateAndTime
			MAX-ACCESS read-only
			STATUS current
			DESCRIPTION
				"The timestamp when the system most recently became unavailable."
			::= { sysAvailabilityEntry 7 }
		
		sysAvailabilityActiveTime OBJECT-TYPE
			SYNTAX ActiveTime
			UNITS "second"
			MAX-ACCESS read-only
			STATUS current
			DESCRIPTION
				"This is a monotonically increasing value in units of
				seconds that represents the total amount of time for
				which the instrument has been able to perform the
				test/measurement.  It can be used to calculate the
				Total Time in the calculation of the availability."
			::= { sysAvailabilityEntry 8 }
		
		sysAvailabilityMeasurementState OBJECT-TYPE
			SYNTAX MeasurementState
			MAX-ACCESS read-only
			STATUS current
			DESCRIPTION
				"Indicates the validity of the measurement"
			::= { sysAvailabilityEntry 9 }
		
		sysAvailabilityUnavailableTime OBJECT-TYPE
			SYNTAX Unsigned32
			UNITS "second"
			MAX-ACCESS read-only
			STATUS current
			DESCRIPTION
				"This is a monotonically increasing time in seconds
				which measures the total Unavailable Time (UAT) since
				the measuring system was last restarted."
			::= { sysAvailabilityEntry 10 }
		
		sysAvailabilityRatio OBJECT-TYPE
			SYNTAX FloatingPoint
			MAX-ACCESS read-only
			STATUS current
			DESCRIPTION
				"This is the System Availability ratio as a percentage
				(e.g. 99.643) measured over the previous 'Total Time'
				measurement period."
			::= { sysAvailabilityEntry 11 }
		
		sysAvailabilityInSETI OBJECT-TYPE
			SYNTAX TruthValue
			MAX-ACCESS read-only
			STATUS current
			DESCRIPTION
				"This object has the value 'true' if and only if the
				most recently completed Time Interval (TI) was a
				Severely Errored Time Interval (SETI)."
			::= { sysAvailabilityEntry 12 }
		
		linkAvailabilityTable OBJECT-TYPE
			SYNTAX SEQUENCE OF LinkAvailabilityEntry
			MAX-ACCESS not-accessible
			STATUS current
			DESCRIPTION
				"Link availability measurement"
			REFERENCE
				"TR 101 290 section 6.2
				TR 101 290 section 5.4"
			::= { tr101290CableSat 2 }
		
		linkAvailabilityEntry OBJECT-TYPE
			SYNTAX LinkAvailabilityEntry
			MAX-ACCESS not-accessible
			STATUS current
			DESCRIPTION
				"Row specification"
			INDEX { linkAvailabilityInputNumber }
			::= { linkAvailabilityTable 1 }
		
		LinkAvailabilityEntry ::=
			SEQUENCE { 
				linkAvailabilityInputNumber
					InputNumber,
				linkAvailabilityTestState
					TestState,
				linkAvailabilityEnable
					Enable,
				linkAvailabilityCounter
					Counter32,
				linkAvailabilityCounterDiscontinuity
					DateAndTime,
				linkAvailabilityCounterReset
					TruthValue,
				linkAvailabilityLatestError
					DateAndTime,
				linkAvailabilityActiveTime
					ActiveTime,
				linkAvailabilityMeasurementState
					MeasurementState,
				linkAvailabilityUnavailableTime
					Unsigned32,
				linkAvailabilityRatio
					FloatingPoint,
				linkAvailabilityInSUTI
					TruthValue
			 }

		linkAvailabilityInputNumber OBJECT-TYPE
			SYNTAX InputNumber
			MAX-ACCESS not-accessible
			STATUS current
			DESCRIPTION
				"Transport Stream on which the measurement is made"
			::= { linkAvailabilityEntry 1 }
		
		linkAvailabilityTestState OBJECT-TYPE
			SYNTAX TestState
			MAX-ACCESS read-only
			STATUS current
			DESCRIPTION
				"A 'fail' is an approximate indication that the system
				is in a period of link unavailable time (LUAT). 'fail'
				is indicated as soon as a trigger period for link
				unavailable time completes. 'pass' is indicated as soon
				as a trigger period for link available time completes.
				This necessarily differs from the strict definition of
				LUAT because the measuring equipment is unable to look
				into the future."
			::= { linkAvailabilityEntry 2 }
		
		linkAvailabilityEnable OBJECT-TYPE
			SYNTAX Enable
			MAX-ACCESS read-write
			STATUS current
			DESCRIPTION
				"Determines whether link availability testing is performed
				and whether the associated traps are generated."
			DEFVAL { { testEnable } }
			::= { linkAvailabilityEntry 3 }
		
		linkAvailabilityCounter OBJECT-TYPE
			SYNTAX Counter32
			MAX-ACCESS read-only
			STATUS current
			DESCRIPTION
				"Count of the number of times the link has become unavailable."
			::= { linkAvailabilityEntry 4 }
		
		linkAvailabilityCounterDiscontinuity OBJECT-TYPE
			SYNTAX DateAndTime
			MAX-ACCESS read-only
			STATUS current
			DESCRIPTION
				"Provides the last time at which there was a discontinuity
				in the linkAvailabilityCounter object."
			::= { linkAvailabilityEntry 5 }
		
		linkAvailabilityCounterReset OBJECT-TYPE
			SYNTAX TruthValue
			MAX-ACCESS read-write
			STATUS current
			DESCRIPTION
				"linkAvailabilityCounter is reset to zero and
				linkAvailabilityCounterDiscontinuity is set to the
				current time if 'true' is written to this variable.
				
				When read, the value of this object is always 'false'."
			DEFVAL { false }
			::= { linkAvailabilityEntry 6 }
		
		linkAvailabilityLatestError OBJECT-TYPE
			SYNTAX DateAndTime
			MAX-ACCESS read-only
			STATUS current
			DESCRIPTION
				"The timestamp when the link most recently became unavailable."
			::= { linkAvailabilityEntry 7 }
		
		linkAvailabilityActiveTime OBJECT-TYPE
			SYNTAX ActiveTime
			UNITS "second"
			MAX-ACCESS read-only
			STATUS current
			DESCRIPTION
				"This is a monotonically increasing value in units
				of seconds that represents the total amount of time
				for which the instrument has been able to perform
				the measurement. It can be used to calculate the
				Total Time in the calculation of the availability."
			::= { linkAvailabilityEntry 8 }
		
		linkAvailabilityMeasurementState OBJECT-TYPE
			SYNTAX MeasurementState
			MAX-ACCESS read-only
			STATUS current
			DESCRIPTION
				"Indicates the validity of the measurement"
			::= { linkAvailabilityEntry 9 }
		
		linkAvailabilityUnavailableTime OBJECT-TYPE
			SYNTAX Unsigned32
			UNITS "second"
			MAX-ACCESS read-only
			STATUS current
			DESCRIPTION
				"This is a monotonically increasing time in seconds which
				measures the total link unavailable time (LUAT) since the
				measuring system was last restarted."
			::= { linkAvailabilityEntry 10 }
		
		linkAvailabilityRatio OBJECT-TYPE
			SYNTAX FloatingPoint
			MAX-ACCESS read-only
			STATUS current
			DESCRIPTION
				"This is the Link Availability ratio as a percentage
				(e.g. 99.643) measured over the previous 'Total Time'
				measurement period."
			::= { linkAvailabilityEntry 11 }
		
		linkAvailabilityInSUTI OBJECT-TYPE
			SYNTAX TruthValue
			MAX-ACCESS read-only
			STATUS current
			DESCRIPTION
				"This object has the value 'true' if and only if the
				most recently completed Time Interval (TI) was a
				Severely Uncorrectable Time Interval (SETI)."
			::= { linkAvailabilityEntry 12 }
		
		berRSinServiceTable OBJECT-TYPE
			SYNTAX SEQUENCE OF BerRSinServiceEntry
			MAX-ACCESS not-accessible
			STATUS current
			DESCRIPTION
				"Measurement of BER before RS decoder"
			REFERENCE
				"TR 101 290 section 6.3.2"
			::= { tr101290CableSat 3 }
		
		berRSinServiceEntry OBJECT-TYPE
			SYNTAX BerRSinServiceEntry
			MAX-ACCESS not-accessible
			STATUS current
			DESCRIPTION
				"Row specification"
			INDEX { berRSinServiceInputNumber }
			::= { berRSinServiceTable 1 }
		
		BerRSinServiceEntry ::=
			SEQUENCE { 
				berRSinServiceInputNumber
					InputNumber,
				berRSinServiceTestState
					TestState,
				berRSinServiceEnable
					Enable,
				berRSinServiceCounter
					Counter32,
				berRSinServiceCounterDiscontinuity
					DateAndTime,
				berRSinServiceCounterReset
					TruthValue,
				berRSinServiceLatestError
					DateAndTime,
				berRSinServiceActiveTime
					ActiveTime,
				berRSinServiceMeasurementState
					MeasurementState,
				berRSinServiceValue
					FloatingPoint
			 }

		berRSinServiceInputNumber OBJECT-TYPE
			SYNTAX InputNumber
			MAX-ACCESS not-accessible
			STATUS current
			DESCRIPTION
				"Transport Stream on which the measurement is made"
			::= { berRSinServiceEntry 1 }
		
		berRSinServiceTestState OBJECT-TYPE
			SYNTAX TestState
			MAX-ACCESS read-only
			STATUS current
			DESCRIPTION
				"This indicates whether the berRSinServiceValue is
				below the maximum."
			::= { berRSinServiceEntry 2 }
		
		berRSinServiceEnable OBJECT-TYPE
			SYNTAX Enable
			MAX-ACCESS read-write
			STATUS current
			DESCRIPTION
				"Determines whether the threshold test and associated traps
				for this measurement are enabled."
			DEFVAL { { testEnable } }
			::= { berRSinServiceEntry 3 }
		
		berRSinServiceCounter OBJECT-TYPE
			SYNTAX Counter32
			MAX-ACCESS read-only
			STATUS current
			DESCRIPTION
				"Count of the number of times a threshold error has
				occurred for this measurement."
			::= { berRSinServiceEntry 4 }
		
		berRSinServiceCounterDiscontinuity OBJECT-TYPE
			SYNTAX DateAndTime
			MAX-ACCESS read-only
			STATUS current
			DESCRIPTION
				"Provides the last time at which there was a discontinuity
				in the berRSinServiceCounter object."
			::= { berRSinServiceEntry 5 }
		
		berRSinServiceCounterReset OBJECT-TYPE
			SYNTAX TruthValue
			MAX-ACCESS read-write
			STATUS current
			DESCRIPTION
				"berRSinServiceCounter is reset to zero and
				berRSinServiceCounterDiscontinuity is set to the current
				time if 'true' is written to this object.
				
				When read, the value of this object is always 'false'."
			DEFVAL { false }
			::= { berRSinServiceEntry 6 }
		
		berRSinServiceLatestError OBJECT-TYPE
			SYNTAX DateAndTime
			MAX-ACCESS read-only
			STATUS current
			DESCRIPTION
				"The timestamp at the most recent occurrence of a
				threshold error on this measurement."
			::= { berRSinServiceEntry 7 }
		
		berRSinServiceActiveTime OBJECT-TYPE
			SYNTAX ActiveTime
			UNITS "second"
			MAX-ACCESS read-only
			STATUS current
			DESCRIPTION
				"The total time when it has been possible to perform this measurement"
			::= { berRSinServiceEntry 8 }
		
		berRSinServiceMeasurementState OBJECT-TYPE
			SYNTAX MeasurementState
			MAX-ACCESS read-only
			STATUS current
			DESCRIPTION
				"Indicates the validity of the measurement"
			::= { berRSinServiceEntry 9 }
		
		berRSinServiceValue OBJECT-TYPE
			SYNTAX FloatingPoint
			MAX-ACCESS read-only
			STATUS current
			DESCRIPTION
				"This is the current BER as a numeric value, for
				example 0.0000023"
			REFERENCE
				"TR 101 290 section 6.3.2"
			::= { berRSinServiceEntry 10 }
		
		rfIFsignalPowerTable OBJECT-TYPE
			SYNTAX SEQUENCE OF RfIFsignalPowerEntry
			MAX-ACCESS not-accessible
			STATUS current
			DESCRIPTION
				"RF or IF signal power measurement"
			REFERENCE
				"TR 101 290 section 6.6"
			::= { tr101290CableSat 6 }
		
		rfIFsignalPowerEntry OBJECT-TYPE
			SYNTAX RfIFsignalPowerEntry
			MAX-ACCESS not-accessible
			STATUS current
			DESCRIPTION
				"Row specification"
			INDEX { rfIFsignalPowerInputNumber }
			::= { rfIFsignalPowerTable 1 }
		
		RfIFsignalPowerEntry ::=
			SEQUENCE { 
				rfIFsignalPowerInputNumber
					InputNumber,
				rfIFsignalPowerTestState
					TestState,
				rfIFsignalPowerEnable
					Enable,
				rfIFsignalPowerCounter
					Counter32,
				rfIFsignalPowerCounterDiscontinuity
					DateAndTime,
				rfIFsignalPowerCounterReset
					TruthValue,
				rfIFsignalPowerLatestError
					DateAndTime,
				rfIFsignalPowerActiveTime
					ActiveTime,
				rfIFsignalPowerMeasurementState
					MeasurementState,
				rfIFsignalPowerValue
					FloatingPoint
			 }

		rfIFsignalPowerInputNumber OBJECT-TYPE
			SYNTAX InputNumber
			MAX-ACCESS not-accessible
			STATUS current
			DESCRIPTION
				"Transport Stream on which the measurement is made"
			::= { rfIFsignalPowerEntry 1 }
		
		rfIFsignalPowerTestState OBJECT-TYPE
			SYNTAX TestState
			MAX-ACCESS read-only
			STATUS current
			DESCRIPTION
				"This indicates whether the rfIFsignalPowerValue is
				currently within the thresholds."
			::= { rfIFsignalPowerEntry 2 }
		
		rfIFsignalPowerEnable OBJECT-TYPE
			SYNTAX Enable
			MAX-ACCESS read-write
			STATUS current
			DESCRIPTION
				"Determines whether the threshold test and associated traps
				for this measurement are enabled."
			DEFVAL { { testEnable } }
			::= { rfIFsignalPowerEntry 3 }
		
		rfIFsignalPowerCounter OBJECT-TYPE
			SYNTAX Counter32
			MAX-ACCESS read-only
			STATUS current
			DESCRIPTION
				"Count of the number of times a threshold error has
				occurred for this measurement."
			::= { rfIFsignalPowerEntry 4 }
		
		rfIFsignalPowerCounterDiscontinuity OBJECT-TYPE
			SYNTAX DateAndTime
			MAX-ACCESS read-only
			STATUS current
			DESCRIPTION
				"Provides the last time at which there was a discontinuity
				in the rfIFsignalPowerCounter object."
			::= { rfIFsignalPowerEntry 5 }
		
		rfIFsignalPowerCounterReset OBJECT-TYPE
			SYNTAX TruthValue
			MAX-ACCESS read-write
			STATUS current
			DESCRIPTION
				"rfIFsignalPowerCounter is reset to zero and
				rfIFsignalPowerCounterDiscontinuity is set to the
				current time if 'true' is written to this object.
				
				When read, the value of this object is always 'false'."
			DEFVAL { false }
			::= { rfIFsignalPowerEntry 6 }
		
		rfIFsignalPowerLatestError OBJECT-TYPE
			SYNTAX DateAndTime
			MAX-ACCESS read-only
			STATUS current
			DESCRIPTION
				"The timestamp at the most recent occurrence of a
				threshold error on this measurement."
			::= { rfIFsignalPowerEntry 7 }
		
		rfIFsignalPowerActiveTime OBJECT-TYPE
			SYNTAX ActiveTime
			UNITS "second"
			MAX-ACCESS read-only
			STATUS current
			DESCRIPTION
				"The total time when it has been possible to perform this measurement"
			::= { rfIFsignalPowerEntry 8 }
		
		rfIFsignalPowerMeasurementState OBJECT-TYPE
			SYNTAX MeasurementState
			MAX-ACCESS read-only
			STATUS current
			DESCRIPTION
				"Indicates the validity of the measurement"
			::= { rfIFsignalPowerEntry 9 }
		
		rfIFsignalPowerValue OBJECT-TYPE
			SYNTAX FloatingPoint
			UNITS "dBm"
			MAX-ACCESS read-only
			STATUS current
			DESCRIPTION
				"The current RF power expressed in dBm, which references
				0 dBm as the power of 1 mW. "
			::= { rfIFsignalPowerEntry 10 }
		
		noisePowerTable OBJECT-TYPE
			SYNTAX SEQUENCE OF NoisePowerEntry
			MAX-ACCESS not-accessible
			STATUS current
			DESCRIPTION
				"Noise power measurement"
			REFERENCE
				"TR 101 290 section 6.7"
			::= { tr101290CableSat 7 }
		
		noisePowerEntry OBJECT-TYPE
			SYNTAX NoisePowerEntry
			MAX-ACCESS not-accessible
			STATUS current
			DESCRIPTION
				"Row specification"
			INDEX { noisePowerInputNumber }
			::= { noisePowerTable 1 }
		
		NoisePowerEntry ::=
			SEQUENCE { 
				noisePowerInputNumber
					InputNumber,
				noisePowerTestState
					TestState,
				noisePowerEnable
					Enable,
				noisePowerCounter
					Counter32,
				noisePowerCounterDiscontinuity
					DateAndTime,
				noisePowerCounterReset
					TruthValue,
				noisePowerLatestError
					DateAndTime,
				noisePowerActiveTime
					ActiveTime,
				noisePowerMeasurementState
					MeasurementState,
				noisePowerValue
					FloatingPoint
			 }

		noisePowerInputNumber OBJECT-TYPE
			SYNTAX InputNumber
			MAX-ACCESS not-accessible
			STATUS current
			DESCRIPTION
				"Transport Stream on which the measurement is made"
			::= { noisePowerEntry 1 }
		
		noisePowerTestState OBJECT-TYPE
			SYNTAX TestState
			MAX-ACCESS read-only
			STATUS current
			DESCRIPTION
				"This indicates whether the noisePowerValue is currently
				below the maximum limit."
			::= { noisePowerEntry 2 }
		
		noisePowerEnable OBJECT-TYPE
			SYNTAX Enable
			MAX-ACCESS read-write
			STATUS current
			DESCRIPTION
				"Determines whether the threshold test and associated traps
				for this measurement are enabled."
			DEFVAL { { testEnable } }
			::= { noisePowerEntry 3 }
		
		noisePowerCounter OBJECT-TYPE
			SYNTAX Counter32
			MAX-ACCESS read-only
			STATUS current
			DESCRIPTION
				"Count of the number of times a threshold error has
				occurred for this measurement."
			::= { noisePowerEntry 4 }
		
		noisePowerCounterDiscontinuity OBJECT-TYPE
			SYNTAX DateAndTime
			MAX-ACCESS read-only
			STATUS current
			DESCRIPTION
				"Provides the last time at which there was a
				discontinuity in the noisePowerCounter object."
			::= { noisePowerEntry 5 }
		
		noisePowerCounterReset OBJECT-TYPE
			SYNTAX TruthValue
			MAX-ACCESS read-write
			STATUS current
			DESCRIPTION
				"noisePowerCounter is reset to zero and
				noisePowerCounterDiscontinuity is set to the
				current time if 'true' is written to this object.
				
				When read, the value of this object is always 'false'."
			::= { noisePowerEntry 6 }
		
		noisePowerLatestError OBJECT-TYPE
			SYNTAX DateAndTime
			MAX-ACCESS read-only
			STATUS current
			DESCRIPTION
				"The timestamp at the most recent occurrence of a
				threshold error on this measurement."
			::= { noisePowerEntry 7 }
		
		noisePowerActiveTime OBJECT-TYPE
			SYNTAX ActiveTime
			UNITS "second"
			MAX-ACCESS read-only
			STATUS current
			DESCRIPTION
				"The total time when it has been possible to perform this measurement"
			::= { noisePowerEntry 8 }
		
		noisePowerMeasurementState OBJECT-TYPE
			SYNTAX MeasurementState
			MAX-ACCESS read-only
			STATUS current
			DESCRIPTION
				"Indicates the validity of the measurement"
			::= { noisePowerEntry 9 }
		
		noisePowerValue OBJECT-TYPE
			SYNTAX FloatingPoint
			UNITS "dBm"
			MAX-ACCESS read-only
			STATUS current
			DESCRIPTION
				"The current RF noise power expressed in dBm, which
				references 0 dBm as the power of 1 mW."
			::= { noisePowerEntry 10 }
		
		iqAnalysisCS OBJECT IDENTIFIER ::= { tr101290CableSat 9 }
		
		merCSTable OBJECT-TYPE
			SYNTAX SEQUENCE OF MerCSEntry
			MAX-ACCESS not-accessible
			STATUS current
			DESCRIPTION
				"Modulation Error Ratio (MER)"
			REFERENCE
				"TR 101 290 section 6.9.2"
			::= { iqAnalysisCS 2 }
		
		merCSEntry OBJECT-TYPE
			SYNTAX MerCSEntry
			MAX-ACCESS not-accessible
			STATUS current
			DESCRIPTION
				"Row specification"
			INDEX { merCSInputNumber }
			::= { merCSTable 1 }
		
		MerCSEntry ::=
			SEQUENCE { 
				merCSInputNumber
					InputNumber,
				merCSTestState
					TestState,
				merCSEnable
					Enable,
				merCSCounter
					Counter32,
				merCSCounterDiscontinuity
					DateAndTime,
				merCSCounterReset
					TruthValue,
				merCSLatestError
					DateAndTime,
				merCSActiveTime
					ActiveTime,
				merCSMeasurementState
					MeasurementState,
				merCSValue
					FloatingPoint
			 }

		merCSInputNumber OBJECT-TYPE
			SYNTAX InputNumber
			MAX-ACCESS not-accessible
			STATUS current
			DESCRIPTION
				"Transport Stream on which the measurement is made"
			::= { merCSEntry 1 }
		
		merCSTestState OBJECT-TYPE
			SYNTAX TestState
			MAX-ACCESS read-only
			STATUS current
			DESCRIPTION
				"This indicates whether the merCSValue is currently
				below the maximum limit."
			::= { merCSEntry 2 }
		
		merCSEnable OBJECT-TYPE
			SYNTAX Enable
			MAX-ACCESS read-write
			STATUS current
			DESCRIPTION
				"Determines whether the threshold test and associated traps
				for this measurement are enabled."
			DEFVAL { { testEnable } }
			::= { merCSEntry 3 }
		
		merCSCounter OBJECT-TYPE
			SYNTAX Counter32
			MAX-ACCESS read-only
			STATUS current
			DESCRIPTION
				"Count of the number of times a threshold error has
				occurred for this measurement."
			::= { merCSEntry 4 }
		
		merCSCounterDiscontinuity OBJECT-TYPE
			SYNTAX DateAndTime
			MAX-ACCESS read-only
			STATUS current
			DESCRIPTION
				"Provides the last time at which there was a discontinuity
				in the merCSCounter object."
			::= { merCSEntry 5 }
		
		merCSCounterReset OBJECT-TYPE
			SYNTAX TruthValue
			MAX-ACCESS read-write
			STATUS current
			DESCRIPTION
				"merCSCounter is reset to zero and merCSCounterDiscontinuity is
				set to the current time if 'true' is written to this object.
				
				When read, the value of this object is always 'false'."
			DEFVAL { false }
			::= { merCSEntry 6 }
		
		merCSLatestError OBJECT-TYPE
			SYNTAX DateAndTime
			MAX-ACCESS read-only
			STATUS current
			DESCRIPTION
				"The timestamp at the most recent occurrence of a
				threshold error on this measurement."
			::= { merCSEntry 7 }
		
		merCSActiveTime OBJECT-TYPE
			SYNTAX ActiveTime
			UNITS "second"
			MAX-ACCESS read-only
			STATUS current
			DESCRIPTION
				"The total time when it has been possible to perform this measurement"
			::= { merCSEntry 8 }
		
		merCSMeasurementState OBJECT-TYPE
			SYNTAX MeasurementState
			MAX-ACCESS read-only
			STATUS current
			DESCRIPTION
				"Indicates the validity of the measurement"
			::= { merCSEntry 9 }
		
		merCSValue OBJECT-TYPE
			SYNTAX FloatingPoint
			UNITS "dB"
			MAX-ACCESS read-only
			STATUS current
			DESCRIPTION
				"The Modulation Error Ratio expressed in dB"
			::= { merCSEntry 10 }
		
-- Separate tables are provided for System Target Error
-- Mean (STEM) and System Target Error Deviation (STED).
		steCS OBJECT IDENTIFIER ::= { iqAnalysisCS 3 }
		
		steMeanCSTable OBJECT-TYPE
			SYNTAX SEQUENCE OF SteMeanCSEntry
			MAX-ACCESS not-accessible
			STATUS current
			DESCRIPTION
				"System Target Error (mean value)"
			REFERENCE
				"TR 101 290 section 6.9.3"
			::= { steCS 1 }
		
		steMeanCSEntry OBJECT-TYPE
			SYNTAX SteMeanCSEntry
			MAX-ACCESS not-accessible
			STATUS current
			DESCRIPTION
				"Row specification"
			INDEX { steMeanCSInputNumber }
			::= { steMeanCSTable 1 }
		
		SteMeanCSEntry ::=
			SEQUENCE { 
				steMeanCSInputNumber
					InputNumber,
				steMeanCSTestState
					TestState,
				steMeanCSEnable
					Enable,
				steMeanCSCounter
					Counter32,
				steMeanCSCounterDiscontinuity
					DateAndTime,
				steMeanCSCounterReset
					TruthValue,
				steMeanCSLatestError
					DateAndTime,
				steMeanCSActiveTime
					ActiveTime,
				steMeanCSMeasurementState
					MeasurementState,
				steMeanCSValue
					FloatingPoint
			 }

		steMeanCSInputNumber OBJECT-TYPE
			SYNTAX InputNumber
			MAX-ACCESS not-accessible
			STATUS current
			DESCRIPTION
				"Transport Stream on which the measurement is made"
			::= { steMeanCSEntry 1 }
		
		steMeanCSTestState OBJECT-TYPE
			SYNTAX TestState
			MAX-ACCESS read-only
			STATUS current
			DESCRIPTION
				"This indicates whether the steMeanCSValue is currently
				within the thresholds."
			::= { steMeanCSEntry 2 }
		
		steMeanCSEnable OBJECT-TYPE
			SYNTAX Enable
			MAX-ACCESS read-write
			STATUS current
			DESCRIPTION
				"Determines whether the threshold test and associated traps
				for this measurement are enabled."
			DEFVAL { { testEnable } }
			::= { steMeanCSEntry 3 }
		
		steMeanCSCounter OBJECT-TYPE
			SYNTAX Counter32
			MAX-ACCESS read-only
			STATUS current
			DESCRIPTION
				"Count of the number of times a threshold error has
				occurred for this measurement."
			::= { steMeanCSEntry 4 }
		
		steMeanCSCounterDiscontinuity OBJECT-TYPE
			SYNTAX DateAndTime
			MAX-ACCESS read-only
			STATUS current
			DESCRIPTION
				"Provides the last time at which there was a discontinuity
				in the counter object."
			::= { steMeanCSEntry 5 }
		
		steMeanCSCounterReset OBJECT-TYPE
			SYNTAX TruthValue
			MAX-ACCESS read-write
			STATUS current
			DESCRIPTION
				"The counter object is reset to zero and the counter
				discontinuity object is set to the current time if
				'true' is written to this object.
				
				When read, the value of this object is always 'false'."
			::= { steMeanCSEntry 6 }
		
		steMeanCSLatestError OBJECT-TYPE
			SYNTAX DateAndTime
			MAX-ACCESS read-only
			STATUS current
			DESCRIPTION
				"The timestamp at the most recent occurrence of a threshold
				error on this measurement."
			::= { steMeanCSEntry 7 }
		
		steMeanCSActiveTime OBJECT-TYPE
			SYNTAX ActiveTime
			UNITS "second"
			MAX-ACCESS read-only
			STATUS current
			DESCRIPTION
				"The total time when it has been possible to perform this measurement"
			::= { steMeanCSEntry 8 }
		
		steMeanCSMeasurementState OBJECT-TYPE
			SYNTAX MeasurementState
			MAX-ACCESS read-only
			STATUS current
			DESCRIPTION
				"Indicates the validity of the measurement"
			::= { steMeanCSEntry 9 }
		
		steMeanCSValue OBJECT-TYPE
			SYNTAX FloatingPoint
			MAX-ACCESS read-only
			STATUS current
			DESCRIPTION
				"The current System Target Error Mean as a numeric value"
			::= { steMeanCSEntry 10 }
		
		steDeviationCSTable OBJECT-TYPE
			SYNTAX SEQUENCE OF SteDeviationCSEntry
			MAX-ACCESS not-accessible
			STATUS current
			DESCRIPTION
				"System Target Error (deviation value)"
			REFERENCE
				"TR 101 290 section 6.9.3"
			::= { steCS 2 }
		
		steDeviationCSEntry OBJECT-TYPE
			SYNTAX SteDeviationCSEntry
			MAX-ACCESS not-accessible
			STATUS current
			DESCRIPTION
				"Row specification"
			INDEX { steDeviationCSInputNumber }
			::= { steDeviationCSTable 1 }
		
		SteDeviationCSEntry ::=
			SEQUENCE { 
				steDeviationCSInputNumber
					InputNumber,
				steDeviationCSTestState
					TestState,
				steDeviationCSEnable
					Enable,
				steDeviationCSCounter
					Counter32,
				steDeviationCSCounterDiscontinuity
					DateAndTime,
				steDeviationCSCounterReset
					TruthValue,
				steDeviationCSLatestError
					DateAndTime,
				steDeviationCSActiveTime
					ActiveTime,
				steDeviationCSMeasurementState
					MeasurementState,
				steDeviationCSValue
					FloatingPoint
			 }

		steDeviationCSInputNumber OBJECT-TYPE
			SYNTAX InputNumber
			MAX-ACCESS not-accessible
			STATUS current
			DESCRIPTION
				"Transport Stream on which the measurement is made"
			::= { steDeviationCSEntry 1 }
		
		steDeviationCSTestState OBJECT-TYPE
			SYNTAX TestState
			MAX-ACCESS read-only
			STATUS current
			DESCRIPTION
				"This indicates whether the steDeviationCSValue is currently
				within the thresholds."
			::= { steDeviationCSEntry 2 }
		
		steDeviationCSEnable OBJECT-TYPE
			SYNTAX Enable
			MAX-ACCESS read-write
			STATUS current
			DESCRIPTION
				"Determines whether the threshold test and associated traps
				for this measurement are enabled."
			DEFVAL { { testEnable } }
			::= { steDeviationCSEntry 3 }
		
		steDeviationCSCounter OBJECT-TYPE
			SYNTAX Counter32
			MAX-ACCESS read-only
			STATUS current
			DESCRIPTION
				"Count of the number of times a threshold error has
				occurred for this measurement."
			::= { steDeviationCSEntry 4 }
		
		steDeviationCSCounterDiscontinuity OBJECT-TYPE
			SYNTAX DateAndTime
			MAX-ACCESS read-only
			STATUS current
			DESCRIPTION
				"Provides the last time at which there was a discontinuity
				in the counter object."
			::= { steDeviationCSEntry 5 }
		
		steDeviationCSCounterReset OBJECT-TYPE
			SYNTAX TruthValue
			MAX-ACCESS read-write
			STATUS current
			DESCRIPTION
				"The counter object is reset to zero and the counter
				discontinuity object is set to the current time if
				'true' is written to this object.
				
				When read, the value of this object is always 'false'."
			DEFVAL { false }
			::= { steDeviationCSEntry 6 }
		
		steDeviationCSLatestError OBJECT-TYPE
			SYNTAX DateAndTime
			MAX-ACCESS read-only
			STATUS current
			DESCRIPTION
				"The timestamp at the most recent occurrence of a
				threshold error on this measurement."
			::= { steDeviationCSEntry 7 }
		
		steDeviationCSActiveTime OBJECT-TYPE
			SYNTAX ActiveTime
			UNITS "second"
			MAX-ACCESS read-only
			STATUS current
			DESCRIPTION
				"The total time when it has been possible to perform this measurement
				"
			::= { steDeviationCSEntry 8 }
		
		steDeviationCSMeasurementState OBJECT-TYPE
			SYNTAX MeasurementState
			MAX-ACCESS read-only
			STATUS current
			DESCRIPTION
				"Indicates the validity of the measurement"
			::= { steDeviationCSEntry 9 }
		
		steDeviationCSValue OBJECT-TYPE
			SYNTAX FloatingPoint
			MAX-ACCESS read-only
			STATUS current
			DESCRIPTION
				"The current System Target Error Deviation as a numeric value"
			::= { steDeviationCSEntry 10 }
		
		csCSTable OBJECT-TYPE
			SYNTAX SEQUENCE OF CsCSEntry
			MAX-ACCESS not-accessible
			STATUS current
			DESCRIPTION
				"Carrier suppression measurement"
			REFERENCE
				"TR 101 290 section 6.9.4"
			::= { iqAnalysisCS 4 }
		
		csCSEntry OBJECT-TYPE
			SYNTAX CsCSEntry
			MAX-ACCESS not-accessible
			STATUS current
			DESCRIPTION
				"Row specification"
			INDEX { csCSInputNumber }
			::= { csCSTable 1 }
		
		CsCSEntry ::=
			SEQUENCE { 
				csCSInputNumber
					InputNumber,
				csCSTestState
					TestState,
				csCSEnable
					Enable,
				csCSCounter
					Counter32,
				csCSCounterDiscontinuity
					DateAndTime,
				csCSCounterReset
					TruthValue,
				csCSLatestError
					DateAndTime,
				csCSActiveTime
					ActiveTime,
				csCSMeasurementState
					MeasurementState,
				csCSValue
					FloatingPoint
			 }

		csCSInputNumber OBJECT-TYPE
			SYNTAX InputNumber
			MAX-ACCESS not-accessible
			STATUS current
			DESCRIPTION
				"Transport Stream on which the measurement is made"
			::= { csCSEntry 1 }
		
		csCSTestState OBJECT-TYPE
			SYNTAX TestState
			MAX-ACCESS read-only
			STATUS current
			DESCRIPTION
				"This indicates whether the csCSValue is currently
				within the thresholds."
			::= { csCSEntry 2 }
		
		csCSEnable OBJECT-TYPE
			SYNTAX Enable
			MAX-ACCESS read-write
			STATUS current
			DESCRIPTION
				"Determines whether the threshold test and associated traps
				for this measurement are enabled."
			DEFVAL { { testEnable } }
			::= { csCSEntry 3 }
		
		csCSCounter OBJECT-TYPE
			SYNTAX Counter32
			MAX-ACCESS read-only
			STATUS current
			DESCRIPTION
				"Count of the number of times a threshold error has
				occurred for this measurement."
			::= { csCSEntry 4 }
		
		csCSCounterDiscontinuity OBJECT-TYPE
			SYNTAX DateAndTime
			MAX-ACCESS read-only
			STATUS current
			DESCRIPTION
				"Provides the last time at which there was a discontinuity
				in the counter object."
			::= { csCSEntry 5 }
		
		csCSCounterReset OBJECT-TYPE
			SYNTAX TruthValue
			MAX-ACCESS read-write
			STATUS current
			DESCRIPTION
				"The counter object is reset to zero and the counter
				discontinuity object is set to the current time if
				'true' is written to this object.
				
				When read, the value of this object is always 'false'."
			DEFVAL { false }
			::= { csCSEntry 6 }
		
		csCSLatestError OBJECT-TYPE
			SYNTAX DateAndTime
			MAX-ACCESS read-only
			STATUS current
			DESCRIPTION
				"The timestamp at the most recent occurrence of a
				threshold error on this measurement."
			::= { csCSEntry 7 }
		
		csCSActiveTime OBJECT-TYPE
			SYNTAX ActiveTime
			UNITS "second"
			MAX-ACCESS read-only
			STATUS current
			DESCRIPTION
				"The total time when it has been possible to perform this measurement"
			::= { csCSEntry 8 }
		
		csCSMeasurementState OBJECT-TYPE
			SYNTAX MeasurementState
			MAX-ACCESS read-only
			STATUS current
			DESCRIPTION
				"Indicates the validity of the measurement"
			::= { csCSEntry 9 }
		
		csCSValue OBJECT-TYPE
			SYNTAX FloatingPoint
			UNITS "dB"
			MAX-ACCESS read-only
			STATUS current
			DESCRIPTION
				"The current Carrier Suppression value in dB."
			::= { csCSEntry 10 }
		
		aiCSTable OBJECT-TYPE
			SYNTAX SEQUENCE OF AiCSEntry
			MAX-ACCESS not-accessible
			STATUS current
			DESCRIPTION
				"Amplitude Imbalance (AI) measurement"
			REFERENCE
				"TR 101 290 section 6.9.5"
			::= { iqAnalysisCS 5 }
		
		aiCSEntry OBJECT-TYPE
			SYNTAX AiCSEntry
			MAX-ACCESS not-accessible
			STATUS current
			DESCRIPTION
				"Row specification"
			INDEX { aiCSInputNumber }
			::= { aiCSTable 1 }
		
		AiCSEntry ::=
			SEQUENCE { 
				aiCSInputNumber
					InputNumber,
				aiCSTestState
					TestState,
				aiCSEnable
					Enable,
				aiCSCounter
					Counter32,
				aiCSCounterDiscontinuity
					DateAndTime,
				aiCSCounterReset
					TruthValue,
				aiCSLatestError
					DateAndTime,
				aiCSActiveTime
					ActiveTime,
				aiCSMeasurementState
					MeasurementState,
				aiCSValue
					FloatingPoint
			 }

		aiCSInputNumber OBJECT-TYPE
			SYNTAX InputNumber
			MAX-ACCESS not-accessible
			STATUS current
			DESCRIPTION
				"Transport Stream on which the measurement is made"
			::= { aiCSEntry 1 }
		
		aiCSTestState OBJECT-TYPE
			SYNTAX TestState
			MAX-ACCESS read-only
			STATUS current
			DESCRIPTION
				"This indicates whether the aiCSValue is currently
				within the thresholds."
			::= { aiCSEntry 2 }
		
		aiCSEnable OBJECT-TYPE
			SYNTAX Enable
			MAX-ACCESS read-write
			STATUS current
			DESCRIPTION
				"Determines whether the threshold test and associated traps
				for this measurement are enabled."
			DEFVAL { { testEnable } }
			::= { aiCSEntry 3 }
		
		aiCSCounter OBJECT-TYPE
			SYNTAX Counter32
			MAX-ACCESS read-only
			STATUS current
			DESCRIPTION
				"Count of the number of times a threshold error has
				occurred for this measurement."
			::= { aiCSEntry 4 }
		
		aiCSCounterDiscontinuity OBJECT-TYPE
			SYNTAX DateAndTime
			MAX-ACCESS read-only
			STATUS current
			DESCRIPTION
				"Provides the last time at which there was a discontinuity
				in the counter object."
			::= { aiCSEntry 5 }
		
		aiCSCounterReset OBJECT-TYPE
			SYNTAX TruthValue
			MAX-ACCESS read-write
			STATUS current
			DESCRIPTION
				"The counter object is reset to zero and the counter
				discontinuity object is set to the current time if
				'true' is written to this object.
				
				When read, the value of this object is always 'false'."
			DEFVAL { false }
			::= { aiCSEntry 6 }
		
		aiCSLatestError OBJECT-TYPE
			SYNTAX DateAndTime
			MAX-ACCESS read-only
			STATUS current
			DESCRIPTION
				"The timestamp at the most recent occurrence of a
				threshold error on this measurement."
			::= { aiCSEntry 7 }
		
		aiCSActiveTime OBJECT-TYPE
			SYNTAX ActiveTime
			UNITS "second"
			MAX-ACCESS read-only
			STATUS current
			DESCRIPTION
				"The total time when it has been possible to perform this measurement"
			::= { aiCSEntry 8 }
		
		aiCSMeasurementState OBJECT-TYPE
			SYNTAX MeasurementState
			MAX-ACCESS read-only
			STATUS current
			DESCRIPTION
				"Indicates the validity of the measurement"
			::= { aiCSEntry 9 }
		
		aiCSValue OBJECT-TYPE
			SYNTAX FloatingPoint
			MAX-ACCESS read-only
			STATUS current
			DESCRIPTION
				"The current Amplitude Imbalance as a percentage"
			::= { aiCSEntry 10 }
		
		qeCSTable OBJECT-TYPE
			SYNTAX SEQUENCE OF QeCSEntry
			MAX-ACCESS not-accessible
			STATUS current
			DESCRIPTION
				"Quadrature Error (QE) measurement"
			REFERENCE
				"TR 101 290 section 6.9.6"
			::= { iqAnalysisCS 6 }
		
		qeCSEntry OBJECT-TYPE
			SYNTAX QeCSEntry
			MAX-ACCESS not-accessible
			STATUS current
			DESCRIPTION
				"Row specification"
			INDEX { qeCSInputNumber }
			::= { qeCSTable 1 }
		
		QeCSEntry ::=
			SEQUENCE { 
				qeCSInputNumber
					InputNumber,
				qeCSTestState
					TestState,
				qeCSEnable
					Enable,
				qeCSCounter
					Counter32,
				qeCSCounterDiscontinuity
					DateAndTime,
				qeCSCounterReset
					TruthValue,
				qeCSLatestError
					DateAndTime,
				qeCSActiveTime
					ActiveTime,
				qeCSMeasurementState
					MeasurementState,
				qeCSValue
					FloatingPoint
			 }

		qeCSInputNumber OBJECT-TYPE
			SYNTAX InputNumber
			MAX-ACCESS not-accessible
			STATUS current
			DESCRIPTION
				"Transport Stream on which the measurement is made"
			::= { qeCSEntry 1 }
		
		qeCSTestState OBJECT-TYPE
			SYNTAX TestState
			MAX-ACCESS read-only
			STATUS current
			DESCRIPTION
				"This indicates whether the qeCSValue is currently
				within the thresholds."
			::= { qeCSEntry 2 }
		
		qeCSEnable OBJECT-TYPE
			SYNTAX Enable
			MAX-ACCESS read-write
			STATUS current
			DESCRIPTION
				"Determines whether the threshold test and associated traps
				for this measurement are enabled."
			DEFVAL { { testEnable } }
			::= { qeCSEntry 3 }
		
		qeCSCounter OBJECT-TYPE
			SYNTAX Counter32
			MAX-ACCESS read-only
			STATUS current
			DESCRIPTION
				"Count of the number of times a threshold error has
				occurred for this measurement."
			::= { qeCSEntry 4 }
		
		qeCSCounterDiscontinuity OBJECT-TYPE
			SYNTAX DateAndTime
			MAX-ACCESS read-only
			STATUS current
			DESCRIPTION
				"Provides the last time at which there was a discontinuity
				in the counter object."
			::= { qeCSEntry 5 }
		
		qeCSCounterReset OBJECT-TYPE
			SYNTAX TruthValue
			MAX-ACCESS read-write
			STATUS current
			DESCRIPTION
				"The counter object is reset to zero and the counter
				discontinuity object is set to the current time if
				'true' is written to this object.
				
				When read, the value of this object is always 'false'."
			DEFVAL { false }
			::= { qeCSEntry 6 }
		
		qeCSLatestError OBJECT-TYPE
			SYNTAX DateAndTime
			MAX-ACCESS read-only
			STATUS current
			DESCRIPTION
				"The timestamp at the most recent occurrence of a
				threshold error on this measurement."
			::= { qeCSEntry 7 }
		
		qeCSActiveTime OBJECT-TYPE
			SYNTAX ActiveTime
			UNITS "second"
			MAX-ACCESS read-only
			STATUS current
			DESCRIPTION
				"The total time when it has been possible to perform this measurement"
			::= { qeCSEntry 8 }
		
		qeCSMeasurementState OBJECT-TYPE
			SYNTAX MeasurementState
			MAX-ACCESS read-only
			STATUS current
			DESCRIPTION
				"Indicates the validity of the measurement"
			::= { qeCSEntry 9 }
		
		qeCSValue OBJECT-TYPE
			SYNTAX FloatingPoint
			UNITS "degree"
			MAX-ACCESS read-only
			STATUS current
			DESCRIPTION
				"The current Quadrature Error value in degrees."
			::= { qeCSEntry 10 }
		
		rteCSTable OBJECT-TYPE
			SYNTAX SEQUENCE OF RteCSEntry
			MAX-ACCESS not-accessible
			STATUS current
			DESCRIPTION
				"Residual Target Error (RTE) measurement"
			REFERENCE
				"TR 101 290 section 6.9.7"
			::= { iqAnalysisCS 7 }
		
		rteCSEntry OBJECT-TYPE
			SYNTAX RteCSEntry
			MAX-ACCESS not-accessible
			STATUS current
			DESCRIPTION
				"Row description"
			INDEX { rteCSInputNumber }
			::= { rteCSTable 1 }
		
		RteCSEntry ::=
			SEQUENCE { 
				rteCSInputNumber
					InputNumber,
				rteCSTestState
					TestState,
				rteCSEnable
					Enable,
				rteCSCounter
					Counter32,
				rteCSCounterDiscontinuity
					DateAndTime,
				rteCSCounterReset
					TruthValue,
				rteCSLatestError
					DateAndTime,
				rteCSActiveTime
					ActiveTime,
				rteCSMeasurementState
					MeasurementState,
				rteCSValue
					FloatingPoint
			 }

		rteCSInputNumber OBJECT-TYPE
			SYNTAX InputNumber
			MAX-ACCESS not-accessible
			STATUS current
			DESCRIPTION
				"Transport Stream on which the measurement is made"
			::= { rteCSEntry 1 }
		
		rteCSTestState OBJECT-TYPE
			SYNTAX TestState
			MAX-ACCESS read-only
			STATUS current
			DESCRIPTION
				"This indicates whether the rteCSValue is currently
				within the thresholds."
			::= { rteCSEntry 2 }
		
		rteCSEnable OBJECT-TYPE
			SYNTAX Enable
			MAX-ACCESS read-write
			STATUS current
			DESCRIPTION
				"Determines whether the threshold test and associated traps
				for this measurement are enabled."
			DEFVAL { { testEnable } }
			::= { rteCSEntry 3 }
		
		rteCSCounter OBJECT-TYPE
			SYNTAX Counter32
			MAX-ACCESS read-only
			STATUS current
			DESCRIPTION
				"Count of the number of times a threshold error has
				occurred for this measurement."
			::= { rteCSEntry 4 }
		
		rteCSCounterDiscontinuity OBJECT-TYPE
			SYNTAX DateAndTime
			MAX-ACCESS read-only
			STATUS current
			DESCRIPTION
				"Provides the last time at which there was a discontinuity
				in the counter object."
			::= { rteCSEntry 5 }
		
		rteCSCounterReset OBJECT-TYPE
			SYNTAX TruthValue
			MAX-ACCESS read-write
			STATUS current
			DESCRIPTION
				"The counter object is reset to zero and the counter
				discontinuity object is set to the current time if
				'true' is written to this object.
				
				When read, the value of this object is always 'false'."
			DEFVAL { false }
			::= { rteCSEntry 6 }
		
		rteCSLatestError OBJECT-TYPE
			SYNTAX DateAndTime
			MAX-ACCESS read-only
			STATUS current
			DESCRIPTION
				"The timestamp at the most recent occurrence of a
				threshold error on this measurement."
			::= { rteCSEntry 7 }
		
		rteCSActiveTime OBJECT-TYPE
			SYNTAX ActiveTime
			UNITS "second"
			MAX-ACCESS read-only
			STATUS current
			DESCRIPTION
				"The total time when it has been possible to perform this measurement"
			::= { rteCSEntry 8 }
		
		rteCSMeasurementState OBJECT-TYPE
			SYNTAX MeasurementState
			MAX-ACCESS read-only
			STATUS current
			DESCRIPTION
				"Indicates the validity of the measurement"
			::= { rteCSEntry 9 }
		
		rteCSValue OBJECT-TYPE
			SYNTAX FloatingPoint
			MAX-ACCESS read-only
			STATUS current
			DESCRIPTION
				"The current Residual Target Error value as a numeric value."
			::= { rteCSEntry 10 }
		
		ciCSTable OBJECT-TYPE
			SYNTAX SEQUENCE OF CiCSEntry
			MAX-ACCESS not-accessible
			STATUS current
			DESCRIPTION
				"Coherent Interferer measurement"
			REFERENCE
				"TR 101 290 section 6.9.8"
			::= { iqAnalysisCS 8 }
		
		ciCSEntry OBJECT-TYPE
			SYNTAX CiCSEntry
			MAX-ACCESS not-accessible
			STATUS current
			DESCRIPTION
				"Row specification"
			INDEX { ciCSInputNumber }
			::= { ciCSTable 1 }
		
		CiCSEntry ::=
			SEQUENCE { 
				ciCSInputNumber
					InputNumber,
				ciCSTestState
					TestState,
				ciCSEnable
					Enable,
				ciCSCounter
					Counter32,
				ciCSCounterDiscontinuity
					DateAndTime,
				ciCSCounterReset
					TruthValue,
				ciCSLatestError
					DateAndTime,
				ciCSActiveTime
					ActiveTime,
				ciCSMeasurementState
					MeasurementState,
				ciCSValue
					FloatingPoint
			 }

		ciCSInputNumber OBJECT-TYPE
			SYNTAX InputNumber
			MAX-ACCESS not-accessible
			STATUS current
			DESCRIPTION
				"Transport Stream on which the measurement is made"
			::= { ciCSEntry 1 }
		
		ciCSTestState OBJECT-TYPE
			SYNTAX TestState
			MAX-ACCESS read-only
			STATUS current
			DESCRIPTION
				"This indicates whether the ciCSValue is currently
				within the thresholds."
			::= { ciCSEntry 2 }
		
		ciCSEnable OBJECT-TYPE
			SYNTAX Enable
			MAX-ACCESS read-write
			STATUS current
			DESCRIPTION
				"Determines whether the threshold test and associated traps
				for this measurement are enabled."
			DEFVAL { { testEnable } }
			::= { ciCSEntry 3 }
		
		ciCSCounter OBJECT-TYPE
			SYNTAX Counter32
			MAX-ACCESS read-only
			STATUS current
			DESCRIPTION
				"Count of the number of times a threshold error has
				occurred for this measurement."
			::= { ciCSEntry 4 }
		
		ciCSCounterDiscontinuity OBJECT-TYPE
			SYNTAX DateAndTime
			MAX-ACCESS read-only
			STATUS current
			DESCRIPTION
				"Provides the last time at which there was a discontinuity
				in the counter object."
			::= { ciCSEntry 5 }
		
		ciCSCounterReset OBJECT-TYPE
			SYNTAX TruthValue
			MAX-ACCESS read-write
			STATUS current
			DESCRIPTION
				"The counter object is reset to zero and the counter
				discontinuity object is set to the current time if
				'true' is written to this object.
				
				When read, the value of this object is always 'false'."
			DEFVAL { false }
			::= { ciCSEntry 6 }
		
		ciCSLatestError OBJECT-TYPE
			SYNTAX DateAndTime
			MAX-ACCESS read-only
			STATUS current
			DESCRIPTION
				"The timestamp at the most recent occurrence of a
				threshold error on this measurement."
			::= { ciCSEntry 7 }
		
		ciCSActiveTime OBJECT-TYPE
			SYNTAX ActiveTime
			UNITS "second"
			MAX-ACCESS read-only
			STATUS current
			DESCRIPTION
				"The total time when it has been possible to perform this measurement"
			::= { ciCSEntry 8 }
		
		ciCSMeasurementState OBJECT-TYPE
			SYNTAX MeasurementState
			MAX-ACCESS read-only
			STATUS current
			DESCRIPTION
				"Indicates the validity of the measurement"
			::= { ciCSEntry 9 }
		
		ciCSValue OBJECT-TYPE
			SYNTAX FloatingPoint
			UNITS "dB"
			MAX-ACCESS read-only
			STATUS current
			DESCRIPTION
				"The current Coherent Interferer value in dB."
			::= { ciCSEntry 10 }
		
		pjCSTable OBJECT-TYPE
			SYNTAX SEQUENCE OF PjCSEntry
			MAX-ACCESS not-accessible
			STATUS current
			DESCRIPTION
				"Phase Jitter (PJ) measurement"
			REFERENCE
				"TR 101 290 section 6.9.9"
			::= { iqAnalysisCS 9 }
		
		pjCSEntry OBJECT-TYPE
			SYNTAX PjCSEntry
			MAX-ACCESS not-accessible
			STATUS current
			DESCRIPTION
				"Row specification"
			INDEX { pjCSInputNumber }
			::= { pjCSTable 1 }
		
		PjCSEntry ::=
			SEQUENCE { 
				pjCSInputNumber
					InputNumber,
				pjCSTestState
					TestState,
				pjCSEnable
					Enable,
				pjCSCounter
					Counter32,
				pjCSCounterDiscontinuity
					DateAndTime,
				pjCSCounterReset
					TruthValue,
				pjCSLatestError
					DateAndTime,
				pjCSActiveTime
					ActiveTime,
				pjCSMeasurementState
					MeasurementState,
				pjCSValue
					FloatingPoint
			 }

		pjCSInputNumber OBJECT-TYPE
			SYNTAX InputNumber
			MAX-ACCESS not-accessible
			STATUS current
			DESCRIPTION
				"Transport Stream on which the measurement is made"
			::= { pjCSEntry 1 }
		
		pjCSTestState OBJECT-TYPE
			SYNTAX TestState
			MAX-ACCESS read-only
			STATUS current
			DESCRIPTION
				"This indicates whether the pjCSValue is currently
				within the thresholds."
			::= { pjCSEntry 2 }
		
		pjCSEnable OBJECT-TYPE
			SYNTAX Enable
			MAX-ACCESS read-write
			STATUS current
			DESCRIPTION
				"Determines whether the threshold test and associated traps
				for this measurement are enabled."
			DEFVAL { { testEnable } }
			::= { pjCSEntry 3 }
		
		pjCSCounter OBJECT-TYPE
			SYNTAX Counter32
			MAX-ACCESS read-only
			STATUS current
			DESCRIPTION
				"Count of the number of times a threshold error has
				occurred for this measurement."
			::= { pjCSEntry 4 }
		
		pjCSCounterDiscontinuity OBJECT-TYPE
			SYNTAX DateAndTime
			MAX-ACCESS read-only
			STATUS current
			DESCRIPTION
				"Provides the last time at which there was a discontinuity
				in the counter object."
			::= { pjCSEntry 5 }
		
		pjCSCounterReset OBJECT-TYPE
			SYNTAX TruthValue
			MAX-ACCESS read-write
			STATUS current
			DESCRIPTION
				"The counter object is reset to zero and the counter
				discontinuity object is set to the current time if
				'true' is written to this object.
				
				When read, the value of this object is always 'false'."
			DEFVAL { false }
			::= { pjCSEntry 6 }
		
		pjCSLatestError OBJECT-TYPE
			SYNTAX DateAndTime
			MAX-ACCESS read-only
			STATUS current
			DESCRIPTION
				"The timestamp at the most recent occurrence of a
				threshold error on this measurement."
			::= { pjCSEntry 7 }
		
		pjCSActiveTime OBJECT-TYPE
			SYNTAX ActiveTime
			UNITS "second"
			MAX-ACCESS read-only
			STATUS current
			DESCRIPTION
				"The total time when it has been possible to perform this measurement"
			::= { pjCSEntry 8 }
		
		pjCSMeasurementState OBJECT-TYPE
			SYNTAX MeasurementState
			MAX-ACCESS read-only
			STATUS current
			DESCRIPTION
				"Indicates the validity of the measurement"
			::= { pjCSEntry 9 }
		
		pjCSValue OBJECT-TYPE
			SYNTAX FloatingPoint
			UNITS "degree"
			MAX-ACCESS read-only
			STATUS current
			DESCRIPTION
				"The current Phase Jitter value in degrees."
			::= { pjCSEntry 10 }
		
		snrCSTable OBJECT-TYPE
			SYNTAX SEQUENCE OF SnrCSEntry
			MAX-ACCESS not-accessible
			STATUS current
			DESCRIPTION
				"Signal-to-Noise Ratio (SNR)"
			REFERENCE
				"TR 101 290 section 6.9.10"
			::= { iqAnalysisCS 10 }
		
		snrCSEntry OBJECT-TYPE
			SYNTAX SnrCSEntry
			MAX-ACCESS not-accessible
			STATUS current
			DESCRIPTION
				"Row specification"
			INDEX { snrCSInputNumber }
			::= { snrCSTable 1 }
		
		SnrCSEntry ::=
			SEQUENCE { 
				snrCSInputNumber
					InputNumber,
				snrCSTestState
					TestState,
				snrCSEnable
					Enable,
				snrCSCounter
					Counter32,
				snrCSCounterDiscontinuity
					DateAndTime,
				snrCSCounterReset
					TruthValue,
				snrCSLatestError
					DateAndTime,
				snrCSActiveTime
					ActiveTime,
				snrCSMeasurementState
					MeasurementState,
				snrCSValue
					FloatingPoint
			 }

		snrCSInputNumber OBJECT-TYPE
			SYNTAX InputNumber
			MAX-ACCESS not-accessible
			STATUS current
			DESCRIPTION
				"Transport Stream on which the measurement is made"
			::= { snrCSEntry 1 }
		
		snrCSTestState OBJECT-TYPE
			SYNTAX TestState
			MAX-ACCESS read-only
			STATUS current
			DESCRIPTION
				"This indicates whether the snrCSValue is currently
				within the thresholds."
			::= { snrCSEntry 2 }
		
		snrCSEnable OBJECT-TYPE
			SYNTAX Enable
			MAX-ACCESS read-write
			STATUS current
			DESCRIPTION
				"Determines whether the threshold test and associated
				traps for this measurement are enabled."
			DEFVAL { { testEnable } }
			::= { snrCSEntry 3 }
		
		snrCSCounter OBJECT-TYPE
			SYNTAX Counter32
			MAX-ACCESS read-only
			STATUS current
			DESCRIPTION
				"Count of the number of times a threshold error has
				occurred for this measurement."
			::= { snrCSEntry 4 }
		
		snrCSCounterDiscontinuity OBJECT-TYPE
			SYNTAX DateAndTime
			MAX-ACCESS read-only
			STATUS current
			DESCRIPTION
				"Provides the last time at which there was a discontinuity
				in the counter object."
			::= { snrCSEntry 5 }
		
		snrCSCounterReset OBJECT-TYPE
			SYNTAX TruthValue
			MAX-ACCESS read-write
			STATUS current
			DESCRIPTION
				"The counter object is reset to zero and the counter
				discontinuity object is set to the current time if
				'true' is written to this object.
				
				When read, the value of this object is always 'false'."
			DEFVAL { false }
			::= { snrCSEntry 6 }
		
		snrCSLatestError OBJECT-TYPE
			SYNTAX DateAndTime
			MAX-ACCESS read-only
			STATUS current
			DESCRIPTION
				"The timestamp at the most recent occurrence of a
				threshold error on this measurement."
			::= { snrCSEntry 7 }
		
		snrCSActiveTime OBJECT-TYPE
			SYNTAX ActiveTime
			UNITS "second"
			MAX-ACCESS read-only
			STATUS current
			DESCRIPTION
				"The total time when it has been possible to perform this measurement"
			::= { snrCSEntry 8 }
		
		snrCSMeasurementState OBJECT-TYPE
			SYNTAX MeasurementState
			MAX-ACCESS read-only
			STATUS current
			DESCRIPTION
				"Indicates the validity of the measurement"
			::= { snrCSEntry 9 }
		
		snrCSValue OBJECT-TYPE
			SYNTAX FloatingPoint
			UNITS "dB"
			MAX-ACCESS read-only
			STATUS current
			DESCRIPTION
				"The current Signal-to-Noise value in dB."
			::= { snrCSEntry 10 }
		
		cableSatPreferencesTable OBJECT-TYPE
			SYNTAX SEQUENCE OF CableSatPreferencesEntry
			MAX-ACCESS not-accessible
			STATUS current
			DESCRIPTION
				"Table containing per input configuration information
				for cable and satellite common measurements."
			::= { tr101290CableSat 100 }
		
		cableSatPreferencesEntry OBJECT-TYPE
			SYNTAX CableSatPreferencesEntry
			MAX-ACCESS not-accessible
			STATUS current
			DESCRIPTION
				"Row specification"
			INDEX { cableSatPrefInputNumber }
			::= { cableSatPreferencesTable 1 }
		
		CableSatPreferencesEntry ::=
			SEQUENCE { 
				cableSatPrefInputNumber
					InputNumber,
				cableSatPrefCentreFrequency
					FloatingPoint,
				cableSatPrefModulation
					Modulation,
				cableSatPrefSysAvailUATMode
					UATMode,
				cableSatPrefSysAvailN
					Unsigned32,
				cableSatPrefSysAvailT
					FloatingPoint,
				cableSatPrefSysAvailM
					Unsigned32,
				cableSatPrefSysAvailTI
					FloatingPoint,
				cableSatPrefSysAvailEBPerCent
					FloatingPoint,
				cableSatPrefSysAvailTotalTime
					FloatingPoint,
				cableSatPrefLinkAvailUATMode
					UATMode,
				cableSatPrefLinkAvailN
					Unsigned32,
				cableSatPrefLinkAvailT
					FloatingPoint,
				cableSatPrefLinkAvailM
					Unsigned32,
				cableSatPrefLinkAvailTI
					FloatingPoint,
				cableSatPrefLinkAvailUPPerCent
					FloatingPoint,
				cableSatPrefLinkAvailTotalTime
					FloatingPoint,
				cableSatPrefBERMax
					FloatingPoint,
				cableSatPrefSignalPowerMin
					FloatingPoint,
				cableSatPrefSignalPowerMax
					FloatingPoint,
				cableSatPrefNoisePowerMax
					FloatingPoint,
				cableSatPrefMerCSMin
					FloatingPoint,
				cableSatPrefSteMeanCSMax
					FloatingPoint,
				cableSatPrefSteDeviationCSMax
					FloatingPoint,
				cableSatPrefCsCSMin
					FloatingPoint,
				cableSatPrefAiCSMax
					FloatingPoint,
				cableSatPrefQeCSMax
					FloatingPoint,
				cableSatPrefRteCSMax
					FloatingPoint,
				cableSatPrefCiCSMin
					FloatingPoint,
				cableSatPrefPjCSMax
					FloatingPoint,
				cableSatPrefSnrCSMin
					FloatingPoint
			 }

		cableSatPrefInputNumber OBJECT-TYPE
			SYNTAX InputNumber
			MAX-ACCESS not-accessible
			STATUS current
			DESCRIPTION
				"Transport Stream input to which the preferences apply"
			::= { cableSatPreferencesEntry 1 }
		
		cableSatPrefCentreFrequency OBJECT-TYPE
			SYNTAX FloatingPoint
			UNITS "MHz"
			MAX-ACCESS read-write
			STATUS current
			DESCRIPTION
				"This is the centre frequency to which the measuring equipment
				is tuned for making cable and satellite measurements. This
				frequency is the actual input frequency to the measuring
				equipment, which may be at an intermediate frequency (IF)
				rather than the final RF.
				
				This setting affects the objects in the 'tr101290Cable' and
				'tr101290Satellite' branches of the MIB as well as the
				'tr101290CableSat' branch."
			::= { cableSatPreferencesEntry 2 }
		
		cableSatPrefModulation OBJECT-TYPE
			SYNTAX Modulation
			MAX-ACCESS read-write
			STATUS current
			DESCRIPTION
				"This is the modulation which the measuring equipment expects to
				see and against which it makes modulation measurements. This
				applies to cable and satellite measurements.
				
				This setting affects the objects in the 'tr101290Cable' and
				'tr101290Satellite' branches of the MIB as well as the
				'tr101290CableSat' branch."
			::= { cableSatPreferencesEntry 3 }
		
		cableSatPrefSysAvailUATMode OBJECT-TYPE
			SYNTAX UATMode
			MAX-ACCESS read-write
			STATUS current
			DESCRIPTION
				"Determines whether the 'N consecutive' or 'rolling window'
				mode of determining the start of a period of Unavailable
				Time (UAT) is used. If the 'N consecutive' mode is
				selected, the 'M' and 'T' preference parameters are
				ignored. Likewise, if the 'rolling window' mode is
				selected, the 'N' preference parameter is ignored."
			REFERENCE
				"TR 101 290 section 5.4.5"
			::= { cableSatPreferencesEntry 4 }
		
		cableSatPrefSysAvailN OBJECT-TYPE
			SYNTAX Unsigned32
			MAX-ACCESS read-write
			STATUS current
			DESCRIPTION
				"The N value used to identify the start and end of a
				period of unavailable time (UAT)."
			REFERENCE
				"TR 101 290 section 5.4.5"
			::= { cableSatPreferencesEntry 5 }
		
		cableSatPrefSysAvailT OBJECT-TYPE
			SYNTAX FloatingPoint
			UNITS "second"
			MAX-ACCESS read-write
			STATUS current
			DESCRIPTION
				"The T value used to identify the start and end of a
				period of unavailable time (UAT)."
			REFERENCE
				"TR 101 290 section 5.4.5"
			::= { cableSatPreferencesEntry 6 }
		
		cableSatPrefSysAvailM OBJECT-TYPE
			SYNTAX Unsigned32
			MAX-ACCESS read-write
			STATUS current
			DESCRIPTION
				"The M value used to identify the start and end of a
				period of unavailable time (UAT)."
			REFERENCE
				"TR 101 290 section 5.4.5"
			::= { cableSatPreferencesEntry 7 }
		
		cableSatPrefSysAvailTI OBJECT-TYPE
			SYNTAX FloatingPoint
			UNITS "second"
			MAX-ACCESS read-write
			STATUS current
			DESCRIPTION
				"Each Time Interval of this length is assessed as to 
				whether it is a Severely Errored Time Interval."
			REFERENCE
				"TR 101 290 section 5.4.4"
			::= { cableSatPreferencesEntry 8 }
		
		cableSatPrefSysAvailEBPerCent OBJECT-TYPE
			SYNTAX FloatingPoint
			MAX-ACCESS read-write
			STATUS current
			DESCRIPTION
				"If more than this percentage of blocks within a Time Interval is
				an Errored Block, the Time Interval is a Severely Errored Time
				Interval (SETI). Example values are: '1.53', '10', '0.33'."
			REFERENCE
				"TR 101 290 section 5.4.4"
			::= { cableSatPreferencesEntry 9 }
		
		cableSatPrefSysAvailTotalTime OBJECT-TYPE
			SYNTAX FloatingPoint
			UNITS "second"
			MAX-ACCESS read-write
			STATUS current
			DESCRIPTION
				"The Total Time over which the System Availability is calculated."
			REFERENCE
				"TR 101 290 section 6.1"
			::= { cableSatPreferencesEntry 10 }
		
		cableSatPrefLinkAvailUATMode OBJECT-TYPE
			SYNTAX UATMode
			MAX-ACCESS read-write
			STATUS current
			DESCRIPTION
				"Determines whether the 'N consecutive' or 'rolling window'
				mode of determining the start of a period of Link Unavailable
				Time (LUAT) is used. If the 'N consecutive' mode is selected,
				the 'M' and 'T' preference parameters are ignored. Likewise,
				if the 'rolling window' mode is selected, the 'N' preference
				parameter is ignored."
			REFERENCE
				"TR 101 290 section 6.2"
			::= { cableSatPreferencesEntry 11 }
		
		cableSatPrefLinkAvailN OBJECT-TYPE
			SYNTAX Unsigned32
			MAX-ACCESS read-write
			STATUS current
			DESCRIPTION
				"The N value used to identify the start and end of a period of
				Link Unavailable Time (LUAT)."
			REFERENCE
				"TR 101 290 section 6.2"
			::= { cableSatPreferencesEntry 12 }
		
		cableSatPrefLinkAvailT OBJECT-TYPE
			SYNTAX FloatingPoint
			UNITS "second"
			MAX-ACCESS read-write
			STATUS current
			DESCRIPTION
				"The T value used to identify the start and end of a period of
				Link Unavailable Time (LUAT)."
			REFERENCE
				"TR 101 290 section 6.2"
			::= { cableSatPreferencesEntry 13 }
		
		cableSatPrefLinkAvailM OBJECT-TYPE
			SYNTAX Unsigned32
			MAX-ACCESS read-write
			STATUS current
			DESCRIPTION
				"The M value used to identify the start and end of a period of
				Link Unavailable Time (LUAT)."
			REFERENCE
				"TR 101 290 section 6.2"
			::= { cableSatPreferencesEntry 14 }
		
		cableSatPrefLinkAvailTI OBJECT-TYPE
			SYNTAX FloatingPoint
			UNITS "second"
			MAX-ACCESS read-write
			STATUS current
			DESCRIPTION
				"Each Time Interval of this length is assessed as to
				whether it is a Severely Uncorrectable Time Interval
				(SUTI)."
			REFERENCE
				"TR 101 290 section 6.2"
			::= { cableSatPreferencesEntry 15 }
		
		cableSatPrefLinkAvailUPPerCent OBJECT-TYPE
			SYNTAX FloatingPoint
			MAX-ACCESS read-write
			STATUS current
			DESCRIPTION
				"If more than this percentage of packets within a Time
				Interval is an Uncorrectable Packet (UP), the Time
				Interval is a Severely Uncorrectable Time Interval (SUTI).
				Example values are: '1.53', '10', '0.33'."
			REFERENCE
				"TR 101 290 section 6.2"
			::= { cableSatPreferencesEntry 16 }
		
		cableSatPrefLinkAvailTotalTime OBJECT-TYPE
			SYNTAX FloatingPoint
			UNITS "second"
			MAX-ACCESS read-write
			STATUS current
			DESCRIPTION
				"The Total Time over which the Link Availability is calculated."
			REFERENCE
				"TR 101 290 section 6.2"
			::= { cableSatPreferencesEntry 17 }
		
		cableSatPrefBERMax OBJECT-TYPE
			SYNTAX FloatingPoint
			MAX-ACCESS read-write
			STATUS current
			DESCRIPTION
				"If the berRSinServiceValue exceeds this value, the
				associated test fails."
			::= { cableSatPreferencesEntry 18 }
		
		cableSatPrefSignalPowerMin OBJECT-TYPE
			SYNTAX FloatingPoint
			UNITS "dBm"
			MAX-ACCESS read-write
			STATUS current
			DESCRIPTION
				"If the power measured by rfIFsignalPowerValue is less
				than this value, the associated test fails."
			REFERENCE
				"TR 101 290 section 6.6"
			::= { cableSatPreferencesEntry 19 }
		
		cableSatPrefSignalPowerMax OBJECT-TYPE
			SYNTAX FloatingPoint
			UNITS "dBm"
			MAX-ACCESS read-write
			STATUS current
			DESCRIPTION
				"If the power measured by rfIFsignalPowerValue is
				greater than this value, the associated test fails."
			REFERENCE
				"TR 101 290 section 6.6"
			::= { cableSatPreferencesEntry 20 }
		
		cableSatPrefNoisePowerMax OBJECT-TYPE
			SYNTAX FloatingPoint
			UNITS "dBm"
			MAX-ACCESS read-write
			STATUS current
			DESCRIPTION
				"If the noise power measured by noisePowerValue exceeds
				 this value, the associated test fails."
			REFERENCE
				"TR 101 290 section 6.7"
			::= { cableSatPreferencesEntry 21 }
		
		cableSatPrefMerCSMin OBJECT-TYPE
			SYNTAX FloatingPoint
			UNITS "dB"
			MAX-ACCESS read-write
			STATUS current
			DESCRIPTION
				"If the merCSValue is less than this value, the
				associated test fails."
			REFERENCE
				"TR 101 290 section 6.9.2"
			::= { cableSatPreferencesEntry 22 }
		
		cableSatPrefSteMeanCSMax OBJECT-TYPE
			SYNTAX FloatingPoint
			UNITS "dB"
			MAX-ACCESS read-write
			STATUS current
			DESCRIPTION
				"If the steMeanCSValue exceeds this value, the
				associated test fails."
			REFERENCE
				"TR 101 290 section 6.9.3"
			::= { cableSatPreferencesEntry 23 }
		
		cableSatPrefSteDeviationCSMax OBJECT-TYPE
			SYNTAX FloatingPoint
			UNITS "dB"
			MAX-ACCESS read-write
			STATUS current
			DESCRIPTION
				"If the steDeviationCSValue exceeds this value, the
				associated test fails."
			REFERENCE
				"TR 101 290 section 6.9.3"
			::= { cableSatPreferencesEntry 24 }
		
		cableSatPrefCsCSMin OBJECT-TYPE
			SYNTAX FloatingPoint
			UNITS "dB"
			MAX-ACCESS read-write
			STATUS current
			DESCRIPTION
				"If the csCSValue is less than this value, the
				associated test fails"
			REFERENCE
				"TR 101 290 section 6.9.4"
			::= { cableSatPreferencesEntry 25 }
		
		cableSatPrefAiCSMax OBJECT-TYPE
			SYNTAX FloatingPoint
			UNITS "dB"
			MAX-ACCESS read-write
			STATUS current
			DESCRIPTION
				"If aiCSValue exceeds this value, the associated test fails."
			REFERENCE
				"TR 101 290 section 6.9.5"
			::= { cableSatPreferencesEntry 26 }
		
		cableSatPrefQeCSMax OBJECT-TYPE
			SYNTAX FloatingPoint
			UNITS "dB"
			MAX-ACCESS read-write
			STATUS current
			DESCRIPTION
				"If qeCSValue exceeds this value, the associated test fails."
			REFERENCE
				"TR 101 290 section 6.9.6"
			::= { cableSatPreferencesEntry 27 }
		
		cableSatPrefRteCSMax OBJECT-TYPE
			SYNTAX FloatingPoint
			UNITS "dB"
			MAX-ACCESS read-write
			STATUS current
			DESCRIPTION
				"If rteCSValue exceeds this value, the associated test fails."
			REFERENCE
				"TR 101 290 section 6.9.7"
			::= { cableSatPreferencesEntry 28 }
		
		cableSatPrefCiCSMin OBJECT-TYPE
			SYNTAX FloatingPoint
			UNITS "dB"
			MAX-ACCESS read-write
			STATUS current
			DESCRIPTION
				"If ciCSValue is less than this value, the associated test fails."
			REFERENCE
				"TR 101 290 section 6.9.8"
			::= { cableSatPreferencesEntry 29 }
		
		cableSatPrefPjCSMax OBJECT-TYPE
			SYNTAX FloatingPoint
			UNITS "dB"
			MAX-ACCESS read-write
			STATUS current
			DESCRIPTION
				"If pjCSValue exceeds this value, the associated test fails."
			REFERENCE
				"TR 101 290 section 6.9.9"
			::= { cableSatPreferencesEntry 30 }
		
		cableSatPrefSnrCSMin OBJECT-TYPE
			SYNTAX FloatingPoint
			UNITS "dB"
			MAX-ACCESS read-write
			STATUS current
			DESCRIPTION
				"If snrCSValue is less than this value, the associated test fails."
			REFERENCE
				"TR 101 290 section 6.9.10"
			::= { cableSatPreferencesEntry 31 }
		
-- Measurements and tests from section 7 of TR 101 290.
-- These apply to cable systems.
		tr101290Cable OBJECT IDENTIFIER ::= { tr101290Objects 7 }
		
		noiseMarginTable OBJECT-TYPE
			SYNTAX SEQUENCE OF NoiseMarginEntry
			MAX-ACCESS not-accessible
			STATUS current
			DESCRIPTION
				"Noise margin measurement"
			REFERENCE
				"TR 101 290 section 7.1"
			::= { tr101290Cable 1 }
		
		noiseMarginEntry OBJECT-TYPE
			SYNTAX NoiseMarginEntry
			MAX-ACCESS not-accessible
			STATUS current
			DESCRIPTION
				"Row description"
			INDEX { noiseMarginInputNumber }
			::= { noiseMarginTable 1 }
		
		NoiseMarginEntry ::=
			SEQUENCE { 
				noiseMarginInputNumber
					InputNumber,
				noiseMarginTestState
					TestState,
				noiseMarginEnable
					Enable,
				noiseMarginCounter
					Counter32,
				noiseMarginCounterDiscontinuity
					DateAndTime,
				noiseMarginCounterReset
					TruthValue,
				noiseMarginLatestError
					DateAndTime,
				noiseMarginActiveTime
					ActiveTime,
				noiseMarginMeasurementState
					MeasurementState,
				noiseMarginValue
					FloatingPoint
			 }

		noiseMarginInputNumber OBJECT-TYPE
			SYNTAX InputNumber
			MAX-ACCESS not-accessible
			STATUS current
			DESCRIPTION
				"Transport Stream on which the measurement is made"
			::= { noiseMarginEntry 1 }
		
		noiseMarginTestState OBJECT-TYPE
			SYNTAX TestState
			MAX-ACCESS read-only
			STATUS current
			DESCRIPTION
				"This indicates whether the noiseMarginValue is currently
				within the thresholds."
			::= { noiseMarginEntry 2 }
		
		noiseMarginEnable OBJECT-TYPE
			SYNTAX Enable
			MAX-ACCESS read-write
			STATUS current
			DESCRIPTION
				"Determines whether the threshold test and associated traps
				for this measurement are enabled."
			DEFVAL { { testEnable } }
			::= { noiseMarginEntry 3 }
		
		noiseMarginCounter OBJECT-TYPE
			SYNTAX Counter32
			MAX-ACCESS read-only
			STATUS current
			DESCRIPTION
				"Count of the number of times a threshold error has
				occurred for this measurement."
			::= { noiseMarginEntry 4 }
		
		noiseMarginCounterDiscontinuity OBJECT-TYPE
			SYNTAX DateAndTime
			MAX-ACCESS read-only
			STATUS current
			DESCRIPTION
				"Provides the last time at which there was a
				discontinuity in the counter object."
			::= { noiseMarginEntry 5 }
		
		noiseMarginCounterReset OBJECT-TYPE
			SYNTAX TruthValue
			MAX-ACCESS read-write
			STATUS current
			DESCRIPTION
				"The counter object is reset to zero and the counter
				discontinuity object is set to the current time if
				'true' is written to this object.
				
				When read, the value of this object is always 'false'."
			DEFVAL { false }
			::= { noiseMarginEntry 6 }
		
		noiseMarginLatestError OBJECT-TYPE
			SYNTAX DateAndTime
			MAX-ACCESS read-only
			STATUS current
			DESCRIPTION
				"The timestamp at the most recent occurrence of a
				threshold error on this measurement."
			::= { noiseMarginEntry 7 }
		
		noiseMarginActiveTime OBJECT-TYPE
			SYNTAX ActiveTime
			UNITS "second"
			MAX-ACCESS read-only
			STATUS current
			DESCRIPTION
				"The total time when it has been possible to perform this measurement
				"
			::= { noiseMarginEntry 8 }
		
		noiseMarginMeasurementState OBJECT-TYPE
			SYNTAX MeasurementState
			MAX-ACCESS read-only
			STATUS current
			DESCRIPTION
				"Indicates the validity of the measurement"
			::= { noiseMarginEntry 9 }
		
		noiseMarginValue OBJECT-TYPE
			SYNTAX FloatingPoint
			UNITS "dB"
			MAX-ACCESS read-only
			STATUS current
			DESCRIPTION
				"The current Noise Margin value in dB."
			::= { noiseMarginEntry 10 }
		
		estNoiseMarginTable OBJECT-TYPE
			SYNTAX SEQUENCE OF EstNoiseMarginEntry
			MAX-ACCESS not-accessible
			STATUS current
			DESCRIPTION
				"Estimated noise margin measurement"
			REFERENCE
				"TR 101 290 section 7.2"
			::= { tr101290Cable 2 }
		
		estNoiseMarginEntry OBJECT-TYPE
			SYNTAX EstNoiseMarginEntry
			MAX-ACCESS not-accessible
			STATUS current
			DESCRIPTION
				"Row description"
			INDEX { estNoiseMarginInputNumber }
			::= { estNoiseMarginTable 1 }
		
		EstNoiseMarginEntry ::=
			SEQUENCE { 
				estNoiseMarginInputNumber
					InputNumber,
				estNoiseMarginTestState
					TestState,
				estNoiseMarginEnable
					Enable,
				estNoiseMarginCounter
					Counter32,
				estNoiseMarginCounterDiscontinuity
					DateAndTime,
				estNoiseMarginCounterReset
					TruthValue,
				estNoiseMarginLatestError
					DateAndTime,
				estNoiseMarginActiveTime
					ActiveTime,
				estNoiseMarginMeasurementState
					MeasurementState,
				estNoiseMarginValue
					FloatingPoint
			 }

		estNoiseMarginInputNumber OBJECT-TYPE
			SYNTAX InputNumber
			MAX-ACCESS not-accessible
			STATUS current
			DESCRIPTION
				"Transport Stream on which the measurement is made"
			::= { estNoiseMarginEntry 1 }
		
		estNoiseMarginTestState OBJECT-TYPE
			SYNTAX TestState
			MAX-ACCESS read-only
			STATUS current
			DESCRIPTION
				"This indicates whether the estNoiseMarginValue is currently
				within the thresholds."
			::= { estNoiseMarginEntry 2 }
		
		estNoiseMarginEnable OBJECT-TYPE
			SYNTAX Enable
			MAX-ACCESS read-write
			STATUS current
			DESCRIPTION
				"Determines whether the threshold test and associated traps
				for this measurement are enabled."
			DEFVAL { { testEnable } }
			::= { estNoiseMarginEntry 3 }
		
		estNoiseMarginCounter OBJECT-TYPE
			SYNTAX Counter32
			MAX-ACCESS read-only
			STATUS current
			DESCRIPTION
				"Count of the number of times a threshold error has
				occurred for this measurement."
			::= { estNoiseMarginEntry 4 }
		
		estNoiseMarginCounterDiscontinuity OBJECT-TYPE
			SYNTAX DateAndTime
			MAX-ACCESS read-only
			STATUS current
			DESCRIPTION
				"Provides the last time at which there was a discontinuity
				in the counter object."
			::= { estNoiseMarginEntry 5 }
		
		estNoiseMarginCounterReset OBJECT-TYPE
			SYNTAX TruthValue
			MAX-ACCESS read-write
			STATUS current
			DESCRIPTION
				"The counter object is reset to zero and the counter
				discontinuity object is set to the current time if
				'true' is written to this object.
				
				When read, the value of this object is always 'false'."
			DEFVAL { false }
			::= { estNoiseMarginEntry 6 }
		
		estNoiseMarginLatestError OBJECT-TYPE
			SYNTAX DateAndTime
			MAX-ACCESS read-only
			STATUS current
			DESCRIPTION
				"The timestamp at the most recent occurrence of a
				threshold error on this measurement."
			::= { estNoiseMarginEntry 7 }
		
		estNoiseMarginActiveTime OBJECT-TYPE
			SYNTAX ActiveTime
			UNITS "second"
			MAX-ACCESS read-only
			STATUS current
			DESCRIPTION
				"The total time when it has been possible to perform this measurement"
			::= { estNoiseMarginEntry 8 }
		
		estNoiseMarginMeasurementState OBJECT-TYPE
			SYNTAX MeasurementState
			MAX-ACCESS read-only
			STATUS current
			DESCRIPTION
				"Indicates the validity of the measurement"
			::= { estNoiseMarginEntry 9 }
		
		estNoiseMarginValue OBJECT-TYPE
			SYNTAX FloatingPoint
			UNITS "dB"
			MAX-ACCESS read-only
			STATUS current
			DESCRIPTION
				"The current Estimated Noise Margin value in dB."
			::= { estNoiseMarginEntry 10 }
		
		signQualMarTTable OBJECT-TYPE
			SYNTAX SEQUENCE OF SignQualMarTEntry
			MAX-ACCESS not-accessible
			STATUS current
			DESCRIPTION
				"Signal quality margin test"
			REFERENCE
				"TR 101 290 section 7.3"
			::= { tr101290Cable 3 }
		
		signQualMarTEntry OBJECT-TYPE
			SYNTAX SignQualMarTEntry
			MAX-ACCESS not-accessible
			STATUS current
			DESCRIPTION
				"Row description"
			INDEX { signQualMarTInputNumber }
			::= { signQualMarTTable 1 }
		
		SignQualMarTEntry ::=
			SEQUENCE { 
				signQualMarTInputNumber
					InputNumber,
				signQualMarTTestState
					TestState,
				signQualMarTEnable
					Enable,
				signQualMarTCounter
					Counter32,
				signQualMarTCounterDiscontinuity
					DateAndTime,
				signQualMarTCounterReset
					TruthValue,
				signQualMarTLatestError
					DateAndTime,
				signQualMarTActiveTime
					ActiveTime
			 }

		signQualMarTInputNumber OBJECT-TYPE
			SYNTAX InputNumber
			MAX-ACCESS not-accessible
			STATUS current
			DESCRIPTION
				"Transport Stream on which the test is done"
			::= { signQualMarTEntry 1 }
		
		signQualMarTTestState OBJECT-TYPE
			SYNTAX TestState
			MAX-ACCESS read-only
			STATUS current
			DESCRIPTION
				"This indicates an error if the percentage of IQ points
				outside the threshold box exceeds cablePrefSignQualPercentMax."
			::= { signQualMarTEntry 2 }
		
		signQualMarTEnable OBJECT-TYPE
			SYNTAX Enable
			MAX-ACCESS read-write
			STATUS current
			DESCRIPTION
				"Determines whether the threshold test and associated traps
				for this measurement are enabled."
			DEFVAL { { testEnable } }
			::= { signQualMarTEntry 3 }
		
		signQualMarTCounter OBJECT-TYPE
			SYNTAX Counter32
			MAX-ACCESS read-only
			STATUS current
			DESCRIPTION
				"Count of the number of times an error has occurred."
			::= { signQualMarTEntry 4 }
		
		signQualMarTCounterDiscontinuity OBJECT-TYPE
			SYNTAX DateAndTime
			MAX-ACCESS read-only
			STATUS current
			DESCRIPTION
				"Provides the last time at which there was a discontinuity
				in the counter object."
			::= { signQualMarTEntry 5 }
		
		signQualMarTCounterReset OBJECT-TYPE
			SYNTAX TruthValue
			MAX-ACCESS read-write
			STATUS current
			DESCRIPTION
				"The counter object is reset to zero and the counter
				discontinuity object is set to the current time if
				'true' is written to this object.
				
				When read, the value of this object is always 'false'."
			::= { signQualMarTEntry 6 }
		
		signQualMarTLatestError OBJECT-TYPE
			SYNTAX DateAndTime
			MAX-ACCESS read-only
			STATUS current
			DESCRIPTION
				"The timestamp at the most recent occurrence of an error."
			::= { signQualMarTEntry 7 }
		
		signQualMarTActiveTime OBJECT-TYPE
			SYNTAX ActiveTime
			UNITS "second"
			MAX-ACCESS read-only
			STATUS current
			DESCRIPTION
				"The total time when it has been possible to perform this measurement"
			::= { signQualMarTEntry 8 }
		
		eNDCTable OBJECT-TYPE
			SYNTAX SEQUENCE OF ENDCEntry
			MAX-ACCESS not-accessible
			STATUS current
			DESCRIPTION
				"Equivalent Noise Degradation (END) measurement"
			REFERENCE
				"TR 101 290 section 7.4"
			::= { tr101290Cable 4 }
		
		eNDCEntry OBJECT-TYPE
			SYNTAX ENDCEntry
			MAX-ACCESS not-accessible
			STATUS current
			DESCRIPTION
				"Row description"
			INDEX { eNDCInputNumber }
			::= { eNDCTable 1 }
		
		ENDCEntry ::=
			SEQUENCE { 
				eNDCInputNumber
					InputNumber,
				eNDCTestState
					TestState,
				eNDCEnable
					Enable,
				eNDCCounter
					Counter32,
				eNDCCounterDiscontinuity
					DateAndTime,
				eNDCCounterReset
					TruthValue,
				eNDCLatestError
					DateAndTime,
				eNDCActiveTime
					ActiveTime,
				eNDCMeasurementState
					MeasurementState,
				eNDCValue
					FloatingPoint
			 }

		eNDCInputNumber OBJECT-TYPE
			SYNTAX InputNumber
			MAX-ACCESS not-accessible
			STATUS current
			DESCRIPTION
				"Transport Stream on which the measurement is made"
			::= { eNDCEntry 1 }
		
		eNDCTestState OBJECT-TYPE
			SYNTAX TestState
			MAX-ACCESS read-only
			STATUS current
			DESCRIPTION
				"This indicates an error when the eNDCValue exceeds
				the threshold."
			::= { eNDCEntry 2 }
		
		eNDCEnable OBJECT-TYPE
			SYNTAX Enable
			MAX-ACCESS read-write
			STATUS current
			DESCRIPTION
				"Determines whether the threshold test and associated traps
				for this measurement are enabled."
			DEFVAL { { testEnable } }
			::= { eNDCEntry 3 }
		
		eNDCCounter OBJECT-TYPE
			SYNTAX Counter32
			MAX-ACCESS read-only
			STATUS current
			DESCRIPTION
				"Count of the number of times a threshold error has
				occurred for this measurement."
			::= { eNDCEntry 4 }
		
		eNDCCounterDiscontinuity OBJECT-TYPE
			SYNTAX DateAndTime
			MAX-ACCESS read-only
			STATUS current
			DESCRIPTION
				"Provides the last time at which there was a discontinuity
				in the counter object."
			::= { eNDCEntry 5 }
		
		eNDCCounterReset OBJECT-TYPE
			SYNTAX TruthValue
			MAX-ACCESS read-write
			STATUS current
			DESCRIPTION
				"The counter object is reset to zero and the counter
				discontinuity object is set to the current time if
				'true' is written to this object.
				
				When read, the value of this object is always 'false'."
			DEFVAL { false }
			::= { eNDCEntry 6 }
		
		eNDCLatestError OBJECT-TYPE
			SYNTAX DateAndTime
			MAX-ACCESS read-only
			STATUS current
			DESCRIPTION
				"The timestamp at the most recent occurrence of a
				threshold error on this measurement."
			::= { eNDCEntry 7 }
		
		eNDCActiveTime OBJECT-TYPE
			SYNTAX ActiveTime
			UNITS "second"
			MAX-ACCESS read-only
			STATUS current
			DESCRIPTION
				"The total time when it has been possible to perform this measurement"
			::= { eNDCEntry 8 }
		
		eNDCMeasurementState OBJECT-TYPE
			SYNTAX MeasurementState
			MAX-ACCESS read-only
			STATUS current
			DESCRIPTION
				"Indicates the validity of the measurement"
			::= { eNDCEntry 9 }
		
		eNDCValue OBJECT-TYPE
			SYNTAX FloatingPoint
			UNITS "dB"
			MAX-ACCESS read-only
			STATUS current
			DESCRIPTION
				"The current Equivalent Noise Degradation value in dB."
			::= { eNDCEntry 10 }
		
		outBandEmissTable OBJECT-TYPE
			SYNTAX SEQUENCE OF OutBandEmissEntry
			MAX-ACCESS not-accessible
			STATUS current
			DESCRIPTION
				"Out of band emissions test"
			REFERENCE
				"TR 101 290 section 7.8"
			::= { tr101290Cable 5 }
		
		outBandEmissEntry OBJECT-TYPE
			SYNTAX OutBandEmissEntry
			MAX-ACCESS not-accessible
			STATUS current
			DESCRIPTION
				"Row specification"
			INDEX { outBandEmissInputNumber }
			::= { outBandEmissTable 1 }
		
		OutBandEmissEntry ::=
			SEQUENCE { 
				outBandEmissInputNumber
					InputNumber,
				outBandEmissTestState
					TestState,
				outBandEmissEnable
					Enable,
				outBandEmissCounter
					Counter32,
				outBandEmissCounterDiscontinuity
					DateAndTime,
				outBandEmissCounterReset
					TruthValue,
				outBandEmissLatestError
					DateAndTime,
				outBandEmissActiveTime
					ActiveTime
			 }

		outBandEmissInputNumber OBJECT-TYPE
			SYNTAX InputNumber
			MAX-ACCESS not-accessible
			STATUS current
			DESCRIPTION
				"Transport Stream on which the test is made"
			::= { outBandEmissEntry 1 }
		
		outBandEmissTestState OBJECT-TYPE
			SYNTAX TestState
			MAX-ACCESS read-only
			STATUS current
			DESCRIPTION
				"This indicates whether the spectrum is within the
				spectrum mask. Note that the spectrum mask must be
				provided to the instrument by means outside the
				scope of this MIB."
			::= { outBandEmissEntry 2 }
		
		outBandEmissEnable OBJECT-TYPE
			SYNTAX Enable
			MAX-ACCESS read-write
			STATUS current
			DESCRIPTION
				"Determines whether the threshold test and associated traps
				for this measurement are enabled."
			DEFVAL { { testEnable } }
			::= { outBandEmissEntry 3 }
		
		outBandEmissCounter OBJECT-TYPE
			SYNTAX Counter32
			MAX-ACCESS read-only
			STATUS current
			DESCRIPTION
				"Count of the number of times an error has occurred for this test."
			::= { outBandEmissEntry 4 }
		
		outBandEmissCounterDiscontinuity OBJECT-TYPE
			SYNTAX DateAndTime
			MAX-ACCESS read-only
			STATUS current
			DESCRIPTION
				"Provides the last time at which there was a discontinuity
				in the counter object."
			::= { outBandEmissEntry 5 }
		
		outBandEmissCounterReset OBJECT-TYPE
			SYNTAX TruthValue
			MAX-ACCESS read-write
			STATUS current
			DESCRIPTION
				"The counter object is reset to zero and the counter
				discontinuity object is set to the current time if
				'true' is written to this object.
				
				When read, the value of this object is always 'false'."
			::= { outBandEmissEntry 6 }
		
		outBandEmissLatestError OBJECT-TYPE
			SYNTAX DateAndTime
			MAX-ACCESS read-only
			STATUS current
			DESCRIPTION
				"The timestamp at the most recent occurrence of an
				error on this test."
			::= { outBandEmissEntry 7 }
		
		outBandEmissActiveTime OBJECT-TYPE
			SYNTAX ActiveTime
			UNITS "second"
			MAX-ACCESS read-only
			STATUS current
			DESCRIPTION
				"The total time when it has been possible to perform this measurement"
			::= { outBandEmissEntry 8 }
		
		cablePreferencesTable OBJECT-TYPE
			SYNTAX SEQUENCE OF CablePreferencesEntry
			MAX-ACCESS not-accessible
			STATUS current
			DESCRIPTION
				"Table containing per input preferences for cable measurements."
			::= { tr101290Cable 100 }
		
		cablePreferencesEntry OBJECT-TYPE
			SYNTAX CablePreferencesEntry
			MAX-ACCESS not-accessible
			STATUS current
			DESCRIPTION
				"Row specification"
			INDEX { cablePrefInputNumber }
			::= { cablePreferencesTable 1 }
		
		CablePreferencesEntry ::=
			SEQUENCE { 
				cablePrefInputNumber
					InputNumber,
				cablePrefNoiseMarginMin
					FloatingPoint,
				cablePrefEstNoiseMarginMin
					FloatingPoint,
				cablePrefSignQualBoxSize
					FloatingPoint,
				cablePrefSignQualPercentMax
					Integer32,
				cablePrefENDBER
					FloatingPoint,
				cablePrefENDCtoNSpecified
					TruthValue,
				cablePrefENDIdeal 
					FloatingPoint,
				cablePrefENDMax
					FloatingPoint
			 }

		cablePrefInputNumber OBJECT-TYPE
			SYNTAX InputNumber
			MAX-ACCESS not-accessible
			STATUS current
			DESCRIPTION
				"Transport Stream input to which the preferences apply"
			::= { cablePreferencesEntry 1 }
		
		cablePrefNoiseMarginMin OBJECT-TYPE
			SYNTAX FloatingPoint
			UNITS "dB"
			MAX-ACCESS read-write
			STATUS current
			DESCRIPTION
				"If the measured noiseMarginValue is less than this
				value the associated test fails."
			REFERENCE
				"TR 101 290 section 7.1"
			::= { cablePreferencesEntry 2 }
		
		cablePrefEstNoiseMarginMin OBJECT-TYPE
			SYNTAX FloatingPoint
			UNITS "dB"
			MAX-ACCESS read-write
			STATUS current
			DESCRIPTION
				"If the measured estNoiseMarginValue is less than this
				value the associated test fails."
			REFERENCE
				"TR 101 290 section 7.1"
			::= { cablePreferencesEntry 3 }
		
		cablePrefSignQualBoxSize OBJECT-TYPE
			SYNTAX FloatingPoint
			MAX-ACCESS read-write
			STATUS current
			DESCRIPTION
				"This object determines the size of the quality threshold
				box for the signal quality margin test. The quality
				threshold box is assumed to be square. The value is the
				ratio of the length of one side of a threshold box to the
				length of one side of the IQ decision boundary box. An
				example value is '0.5'."
			REFERENCE
				"TR 101 290 section 7.3"
			::= { cablePreferencesEntry 4 }
		
		cablePrefSignQualPercentMax OBJECT-TYPE
			SYNTAX Integer32
			MAX-ACCESS read-write
			STATUS current
			DESCRIPTION
				"This object sets the limit on how many constellation
				points may fall outside the threshold box before the
				signal quality margin test fails. The value is
				expressed as a percentage, for example '7.5'."
			REFERENCE
				"TR 101 290 section 7.3"
			::= { cablePreferencesEntry 5 }
		
		cablePrefENDBER OBJECT-TYPE
			SYNTAX FloatingPoint
			MAX-ACCESS read-write
			STATUS current
			DESCRIPTION
				"BER value which is to be used for the END measurement."
			REFERENCE
				"TR 101 290 section 7.4"
			DEFVAL { "1E-04" }
			::= { cablePreferencesEntry 6 }
		
		cablePrefENDCtoNSpecified OBJECT-TYPE
			SYNTAX TruthValue
			MAX-ACCESS read-write
			STATUS current
			DESCRIPTION
				"This determines whether cablePrefENDIdeal is expressed
				as a C/N ratio (value is true) or an Eb/No ratio
				(value is false)."
			REFERENCE
				"TR 101 290 section 7.4"
			::= { cablePreferencesEntry 7 }
		
		cablePrefENDIdeal  OBJECT-TYPE
			SYNTAX FloatingPoint
			UNITS "dB"
			MAX-ACCESS read-write
			STATUS current
			DESCRIPTION
				"This is the 'ideal' value of C/N or Eb/No for the given BER."
			REFERENCE
				"TR 101 290 section 7.4"
			::= { cablePreferencesEntry 8 }
		
		cablePrefENDMax OBJECT-TYPE
			SYNTAX FloatingPoint
			UNITS "dB"
			MAX-ACCESS read-write
			STATUS current
			DESCRIPTION
				"If the measured END exceeds this value the associated test fails."
			REFERENCE
				"TR 101 290 section 7.4"
			::= { cablePreferencesEntry 9 }
		
-- Measurements and tests from section 8 of TR 101 290.
-- These apply to satellite systems.
		tr101290Satellite OBJECT IDENTIFIER ::= { tr101290Objects 8 }
		
		berViterbiSTable OBJECT-TYPE
			SYNTAX SEQUENCE OF BerViterbiSEntry
			MAX-ACCESS not-accessible
			STATUS current
			DESCRIPTION
				"BER before Viterbi decoding measurement"
			REFERENCE
				"TR 101 290 section 8.1"
			::= { tr101290Satellite 1 }
		
		berViterbiSEntry OBJECT-TYPE
			SYNTAX BerViterbiSEntry
			MAX-ACCESS not-accessible
			STATUS current
			DESCRIPTION
				"Row description"
			INDEX { berViterbiSInputNumber }
			::= { berViterbiSTable 1 }
		
		BerViterbiSEntry ::=
			SEQUENCE { 
				berViterbiSInputNumber
					InputNumber,
				berViterbiSTestState
					TestState,
				berViterbiSEnable
					Enable,
				berViterbiSCounter
					Counter32,
				berViterbiSCounterDiscontinuity
					DateAndTime,
				berViterbiSCounterReset
					TruthValue,
				berViterbiSLatestError
					DateAndTime,
				berViterbiSActiveTime
					ActiveTime,
				berViterbiSMeasurementState
					MeasurementState,
				berViterbiSIValue
					FloatingPoint,
				berViterbiSQValue
					FloatingPoint,
				berViterbiSMeasurementMethod
					BERMeasurementMethod
			 }

		berViterbiSInputNumber OBJECT-TYPE
			SYNTAX InputNumber
			MAX-ACCESS not-accessible
			STATUS current
			DESCRIPTION
				"Transport Stream on which the measurement is made"
			::= { berViterbiSEntry 1 }
		
		berViterbiSTestState OBJECT-TYPE
			SYNTAX TestState
			MAX-ACCESS read-only
			STATUS current
			DESCRIPTION
				"This test fails if either berViterbiSIValue or
				berViterbiSQValue exceeds the threshold set by
				satellitePrefBERMax."
			::= { berViterbiSEntry 2 }
		
		berViterbiSEnable OBJECT-TYPE
			SYNTAX Enable
			MAX-ACCESS read-write
			STATUS current
			DESCRIPTION
				"Determines whether the threshold test and associated traps
				for this measurement are enabled."
			DEFVAL { { testEnable } }
			::= { berViterbiSEntry 3 }
		
		berViterbiSCounter OBJECT-TYPE
			SYNTAX Counter32
			MAX-ACCESS read-only
			STATUS current
			DESCRIPTION
				"Count of the number of times a threshold error has
				occurred for this measurement."
			::= { berViterbiSEntry 4 }
		
		berViterbiSCounterDiscontinuity OBJECT-TYPE
			SYNTAX DateAndTime
			MAX-ACCESS read-only
			STATUS current
			DESCRIPTION
				"Provides the last time at which there was a
				discontinuity in the berViterbiSCounter object."
			::= { berViterbiSEntry 5 }
		
		berViterbiSCounterReset OBJECT-TYPE
			SYNTAX TruthValue
			MAX-ACCESS read-write
			STATUS current
			DESCRIPTION
				"The counter object is reset to zero and the counter
				discontinuity object is set to the current time if
				'true' is written to this object.
				
				When read, the value of this object is always 'false'."
			DEFVAL { false }
			::= { berViterbiSEntry 6 }
		
		berViterbiSLatestError OBJECT-TYPE
			SYNTAX DateAndTime
			MAX-ACCESS read-only
			STATUS current
			DESCRIPTION
				"The timestamp at the most recent occurrence of a
				threshold error on this measurement."
			::= { berViterbiSEntry 7 }
		
		berViterbiSActiveTime OBJECT-TYPE
			SYNTAX ActiveTime
			UNITS "second"
			MAX-ACCESS read-only
			STATUS current
			DESCRIPTION
				"The total time when it has been possible to perform this measurement"
			::= { berViterbiSEntry 8 }
		
		berViterbiSMeasurementState OBJECT-TYPE
			SYNTAX MeasurementState
			MAX-ACCESS read-only
			STATUS current
			DESCRIPTION
				"Indicates the validity of the measurement"
			::= { berViterbiSEntry 9 }
		
		berViterbiSIValue OBJECT-TYPE
			SYNTAX FloatingPoint
			MAX-ACCESS read-only
			STATUS current
			DESCRIPTION
				"This is the pre-Viterbi I path BER value, for example 0.0000023"
			REFERENCE
				"TR 101 290 section 8.1"
			::= { berViterbiSEntry 10 }
		
		berViterbiSQValue OBJECT-TYPE
			SYNTAX FloatingPoint
			MAX-ACCESS read-only
			STATUS current
			DESCRIPTION
				"This is the pre-Viterbi Q path BER value, for example 0.0000023"
			REFERENCE
				"TR 101 290 section 8.1"
			::= { berViterbiSEntry 11 }
		
		berViterbiSMeasurementMethod OBJECT-TYPE
			SYNTAX BERMeasurementMethod
			MAX-ACCESS read-only
			STATUS current
			DESCRIPTION
				"This indicates whether the measurement was made
				separately for the I and Q parts of the signal or
				by a measurement of I and Q combined."
			::= { berViterbiSEntry 12 }
		
		ifSpectrumTable OBJECT-TYPE
			SYNTAX SEQUENCE OF IfSpectrumEntry
			MAX-ACCESS not-accessible
			STATUS current
			DESCRIPTION
				"IF spectrum test"
			REFERENCE
				"TR 101 290 section 8.3"
			::= { tr101290Satellite 2 }
		
		ifSpectrumEntry OBJECT-TYPE
			SYNTAX IfSpectrumEntry
			MAX-ACCESS not-accessible
			STATUS current
			DESCRIPTION
				"Row specification"
			INDEX { ifSpectrumInputNumber }
			::= { ifSpectrumTable 1 }
		
		IfSpectrumEntry ::=
			SEQUENCE { 
				ifSpectrumInputNumber
					InputNumber,
				ifSpectrumTestState
					TestState,
				ifSpectrumEnable
					Enable,
				ifSpectrumCounter
					Counter32,
				ifSpectrumCounterDiscontinuity
					DateAndTime,
				ifSpectrumCounterReset
					TruthValue,
				ifSpectrumLatestError
					DateAndTime,
				ifSpectrumActiveTime
					ActiveTime
			 }

		ifSpectrumInputNumber OBJECT-TYPE
			SYNTAX InputNumber
			MAX-ACCESS not-accessible
			STATUS current
			DESCRIPTION
				"Transport Stream on which the measurement is made"
			::= { ifSpectrumEntry 1 }
		
		ifSpectrumTestState OBJECT-TYPE
			SYNTAX TestState
			MAX-ACCESS read-only
			STATUS current
			DESCRIPTION
				"This indicates whether the spectrum conforms to the
				template. Note that the spectrum mask must be provided
				to the instrument by means outside the scope of this MIB.
				The group delay is not tested."
			::= { ifSpectrumEntry 2 }
		
		ifSpectrumEnable OBJECT-TYPE
			SYNTAX Enable
			MAX-ACCESS read-write
			STATUS current
			DESCRIPTION
				"Determines whether the threshold test and associated traps
				for this measurement are enabled."
			DEFVAL { { testEnable } }
			::= { ifSpectrumEntry 3 }
		
		ifSpectrumCounter OBJECT-TYPE
			SYNTAX Counter32
			MAX-ACCESS read-only
			STATUS current
			DESCRIPTION
				"Count of the number of times an error has occurred
				for this test."
			::= { ifSpectrumEntry 4 }
		
		ifSpectrumCounterDiscontinuity OBJECT-TYPE
			SYNTAX DateAndTime
			MAX-ACCESS read-only
			STATUS current
			DESCRIPTION
				"Provides the last time at which there was a
				discontinuity in the counter object."
			::= { ifSpectrumEntry 5 }
		
		ifSpectrumCounterReset OBJECT-TYPE
			SYNTAX TruthValue
			MAX-ACCESS read-write
			STATUS current
			DESCRIPTION
				"The counter object is reset to zero and the counter
				discontinuity object is set to the current time if
				'true' is written to this object.
				
				When read, the value of this object is always 'false'."
			DEFVAL { false }
			::= { ifSpectrumEntry 6 }
		
		ifSpectrumLatestError OBJECT-TYPE
			SYNTAX DateAndTime
			MAX-ACCESS read-only
			STATUS current
			DESCRIPTION
				"The timestamp at the most recent occurrence of an
				error on this test."
			::= { ifSpectrumEntry 7 }
		
		ifSpectrumActiveTime OBJECT-TYPE
			SYNTAX ActiveTime
			UNITS "second"
			MAX-ACCESS read-only
			STATUS current
			DESCRIPTION
				"The total time when it has been possible to perform this measurement"
			::= { ifSpectrumEntry 8 }
		
		satellitePreferencesTable OBJECT-TYPE
			SYNTAX SEQUENCE OF SatellitePreferencesEntry
			MAX-ACCESS not-accessible
			STATUS current
			DESCRIPTION
				"Table of satellite specific measurement preferences."
			::= { tr101290Satellite 100 }
		
		satellitePreferencesEntry OBJECT-TYPE
			SYNTAX SatellitePreferencesEntry
			MAX-ACCESS not-accessible
			STATUS current
			DESCRIPTION
				"Row specification"
			INDEX { satellitePrefInputNumber }
			::= { satellitePreferencesTable 1 }
		
		SatellitePreferencesEntry ::=
			SEQUENCE { 
				satellitePrefInputNumber
					InputNumber,
				satellitePrefBERMax
					FloatingPoint
			 }

		satellitePrefInputNumber OBJECT-TYPE
			SYNTAX InputNumber
			MAX-ACCESS not-accessible
			STATUS current
			DESCRIPTION
				"Transport Stream input to which the preferences apply"
			::= { satellitePreferencesEntry 1 }
		
		satellitePrefBERMax OBJECT-TYPE
			SYNTAX FloatingPoint
			MAX-ACCESS read-write
			STATUS current
			DESCRIPTION
				"This defines the upper limit on the BER before
				Viterbi measurement"
			REFERENCE
				"TR 101 290 section 8.1"
			::= { satellitePreferencesEntry 2 }
		
-- Measurements and tests from section 9 of TR 101 290.
-- These apply to terrestrial systems.
		tr101290Terrestrial OBJECT IDENTIFIER ::= { tr101290Objects 9 }
		
		rfTerr OBJECT IDENTIFIER ::= { tr101290Terrestrial 1 }
		
		rfAccuracyTable OBJECT-TYPE
			SYNTAX SEQUENCE OF RfAccuracyEntry
			MAX-ACCESS not-accessible
			STATUS current
			DESCRIPTION
				"RF frequency accuracy (Precision)"
			REFERENCE
				"TR 101 290 section 9.1.1"
			::= { rfTerr 1 }
		
		rfAccuracyEntry OBJECT-TYPE
			SYNTAX RfAccuracyEntry
			MAX-ACCESS not-accessible
			STATUS current
			DESCRIPTION
				"Row specification"
			INDEX { rfAccuracyInputNumber }
			::= { rfAccuracyTable 1 }
		
		RfAccuracyEntry ::=
			SEQUENCE { 
				rfAccuracyInputNumber
					InputNumber,
				rfAccuracyTestState
					TestState,
				rfAccuracyEnable
					Enable,
				rfAccuracyCounter
					Counter32,
				rfAccuracyCounterDiscontinuity
					DateAndTime,
				rfAccuracyCounterReset
					TruthValue,
				rfAccuracyLatestError
					DateAndTime,
				rfAccuracyActiveTime
					ActiveTime,
				rfAccuracyMeasurementState
					MeasurementState,
				rfAccuracyValue
					FloatingPoint
			 }

		rfAccuracyInputNumber OBJECT-TYPE
			SYNTAX InputNumber
			MAX-ACCESS not-accessible
			STATUS current
			DESCRIPTION
				"RF input on which the measurement is made"
			::= { rfAccuracyEntry 1 }
		
		rfAccuracyTestState OBJECT-TYPE
			SYNTAX TestState
			MAX-ACCESS read-only
			STATUS current
			DESCRIPTION
				"This indicates whether the rfAccuracyValue is within
				the thresholds."
			::= { rfAccuracyEntry 2 }
		
		rfAccuracyEnable OBJECT-TYPE
			SYNTAX Enable
			MAX-ACCESS read-write
			STATUS current
			DESCRIPTION
				"Determines whether the threshold test and associated traps
				for this measurement are enabled."
			DEFVAL { { testEnable } }
			::= { rfAccuracyEntry 3 }
		
		rfAccuracyCounter OBJECT-TYPE
			SYNTAX Counter32
			MAX-ACCESS read-only
			STATUS current
			DESCRIPTION
				"Count of the number of times a threshold error has
				occurred for this measurement."
			::= { rfAccuracyEntry 4 }
		
		rfAccuracyCounterDiscontinuity OBJECT-TYPE
			SYNTAX DateAndTime
			MAX-ACCESS read-only
			STATUS current
			DESCRIPTION
				"Provides the last time at which there was a discontinuity
				in the counter object."
			::= { rfAccuracyEntry 5 }
		
		rfAccuracyCounterReset OBJECT-TYPE
			SYNTAX TruthValue
			MAX-ACCESS read-write
			STATUS current
			DESCRIPTION
				"The counter object is reset to zero and the counter
				discontinuity object is set to the current time if
				'true' is written to this object.
				
				When read, the value of this object is always 'false'."
			DEFVAL { false }
			::= { rfAccuracyEntry 6 }
		
		rfAccuracyLatestError OBJECT-TYPE
			SYNTAX DateAndTime
			MAX-ACCESS read-only
			STATUS current
			DESCRIPTION
				"The timestamp at the most recent occurrence of a
				threshold error on this measurement."
			::= { rfAccuracyEntry 7 }
		
		rfAccuracyActiveTime OBJECT-TYPE
			SYNTAX ActiveTime
			UNITS "second"
			MAX-ACCESS read-only
			STATUS current
			DESCRIPTION
				"The total time when it has been possible to perform this measurement"
			::= { rfAccuracyEntry 8 }
		
		rfAccuracyMeasurementState OBJECT-TYPE
			SYNTAX MeasurementState
			MAX-ACCESS read-only
			STATUS current
			DESCRIPTION
				"Indicates the validity of the measurement"
			::= { rfAccuracyEntry 9 }
		
		rfAccuracyValue OBJECT-TYPE
			SYNTAX FloatingPoint
			UNITS "Hz"
			MAX-ACCESS read-only
			STATUS current
			DESCRIPTION
				"This is the RF carrier frequency in Hz."
			::= { rfAccuracyEntry 10 }
		
		rfChannelWidthTable OBJECT-TYPE
			SYNTAX SEQUENCE OF RfChannelWidthEntry
			MAX-ACCESS not-accessible
			STATUS current
			DESCRIPTION
				"RF channel width (Sampling Frequency Accuracy)"
			REFERENCE
				"TR 101 290 section 9.1.2"
			::= { rfTerr 2 }
		
		rfChannelWidthEntry OBJECT-TYPE
			SYNTAX RfChannelWidthEntry
			MAX-ACCESS not-accessible
			STATUS current
			DESCRIPTION
				"Row specification"
			INDEX { rfChannelWidthInputNumber }
			::= { rfChannelWidthTable 1 }
		
		RfChannelWidthEntry ::=
			SEQUENCE { 
				rfChannelWidthInputNumber
					InputNumber,
				rfChannelWidthTestState
					TestState,
				rfChannelWidthEnable
					Enable,
				rfChannelWidthCounter
					Counter32,
				rfChannelWidthCounterDiscontinuity
					DateAndTime,
				rfChannelWidthCounterReset
					TruthValue,
				rfChannelWidthLatestError
					DateAndTime,
				rfChannelWidthActiveTime
					ActiveTime,
				rfChannelWidthMeasurementState
					MeasurementState,
				rfChannelWidthValue
					FloatingPoint
			 }

		rfChannelWidthInputNumber OBJECT-TYPE
			SYNTAX InputNumber
			MAX-ACCESS not-accessible
			STATUS current
			DESCRIPTION
				"Transport Stream on which the measurement is made"
			::= { rfChannelWidthEntry 1 }
		
		rfChannelWidthTestState OBJECT-TYPE
			SYNTAX TestState
			MAX-ACCESS read-only
			STATUS current
			DESCRIPTION
				"This indicates whether the rfChannelWidthValue
				is within the thresholds."
			::= { rfChannelWidthEntry 2 }
		
		rfChannelWidthEnable OBJECT-TYPE
			SYNTAX Enable
			MAX-ACCESS read-write
			STATUS current
			DESCRIPTION
				"Determines whether the threshold test and associated traps
				for this measurement are enabled."
			DEFVAL { { testEnable } }
			::= { rfChannelWidthEntry 3 }
		
		rfChannelWidthCounter OBJECT-TYPE
			SYNTAX Counter32
			MAX-ACCESS read-only
			STATUS current
			DESCRIPTION
				"Count of the number of times a threshold error has
				occurred for this measurement."
			::= { rfChannelWidthEntry 4 }
		
		rfChannelWidthCounterDiscontinuity OBJECT-TYPE
			SYNTAX DateAndTime
			MAX-ACCESS read-only
			STATUS current
			DESCRIPTION
				"Provides the last time at which there was a discontinuity
				in the counter object."
			::= { rfChannelWidthEntry 5 }
		
		rfChannelWidthCounterReset OBJECT-TYPE
			SYNTAX TruthValue
			MAX-ACCESS read-write
			STATUS current
			DESCRIPTION
				"The counter object is reset to zero and the counter
				discontinuity object is set to the current time if
				'true' is written to this object.
				
				When read, the value of this object is always 'false'."
			DEFVAL { false }
			::= { rfChannelWidthEntry 6 }
		
		rfChannelWidthLatestError OBJECT-TYPE
			SYNTAX DateAndTime
			MAX-ACCESS read-only
			STATUS current
			DESCRIPTION
				"The timestamp at the most recent occurrence of a
				threshold error on this measurement."
			::= { rfChannelWidthEntry 7 }
		
		rfChannelWidthActiveTime OBJECT-TYPE
			SYNTAX ActiveTime
			UNITS "second"
			MAX-ACCESS read-only
			STATUS current
			DESCRIPTION
				"The total time when it has been possible to perform this measurement"
			::= { rfChannelWidthEntry 8 }
		
		rfChannelWidthMeasurementState OBJECT-TYPE
			SYNTAX MeasurementState
			MAX-ACCESS read-only
			STATUS current
			DESCRIPTION
				"Specifies the validity of the measurement value"
			::= { rfChannelWidthEntry 9 }
		
		rfChannelWidthValue OBJECT-TYPE
			SYNTAX FloatingPoint
			UNITS "Hz"
			MAX-ACCESS read-only
			STATUS current
			DESCRIPTION
				"This is the RF channel width in Hz."
			::= { rfChannelWidthEntry 10 }
		
		symbolLengthTable OBJECT-TYPE
			SYNTAX SEQUENCE OF SymbolLengthEntry
			MAX-ACCESS not-accessible
			STATUS current
			DESCRIPTION
				"Symbol Length measurement at RF (Guard Interval verification)"
			REFERENCE
				"TR 101 290 section 9.1.3"
			::= { rfTerr 3 }
		
		symbolLengthEntry OBJECT-TYPE
			SYNTAX SymbolLengthEntry
			MAX-ACCESS not-accessible
			STATUS current
			DESCRIPTION
				"Row specification"
			INDEX { symbolLengthInputNumber }
			::= { symbolLengthTable 1 }
		
		SymbolLengthEntry ::=
			SEQUENCE { 
				symbolLengthInputNumber
					InputNumber,
				symbolLengthTestState
					TestState,
				symbolLengthEnable
					Enable,
				symbolLengthCounter
					Counter32,
				symbolLengthCounterDiscontinuity
					DateAndTime,
				symbolLengthCounterReset
					TruthValue,
				symbolLengthLatestError
					DateAndTime,
				symbolLengthActiveTime
					ActiveTime,
				symbolLengthMeasurementState
					MeasurementState,
				symbolLengthValue
					FloatingPoint
			 }

		symbolLengthInputNumber OBJECT-TYPE
			SYNTAX InputNumber
			MAX-ACCESS not-accessible
			STATUS current
			DESCRIPTION
				"Transport Stream on which the measurement is made"
			::= { symbolLengthEntry 1 }
		
		symbolLengthTestState OBJECT-TYPE
			SYNTAX TestState
			MAX-ACCESS read-only
			STATUS current
			DESCRIPTION
				"This indicates whether the symbolLengthValue is within the thresholds."
			::= { symbolLengthEntry 2 }
		
		symbolLengthEnable OBJECT-TYPE
			SYNTAX Enable
			MAX-ACCESS read-write
			STATUS current
			DESCRIPTION
				"Determines whether the threshold test and associated traps
				for this measurement are enabled."
			DEFVAL { { testEnable } }
			::= { symbolLengthEntry 3 }
		
		symbolLengthCounter OBJECT-TYPE
			SYNTAX Counter32
			MAX-ACCESS read-only
			STATUS current
			DESCRIPTION
				"Count of the number of times a threshold error has
				occurred for this measurement."
			::= { symbolLengthEntry 4 }
		
		symbolLengthCounterDiscontinuity OBJECT-TYPE
			SYNTAX DateAndTime
			MAX-ACCESS read-only
			STATUS current
			DESCRIPTION
				"Provides the last time at which there was a discontinuity
				in the counter object."
			::= { symbolLengthEntry 5 }
		
		symbolLengthCounterReset OBJECT-TYPE
			SYNTAX TruthValue
			MAX-ACCESS read-write
			STATUS current
			DESCRIPTION
				"The counter object is reset to zero and the counter
				discontinuity object is set to the current time if
				'true' is written to this object.
				
				When read, the value of this object is always 'false'."
			DEFVAL { false }
			::= { symbolLengthEntry 6 }
		
		symbolLengthLatestError OBJECT-TYPE
			SYNTAX DateAndTime
			MAX-ACCESS read-only
			STATUS current
			DESCRIPTION
				"The timestamp at the most recent occurrence of a
				threshold error on this measurement."
			::= { symbolLengthEntry 7 }
		
		symbolLengthActiveTime OBJECT-TYPE
			SYNTAX ActiveTime
			UNITS "second"
			MAX-ACCESS read-only
			STATUS current
			DESCRIPTION
				"The total time when it has been possible to perform this measurement"
			::= { symbolLengthEntry 8 }
		
		symbolLengthMeasurementState OBJECT-TYPE
			SYNTAX MeasurementState
			MAX-ACCESS read-only
			STATUS current
			DESCRIPTION
				"Specifies the validity of the measurement value"
			::= { symbolLengthEntry 9 }
		
		symbolLengthValue OBJECT-TYPE
			SYNTAX FloatingPoint
			UNITS "microsecond"
			MAX-ACCESS read-only
			STATUS current
			DESCRIPTION
				"This is the symbol length in microseconds."
			::= { symbolLengthEntry 10 }
		
		rfIfPowerTable OBJECT-TYPE
			SYNTAX SEQUENCE OF RfIfPowerEntry
			MAX-ACCESS not-accessible
			STATUS current
			DESCRIPTION
				"RF/IF signal power"
			REFERENCE
				"TR 101 290 section 9.5"
			::= { tr101290Terrestrial 5 }
		
		rfIfPowerEntry OBJECT-TYPE
			SYNTAX RfIfPowerEntry
			MAX-ACCESS not-accessible
			STATUS current
			DESCRIPTION
				"Row specification"
			INDEX { rfIfPowerInputNumber }
			::= { rfIfPowerTable 1 }
		
		RfIfPowerEntry ::=
			SEQUENCE { 
				rfIfPowerInputNumber
					InputNumber,
				rfIfPowerTestState
					TestState,
				rfIfPowerEnable
					Enable,
				rfIfPowerCounter
					Counter32,
				rfIfPowerCounterDiscontinuity
					DateAndTime,
				rfIfPowerCounterReset
					TruthValue,
				rfIfPowerLatestError
					DateAndTime,
				rfIfPowerActiveTime
					ActiveTime,
				rfIfPowerMeasurementState
					MeasurementState,
				rfIfPowerValue
					FloatingPoint
			 }

		rfIfPowerInputNumber OBJECT-TYPE
			SYNTAX InputNumber
			MAX-ACCESS not-accessible
			STATUS current
			DESCRIPTION
				"RF input on which the measurement is made"
			::= { rfIfPowerEntry 1 }
		
		rfIfPowerTestState OBJECT-TYPE
			SYNTAX TestState
			MAX-ACCESS read-only
			STATUS current
			DESCRIPTION
				"This indicates whether the rfIfPowerValue is within
				the thresholds."
			::= { rfIfPowerEntry 2 }
		
		rfIfPowerEnable OBJECT-TYPE
			SYNTAX Enable
			MAX-ACCESS read-write
			STATUS current
			DESCRIPTION
				"Determines whether the threshold test and associated traps
				for this measurement are enabled."
			DEFVAL { { testEnable } }
			::= { rfIfPowerEntry 3 }
		
		rfIfPowerCounter OBJECT-TYPE
			SYNTAX Counter32
			MAX-ACCESS read-only
			STATUS current
			DESCRIPTION
				"Count of the number of times a threshold error has
				occurred for this measurement."
			::= { rfIfPowerEntry 4 }
		
		rfIfPowerCounterDiscontinuity OBJECT-TYPE
			SYNTAX DateAndTime
			MAX-ACCESS read-only
			STATUS current
			DESCRIPTION
				"Provides the last time at which there was a discontinuity
				in the counter object."
			::= { rfIfPowerEntry 5 }
		
		rfIfPowerCounterReset OBJECT-TYPE
			SYNTAX TruthValue
			MAX-ACCESS read-write
			STATUS current
			DESCRIPTION
				"The counter object is reset to zero and the counter
				discontinuity object is set to the current time if
				'true' is written to this object.
				
				When read, the value of this object is always 'false'."
			DEFVAL { false }
			::= { rfIfPowerEntry 6 }
		
		rfIfPowerLatestError OBJECT-TYPE
			SYNTAX DateAndTime
			MAX-ACCESS read-only
			STATUS current
			DESCRIPTION
				"The timestamp at the most recent occurrence of a
				threshold error on this measurement."
			::= { rfIfPowerEntry 7 }
		
		rfIfPowerActiveTime OBJECT-TYPE
			SYNTAX ActiveTime
			UNITS "second"
			MAX-ACCESS read-only
			STATUS current
			DESCRIPTION
				"The total time when it has been possible to perform this measurement"
			::= { rfIfPowerEntry 8 }
		
		rfIfPowerMeasurementState OBJECT-TYPE
			SYNTAX MeasurementState
			MAX-ACCESS read-only
			STATUS current
			DESCRIPTION
				"Specifies the validity of the measurement value"
			::= { rfIfPowerEntry 9 }
		
		rfIfPowerValue OBJECT-TYPE
			SYNTAX FloatingPoint
			UNITS "dBm"
			MAX-ACCESS read-only
			STATUS current
			DESCRIPTION
				"The current RF power expressed in dBm, which references
				0 dBm as the power of 1 mW."
			::= { rfIfPowerEntry 10 }
		
		rfIfSpectrumTable OBJECT-TYPE
			SYNTAX SEQUENCE OF RfIfSpectrumEntry
			MAX-ACCESS not-accessible
			STATUS current
			DESCRIPTION
				"RF and IF spectrum mask test"
			REFERENCE
				"TR 101 290 section 9.7"
			::= { tr101290Terrestrial 7 }
		
		rfIfSpectrumEntry OBJECT-TYPE
			SYNTAX RfIfSpectrumEntry
			MAX-ACCESS not-accessible
			STATUS current
			DESCRIPTION
				"Row specification"
			INDEX { rfIfSpectrumInputNumber }
			::= { rfIfSpectrumTable 1 }
		
		RfIfSpectrumEntry ::=
			SEQUENCE { 
				rfIfSpectrumInputNumber
					InputNumber,
				rfIfSpectrumTestState
					TestState,
				rfIfSpectrumEnable
					Enable,
				rfIfSpectrumCounter
					Counter32,
				rfIfSpectrumCounterDiscontinuity
					DateAndTime,
				rfIfSpectrumCounterReset
					TruthValue,
				rfIfSpectrumLatestError
					DateAndTime,
				rfIfSpectrumActiveTime
					ActiveTime
			 }

		rfIfSpectrumInputNumber OBJECT-TYPE
			SYNTAX InputNumber
			MAX-ACCESS not-accessible
			STATUS current
			DESCRIPTION
				"Transport Stream on which the measurement is made"
			::= { rfIfSpectrumEntry 1 }
		
		rfIfSpectrumTestState OBJECT-TYPE
			SYNTAX TestState
			MAX-ACCESS read-only
			STATUS current
			DESCRIPTION
				"This indicates whether the signal conforms to the
				spectrum mask"
			::= { rfIfSpectrumEntry 2 }
		
		rfIfSpectrumEnable OBJECT-TYPE
			SYNTAX Enable
			MAX-ACCESS read-write
			STATUS current
			DESCRIPTION
				"Determines whether the spectrum mask test and the associated
				trap are enabled."
			DEFVAL { { testEnable } }
			::= { rfIfSpectrumEntry 3 }
		
		rfIfSpectrumCounter OBJECT-TYPE
			SYNTAX Counter32
			MAX-ACCESS read-only
			STATUS current
			DESCRIPTION
				"Count of the number of times an error has occurred."
			::= { rfIfSpectrumEntry 4 }
		
		rfIfSpectrumCounterDiscontinuity OBJECT-TYPE
			SYNTAX DateAndTime
			MAX-ACCESS read-only
			STATUS current
			DESCRIPTION
				"Provides the last time at which there was a discontinuity
				in the counter object."
			::= { rfIfSpectrumEntry 5 }
		
		rfIfSpectrumCounterReset OBJECT-TYPE
			SYNTAX TruthValue
			MAX-ACCESS read-write
			STATUS current
			DESCRIPTION
				"The counter object is reset to zero and the counter
				discontinuity object is set to the current time if
				'true' is written to this object.
				
				When read, the value of this object is always 'false'."
			DEFVAL { false }
			::= { rfIfSpectrumEntry 6 }
		
		rfIfSpectrumLatestError OBJECT-TYPE
			SYNTAX DateAndTime
			MAX-ACCESS read-only
			STATUS current
			DESCRIPTION
				"The timestamp at the most recent occurrence of an error."
			::= { rfIfSpectrumEntry 7 }
		
		rfIfSpectrumActiveTime OBJECT-TYPE
			SYNTAX ActiveTime
			UNITS "second"
			MAX-ACCESS read-only
			STATUS current
			DESCRIPTION
				"The total time when it has been possible to perform this measurement"
			::= { rfIfSpectrumEntry 8 }
		
-- Equivalent Noise Degradation and Equivalent Noise Floor measurements
		eNDT OBJECT IDENTIFIER ::= { tr101290Terrestrial 9 }
		
		eNDTTable OBJECT-TYPE
			SYNTAX SEQUENCE OF ENDTEntry
			MAX-ACCESS not-accessible
			STATUS current
			DESCRIPTION
				"Equivalent Noise Degradation measurement. If the DVB-T
				transmission is hierarchical, this table contains the
				measurement for the HP (high priority) stream. If the
				transmission is not hierarchical, this table contains
				the measurement for the whole stream."
			REFERENCE
				"TR 101 290 section 9.9"
			::= { eNDT 1 }
		
		eNDTEntry OBJECT-TYPE
			SYNTAX ENDTEntry
			MAX-ACCESS not-accessible
			STATUS current
			DESCRIPTION
				"Row specification"
			INDEX { eNDTInputNumber }
			::= { eNDTTable 1 }
		
		ENDTEntry ::=
			SEQUENCE { 
				eNDTInputNumber
					InputNumber,
				eNDTTestState
					TestState,
				eNDTEnable
					Enable,
				eNDTCounter
					Counter32,
				eNDTCounterDiscontinuity
					DateAndTime,
				eNDTCounterReset
					TruthValue,
				eNDTLatestError
					DateAndTime,
				eNDTActiveTime
					ActiveTime,
				eNDTMeasurementState
					MeasurementState,
				eNDTValue
					FloatingPoint
			 }

		eNDTInputNumber OBJECT-TYPE
			SYNTAX InputNumber
			MAX-ACCESS not-accessible
			STATUS current
			DESCRIPTION
				"Transport Stream on which the measurement is made"
			::= { eNDTEntry 1 }
		
		eNDTTestState OBJECT-TYPE
			SYNTAX TestState
			MAX-ACCESS read-only
			STATUS current
			DESCRIPTION
				"This indicates whether eNDTValue is within the thresholds."
			::= { eNDTEntry 2 }
		
		eNDTEnable OBJECT-TYPE
			SYNTAX Enable
			MAX-ACCESS read-write
			STATUS current
			DESCRIPTION
				"Determines whether the threshold test and associated traps
				for this measurement are enabled."
			DEFVAL { { testEnable } }
			::= { eNDTEntry 3 }
		
		eNDTCounter OBJECT-TYPE
			SYNTAX Counter32
			MAX-ACCESS read-only
			STATUS current
			DESCRIPTION
				"Count of the number of times a threshold error has
				occurred for this measurement."
			::= { eNDTEntry 4 }
		
		eNDTCounterDiscontinuity OBJECT-TYPE
			SYNTAX DateAndTime
			MAX-ACCESS read-only
			STATUS current
			DESCRIPTION
				"Provides the last time at which there was a discontinuity
				in the counter object."
			::= { eNDTEntry 5 }
		
		eNDTCounterReset OBJECT-TYPE
			SYNTAX TruthValue
			MAX-ACCESS read-write
			STATUS current
			DESCRIPTION
				"The counter object is reset to zero and the counter
				discontinuity object is set to the current time if
				'true' is written to this object.
				
				When read, the value of this object is always 'false'."
			DEFVAL { false }
			::= { eNDTEntry 6 }
		
		eNDTLatestError OBJECT-TYPE
			SYNTAX DateAndTime
			MAX-ACCESS read-only
			STATUS current
			DESCRIPTION
				"The timestamp at the most recent occurrence of a
				threshold error on this measurement."
			::= { eNDTEntry 7 }
		
		eNDTActiveTime OBJECT-TYPE
			SYNTAX ActiveTime
			UNITS "second"
			MAX-ACCESS read-only
			STATUS current
			DESCRIPTION
				"The total time when it has been possible to perform this measurement"
			::= { eNDTEntry 8 }
		
		eNDTMeasurementState OBJECT-TYPE
			SYNTAX MeasurementState
			MAX-ACCESS read-only
			STATUS current
			DESCRIPTION
				"Specifies the validity of the measurement value"
			::= { eNDTEntry 9 }
		
		eNDTValue OBJECT-TYPE
			SYNTAX FloatingPoint
			UNITS "dB"
			MAX-ACCESS read-only
			STATUS current
			DESCRIPTION
				"The current Equivalent Noise Degradation expressed in dB."
			::= { eNDTEntry 10 }
		
		eNFTTable OBJECT-TYPE
			SYNTAX SEQUENCE OF ENFTEntry
			MAX-ACCESS not-accessible
			STATUS current
			DESCRIPTION
				"Equivalent Noise Floor measurement. If the DVB-T transmission
				is hierarchical, this table contains the measurement for the HP
				(high priority) stream. If the transmission is not hierarchical,
				this table contains the measurement for the whole stream."
			REFERENCE
				"TR 101 290 section 9.9.1"
			::= { eNDT 2 }
		
		eNFTEntry OBJECT-TYPE
			SYNTAX ENFTEntry
			MAX-ACCESS not-accessible
			STATUS current
			DESCRIPTION
				"Row specification"
			INDEX { eNFTInputNumber }
			::= { eNFTTable 1 }
		
		ENFTEntry ::=
			SEQUENCE { 
				eNFTInputNumber
					InputNumber,
				eNFTTestState
					TestState,
				eNFTEnable
					Enable,
				eNFTCounter
					Counter32,
				eNFTCounterDiscontinuity
					DateAndTime,
				eNFTCounterReset
					TruthValue,
				eNFTLatestError
					DateAndTime,
				eNFTActiveTime
					ActiveTime,
				eNFTMeasurementState
					MeasurementState,
				eNFTValue
					FloatingPoint
			 }

		eNFTInputNumber OBJECT-TYPE
			SYNTAX InputNumber
			MAX-ACCESS not-accessible
			STATUS current
			DESCRIPTION
				"Transport Stream on which the measurement is made"
			::= { eNFTEntry 1 }
		
		eNFTTestState OBJECT-TYPE
			SYNTAX TestState
			MAX-ACCESS read-only
			STATUS current
			DESCRIPTION
				"This indicates whether the eNFTValue is within the thresholds."
			::= { eNFTEntry 2 }
		
		eNFTEnable OBJECT-TYPE
			SYNTAX Enable
			MAX-ACCESS read-write
			STATUS current
			DESCRIPTION
				"Determines whether the threshold test and associated traps
				for this measurement are enabled."
			DEFVAL { { testEnable } }
			::= { eNFTEntry 3 }
		
		eNFTCounter OBJECT-TYPE
			SYNTAX Counter32
			MAX-ACCESS read-only
			STATUS current
			DESCRIPTION
				"Count of the number of times a threshold error has
				occurred for this measurement."
			::= { eNFTEntry 4 }
		
		eNFTCounterDiscontinuity OBJECT-TYPE
			SYNTAX DateAndTime
			MAX-ACCESS read-only
			STATUS current
			DESCRIPTION
				"Provides the last time at which there was a discontinuity
				in the counter object."
			::= { eNFTEntry 5 }
		
		eNFTCounterReset OBJECT-TYPE
			SYNTAX TruthValue
			MAX-ACCESS read-write
			STATUS current
			DESCRIPTION
				"The counter object is reset to zero and the counter
				discontinuity object is set to the current time if
				'true' is written to this object.
				
				When read, the value of this object is always 'false'."
			DEFVAL { false }
			::= { eNFTEntry 6 }
		
		eNFTLatestError OBJECT-TYPE
			SYNTAX DateAndTime
			MAX-ACCESS read-only
			STATUS current
			DESCRIPTION
				"The timestamp at the most recent occurrence of a
				threshold error on this measurement."
			::= { eNFTEntry 7 }
		
		eNFTActiveTime OBJECT-TYPE
			SYNTAX ActiveTime
			UNITS "second"
			MAX-ACCESS read-only
			STATUS current
			DESCRIPTION
				"The total time when it has been possible to perform this measurement"
			::= { eNFTEntry 8 }
		
		eNFTMeasurementState OBJECT-TYPE
			SYNTAX MeasurementState
			MAX-ACCESS read-only
			STATUS current
			DESCRIPTION
				"Specifies the validity of the measurement value"
			::= { eNFTEntry 9 }
		
		eNFTValue OBJECT-TYPE
			SYNTAX FloatingPoint
			UNITS "dB"
			MAX-ACCESS read-only
			STATUS current
			DESCRIPTION
				"The current Equivalent Noise Floor expressed in dB,
				see the reference for the method of calculation."
			REFERENCE
				"TR 101 290 E.9.1"
			::= { eNFTEntry 10 }
		
		eNDTLPTable OBJECT-TYPE
			SYNTAX SEQUENCE OF ENDTLPEntry
			MAX-ACCESS not-accessible
			STATUS current
			DESCRIPTION
				"Equivalent Noise Degradation measurement. If the
				DVB-T transmission is hierarchical, this table
				contains the measurement for the LP (low priority)
				stream. If the transmission is not hierarchical,
				the MeasurementState for this table will be 'unknown'."
			::= { eNDT 3 }
		
		eNDTLPEntry OBJECT-TYPE
			SYNTAX ENDTLPEntry
			MAX-ACCESS not-accessible
			STATUS current
			DESCRIPTION
				"Row specification"
			INDEX { eNDTLPInputNumber }
			::= { eNDTLPTable 1 }
		
		ENDTLPEntry ::=
			SEQUENCE { 
				eNDTLPInputNumber
					InputNumber,
				eNDTLPTestState
					TestState,
				eNDTLPEnable
					Enable,
				eNDTLPCounter
					Counter32,
				eNDTLPCounterDiscontinuity
					DateAndTime,
				eNDTLPCounterReset
					TruthValue,
				eNDTLPLatestError
					DateAndTime,
				eNDTLPActiveTime
					ActiveTime,
				eNDTLPMeasurementState
					MeasurementState,
				eNDTLPValue
					FloatingPoint
			 }

		eNDTLPInputNumber OBJECT-TYPE
			SYNTAX InputNumber
			MAX-ACCESS not-accessible
			STATUS current
			DESCRIPTION
				"Transport Stream on which the measurement is made"
			::= { eNDTLPEntry 1 }
		
		eNDTLPTestState OBJECT-TYPE
			SYNTAX TestState
			MAX-ACCESS read-only
			STATUS current
			DESCRIPTION
				"This indicates whether eNDTLPValue is within the thresholds."
			::= { eNDTLPEntry 2 }
		
		eNDTLPEnable OBJECT-TYPE
			SYNTAX Enable
			MAX-ACCESS read-write
			STATUS current
			DESCRIPTION
				"Determines whether the threshold test and associated traps
				for this measurement are enabled."
			DEFVAL { { testEnable } }
			::= { eNDTLPEntry 3 }
		
		eNDTLPCounter OBJECT-TYPE
			SYNTAX Counter32
			MAX-ACCESS read-only
			STATUS current
			DESCRIPTION
				"Count of the number of times a threshold error
				has occurred for this measurement."
			::= { eNDTLPEntry 4 }
		
		eNDTLPCounterDiscontinuity OBJECT-TYPE
			SYNTAX DateAndTime
			MAX-ACCESS read-only
			STATUS current
			DESCRIPTION
				"Provides the last time at which there was a discontinuity
				in the counter object."
			::= { eNDTLPEntry 5 }
		
		eNDTLPCounterReset OBJECT-TYPE
			SYNTAX TruthValue
			MAX-ACCESS read-write
			STATUS current
			DESCRIPTION
				"The counter object is reset to zero and the counter
				discontinuity object is set to the current time if
				'true' is written to this object.
				
				When read, the value of this object is always 'false'."
			::= { eNDTLPEntry 6 }
		
		eNDTLPLatestError OBJECT-TYPE
			SYNTAX DateAndTime
			MAX-ACCESS read-only
			STATUS current
			DESCRIPTION
				"The timestamp at the most recent occurrence of a
				threshold error on this measurement."
			::= { eNDTLPEntry 7 }
		
		eNDTLPActiveTime OBJECT-TYPE
			SYNTAX ActiveTime
			MAX-ACCESS read-only
			STATUS current
			DESCRIPTION
				"The total time when it has been possible to perform this measurement"
			::= { eNDTLPEntry 8 }
		
		eNDTLPMeasurementState OBJECT-TYPE
			SYNTAX MeasurementState
			MAX-ACCESS read-only
			STATUS current
			DESCRIPTION
				"Specifies the validity of the measurement value"
			::= { eNDTLPEntry 9 }
		
		eNDTLPValue OBJECT-TYPE
			SYNTAX FloatingPoint
			UNITS "dB"
			MAX-ACCESS read-only
			STATUS current
			DESCRIPTION
				"The current Equivalent Noise Degradation for the low
				priority stream expressed in dB."
			::= { eNDTLPEntry 10 }
		
		eNFTLPTable OBJECT-TYPE
			SYNTAX SEQUENCE OF ENFTLPEntry
			MAX-ACCESS not-accessible
			STATUS current
			DESCRIPTION
				"Equivalent Noise Floor measurement. If the DVB-T transmission
				is hierarchical, this table contains the measurement for the LP
				(low priority) stream. If the transmission is not hierarchical,
				the MeasurementState for this table will be 'unknown'."
			::= { eNDT 4 }
		
		eNFTLPEntry OBJECT-TYPE
			SYNTAX ENFTLPEntry
			MAX-ACCESS not-accessible
			STATUS current
			DESCRIPTION
				"Row specification"
			INDEX { eNDTLPInputNumber }
			::= { eNFTLPTable 1 }
		
		ENFTLPEntry ::=
			SEQUENCE { 
				eNFTLPInputNumber
					InputNumber,
				eNFTLPTestState
					TestState,
				eNFTLPEnable
					Enable,
				eNFTLPCounter
					Counter32,
				eNFTLPCounterDiscontinuity
					DateAndTime,
				eNFTLPCounterReset
					TruthValue,
				eNFTLPLatestError
					DateAndTime,
				eNFTLPActiveTime
					ActiveTime,
				eNFTLPMeasurementState
					MeasurementState,
				eNFTLPValue
					FloatingPoint
			 }

		eNFTLPInputNumber OBJECT-TYPE
			SYNTAX InputNumber
			MAX-ACCESS not-accessible
			STATUS current
			DESCRIPTION
				"Transport Stream on which the measurement is made"
			::= { eNFTLPEntry 1 }
		
		eNFTLPTestState OBJECT-TYPE
			SYNTAX TestState
			MAX-ACCESS read-only
			STATUS current
			DESCRIPTION
				"This indicates whether eNFTLPValue is within the thresholds."
			::= { eNFTLPEntry 2 }
		
		eNFTLPEnable OBJECT-TYPE
			SYNTAX Enable
			MAX-ACCESS read-write
			STATUS current
			DESCRIPTION
				"Determines whether the threshold test and associated traps
				for this measurement are enabled."
			DEFVAL { { testEnable } }
			::= { eNFTLPEntry 3 }
		
		eNFTLPCounter OBJECT-TYPE
			SYNTAX Counter32
			MAX-ACCESS read-only
			STATUS current
			DESCRIPTION
				"Count of the number of times a threshold error
				has occurred for this measurement."
			::= { eNFTLPEntry 4 }
		
		eNFTLPCounterDiscontinuity OBJECT-TYPE
			SYNTAX DateAndTime
			MAX-ACCESS read-only
			STATUS current
			DESCRIPTION
				"Provides the last time at which there was a discontinuity
				in the counter object."
			::= { eNFTLPEntry 5 }
		
		eNFTLPCounterReset OBJECT-TYPE
			SYNTAX TruthValue
			MAX-ACCESS read-write
			STATUS current
			DESCRIPTION
				"The counter object is reset to zero and the counter
				discontinuity object is set to the current time if
				'true' is written to this object.
				
				When read, the value of this object is always 'false'."
			::= { eNFTLPEntry 6 }
		
		eNFTLPLatestError OBJECT-TYPE
			SYNTAX DateAndTime
			MAX-ACCESS read-only
			STATUS current
			DESCRIPTION
				"The timestamp at the most recent occurrence of a
				threshold error on this measurement."
			::= { eNFTLPEntry 7 }
		
		eNFTLPActiveTime OBJECT-TYPE
			SYNTAX ActiveTime
			MAX-ACCESS read-only
			STATUS current
			DESCRIPTION
				"The total time when it has been possible to perform this measurement"
			::= { eNFTLPEntry 8 }
		
		eNFTLPMeasurementState OBJECT-TYPE
			SYNTAX MeasurementState
			MAX-ACCESS read-only
			STATUS current
			DESCRIPTION
				"Specifies the validity of the measurement value"
			::= { eNFTLPEntry 9 }
		
		eNFTLPValue OBJECT-TYPE
			SYNTAX FloatingPoint
			UNITS "dB"
			MAX-ACCESS read-only
			STATUS current
			DESCRIPTION
				"The current Equivalent Noise Floor for the low priority
				stream, expressed in dB, see the reference for the
				method of calculation."
			REFERENCE
				"TR 101 290 E.9.1"
			::= { eNFTLPEntry 10 }
		
		linearityTable OBJECT-TYPE
			SYNTAX SEQUENCE OF LinearityEntry
			MAX-ACCESS not-accessible
			STATUS current
			DESCRIPTION
				"Linearity characterization (shoulder attenuation)"
			REFERENCE
				"TR 101 290 section 9.10"
			::= { tr101290Terrestrial 10 }
		
		linearityEntry OBJECT-TYPE
			SYNTAX LinearityEntry
			MAX-ACCESS not-accessible
			STATUS current
			DESCRIPTION
				"Row specification"
			INDEX { linearityInputNumber }
			::= { linearityTable 1 }
		
		LinearityEntry ::=
			SEQUENCE { 
				linearityInputNumber
					InputNumber,
				linearityTestState
					TestState,
				linearityEnable
					Enable,
				linearityCounter
					Counter32,
				linearityCounterDiscontinuity
					DateAndTime,
				linearityCounterReset
					TruthValue,
				linearityLatestError
					DateAndTime,
				linearityActiveTime
					ActiveTime,
				linearityMeasurementState
					MeasurementState,
				linearityValue
					FloatingPoint
			 }

		linearityInputNumber OBJECT-TYPE
			SYNTAX InputNumber
			MAX-ACCESS not-accessible
			STATUS current
			DESCRIPTION
				"Transport Stream on which the measurement is made"
			::= { linearityEntry 1 }
		
		linearityTestState OBJECT-TYPE
			SYNTAX TestState
			MAX-ACCESS read-only
			STATUS current
			DESCRIPTION
				"This indicates whether the linearityValue is above
				the minimum permitted."
			::= { linearityEntry 2 }
		
		linearityEnable OBJECT-TYPE
			SYNTAX Enable
			MAX-ACCESS read-write
			STATUS current
			DESCRIPTION
				"Determines whether the threshold test and associated traps
				for this measurement are enabled."
			DEFVAL { { testEnable } }
			::= { linearityEntry 3 }
		
		linearityCounter OBJECT-TYPE
			SYNTAX Counter32
			MAX-ACCESS read-only
			STATUS current
			DESCRIPTION
				"Count of the number of times a threshold error has
				occurred for this measurement."
			::= { linearityEntry 4 }
		
		linearityCounterDiscontinuity OBJECT-TYPE
			SYNTAX DateAndTime
			MAX-ACCESS read-only
			STATUS current
			DESCRIPTION
				"Provides the last time at which there was a discontinuity
				in the counter object."
			::= { linearityEntry 5 }
		
		linearityCounterReset OBJECT-TYPE
			SYNTAX TruthValue
			MAX-ACCESS read-write
			STATUS current
			DESCRIPTION
				"The counter object is reset to zero and the counter
				discontinuity object is set to the current time if
				'true' is written to this object.
				
				When read, the value of this object is always 'false'."
			::= { linearityEntry 6 }
		
		linearityLatestError OBJECT-TYPE
			SYNTAX DateAndTime
			MAX-ACCESS read-only
			STATUS current
			DESCRIPTION
				"The timestamp at the most recent occurrence of a
				threshold error on this measurement."
			::= { linearityEntry 7 }
		
		linearityActiveTime OBJECT-TYPE
			SYNTAX ActiveTime
			UNITS "second"
			MAX-ACCESS read-only
			STATUS current
			DESCRIPTION
				"The total time when it has been possible to perform this measurement"
			::= { linearityEntry 8 }
		
		linearityMeasurementState OBJECT-TYPE
			SYNTAX MeasurementState
			MAX-ACCESS read-only
			STATUS current
			DESCRIPTION
				"Specifies the validity of the measurement value"
			::= { linearityEntry 9 }
		
		linearityValue OBJECT-TYPE
			SYNTAX FloatingPoint
			UNITS "dB"
			MAX-ACCESS read-only
			STATUS current
			DESCRIPTION
				"The current linearity (shoulder attenuation) expressed in dB."
			::= { linearityEntry 10 }
		
-- BER before Viterbi (inner) decoder measurements
		berViterbiT OBJECT IDENTIFIER ::= { tr101290Terrestrial 15 }
		
		berViterbiTTable OBJECT-TYPE
			SYNTAX SEQUENCE OF BerViterbiTEntry
			MAX-ACCESS not-accessible
			STATUS current
			DESCRIPTION
				"BER before Viterbi measurement. If the DVB-T transmission
				is hierarchical, this table contains the measurement
				for the HP (high priority) stream. If the transmission is
				not hierarchical, this table contains the measurement for
				the whole stream."
			REFERENCE
				"TR 101 290 section 9.15"
			::= { berViterbiT 1 }
		
		berViterbiTEntry OBJECT-TYPE
			SYNTAX BerViterbiTEntry
			MAX-ACCESS not-accessible
			STATUS current
			DESCRIPTION
				"Row specification"
			INDEX { berViterbiTInputNumber }
			::= { berViterbiTTable 1 }
		
		BerViterbiTEntry ::=
			SEQUENCE { 
				berViterbiTInputNumber
					InputNumber,
				berViterbiTTestState
					TestState,
				berViterbiTEnable
					Enable,
				berViterbiTCounter
					Counter32,
				berViterbiTCounterDiscontinuity
					DateAndTime,
				berViterbiTCounterReset
					TruthValue,
				berViterbiTLatestError
					DateAndTime,
				berViterbiTActiveTime
					ActiveTime,
				berViterbiTMeasurementState
					MeasurementState,
				berViterbiTValue
					FloatingPoint
			 }

		berViterbiTInputNumber OBJECT-TYPE
			SYNTAX InputNumber
			MAX-ACCESS not-accessible
			STATUS current
			DESCRIPTION
				"Transport Stream on which the measurement is made"
			::= { berViterbiTEntry 1 }
		
		berViterbiTTestState OBJECT-TYPE
			SYNTAX TestState
			MAX-ACCESS read-only
			STATUS current
			DESCRIPTION
				"This indicates whether the berViterbiTValue is
				within the thresholds."
			::= { berViterbiTEntry 2 }
		
		berViterbiTEnable OBJECT-TYPE
			SYNTAX Enable
			MAX-ACCESS read-write
			STATUS current
			DESCRIPTION
				"Determines whether the threshold test and associated traps
				for this measurement are enabled."
			DEFVAL { { testEnable } }
			::= { berViterbiTEntry 3 }
		
		berViterbiTCounter OBJECT-TYPE
			SYNTAX Counter32
			MAX-ACCESS read-only
			STATUS current
			DESCRIPTION
				"Count of the number of times a threshold error has
				occurred for this measurement."
			::= { berViterbiTEntry 4 }
		
		berViterbiTCounterDiscontinuity OBJECT-TYPE
			SYNTAX DateAndTime
			MAX-ACCESS read-only
			STATUS current
			DESCRIPTION
				"Provides the last time at which there was a discontinuity
				in the counter object."
			::= { berViterbiTEntry 5 }
		
		berViterbiTCounterReset OBJECT-TYPE
			SYNTAX TruthValue
			MAX-ACCESS read-write
			STATUS current
			DESCRIPTION
				"The counter object is reset to zero and the counter
				discontinuity object is set to the current time if
				'true' is written to this object.
				
				When read, the value of this object is always 'false'."
			::= { berViterbiTEntry 6 }
		
		berViterbiTLatestError OBJECT-TYPE
			SYNTAX DateAndTime
			MAX-ACCESS read-only
			STATUS current
			DESCRIPTION
				"The timestamp at the most recent occurrence of a
				threshold error on this measurement."
			::= { berViterbiTEntry 7 }
		
		berViterbiTActiveTime OBJECT-TYPE
			SYNTAX ActiveTime
			MAX-ACCESS read-only
			STATUS current
			DESCRIPTION
				"The total time when it has been possible to perform this measurement"
			::= { berViterbiTEntry 8 }
		
		berViterbiTMeasurementState OBJECT-TYPE
			SYNTAX MeasurementState
			MAX-ACCESS read-only
			STATUS current
			DESCRIPTION
				"Specifies the validity of the measurement value"
			::= { berViterbiTEntry 9 }
		
		berViterbiTValue OBJECT-TYPE
			SYNTAX FloatingPoint
			MAX-ACCESS read-only
			STATUS current
			DESCRIPTION
				"This is the overall pre-Viterbi BER value, for
				example 0.0000046"
			::= { berViterbiTEntry 10 }
		
		berViterbiTLPTable OBJECT-TYPE
			SYNTAX SEQUENCE OF BerViterbiTLPEntry
			MAX-ACCESS not-accessible
			STATUS current
			DESCRIPTION
				"BER before Viterbi measurement. If the DVB-T transmission
				is hierarchical, this table contains the measurement for
				the LP (low priority) stream. If the transmission is not
				hierarchical, the MeasurementState for this table will be
				'unknown'."
			::= { berViterbiT 2 }
		
		berViterbiTLPEntry OBJECT-TYPE
			SYNTAX BerViterbiTLPEntry
			MAX-ACCESS not-accessible
			STATUS current
			DESCRIPTION
				"Row specification"
			INDEX { berViterbiTLPInputNumber }
			::= { berViterbiTLPTable 1 }
		
		BerViterbiTLPEntry ::=
			SEQUENCE { 
				berViterbiTLPInputNumber
					InputNumber,
				berViterbiTLPTestState
					TestState,
				berViterbiTLPEnable
					Enable,
				berViterbiTLPCounter
					Counter32,
				berViterbiTLPCounterDiscontinuity
					DateAndTime,
				berViterbiTLPCounterReset
					TruthValue,
				berViterbiTLPLatestError
					DateAndTime,
				berViterbiTLPActiveTime
					ActiveTime,
				berViterbiTLPMeasurementState
					MeasurementState,
				berViterbiTLPValue
					FloatingPoint
			 }

		berViterbiTLPInputNumber OBJECT-TYPE
			SYNTAX InputNumber
			MAX-ACCESS not-accessible
			STATUS current
			DESCRIPTION
				"Transport Stream on which the measurement is made"
			::= { berViterbiTLPEntry 1 }
		
		berViterbiTLPTestState OBJECT-TYPE
			SYNTAX TestState
			MAX-ACCESS read-only
			STATUS current
			DESCRIPTION
				"This indicates whether the berViterbiTLPValue is
				within the thresholds."
			::= { berViterbiTLPEntry 2 }
		
		berViterbiTLPEnable OBJECT-TYPE
			SYNTAX Enable
			MAX-ACCESS read-write
			STATUS current
			DESCRIPTION
				"Determines whether the threshold test and associated traps
				for this measurement are enabled."
			DEFVAL { { testEnable } }
			::= { berViterbiTLPEntry 3 }
		
		berViterbiTLPCounter OBJECT-TYPE
			SYNTAX Counter32
			MAX-ACCESS read-only
			STATUS current
			DESCRIPTION
				"Count of the number of times a threshold error has
				occurred for this measurement."
			::= { berViterbiTLPEntry 4 }
		
		berViterbiTLPCounterDiscontinuity OBJECT-TYPE
			SYNTAX DateAndTime
			MAX-ACCESS read-only
			STATUS current
			DESCRIPTION
				"Provides the last time at which there was a discontinuity
				in the counter object."
			::= { berViterbiTLPEntry 5 }
		
		berViterbiTLPCounterReset OBJECT-TYPE
			SYNTAX TruthValue
			MAX-ACCESS read-write
			STATUS current
			DESCRIPTION
				"The counter object is reset to zero and the counter
				discontinuity object is set to the current time if
				'true' is written to this object.
				
				When read, the value of this object is always 'false'."
			::= { berViterbiTLPEntry 6 }
		
		berViterbiTLPLatestError OBJECT-TYPE
			SYNTAX DateAndTime
			MAX-ACCESS read-only
			STATUS current
			DESCRIPTION
				"The timestamp at the most recent occurrence of a
				threshold error on this measurement."
			::= { berViterbiTLPEntry 7 }
		
		berViterbiTLPActiveTime OBJECT-TYPE
			SYNTAX ActiveTime
			MAX-ACCESS read-only
			STATUS current
			DESCRIPTION
				"The total time when it has been possible to perform this measurement"
			::= { berViterbiTLPEntry 8 }
		
		berViterbiTLPMeasurementState OBJECT-TYPE
			SYNTAX MeasurementState
			MAX-ACCESS read-only
			STATUS current
			DESCRIPTION
				"Specifies the validity of the measurement value"
			::= { berViterbiTLPEntry 9 }
		
		berViterbiTLPValue OBJECT-TYPE
			SYNTAX FloatingPoint
			UNITS "dB"
			MAX-ACCESS read-only
			STATUS current
			DESCRIPTION
				"This is the overall pre-Viterbi BER value, for
				example 0.0000046"
			::= { berViterbiTLPEntry 10 }
		
-- BER before RS (outer) decoder measurements
		berRS OBJECT IDENTIFIER ::= { tr101290Terrestrial 16 }
		
		berRSTable OBJECT-TYPE
			SYNTAX SEQUENCE OF BerRSEntry
			MAX-ACCESS not-accessible
			STATUS current
			DESCRIPTION
				"BER before RS measurement. If the DVB-T transmission
				is hierarchical, this table contains the measurement
				for the HP (high priority) stream. If the transmission
				is not hierarchical, this table contains the measurement
				for the whole stream."
			REFERENCE
				"TR 101 290 section 9.16"
			::= { berRS 1 }
		
		berRSEntry OBJECT-TYPE
			SYNTAX BerRSEntry
			MAX-ACCESS not-accessible
			STATUS current
			DESCRIPTION
				"Row specification"
			INDEX { berRSInputNumber }
			::= { berRSTable 1 }
		
		BerRSEntry ::=
			SEQUENCE { 
				berRSInputNumber
					InputNumber,
				berRSTestState
					TestState,
				berRSEnable
					Enable,
				berRSCounter
					Counter32,
				berRSCounterDiscontinuity
					DateAndTime,
				berRSCounterReset
					TruthValue,
				berRSLatestError
					DateAndTime,
				berRSActiveTime
					ActiveTime,
				berRSMeasurementState
					MeasurementState,
				berRSValue
					FloatingPoint
			 }

		berRSInputNumber OBJECT-TYPE
			SYNTAX InputNumber
			MAX-ACCESS not-accessible
			STATUS current
			DESCRIPTION
				"Transport Stream on which the measurement is made"
			::= { berRSEntry 1 }
		
		berRSTestState OBJECT-TYPE
			SYNTAX TestState
			MAX-ACCESS read-only
			STATUS current
			DESCRIPTION
				"This indicates whether berRSValue is below the maximum."
			::= { berRSEntry 2 }
		
		berRSEnable OBJECT-TYPE
			SYNTAX Enable
			MAX-ACCESS read-write
			STATUS current
			DESCRIPTION
				"Determines whether the threshold test and associated traps
				for this measurement are enabled."
			DEFVAL { { testEnable } }
			::= { berRSEntry 3 }
		
		berRSCounter OBJECT-TYPE
			SYNTAX Counter32
			MAX-ACCESS read-only
			STATUS current
			DESCRIPTION
				"Count of the number of times a threshold error has
				occurred for this measurement."
			::= { berRSEntry 4 }
		
		berRSCounterDiscontinuity OBJECT-TYPE
			SYNTAX DateAndTime
			MAX-ACCESS read-only
			STATUS current
			DESCRIPTION
				"Provides the last time at which there was a discontinuity
				in the counter object."
			::= { berRSEntry 5 }
		
		berRSCounterReset OBJECT-TYPE
			SYNTAX TruthValue
			MAX-ACCESS read-write
			STATUS current
			DESCRIPTION
				"The counter object is reset to zero and the counter
				discontinuity object is set to the current time if
				'true' is written to this object.
				
				When read, the value of this object is always 'false'."
			::= { berRSEntry 6 }
		
		berRSLatestError OBJECT-TYPE
			SYNTAX DateAndTime
			MAX-ACCESS read-only
			STATUS current
			DESCRIPTION
				"The timestamp at the most recent occurrence of a
				threshold error on this measurement."
			::= { berRSEntry 7 }
		
		berRSActiveTime OBJECT-TYPE
			SYNTAX ActiveTime
			MAX-ACCESS read-only
			STATUS current
			DESCRIPTION
				"The total time when it has been possible to perform this measurement"
			::= { berRSEntry 8 }
		
		berRSMeasurementState OBJECT-TYPE
			SYNTAX MeasurementState
			MAX-ACCESS read-only
			STATUS current
			DESCRIPTION
				"Specifies the validity of the measurement value"
			::= { berRSEntry 9 }
		
		berRSValue OBJECT-TYPE
			SYNTAX FloatingPoint
			MAX-ACCESS read-only
			STATUS current
			DESCRIPTION
				"This is the BER before RS (outer) decoder measured using
				the in-service method.  It is expressed as a number,
				e.g. 0.0000034"
			::= { berRSEntry 10 }
		
		berRSLPTable OBJECT-TYPE
			SYNTAX SEQUENCE OF BerRSLPEntry
			MAX-ACCESS not-accessible
			STATUS current
			DESCRIPTION
				"BER before RS measurement. If the DVB-T transmission
				is hierarchical, this table contains the measurement
				for the LP (low priority) stream. If the transmission
				is not hierarchical, the MeasurementState for this
				table will be 'unknown'."
			::= { berRS 2 }
		
		berRSLPEntry OBJECT-TYPE
			SYNTAX BerRSLPEntry
			MAX-ACCESS not-accessible
			STATUS current
			DESCRIPTION
				"Row specification"
			INDEX { berRSLPInputNumber }
			::= { berRSLPTable 1 }
		
		BerRSLPEntry ::=
			SEQUENCE { 
				berRSLPInputNumber
					InputNumber,
				berRSLPTestState
					TestState,
				berRSLPEnable
					Enable,
				berRSLPCounter
					Counter32,
				berRSLPCounterDiscontinuity
					DateAndTime,
				berRSLPCounterReset
					TruthValue,
				berRSLPLatestError
					DateAndTime,
				berRSLPActiveTime
					ActiveTime,
				berRSLPMeasurementState
					MeasurementState,
				berRSLPValue
					FloatingPoint
			 }

		berRSLPInputNumber OBJECT-TYPE
			SYNTAX InputNumber
			MAX-ACCESS not-accessible
			STATUS current
			DESCRIPTION
				"Transport Stream on which the measurement is made"
			::= { berRSLPEntry 1 }
		
		berRSLPTestState OBJECT-TYPE
			SYNTAX TestState
			MAX-ACCESS read-only
			STATUS current
			DESCRIPTION
				"This indicates whether berRSLPValue is within the thresholds."
			::= { berRSLPEntry 2 }
		
		berRSLPEnable OBJECT-TYPE
			SYNTAX Enable
			MAX-ACCESS read-write
			STATUS current
			DESCRIPTION
				"Determines whether the threshold test and associated traps
				for this measurement are enabled."
			DEFVAL { { testEnable } }
			::= { berRSLPEntry 3 }
		
		berRSLPCounter OBJECT-TYPE
			SYNTAX Counter32
			MAX-ACCESS read-only
			STATUS current
			DESCRIPTION
				"Count of the number of times a threshold error has
				occurred for this measurement."
			::= { berRSLPEntry 4 }
		
		berRSLPCounterDiscontinuity OBJECT-TYPE
			SYNTAX DateAndTime
			MAX-ACCESS read-only
			STATUS current
			DESCRIPTION
				"Provides the last time at which there was a discontinuity
				in the counter object."
			::= { berRSLPEntry 5 }
		
		berRSLPCounterReset OBJECT-TYPE
			SYNTAX TruthValue
			MAX-ACCESS read-write
			STATUS current
			DESCRIPTION
				"The counter object is reset to zero and the counter
				discontinuity object is set to the current time if
				'true' is written to this object.
				
				When read, the value of this object is always 'false'."
			::= { berRSLPEntry 6 }
		
		berRSLPLatestError OBJECT-TYPE
			SYNTAX DateAndTime
			MAX-ACCESS read-only
			STATUS current
			DESCRIPTION
				"The timestamp at the most recent occurrence of a
				threshold error on this measurement."
			::= { berRSLPEntry 7 }
		
		berRSLPActiveTime OBJECT-TYPE
			SYNTAX ActiveTime
			MAX-ACCESS read-only
			STATUS current
			DESCRIPTION
				"The total time when it has been possible to perform this measurement"
			::= { berRSLPEntry 8 }
		
		berRSLPMeasurementState OBJECT-TYPE
			SYNTAX MeasurementState
			MAX-ACCESS read-only
			STATUS current
			DESCRIPTION
				"Specifies the validity of the measurement value"
			::= { berRSLPEntry 9 }
		
		berRSLPValue OBJECT-TYPE
			SYNTAX FloatingPoint
			MAX-ACCESS read-only
			STATUS current
			DESCRIPTION
				"This is the BER before RS (outer) decoder for the low
				priority stream measured using the in-service method.
				It is expressed as a number, e.g. 0.0000034"
			::= { berRSLPEntry 10 }
		
		iqAnalysisT OBJECT IDENTIFIER ::= { tr101290Terrestrial 18 }
		
		merTTable OBJECT-TYPE
			SYNTAX SEQUENCE OF MerTEntry
			MAX-ACCESS not-accessible
			STATUS current
			DESCRIPTION
				"Modulation Error Ratio (MER) measurement"
			REFERENCE
				"TR 101 290 section 9.18.2"
			::= { iqAnalysisT 2 }
		
		merTEntry OBJECT-TYPE
			SYNTAX MerTEntry
			MAX-ACCESS not-accessible
			STATUS current
			DESCRIPTION
				"Row specification"
			INDEX { merTInputNumber }
			::= { merTTable 1 }
		
		MerTEntry ::=
			SEQUENCE { 
				merTInputNumber
					InputNumber,
				merTTestState
					TestState,
				merTEnable
					Enable,
				merTCounter
					Counter32,
				merTCounterDiscontinuity
					DateAndTime,
				merTCounterReset
					TruthValue,
				merTLatestError
					DateAndTime,
				merTActiveTime
					ActiveTime,
				merTMeasurementState
					MeasurementState,
				merTValue
					FloatingPoint
			 }

		merTInputNumber OBJECT-TYPE
			SYNTAX InputNumber
			MAX-ACCESS not-accessible
			STATUS current
			DESCRIPTION
				"Transport Stream on which the measurement is made"
			::= { merTEntry 1 }
		
		merTTestState OBJECT-TYPE
			SYNTAX TestState
			MAX-ACCESS read-only
			STATUS current
			DESCRIPTION
				"This indicates whether merTValue is within the thresholds."
			::= { merTEntry 2 }
		
		merTEnable OBJECT-TYPE
			SYNTAX Enable
			MAX-ACCESS read-write
			STATUS current
			DESCRIPTION
				"Determines whether the threshold test and associated traps
				for this measurement are enabled."
			DEFVAL { { testEnable } }
			::= { merTEntry 3 }
		
		merTCounter OBJECT-TYPE
			SYNTAX Counter32
			MAX-ACCESS read-only
			STATUS current
			DESCRIPTION
				"Count of the number of times a threshold error has
				occurred for this measurement."
			::= { merTEntry 4 }
		
		merTCounterDiscontinuity OBJECT-TYPE
			SYNTAX DateAndTime
			MAX-ACCESS read-only
			STATUS current
			DESCRIPTION
				"Provides the last time at which there was a discontinuity
				in the merTCounter object."
			::= { merTEntry 5 }
		
		merTCounterReset OBJECT-TYPE
			SYNTAX TruthValue
			MAX-ACCESS read-write
			STATUS current
			DESCRIPTION
				"The counter object is reset to zero and the counter
				discontinuity object is set to the current time if
				'true' is written to this object.
				
				When read, the value of this object is always 'false'."
			DEFVAL { false }
			::= { merTEntry 6 }
		
		merTLatestError OBJECT-TYPE
			SYNTAX DateAndTime
			MAX-ACCESS read-only
			STATUS current
			DESCRIPTION
				"The timestamp at the most recent occurrence of a
				threshold error on this measurement."
			::= { merTEntry 7 }
		
		merTActiveTime OBJECT-TYPE
			SYNTAX ActiveTime
			UNITS "second"
			MAX-ACCESS read-only
			STATUS current
			DESCRIPTION
				"The total time when it has been possible to perform this measurement"
			::= { merTEntry 8 }
		
		merTMeasurementState OBJECT-TYPE
			SYNTAX MeasurementState
			MAX-ACCESS read-only
			STATUS current
			DESCRIPTION
				"Specifies the validity of the measurement value"
			::= { merTEntry 9 }
		
		merTValue OBJECT-TYPE
			SYNTAX FloatingPoint
			UNITS "dB"
			MAX-ACCESS read-only
			STATUS current
			DESCRIPTION
				"The current Modulation Error Ratio expressed in dB"
			::= { merTEntry 10 }
		
		steT OBJECT IDENTIFIER ::= { iqAnalysisT 3 }
		
		steMeanTTable OBJECT-TYPE
			SYNTAX SEQUENCE OF SteMeanTEntry
			MAX-ACCESS not-accessible
			STATUS current
			DESCRIPTION
				"System Target Error Mean (STEM) measurement"
			REFERENCE
				"TR 101 290 section 9.18.3"
			::= { steT 1 }
		
		steMeanTEntry OBJECT-TYPE
			SYNTAX SteMeanTEntry
			MAX-ACCESS not-accessible
			STATUS current
			DESCRIPTION
				"Row specification"
			INDEX { steMeanTInputNumber }
			::= { steMeanTTable 1 }
		
		SteMeanTEntry ::=
			SEQUENCE { 
				steMeanTInputNumber
					InputNumber,
				steMeanTTestState
					TestState,
				steMeanTEnable
					Enable,
				steMeanTCounter
					Counter32,
				steMeanTCounterDiscontinuity
					DateAndTime,
				steMeanTCounterReset
					TruthValue,
				steMeanTLatestError
					DateAndTime,
				steMeanTActiveTime
					ActiveTime,
				steMeanTMeasurementState
					MeasurementState,
				steMeanTValue
					FloatingPoint
			 }

		steMeanTInputNumber OBJECT-TYPE
			SYNTAX InputNumber
			MAX-ACCESS not-accessible
			STATUS current
			DESCRIPTION
				"Transport Stream on which the measurement is made"
			::= { steMeanTEntry 1 }
		
		steMeanTTestState OBJECT-TYPE
			SYNTAX TestState
			MAX-ACCESS read-only
			STATUS current
			DESCRIPTION
				"This indicates whether steMeanTValue is currently
				within the thresholds."
			::= { steMeanTEntry 2 }
		
		steMeanTEnable OBJECT-TYPE
			SYNTAX Enable
			MAX-ACCESS read-write
			STATUS current
			DESCRIPTION
				"Determines whether the threshold test and associated traps
				for this measurement are enabled."
			DEFVAL { { testEnable } }
			::= { steMeanTEntry 3 }
		
		steMeanTCounter OBJECT-TYPE
			SYNTAX Counter32
			MAX-ACCESS read-only
			STATUS current
			DESCRIPTION
				"Count of the number of times a threshold error has
				occurred for this measurement."
			::= { steMeanTEntry 4 }
		
		steMeanTCounterDiscontinuity OBJECT-TYPE
			SYNTAX DateAndTime
			MAX-ACCESS read-only
			STATUS current
			DESCRIPTION
				"Provides the last time at which there was a discontinuity
				in the counter object."
			::= { steMeanTEntry 5 }
		
		steMeanTCounterReset OBJECT-TYPE
			SYNTAX TruthValue
			MAX-ACCESS read-write
			STATUS current
			DESCRIPTION
				"The counter object is reset to zero and the counter
				discontinuity object is set to the current time if
				'true' is written to this object.
				
				When read, the value of this object is always 'false'."
			DEFVAL { false }
			::= { steMeanTEntry 6 }
		
		steMeanTLatestError OBJECT-TYPE
			SYNTAX DateAndTime
			MAX-ACCESS read-only
			STATUS current
			DESCRIPTION
				"The timestamp at the most recent occurrence of a
				threshold error on this measurement."
			::= { steMeanTEntry 7 }
		
		steMeanTActiveTime OBJECT-TYPE
			SYNTAX ActiveTime
			UNITS "second"
			MAX-ACCESS read-only
			STATUS current
			DESCRIPTION
				"The total time when it has been possible to perform this measurement"
			::= { steMeanTEntry 8 }
		
		steMeanTMeasurementState OBJECT-TYPE
			SYNTAX MeasurementState
			MAX-ACCESS read-only
			STATUS current
			DESCRIPTION
				"Specifies the validity of the measurement value"
			::= { steMeanTEntry 9 }
		
		steMeanTValue OBJECT-TYPE
			SYNTAX FloatingPoint
			MAX-ACCESS read-only
			STATUS current
			DESCRIPTION
				"The current System Target Error Mean as a numeric value"
			::= { steMeanTEntry 10 }
		
		steDeviationTTable OBJECT-TYPE
			SYNTAX SEQUENCE OF SteDeviationTEntry
			MAX-ACCESS not-accessible
			STATUS current
			DESCRIPTION
				"System Target Error Deviation (STED) measurement"
			REFERENCE
				"TR 101 290 section 9.18.3"
			::= { steT 2 }
		
		steDeviationTEntry OBJECT-TYPE
			SYNTAX SteDeviationTEntry
			MAX-ACCESS not-accessible
			STATUS current
			DESCRIPTION
				"Row specification"
			INDEX { steDeviationTInputNumber }
			::= { steDeviationTTable 1 }
		
		SteDeviationTEntry ::=
			SEQUENCE { 
				steDeviationTInputNumber
					InputNumber,
				steDeviationTTestState
					TestState,
				steDeviationTEnable
					Enable,
				steDeviationTCounter
					Counter32,
				steDeviationTCounterDiscontinuity
					DateAndTime,
				steDeviationTCounterReset
					TruthValue,
				steDeviationTLatestError
					DateAndTime,
				steDeviationTActiveTime
					ActiveTime,
				steDeviationTMeasurementState
					MeasurementState,
				steDeviationTValue
					FloatingPoint
			 }

		steDeviationTInputNumber OBJECT-TYPE
			SYNTAX InputNumber
			MAX-ACCESS not-accessible
			STATUS current
			DESCRIPTION
				"Transport Stream on which the measurement is made"
			::= { steDeviationTEntry 1 }
		
		steDeviationTTestState OBJECT-TYPE
			SYNTAX TestState
			MAX-ACCESS read-only
			STATUS current
			DESCRIPTION
				"This indicates whether steDeviationTValue is currently
				within the thresholds."
			::= { steDeviationTEntry 2 }
		
		steDeviationTEnable OBJECT-TYPE
			SYNTAX Enable
			MAX-ACCESS read-write
			STATUS current
			DESCRIPTION
				"Determines whether the threshold test and associated traps
				for this measurement are enabled."
			DEFVAL { { testEnable } }
			::= { steDeviationTEntry 3 }
		
		steDeviationTCounter OBJECT-TYPE
			SYNTAX Counter32
			MAX-ACCESS read-only
			STATUS current
			DESCRIPTION
				"Count of the number of times a threshold error has
				occurred for this measurement."
			::= { steDeviationTEntry 4 }
		
		steDeviationTCounterDiscontinuity OBJECT-TYPE
			SYNTAX DateAndTime
			MAX-ACCESS read-only
			STATUS current
			DESCRIPTION
				"Provides the last time at which there was a discontinuity
				in the counter object."
			::= { steDeviationTEntry 5 }
		
		steDeviationTCounterReset OBJECT-TYPE
			SYNTAX TruthValue
			MAX-ACCESS read-write
			STATUS current
			DESCRIPTION
				"The counter object is reset to zero and the counter
				discontinuity object is set to the current time if
				'true' is written to this object.
				
				When read, the value of this object is always 'false'."
			::= { steDeviationTEntry 6 }
		
		steDeviationTLatestError OBJECT-TYPE
			SYNTAX DateAndTime
			MAX-ACCESS read-only
			STATUS current
			DESCRIPTION
				"The timestamp at the most recent occurrence of a
				threshold error on this measurement."
			::= { steDeviationTEntry 7 }
		
		steDeviationTActiveTime OBJECT-TYPE
			SYNTAX ActiveTime
			UNITS "second"
			MAX-ACCESS read-only
			STATUS current
			DESCRIPTION
				"The total time when it has been possible to perform this measurement"
			::= { steDeviationTEntry 8 }
		
		steDeviationTMeasurementState OBJECT-TYPE
			SYNTAX MeasurementState
			MAX-ACCESS read-only
			STATUS current
			DESCRIPTION
				"Specifies the validity of the measurement value"
			::= { steDeviationTEntry 9 }
		
		steDeviationTValue OBJECT-TYPE
			SYNTAX FloatingPoint
			MAX-ACCESS read-only
			STATUS current
			DESCRIPTION
				"The current System Target Error Deviation as a numeric value"
			::= { steDeviationTEntry 10 }
		
		csTTable OBJECT-TYPE
			SYNTAX SEQUENCE OF CsTEntry
			MAX-ACCESS not-accessible
			STATUS current
			DESCRIPTION
				"Carrier Suppression (CS) measurement"
			REFERENCE
				"TR 101 290 section 9.18.4"
			::= { iqAnalysisT 4 }
		
		csTEntry OBJECT-TYPE
			SYNTAX CsTEntry
			MAX-ACCESS not-accessible
			STATUS current
			DESCRIPTION
				"Row specification"
			INDEX { csTInputNumber }
			::= { csTTable 1 }
		
		CsTEntry ::=
			SEQUENCE { 
				csTInputNumber
					InputNumber,
				csTTestState
					TestState,
				csTEnable
					Enable,
				csTCounter
					Counter32,
				csTCounterDiscontinuity
					DateAndTime,
				csTCounterReset
					TruthValue,
				csTLatestError
					DateAndTime,
				csTActiveTime
					ActiveTime,
				csTMeasurementState
					MeasurementState,
				csTValue
					FloatingPoint
			 }

		csTInputNumber OBJECT-TYPE
			SYNTAX InputNumber
			MAX-ACCESS not-accessible
			STATUS current
			DESCRIPTION
				"Transport Stream on which the measurement is made"
			::= { csTEntry 1 }
		
		csTTestState OBJECT-TYPE
			SYNTAX TestState
			MAX-ACCESS read-only
			STATUS current
			DESCRIPTION
				"This indicates whether csTValue is currently
				within the thresholds."
			::= { csTEntry 2 }
		
		csTEnable OBJECT-TYPE
			SYNTAX Enable
			MAX-ACCESS read-write
			STATUS current
			DESCRIPTION
				"Determines whether the threshold test and associated traps
				for this measurement are enabled."
			DEFVAL { { testEnable } }
			::= { csTEntry 3 }
		
		csTCounter OBJECT-TYPE
			SYNTAX Counter32
			MAX-ACCESS read-only
			STATUS current
			DESCRIPTION
				"Count of the number of times a threshold error
				has occurred for this measurement."
			::= { csTEntry 4 }
		
		csTCounterDiscontinuity OBJECT-TYPE
			SYNTAX DateAndTime
			MAX-ACCESS read-only
			STATUS current
			DESCRIPTION
				"Provides the last time at which there was a discontinuity
				in the counter object."
			::= { csTEntry 5 }
		
		csTCounterReset OBJECT-TYPE
			SYNTAX TruthValue
			MAX-ACCESS read-write
			STATUS current
			DESCRIPTION
				"The counter object is reset to zero and the counter
				discontinuity object is set to the current time if
				'true' is written to this object.
				
				When read, the value of this object is always 'false'."
			::= { csTEntry 6 }
		
		csTLatestError OBJECT-TYPE
			SYNTAX DateAndTime
			MAX-ACCESS read-only
			STATUS current
			DESCRIPTION
				"The timestamp at the most recent occurrence of a
				threshold error on this measurement."
			::= { csTEntry 7 }
		
		csTActiveTime OBJECT-TYPE
			SYNTAX ActiveTime
			UNITS "second"
			MAX-ACCESS read-only
			STATUS current
			DESCRIPTION
				"The total time when it has been possible to perform this measurement"
			::= { csTEntry 8 }
		
		csTMeasurementState OBJECT-TYPE
			SYNTAX MeasurementState
			MAX-ACCESS read-only
			STATUS current
			DESCRIPTION
				"Specifies the validity of the measurement value"
			::= { csTEntry 9 }
		
		csTValue OBJECT-TYPE
			SYNTAX FloatingPoint
			UNITS "dB"
			MAX-ACCESS read-only
			STATUS current
			DESCRIPTION
				"The current Carrier Suppression value in dB."
			::= { csTEntry 10 }
		
		aiTTable OBJECT-TYPE
			SYNTAX SEQUENCE OF AiTEntry
			MAX-ACCESS not-accessible
			STATUS current
			DESCRIPTION
				"Amplitude Imbalance (AI) measurement"
			REFERENCE
				"TR 101 290 section 9.18.5"
			::= { iqAnalysisT 5 }
		
		aiTEntry OBJECT-TYPE
			SYNTAX AiTEntry
			MAX-ACCESS not-accessible
			STATUS current
			DESCRIPTION
				"Row specification"
			INDEX { aiTInputNumber }
			::= { aiTTable 1 }
		
		AiTEntry ::=
			SEQUENCE { 
				aiTInputNumber
					InputNumber,
				aiTTestState
					TestState,
				aiTEnable
					Enable,
				aiTCounter
					Counter32,
				aiTCounterDiscontinuity
					DateAndTime,
				aiTCounterReset
					TruthValue,
				aiTLatestError
					DateAndTime,
				aiTActiveTime
					ActiveTime,
				aiTMeasurementState
					MeasurementState,
				aiTValue
					FloatingPoint
			 }

		aiTInputNumber OBJECT-TYPE
			SYNTAX InputNumber
			MAX-ACCESS not-accessible
			STATUS current
			DESCRIPTION
				"Transport Stream on which the measurement is made"
			::= { aiTEntry 1 }
		
		aiTTestState OBJECT-TYPE
			SYNTAX TestState
			MAX-ACCESS read-only
			STATUS current
			DESCRIPTION
				"This indicates whether aiTValue is currently
				within the thresholds."
			::= { aiTEntry 2 }
		
		aiTEnable OBJECT-TYPE
			SYNTAX Enable
			MAX-ACCESS read-write
			STATUS current
			DESCRIPTION
				"Determines whether the threshold test and associated traps
				for this measurement are enabled."
			DEFVAL { { testEnable } }
			::= { aiTEntry 3 }
		
		aiTCounter OBJECT-TYPE
			SYNTAX Counter32
			MAX-ACCESS read-only
			STATUS current
			DESCRIPTION
				"Count of the number of times a threshold error has
				occurred for this measurement."
			::= { aiTEntry 4 }
		
		aiTCounterDiscontinuity OBJECT-TYPE
			SYNTAX DateAndTime
			MAX-ACCESS read-only
			STATUS current
			DESCRIPTION
				"Provides the last time at which there was a
				discontinuity in the counter object."
			::= { aiTEntry 5 }
		
		aiTCounterReset OBJECT-TYPE
			SYNTAX TruthValue
			MAX-ACCESS read-write
			STATUS current
			DESCRIPTION
				"The counter object is reset to zero and the counter
				discontinuity object is set to the current time if
				'true' is written to this object.
				
				When read, the value of this object is always 'false'."
			DEFVAL { false }
			::= { aiTEntry 6 }
		
		aiTLatestError OBJECT-TYPE
			SYNTAX DateAndTime
			MAX-ACCESS read-only
			STATUS current
			DESCRIPTION
				"The timestamp at the most recent occurrence of a
				threshold error on this measurement."
			::= { aiTEntry 7 }
		
		aiTActiveTime OBJECT-TYPE
			SYNTAX ActiveTime
			UNITS "second"
			MAX-ACCESS read-only
			STATUS current
			DESCRIPTION
				"The total time when it has been possible to perform this measurement"
			::= { aiTEntry 8 }
		
		aiTMeasurementState OBJECT-TYPE
			SYNTAX MeasurementState
			MAX-ACCESS read-only
			STATUS current
			DESCRIPTION
				"Specifies the validity of the measurement value"
			::= { aiTEntry 9 }
		
		aiTValue OBJECT-TYPE
			SYNTAX FloatingPoint
			MAX-ACCESS read-only
			STATUS current
			DESCRIPTION
				"The current Amplitude Imbalance as a percentage"
			::= { aiTEntry 10 }
		
		qeTTable OBJECT-TYPE
			SYNTAX SEQUENCE OF QeTEntry
			MAX-ACCESS not-accessible
			STATUS current
			DESCRIPTION
				"Quadrature Error (QE) measurement"
			REFERENCE
				"TR 101 290 section 9.18.6"
			::= { iqAnalysisT 6 }
		
		qeTEntry OBJECT-TYPE
			SYNTAX QeTEntry
			MAX-ACCESS not-accessible
			STATUS current
			DESCRIPTION
				"Row specification"
			INDEX { qeTInputNumber }
			::= { qeTTable 1 }
		
		QeTEntry ::=
			SEQUENCE { 
				qeTInputNumber
					InputNumber,
				qeTTestState
					TestState,
				qeTEnable
					Enable,
				qeTCounter
					Counter32,
				qeTCounterDiscontinuity
					DateAndTime,
				qeTCounterReset
					TruthValue,
				qeTLatestError
					DateAndTime,
				qeTActiveTime
					ActiveTime,
				qeTMeasurementState
					MeasurementState,
				qeTValue
					FloatingPoint
			 }

		qeTInputNumber OBJECT-TYPE
			SYNTAX InputNumber
			MAX-ACCESS not-accessible
			STATUS current
			DESCRIPTION
				"Transport Stream on which the measurement is made"
			::= { qeTEntry 1 }
		
		qeTTestState OBJECT-TYPE
			SYNTAX TestState
			MAX-ACCESS read-only
			STATUS current
			DESCRIPTION
				"This indicates whether qeTValue is currently
				within the thresholds."
			::= { qeTEntry 2 }
		
		qeTEnable OBJECT-TYPE
			SYNTAX Enable
			MAX-ACCESS read-write
			STATUS current
			DESCRIPTION
				"Determines whether the threshold test and associated traps
				for this measurement are enabled."
			DEFVAL { { testEnable } }
			::= { qeTEntry 3 }
		
		qeTCounter OBJECT-TYPE
			SYNTAX Counter32
			MAX-ACCESS read-only
			STATUS current
			DESCRIPTION
				"Count of the number of times a threshold error has
				occurred for this measurement."
			::= { qeTEntry 4 }
		
		qeTCounterDiscontinuity OBJECT-TYPE
			SYNTAX DateAndTime
			MAX-ACCESS read-only
			STATUS current
			DESCRIPTION
				"Provides the last time at which there was a
				discontinuity in the counter object."
			::= { qeTEntry 5 }
		
		qeTCounterReset OBJECT-TYPE
			SYNTAX TruthValue
			MAX-ACCESS read-write
			STATUS current
			DESCRIPTION
				"The counter object is reset to zero and the counter
				discontinuity object is set to the current time if
				'true' is written to this object.
				
				When read, the value of this object is always 'false'."
			DEFVAL { false }
			::= { qeTEntry 6 }
		
		qeTLatestError OBJECT-TYPE
			SYNTAX DateAndTime
			MAX-ACCESS read-only
			STATUS current
			DESCRIPTION
				"The timestamp at the most recent occurrence of a
				threshold error on this measurement."
			::= { qeTEntry 7 }
		
		qeTActiveTime OBJECT-TYPE
			SYNTAX ActiveTime
			UNITS "second"
			MAX-ACCESS read-only
			STATUS current
			DESCRIPTION
				"The total time when it has been possible to perform this measurement"
			::= { qeTEntry 8 }
		
		qeTMeasurementState OBJECT-TYPE
			SYNTAX MeasurementState
			MAX-ACCESS read-only
			STATUS current
			DESCRIPTION
				"Specifies the validity of the measurement value"
			::= { qeTEntry 9 }
		
		qeTValue OBJECT-TYPE
			SYNTAX FloatingPoint
			UNITS "degree"
			MAX-ACCESS read-only
			STATUS current
			DESCRIPTION
				"The current Quadrature Error value in degrees."
			::= { qeTEntry 10 }
		
		pjTTable OBJECT-TYPE
			SYNTAX SEQUENCE OF PjTEntry
			MAX-ACCESS not-accessible
			STATUS current
			DESCRIPTION
				"Phase Jitter (PJ) measurement"
			REFERENCE
				"TR 101 290 section 9.18.7"
			::= { iqAnalysisT 7 }
		
		pjTEntry OBJECT-TYPE
			SYNTAX PjTEntry
			MAX-ACCESS not-accessible
			STATUS current
			DESCRIPTION
				"Row specification"
			INDEX { pjTInputNumber }
			::= { pjTTable 1 }
		
		PjTEntry ::=
			SEQUENCE { 
				pjTInputNumber
					InputNumber,
				pjTTestState
					TestState,
				pjTEnable
					Enable,
				pjTCounter
					Counter32,
				pjTCounterDiscontinuity
					DateAndTime,
				pjTCounterReset
					TruthValue,
				pjTLatestError
					DateAndTime,
				pjTActiveTime
					ActiveTime,
				pjTMeasurementState
					MeasurementState,
				pjTValue
					FloatingPoint
			 }

		pjTInputNumber OBJECT-TYPE
			SYNTAX InputNumber
			MAX-ACCESS not-accessible
			STATUS current
			DESCRIPTION
				"Transport Stream on which the measurement is made"
			::= { pjTEntry 1 }
		
		pjTTestState OBJECT-TYPE
			SYNTAX TestState
			MAX-ACCESS read-only
			STATUS current
			DESCRIPTION
				"This indicates whether pjTValue is currently
				within the thresholds."
			::= { pjTEntry 2 }
		
		pjTEnable OBJECT-TYPE
			SYNTAX Enable
			MAX-ACCESS read-write
			STATUS current
			DESCRIPTION
				"Determines whether the threshold test and associated traps
				for this measurement are enabled."
			DEFVAL { { testEnable } }
			::= { pjTEntry 3 }
		
		pjTCounter OBJECT-TYPE
			SYNTAX Counter32
			MAX-ACCESS read-only
			STATUS current
			DESCRIPTION
				"Count of the number of times a threshold error has
				occurred for this measurement."
			::= { pjTEntry 4 }
		
		pjTCounterDiscontinuity OBJECT-TYPE
			SYNTAX DateAndTime
			MAX-ACCESS read-only
			STATUS current
			DESCRIPTION
				"Provides the last time at which there was a
				discontinuity in the counter object."
			::= { pjTEntry 5 }
		
		pjTCounterReset OBJECT-TYPE
			SYNTAX TruthValue
			MAX-ACCESS read-write
			STATUS current
			DESCRIPTION
				"The counter object is reset to zero and the counter
				discontinuity object is set to the current time if
				'true' is written to this object.
				
				When read, the value of this object is always 'false'."
			DEFVAL { false }
			::= { pjTEntry 6 }
		
		pjTLatestError OBJECT-TYPE
			SYNTAX DateAndTime
			MAX-ACCESS read-only
			STATUS current
			DESCRIPTION
				"The timestamp at the most recent occurrence of a
				threshold error on this measurement."
			::= { pjTEntry 7 }
		
		pjTActiveTime OBJECT-TYPE
			SYNTAX ActiveTime
			UNITS "second"
			MAX-ACCESS read-only
			STATUS current
			DESCRIPTION
				"The total time when it has been possible to perform this measurement"
			::= { pjTEntry 8 }
		
		pjTMeasurementState OBJECT-TYPE
			SYNTAX MeasurementState
			MAX-ACCESS read-only
			STATUS current
			DESCRIPTION
				"Specifies the validity of the measurement value"
			::= { pjTEntry 9 }
		
		pjTValue OBJECT-TYPE
			SYNTAX FloatingPoint
			UNITS "degree"
			MAX-ACCESS read-only
			STATUS current
			DESCRIPTION
				"The current Phase Jitter value in degrees."
			::= { pjTEntry 10 }
		
		mipSyntaxTable OBJECT-TYPE
			SYNTAX SEQUENCE OF MipSyntaxEntry
			MAX-ACCESS not-accessible
			STATUS current
			DESCRIPTION
				"SFN MIP baseband tests"
			REFERENCE
				"TR 101 290 section 9.20"
			::= { tr101290Terrestrial 20 }
		
		mipSyntaxEntry OBJECT-TYPE
			SYNTAX MipSyntaxEntry
			MAX-ACCESS not-accessible
			STATUS current
			DESCRIPTION
				"Row specification"
			INDEX { mipSyntaxTestNumber, mipSyntaxInputNumber }
			::= { mipSyntaxTable 1 }
		
		MipSyntaxEntry ::=
			SEQUENCE { 
				mipSyntaxInputNumber
					InputNumber,
				mipSyntaxTestNumber
					IndexMIPSyntaxTest,
				mipSyntaxState
					TestState,
				mipSyntaxEnable
					Enable,
				mipSyntaxCounter
					Counter32,
				mipSyntaxCounterDiscontinuity
					DateAndTime,
				mipSyntaxCounterReset
					TruthValue,
				mipSyntaxLatestError
					DateAndTime,
				mipSyntaxActiveTime
					ActiveTime
			 }

		mipSyntaxInputNumber OBJECT-TYPE
			SYNTAX InputNumber
			MAX-ACCESS not-accessible
			STATUS current
			DESCRIPTION
				"Transport Stream on which the measurement is made"
			::= { mipSyntaxEntry 1 }
		
		mipSyntaxTestNumber OBJECT-TYPE
			SYNTAX IndexMIPSyntaxTest
			MAX-ACCESS not-accessible
			STATUS current
			DESCRIPTION
				"The specific SFN MIP test that this row applies to"
			::= { mipSyntaxEntry 2 }
		
		mipSyntaxState OBJECT-TYPE
			SYNTAX TestState
			MAX-ACCESS read-only
			STATUS current
			DESCRIPTION
				"This gives the overall pass/fail state of the test."
			::= { mipSyntaxEntry 3 }
		
		mipSyntaxEnable OBJECT-TYPE
			SYNTAX Enable
			MAX-ACCESS read-write
			STATUS current
			DESCRIPTION
				"Determines whether this test and the associated trap are enabled."
			DEFVAL { { testEnable } }
			::= { mipSyntaxEntry 4 }
		
		mipSyntaxCounter OBJECT-TYPE
			SYNTAX Counter32
			MAX-ACCESS read-only
			STATUS current
			DESCRIPTION
				"Count of the number of times this error has occurred"
			::= { mipSyntaxEntry 5 }
		
		mipSyntaxCounterDiscontinuity OBJECT-TYPE
			SYNTAX DateAndTime
			MAX-ACCESS read-only
			STATUS current
			DESCRIPTION
				"Provides the last time at which there was a discontinuity
				in the mipSyntaxCounter object."
			::= { mipSyntaxEntry 6 }
		
		mipSyntaxCounterReset OBJECT-TYPE
			SYNTAX TruthValue
			MAX-ACCESS read-write
			STATUS current
			DESCRIPTION
				"The counter object is reset to zero and the counter
				discontinuity object is set to the current time if
				'true' is written to this object.
				
				When read, the value of this object is always 'false'."
			::= { mipSyntaxEntry 7 }
		
		mipSyntaxLatestError OBJECT-TYPE
			SYNTAX DateAndTime
			MAX-ACCESS read-only
			STATUS current
			DESCRIPTION
				"The timestamp at the most recent occurrence of the error"
			::= { mipSyntaxEntry 8 }
		
		mipSyntaxActiveTime OBJECT-TYPE
			SYNTAX ActiveTime
			UNITS "second"
			MAX-ACCESS read-only
			STATUS current
			DESCRIPTION
				"The total time when it has been possible to perform this measurement"
			::= { mipSyntaxEntry 9 }
		
		systemErrorPerformance OBJECT IDENTIFIER ::= { tr101290Terrestrial 21 }
		
		sepEtiTable OBJECT-TYPE
			SYNTAX SEQUENCE OF SepEtiEntry
			MAX-ACCESS not-accessible
			STATUS current
			DESCRIPTION
				"Measurement of Errored Second Ratio (ESR) or
				Errored Time Interval Ratio (ETIR)."
			REFERENCE
				"TR 101 290 section 9.21"
			::= { systemErrorPerformance 1 }
		
		sepEtiEntry OBJECT-TYPE
			SYNTAX SepEtiEntry
			MAX-ACCESS not-accessible
			STATUS current
			DESCRIPTION
				"Row specification"
			INDEX { sepEtiInputNumber }
			::= { sepEtiTable 1 }
		
		SepEtiEntry ::=
			SEQUENCE { 
				sepEtiInputNumber
					InputNumber,
				sepEtiTestState
					TestState,
				sepEtiEnable
					Enable,
				sepEtiCounter
					Counter32,
				sepEtiCounterDiscontinuity
					DateAndTime,
				sepEtiCounterReset
					TruthValue,
				sepEtiLatestError
					DateAndTime,
				sepEtiActiveTime
					ActiveTime,
				sepEtiMeasurementState
					MeasurementState,
				sepEtiValue
					FloatingPoint
			 }

		sepEtiInputNumber OBJECT-TYPE
			SYNTAX InputNumber
			MAX-ACCESS not-accessible
			STATUS current
			DESCRIPTION
				"Transport Stream on which the measurement is made"
			::= { sepEtiEntry 1 }
		
		sepEtiTestState OBJECT-TYPE
			SYNTAX TestState
			MAX-ACCESS read-only
			STATUS current
			DESCRIPTION
				"A 'fail' indicaties that the most recently completed
				time interval TI was an Errored Time Interval (ETI).
				A 'pass' indicates that the most recent TI was not
				errored."
			::= { sepEtiEntry 2 }
		
		sepEtiEnable OBJECT-TYPE
			SYNTAX Enable
			MAX-ACCESS read-write
			STATUS current
			DESCRIPTION
				"Determines whether the threshold test and associated traps
				for this measurement are enabled."
			DEFVAL { { testEnable } }
			::= { sepEtiEntry 3 }
		
		sepEtiCounter OBJECT-TYPE
			SYNTAX Counter32
			MAX-ACCESS read-only
			STATUS current
			DESCRIPTION
				"Count of the number of times an ETI has occurred."
			::= { sepEtiEntry 4 }
		
		sepEtiCounterDiscontinuity OBJECT-TYPE
			SYNTAX DateAndTime
			MAX-ACCESS read-only
			STATUS current
			DESCRIPTION
				"Provides the last time at which there was a discontinuity
				in the counter object."
			::= { sepEtiEntry 5 }
		
		sepEtiCounterReset OBJECT-TYPE
			SYNTAX TruthValue
			MAX-ACCESS read-write
			STATUS current
			DESCRIPTION
				"The counter object is reset to zero and the counter
				discontinuity object is set to the current time if
				'true' is written to this object.
				
				When read, the value of this object is always 'false'."
			::= { sepEtiEntry 6 }
		
		sepEtiLatestError OBJECT-TYPE
			SYNTAX DateAndTime
			MAX-ACCESS read-only
			STATUS current
			DESCRIPTION
				"The timestamp at the most recent occurrence of an ETI."
			::= { sepEtiEntry 7 }
		
		sepEtiActiveTime OBJECT-TYPE
			SYNTAX ActiveTime
			UNITS "second"
			MAX-ACCESS read-only
			STATUS current
			DESCRIPTION
				"The total time when it has been possible to perform this measurement"
			::= { sepEtiEntry 8 }
		
		sepEtiMeasurementState OBJECT-TYPE
			SYNTAX MeasurementState
			MAX-ACCESS read-only
			STATUS current
			DESCRIPTION
				"Specifies the validity of the measurement value"
			::= { sepEtiEntry 9 }
		
		sepEtiValue OBJECT-TYPE
			SYNTAX FloatingPoint
			MAX-ACCESS read-only
			STATUS current
			DESCRIPTION
				"This is the Errored Time Interval Ratio (ETIR) for
				the most recently completed Measurement Interval (MI).
				It is expressed as a numeric value."
			::= { sepEtiEntry 10 }
		
		sepSetiTable OBJECT-TYPE
			SYNTAX SEQUENCE OF SepSetiEntry
			MAX-ACCESS not-accessible
			STATUS current
			DESCRIPTION
				"Measurement of Severly Errored Second Ratio (SESR)
				or Severely Errored Time Interval Ratio (SETIR)."
			REFERENCE
				"TR 101 290 section 9.21"
			::= { systemErrorPerformance 2 }
		
		sepSetiEntry OBJECT-TYPE
			SYNTAX SepSetiEntry
			MAX-ACCESS not-accessible
			STATUS current
			DESCRIPTION
				"Row specification"
			INDEX { sepSetiInputNumber }
			::= { sepSetiTable 1 }
		
		SepSetiEntry ::=
			SEQUENCE { 
				sepSetiInputNumber
					InputNumber,
				sepSetiTestState
					TestState,
				sepSetiEnable
					Enable,
				sepSetiCounter
					Counter32,
				sepSetiCounterDiscontinuity
					DateAndTime,
				sepSetiCounterReset
					TruthValue,
				sepSetiLatestError
					DateAndTime,
				sepSetiActiveTime
					ActiveTime,
				sepSetiMeasurementState
					MeasurementState,
				sepSetiValue
					FloatingPoint
			 }

		sepSetiInputNumber OBJECT-TYPE
			SYNTAX InputNumber
			MAX-ACCESS not-accessible
			STATUS current
			DESCRIPTION
				"Transport Stream on which the measurement is made"
			::= { sepSetiEntry 1 }
		
		sepSetiTestState OBJECT-TYPE
			SYNTAX TestState
			MAX-ACCESS read-only
			STATUS current
			DESCRIPTION
				"A 'fail' indicaties that the most recently completed
				time interval TI was a Severely Errored Time Interval
				(SETI).  A 'pass' indicates that the most recent TI
				was not severely errored."
			::= { sepSetiEntry 2 }
		
		sepSetiEnable OBJECT-TYPE
			SYNTAX Enable
			MAX-ACCESS read-write
			STATUS current
			DESCRIPTION
				"Determines whether the threshold test and associated traps
				for this measurement are enabled."
			DEFVAL { { testEnable } }
			::= { sepSetiEntry 3 }
		
		sepSetiCounter OBJECT-TYPE
			SYNTAX Counter32
			MAX-ACCESS read-only
			STATUS current
			DESCRIPTION
				"Count of the number of times an SETI has occurred."
			::= { sepSetiEntry 4 }
		
		sepSetiCounterDiscontinuity OBJECT-TYPE
			SYNTAX DateAndTime
			MAX-ACCESS read-only
			STATUS current
			DESCRIPTION
				"Provides the last time at which there was a
				discontinuity in the counter object."
			::= { sepSetiEntry 5 }
		
		sepSetiCounterReset OBJECT-TYPE
			SYNTAX TruthValue
			MAX-ACCESS read-write
			STATUS current
			DESCRIPTION
				"The counter object is reset to zero and the counter
				discontinuity object is set to the current time if
				'true' is written to this object.
				
				When read, the value of this object is always 'false'."
			::= { sepSetiEntry 6 }
		
		sepSetiLatestError OBJECT-TYPE
			SYNTAX DateAndTime
			MAX-ACCESS read-only
			STATUS current
			DESCRIPTION
				"The timestamp at the most recent occurrence of a SETI."
			::= { sepSetiEntry 7 }
		
		sepSetiActiveTime OBJECT-TYPE
			SYNTAX ActiveTime
			UNITS "second"
			MAX-ACCESS read-only
			STATUS current
			DESCRIPTION
				"The total time when it has been possible to perform this measurement"
			::= { sepSetiEntry 8 }
		
		sepSetiMeasurementState OBJECT-TYPE
			SYNTAX MeasurementState
			MAX-ACCESS read-only
			STATUS current
			DESCRIPTION
				"Specifies the validity of the measurement value"
			::= { sepSetiEntry 9 }
		
		sepSetiValue OBJECT-TYPE
			SYNTAX FloatingPoint
			MAX-ACCESS read-only
			STATUS current
			DESCRIPTION
				"This is the Severely Errored Time Interval Ratio (SETIR)
				for the most recently completed Measurement Interval (MI).
				It is expressed as a numeric value."
			::= { sepSetiEntry 10 }
		
		terrestrialPreferencesTable OBJECT-TYPE
			SYNTAX SEQUENCE OF TerrestrialPreferencesEntry
			MAX-ACCESS not-accessible
			STATUS current
			DESCRIPTION
				"Table of terrestrial specific measurement preferences."
			::= { tr101290Terrestrial 100 }
		
		terrestrialPreferencesEntry OBJECT-TYPE
			SYNTAX TerrestrialPreferencesEntry
			MAX-ACCESS not-accessible
			STATUS current
			DESCRIPTION
				"Row specification"
			INDEX { terrestrialPrefInputNumber }
			::= { terrestrialPreferencesTable 1 }
		
		TerrestrialPreferencesEntry ::=
			SEQUENCE { 
				terrestrialPrefInputNumber
					InputNumber,
				terrestrialPrefCentreFrequency
					FloatingPoint,
				terrestrialPrefBandwidth
					FloatingPoint,
				terrestrialPrefModulation
					Modulation,
				terrestrialPrefTransmissionMode
					TerrestrialTransmissionMode,
				terrestrialPrefGuardInterval
					GuardInterval,
				terrestrialPrefHierarchical
					Hierarchy,
				terrestrialPrefCentreFreqExpected
					FloatingPoint,
				terrestrialPrefCentreFreqLimit
					FloatingPoint,
				terrestrialPrefChannelWidthLimit
					FloatingPoint,
				terrestrialPrefSymbolLengthLimit
					FloatingPoint,
				terrestrialPrefPowerMin
					FloatingPoint,
				terrestrialPrefPowerMax
					FloatingPoint,
				terrestrialPrefENDBER
					FloatingPoint,
				terrestrialPrefENDIdeal 
					FloatingPoint,
				terrestrialPrefENDMax
					FloatingPoint,
				terrestrialPrefENFIdeal 
					FloatingPoint,
				terrestrialPrefENFMax
					FloatingPoint,
				terrestrialPrefENDLPIdeal 
					FloatingPoint,
				terrestrialPrefENDLPMax
					FloatingPoint,
				terrestrialPrefENFLPIdeal 
					FloatingPoint,
				terrestrialPrefENFLPMax
					FloatingPoint,
				terrestrialPrefLinearityMin
					FloatingPoint,
				terrestrialPrefBERViterbiMax
					FloatingPoint,
				terrestrialPrefBERViterbiLPMax
					FloatingPoint,
				terrestrialPrefBERRSMax
					FloatingPoint,
				terrestrialPrefBERRSLPMax
					FloatingPoint,
				terrestrialPrefMerTMin
					FloatingPoint,
				terrestrialPrefSteMeanMax
					FloatingPoint,
				terrestrialPrefSteDeviationMax
					FloatingPoint,
				terrestrialPrefCsMin
					FloatingPoint,
				terrestrialPrefAiMax
					FloatingPoint,
				terrestrialPrefQeMax
					FloatingPoint,
				terrestrialPrefPjMax
					FloatingPoint,
				terrestrialPrefMIPTimingLimit
					FloatingPoint,
				terrestrialPrefMIPDeviationMax
					FloatingPoint,
				terrestrialPrefSEPUATMode
					UATMode,
				terrestrialPrefSEPN
					Unsigned32,
				terrestrialPrefSEPT
					FloatingPoint,
				terrestrialPrefSEPM
					Unsigned32,
				terrestrialPrefSEPTI
					FloatingPoint,
				terrestrialPrefSEPEBPerCent
					FloatingPoint,
				terrestrialPrefSEPMeasurementInterval
					FloatingPoint
			 }

		terrestrialPrefInputNumber OBJECT-TYPE
			SYNTAX InputNumber
			MAX-ACCESS not-accessible
			STATUS current
			DESCRIPTION
				"Transport Stream input to which the preferences apply"
			::= { terrestrialPreferencesEntry 1 }
		
		terrestrialPrefCentreFrequency OBJECT-TYPE
			SYNTAX FloatingPoint
			UNITS "MHz"
			MAX-ACCESS read-write
			STATUS current
			DESCRIPTION
				"This is the centre frequency to which the measuring
				equipment is tuned for making terrestrial measurements.
				This frequency is the actual input frequency to the
				measuring equipment, which may be at an intermediate
				frequency (IF) rather than the final RF."
			::= { terrestrialPreferencesEntry 2 }
		
		terrestrialPrefBandwidth OBJECT-TYPE
			SYNTAX FloatingPoint
			UNITS "MHz"
			MAX-ACCESS read-write
			STATUS current
			DESCRIPTION
				"The instrument is set to expect a DVB-T transmission
				adapted for this bandwidth. Normal values will be
				6.0MHz, 7.0MHz or 8.0MHz."
			::= { terrestrialPreferencesEntry 3 }
		
		terrestrialPrefModulation OBJECT-TYPE
			SYNTAX Modulation
			MAX-ACCESS read-write
			STATUS current
			DESCRIPTION
				"This is the modulation which the measuring equipment
				expects to see and against which it makes modulation
				measurements. This applies to terrestrial measurements."
			REFERENCE
				"EN 300 744 section 4.3.5"
			::= { terrestrialPreferencesEntry 4 }
		
		terrestrialPrefTransmissionMode OBJECT-TYPE
			SYNTAX TerrestrialTransmissionMode
			MAX-ACCESS read-write
			STATUS current
			DESCRIPTION
				"The instrument is set to expect a transmission in
				either 2k mode or 8k mode as set by this object."
			::= { terrestrialPreferencesEntry 5 }
		
		terrestrialPrefGuardInterval OBJECT-TYPE
			SYNTAX GuardInterval
			MAX-ACCESS read-write
			STATUS current
			DESCRIPTION
				"The instrument is set to expect a transmission using
				the guard interval specified by this object."
			::= { terrestrialPreferencesEntry 6 }
		
		terrestrialPrefHierarchical OBJECT-TYPE
			SYNTAX Hierarchy
			MAX-ACCESS read-write
			STATUS current
			DESCRIPTION
				"The instrument is set according to the value of
				this object to expect a transmission which is
				either non-hierachical or hierarchical using the
				specified alpha value."
			::= { terrestrialPreferencesEntry 7 }
		
		terrestrialPrefCentreFreqExpected OBJECT-TYPE
			SYNTAX FloatingPoint
			UNITS "Hz"
			MAX-ACCESS read-write
			STATUS current
			DESCRIPTION
				"This is the expected value for the centre frequency
				as measured by rfAccuracyValue."
			REFERENCE
				"TR 101 290 section 9.1.1"
			::= { terrestrialPreferencesEntry 8 }
		
		terrestrialPrefCentreFreqLimit OBJECT-TYPE
			SYNTAX FloatingPoint
			UNITS "Hz"
			MAX-ACCESS read-write
			STATUS current
			DESCRIPTION
				"This is the permitted deviation for the centre frequency
				as measured by rfAccuracyValue.  If rfAccuracyValue is
				outside the range:
				
				[terrestrialPrefCentreFreqExpected - terrestrialPrefCentreFreqLimit ..
				 terrestrialPrefCentreFreqExpected + terrestrialPrefCentreFreqLimit]
				
				an error will be indicated."
			REFERENCE
				"TR 101 290 section 9.1.1"
			::= { terrestrialPreferencesEntry 9 }
		
		terrestrialPrefChannelWidthLimit OBJECT-TYPE
			SYNTAX FloatingPoint
			UNITS "Hz"
			MAX-ACCESS read-write
			STATUS current
			DESCRIPTION
				"This is the permitted deviation for the channel width
				as measured by rfChannelWidthValue. The nominal value
				of the channel width has a fixed value which depends
				on the bandwidth (as set by terrestrialPrefBandwidth).
				If rfChannelWidthValue is outside the range
				
				[nominalWidth - terrestrialPrefChannelWidthLimit ..
				 nominalWidth + terrestrialPrefChannelWidthLimit]
				
				an error will be indicated."
			REFERENCE
				"TR 101 290 section 9.1.2"
			::= { terrestrialPreferencesEntry 10 }
		
		terrestrialPrefSymbolLengthLimit OBJECT-TYPE
			SYNTAX FloatingPoint
			UNITS "s"
			MAX-ACCESS read-write
			STATUS current
			DESCRIPTION
				"This is the permitted deviation for the symbol length
				as measured by symbolLengthValue. The nominal value of
				the symbol length has a fixed value which depends on
				the bandwidth, the mode and the guard interval (as set
				by terrestrialPrefBandwidth, terrestrialPrefTransmissionMode
				and terrestrialPrefGuardInterval respectively).
				
				If symbolLengthValue is outside the range
				
				[nominalLength - terrestrialPrefSymbolLengthLimit ..
				 nominalLength + terrestrialPrefSymbolLengthLimit]
				
				an error will be indicated."
			REFERENCE
				"TR 101 290 section 9.1.3
				EN 300 744 section 4.4 and Annex E"
			::= { terrestrialPreferencesEntry 11 }
		
		terrestrialPrefPowerMin OBJECT-TYPE
			SYNTAX FloatingPoint
			UNITS "dBm"
			MAX-ACCESS read-write
			STATUS current
			DESCRIPTION
				"If the power measured by rfIfPowerValue is less
				than this value, the associated test fails."
			REFERENCE
				"TR 101 290 section 9.5"
			::= { terrestrialPreferencesEntry 12 }
		
		terrestrialPrefPowerMax OBJECT-TYPE
			SYNTAX FloatingPoint
			UNITS "dBm"
			MAX-ACCESS read-write
			STATUS current
			DESCRIPTION
				"If the power measured by rfIfPowerValue is greater
				than this value, the associated test fails."
			REFERENCE
				"TR 101 290 section 9.5"
			::= { terrestrialPreferencesEntry 13 }
		
		terrestrialPrefENDBER OBJECT-TYPE
			SYNTAX FloatingPoint
			MAX-ACCESS read-write
			STATUS current
			DESCRIPTION
				"BER value which is to be used for the END and ENF
				measurements."
			REFERENCE
				"TR 101 290 section 9.9"
			DEFVAL { "2E-04" }
			::= { terrestrialPreferencesEntry 14 }
		
		terrestrialPrefENDIdeal  OBJECT-TYPE
			SYNTAX FloatingPoint
			UNITS "dB"
			MAX-ACCESS read-write
			STATUS current
			DESCRIPTION
				"This is the 'ideal' value of C/N for measurement of
				END on the whole or high priority stream. It is used
				in the measurement of eNDTValue."
			REFERENCE
				"TR 101 290 section 9.9"
			::= { terrestrialPreferencesEntry 15 }
		
		terrestrialPrefENDMax OBJECT-TYPE
			SYNTAX FloatingPoint
			UNITS "dB"
			MAX-ACCESS read-write
			STATUS current
			DESCRIPTION
				"If the measured value of eNDTValue exceeds this,
				the associated test fails."
			REFERENCE
				"TR 101 290 section 9.9"
			::= { terrestrialPreferencesEntry 16 }
		
		terrestrialPrefENFIdeal  OBJECT-TYPE
			SYNTAX FloatingPoint
			UNITS "dB"
			MAX-ACCESS read-write
			STATUS current
			DESCRIPTION
				"This is the 'ideal' value of C/N for measurement of ENF
				on the whole or high priority stream. It is used in the
				measurement of eNFTValue."
			REFERENCE
				"TR 101 290 section 9.9.1"
			::= { terrestrialPreferencesEntry 17 }
		
		terrestrialPrefENFMax OBJECT-TYPE
			SYNTAX FloatingPoint
			MAX-ACCESS read-write
			STATUS current
			DESCRIPTION
				"If the measured value of eNFTValue is exceeds this value,
				the associated test fails."
			REFERENCE
				"TR 101 290 section 9.9.1"
			::= { terrestrialPreferencesEntry 18 }
		
		terrestrialPrefENDLPIdeal  OBJECT-TYPE
			SYNTAX FloatingPoint
			UNITS "dB"
			MAX-ACCESS read-write
			STATUS current
			DESCRIPTION
				"This is the 'ideal' value of C/N for measurement of END
				on the low priority stream. It is used in the measurement
				of eNDTLPValue."
			REFERENCE
				"TR 101 290 section 9.9"
			::= { terrestrialPreferencesEntry 19 }
		
		terrestrialPrefENDLPMax OBJECT-TYPE
			SYNTAX FloatingPoint
			UNITS "dB"
			MAX-ACCESS read-write
			STATUS current
			DESCRIPTION
				"If the measured value of eNDTLPValue exceeds this,
				the associated test fails."
			REFERENCE
				"TR 101 290 section 9.9"
			::= { terrestrialPreferencesEntry 20 }
		
		terrestrialPrefENFLPIdeal  OBJECT-TYPE
			SYNTAX FloatingPoint
			UNITS "dB"
			MAX-ACCESS read-write
			STATUS current
			DESCRIPTION
				"This is the 'ideal' value of C/N for measurement of ENF
				on the low priority stream. It is used in the measurement
				of eNFTLPValue."
			REFERENCE
				"TR 101 290 section 9.9.1"
			::= { terrestrialPreferencesEntry 21 }
		
		terrestrialPrefENFLPMax OBJECT-TYPE
			SYNTAX FloatingPoint
			UNITS "dB"
			MAX-ACCESS read-write
			STATUS current
			DESCRIPTION
				"If the measured value of eNFTLPValue exeeds this value,
				the associated test fails."
			REFERENCE
				"TR 101 290 section 9.9.1"
			::= { terrestrialPreferencesEntry 22 }
		
		terrestrialPrefLinearityMin OBJECT-TYPE
			SYNTAX FloatingPoint
			UNITS "dB"
			MAX-ACCESS read-write
			STATUS current
			DESCRIPTION
				"If the shoulder attenuation as measured by linearityValue is
				less than this value, an error is indicated."
			REFERENCE
				"TR 101 290 section 9.10"
			::= { terrestrialPreferencesEntry 23 }
		
		terrestrialPrefBERViterbiMax OBJECT-TYPE
			SYNTAX FloatingPoint
			MAX-ACCESS read-write
			STATUS current
			DESCRIPTION
				"If the BER measured by berViterbiTValue exceeds this value,
				an error is indicated."
			REFERENCE
				"TR 101 290 section 9.15"
			::= { terrestrialPreferencesEntry 24 }
		
		terrestrialPrefBERViterbiLPMax OBJECT-TYPE
			SYNTAX FloatingPoint
			MAX-ACCESS read-write
			STATUS current
			DESCRIPTION
				"If the BER measured by berViterbiTLPValue exceeds this value,
				an error is indicated."
			REFERENCE
				"TR 101 290 section 9.15"
			::= { terrestrialPreferencesEntry 25 }
		
		terrestrialPrefBERRSMax OBJECT-TYPE
			SYNTAX FloatingPoint
			MAX-ACCESS read-write
			STATUS current
			DESCRIPTION
				"If the BER measured by berRSValue exceeds this value,
				an error is indicated."
			REFERENCE
				"TR 101 290 section 9.16"
			::= { terrestrialPreferencesEntry 26 }
		
		terrestrialPrefBERRSLPMax OBJECT-TYPE
			SYNTAX FloatingPoint
			MAX-ACCESS read-write
			STATUS current
			DESCRIPTION
				"If the BER measured by berRSLPValue exceeds this value,
				an error is indicated."
			REFERENCE
				"TR 101 290 section 9.16"
			::= { terrestrialPreferencesEntry 27 }
		
		terrestrialPrefMerTMin OBJECT-TYPE
			SYNTAX FloatingPoint
			MAX-ACCESS read-write
			STATUS current
			DESCRIPTION
				"If merTValue is less than this value, the associated
				test fails."
			REFERENCE
				"TR 101 290 section 9.18.2"
			::= { terrestrialPreferencesEntry 28 }
		
		terrestrialPrefSteMeanMax OBJECT-TYPE
			SYNTAX FloatingPoint
			UNITS "dB"
			MAX-ACCESS read-write
			STATUS current
			DESCRIPTION
				"If steMeanTValue exceeds this value, the associated
				test fails."
			REFERENCE
				"TR 101 290 section 9.18.3"
			::= { terrestrialPreferencesEntry 29 }
		
		terrestrialPrefSteDeviationMax OBJECT-TYPE
			SYNTAX FloatingPoint
			UNITS "dB"
			MAX-ACCESS read-write
			STATUS current
			DESCRIPTION
				"If steDeviationTValue exceeds this value, the associated
				test fails."
			REFERENCE
				"TR 101 290 section 9.18.3"
			::= { terrestrialPreferencesEntry 30 }
		
		terrestrialPrefCsMin OBJECT-TYPE
			SYNTAX FloatingPoint
			UNITS "dB"
			MAX-ACCESS read-write
			STATUS current
			DESCRIPTION
				"If csTValue is less than this value, the associated
				test fails"
			REFERENCE
				"TR 101 290 section 9.18.4"
			::= { terrestrialPreferencesEntry 31 }
		
		terrestrialPrefAiMax OBJECT-TYPE
			SYNTAX FloatingPoint
			UNITS "dB"
			MAX-ACCESS read-write
			STATUS current
			DESCRIPTION
				"If aiTValue exceeds this value, the associated
				test fails."
			REFERENCE
				"TR 101 290 section 9.18.5"
			::= { terrestrialPreferencesEntry 32 }
		
		terrestrialPrefQeMax OBJECT-TYPE
			SYNTAX FloatingPoint
			UNITS "dB"
			MAX-ACCESS read-write
			STATUS current
			DESCRIPTION
				"If qeTValue exceeds this value, the associated test fails."
			REFERENCE
				"TR 101 290 section 9.18.6"
			::= { terrestrialPreferencesEntry 33 }
		
		terrestrialPrefPjMax OBJECT-TYPE
			SYNTAX FloatingPoint
			UNITS "dB"
			MAX-ACCESS read-write
			STATUS current
			DESCRIPTION
				"If pjTValue exceeds this value, the associated test fails."
			REFERENCE
				"TR 101 290 section 9.18.7"
			::= { terrestrialPreferencesEntry 34 }
		
		terrestrialPrefMIPTimingLimit OBJECT-TYPE
			SYNTAX FloatingPoint
			UNITS "second"
			MAX-ACCESS read-write
			STATUS current
			DESCRIPTION
				"This preference affects the MIP_timing_error test. If
				the calculated value of nT differs from an integral number
				of seconds by more than terrestrialPrefMIPTimingLimit then
				an error is indicated."
			REFERENCE
				"TR 101 290 section 9.20.1"
			::= { terrestrialPreferencesEntry 35 }
		
		terrestrialPrefMIPDeviationMax OBJECT-TYPE
			SYNTAX FloatingPoint
			UNITS "bit/s"
			MAX-ACCESS read-write
			STATUS current
			DESCRIPTION
				"This preference affects the MIP_ts_rate_error test. It
				is the value of Max_deviation in the inequality given
				in TR 101 290 as the condition for an error indication."
			REFERENCE
				"TR 101 290 section 9.20.6"
			::= { terrestrialPreferencesEntry 36 }
		
		terrestrialPrefSEPUATMode OBJECT-TYPE
			SYNTAX UATMode
			MAX-ACCESS read-write
			STATUS current
			DESCRIPTION
				"Determines whether the 'N consecutive' or 'rolling window'
				mode of determining the start of a period of Unavailable
				Time (UAT) is used. If the 'N consecutive' mode is selected,
				the 'M' and 'T' preference parameters are ignored. Likewise,
				if the 'rolling window' mode is selected, the 'N' preference
				parameter is ignored."
			REFERENCE
				"TR 101 290 section 9.21"
			::= { terrestrialPreferencesEntry 37 }
		
		terrestrialPrefSEPN OBJECT-TYPE
			SYNTAX Unsigned32
			MAX-ACCESS read-write
			STATUS current
			DESCRIPTION
				"The N value used to identify the start and end of a
				period of unavailable time (UAT)."
			REFERENCE
				"TR 101 290 section 9.21"
			::= { terrestrialPreferencesEntry 38 }
		
		terrestrialPrefSEPT OBJECT-TYPE
			SYNTAX FloatingPoint
			UNITS "second"
			MAX-ACCESS read-write
			STATUS current
			DESCRIPTION
				"The T value used to identify the start and end of a
				period of unavailable time (UAT)."
			REFERENCE
				"TR 101 290 section 9.21"
			::= { terrestrialPreferencesEntry 39 }
		
		terrestrialPrefSEPM OBJECT-TYPE
			SYNTAX Unsigned32
			MAX-ACCESS read-write
			STATUS current
			DESCRIPTION
				"The M value used to identify the start and end of a
				period of unavailable time (UAT)."
			REFERENCE
				"TR 101 290 section 9.21"
			::= { terrestrialPreferencesEntry 40 }
		
		terrestrialPrefSEPTI OBJECT-TYPE
			SYNTAX FloatingPoint
			UNITS "second"
			MAX-ACCESS read-write
			STATUS current
			DESCRIPTION
				"Each Time Interval of this length is assessed as to
				whether it is an Errored Time Interval or a Severely
				Errored Time Interval."
			REFERENCE
				"TR 101 290 section 9.21"
			::= { terrestrialPreferencesEntry 41 }
		
		terrestrialPrefSEPEBPerCent OBJECT-TYPE
			SYNTAX FloatingPoint
			MAX-ACCESS read-write
			STATUS current
			DESCRIPTION
				"If more than this percentage of blocks within a Time
				Interval is an Errored Block, the Time Interval is a
				Severely Errored Time Interval (SETI). Example values
				are: '1.53', '10', '0.33'."
			REFERENCE
				"TR 101 290 section 9.21"
			::= { terrestrialPreferencesEntry 42 }
		
		terrestrialPrefSEPMeasurementInterval OBJECT-TYPE
			SYNTAX FloatingPoint
			UNITS "second"
			MAX-ACCESS read-write
			STATUS current
			DESCRIPTION
				"The Measurement Interval (MI) over which the ESR/ETIR
				and SESR/SETIR are calculated."
			REFERENCE
				"TR 101 290 section 6.1"
			::= { terrestrialPreferencesEntry 43 }
		
		tr101290Conformance OBJECT IDENTIFIER ::= { tr101290 3 }
		
		tr101290Compliances OBJECT IDENTIFIER ::= { tr101290Conformance 1 }
		
		complianceTransportStream MODULE-COMPLIANCE
			STATUS current
			DESCRIPTION
				"Compliance for Transport Stream monitor devices"
			MODULE -- this module
				MANDATORY-GROUPS { groupControl, groupCapability, groupTransportStream, groupTrapControl, groupTraps
					 }
			::= { tr101290Compliances 1 }
		
		complianceCable MODULE-COMPLIANCE
			STATUS current
			DESCRIPTION
				"Compliance for Cable RF measurement devices"
			MODULE -- this module
				MANDATORY-GROUPS { groupControl, groupTrapControl, groupTraps, groupCapability, groupCable
					 }
			::= { tr101290Compliances 2 }
		
		complianceSatellite MODULE-COMPLIANCE
			STATUS current
			DESCRIPTION
				"Compliance for Satellite RF measurement devices"
			MODULE -- this module
				MANDATORY-GROUPS { groupControl, groupTrapControl, groupTraps, groupCapability, groupSatellite
					 }
			::= { tr101290Compliances 3 }
		
		complianceTerrestrial MODULE-COMPLIANCE
			STATUS current
			DESCRIPTION
				"Compliance for Terrestrial RF measurement devices"
			MODULE -- this module
				MANDATORY-GROUPS { groupControl, groupTrapControl, groupTraps, groupCapability, groupTerrestrial
					 }
			::= { tr101290Compliances 4 }
		
		tr101290ObjectGroups OBJECT IDENTIFIER ::= { tr101290Conformance 2 }
		
		groupControl OBJECT-GROUP
			OBJECTS { controlNow, controlEventPersistence, rfSystemDelivery, controlSynchronizedTime }
			STATUS current
			DESCRIPTION
				"Contains all the objects from the tr101290Control
				branch of the MIB"
			::= { tr101290ObjectGroups 1 }
		
		groupTrapControl OBJECT-GROUP
			OBJECTS { trapControlOID, trapControlGenerationTime, trapControlMeasurementValue, trapControlRateStatus, trapControlPeriod , 
				trapControlFailureSummary, trapInput }
			STATUS current
			DESCRIPTION
				"Contains all the normal objects from the tr101290Trap
				branch of the MIB"
			::= { tr101290ObjectGroups 2 }
		
		groupTraps NOTIFICATION-GROUP
			NOTIFICATIONS { testFailTrap, measurementFailTrap, measurementUnknownTrap }
			STATUS current
			DESCRIPTION
				"Contains all the traps/notifications from the MIB."
			::= { tr101290ObjectGroups 3 }
		
		groupCapability OBJECT-GROUP
			OBJECTS { capabilityMIBRevision, capabilityTSGroup, capabilityTSAvailability, capabilityTSPollInterval, capabilityCableSatGroup, 
				capabilityCableSatAvailability, capabilityCableSatPollInterval, capabilityCableGroup, capabilityCableAvailability, capabilityCablePollInterval, 
				capabilitySatelliteGroup, capabilitySatelliteAvailability, capabilitySatellitePollInterval, capabilityTerrestrialGroup, capabilityTerrestrialAvailability, 
				capabilityTerrestrialPollInterval }
			STATUS current
			DESCRIPTION
				"Contains all objects from the tr101290Capability
				branch of the MIB"
			::= { tr101290ObjectGroups 4 }
		
		groupTransportStream OBJECT-GROUP
			OBJECTS { tsTestsSummaryState, tsTestsSummaryEnable, tsTestsSummaryCounter, tsTestsSummaryCounterDiscontinuity, tsTestsSummaryCounterReset, 
				tsTestsSummaryLatestError, tsTestsSummaryActiveTime, tsTestsPIDRowStatus, tsTestsPIDState, tsTestsPIDEnable, 
				tsTestsPIDCounter, tsTestsPIDCounterDiscontinuity, tsTestsPIDCounterReset, tsTestsPIDLatestError, tsTestsPIDActiveTime, 
				tsTestsPrefTransitionDuration, tsTestsPrefPATSectionIntervalMax, tsTestsPrefPMTSectionIntervalMax, tsTestsPrefReferredIntervalMax, tsTestsPrefPCRIntervalMax, 
				tsTestsPrefPCRDiscontinuityMax, tsTestsPrefPCRInaccuracyMax, tsTestsPrefPTSIntervalMax, tsTestsPrefNITActualIntervalMax, tsTestsPrefNITActualIntervalMin, 
				tsTestsPrefNITOtherIntervalMax, tsTestsPrefSIGapMin, tsTestsPrefNITTableIntervalMax, tsTestsPrefBATTableIntervalMax, tsTestsPrefSDTActualTableIntervalMax, 
				tsTestsPrefSDTOtherTableIntervalMax, tsTestsPrefEITPFActualTableIntervalMax, tsTestsPrefEITPFOtherTableIntervalMax, tsTestsPrefEITSActualNearTableIntervalMax, tsTestsPrefEITSActualFarTableIntervalMax, 
				tsTestsPrefEITSOtherNearTableIntervalMax, tsTestsPrefEITSOtherFarTableIntervalMax, tsTestsPrefTxTTableIntervalMax, tsTestsPrefSDTActualIntervalMax, tsTestsPrefSDTActualIntervalMin, 
				tsTestsPrefSDTOtherIntervalMax, tsTestsPrefEITActualIntervalMax, tsTestsPrefEITActualIntervalMin, tsTestsPrefEITOtherIntervalMax, tsTestsPrefRSTIntervalMin, 
				tsTestsPrefTDTIntervalMax, tsTestsPrefTDTIntervalMin, tsTestsPrefPIDRowStatus, tsTestsPrefPIDReferredIntervalMax, tsPcrMeasurementRowStatus, 
				tsPcrMeasurementState, tsPcrMeasurementEnable, tsPcrMeasurementCounter, tsPcrMeasurementCounterDiscontinuity, tsPcrMeasurementCounterReset, 
				tsPcrMeasurementLatestError, tsPcrMeasurementActiveTime, tsPcrMeasurementMeasurementState, tsPcrMeasurementValue, tsTransportStreamBitRateState, 
				tsTransportStreamBitRateEnable, tsTransportStreamBitRateCounter, tsTransportStreamBitRateCounterDiscontinuity, tsTransportStreamBitRateCounterReset, tsTransportStreamBitRateLatestError, 
				tsTransportStreamBitRateActiveTime, tsTransportStreamBitRateMeasurementState, tsTransportStreamBitRateValue, tsTransportStreamBitRateNomenclature, tsServiceBitRateRowStatus, 
				tsServiceBitRateState, tsServiceBitRateEnable, tsServiceBitRateCounter, tsServiceBitRateCounterDiscontinuity, tsServiceBitRateCounterReset, 
				tsServiceBitRateLatestError, tsServiceBitRateActiveTime, tsServiceBitRateMeasurementState, tsServiceBitRateValue, tsServiceBitRateNomenclature, 
				tsPIDBitRateRowStatus, tsPIDBitRateState, tsPIDBitRateEnable, tsPIDBitRateCounter, tsPIDBitRateCounterDiscontinuity, 
				tsPIDBitRateCounterReset, tsPIDBitRateLatestError, tsPIDBitRateActiveTime, tsPIDBitRateMeasurementState, tsPIDBitRateValue, 
				tsPIDBitRateNomenclature, tsConsistencyState, tsConsistencyEnable, tsConsistencyCounter, tsConsistencyCounterDiscontinuity, 
				tsConsistencyCounterReset, tsConsistencyLatestError, tsConsistencyActiveTime, tsMeasurePrefPCRDemarcationFrequency, tsMeasurePrefPCRFOMax, 
				tsMeasurePrefPCRDRMax, tsMeasurePrefPCROJMax, tsMeasurePrefTSBitRateTau, tsMeasurePrefTSBitRateN, tsMeasurePrefTSBitRateElement, 
				tsMeasurePrefTSBitRateMin, tsMeasurePrefTSBitRateMax, tsMeasurePrefAllServiceBitRateTau, tsMeasurePrefAllServiceBitRateN, tsMeasurePrefAllServiceBitRateElement, 
				tsMeasurePrefAllPIDBitRateTau, tsMeasurePrefAllPIDBitRateN, tsMeasurePrefAllPIDBitRateElement, tsMeasurePrefExpectedTSID, tsMeasurePrefServiceRowStatus, 
				tsMeasurePrefServiceBitRateTau, tsMeasurePrefServiceBitRateN, tsMeasurePrefServiceBitRateElement, tsMeasurePrefServiceBitRateMin, tsMeasurePrefServiceBitRateMax, 
				tsMeasurePrefPIDRowStatus, tsMeasurePrefPIDBitRateTau, tsMeasurePrefPIDBitRateN, tsMeasurePrefPIDBitRateElement, tsMeasurePrefPIDBitRateMin, 
				tsMeasurePrefPIDBitRateMax, tsServicePerformanceState, tsServicePerformanceEnable, tsServicePerformanceCounter, tsServicePerformanceCounterDiscontinuity, 
				tsServicePerformanceCounterReset, tsServicePerformanceLatestError, tsServicePerformanceActiveTime, tsServicePerformanceMeasurementState, tsServicePerformanceError, 
				tsServicePerformanceErrorRatio, tsSPPrefDeltaT, tsSPPrefEvaluationTime, tsSPPrefThreshold }
			STATUS current
			DESCRIPTION
				"Contains all objects relevant to Transport Stream measurement"
			::= { tr101290ObjectGroups 5 }
		
		groupCable OBJECT-GROUP
			OBJECTS { sysAvailabilityTestState, sysAvailabilityEnable, sysAvailabilityCounter, sysAvailabilityCounterDiscontinuity, sysAvailabilityCounterReset, 
				sysAvailabilityLatestError, sysAvailabilityActiveTime, sysAvailabilityMeasurementState, sysAvailabilityUnavailableTime, sysAvailabilityRatio, 
				sysAvailabilityInSETI, linkAvailabilityTestState, linkAvailabilityEnable, linkAvailabilityCounter, linkAvailabilityCounterDiscontinuity, 
				linkAvailabilityCounterReset, linkAvailabilityLatestError, linkAvailabilityActiveTime, linkAvailabilityMeasurementState, linkAvailabilityUnavailableTime, 
				linkAvailabilityRatio, linkAvailabilityInSUTI, berRSinServiceTestState, berRSinServiceEnable, berRSinServiceCounter, 
				berRSinServiceCounterDiscontinuity, berRSinServiceCounterReset, berRSinServiceLatestError, berRSinServiceActiveTime, berRSinServiceMeasurementState, 
				berRSinServiceValue, rfIFsignalPowerTestState, rfIFsignalPowerEnable, rfIFsignalPowerCounter, rfIFsignalPowerCounterDiscontinuity, 
				rfIFsignalPowerCounterReset, rfIFsignalPowerLatestError, rfIFsignalPowerActiveTime, rfIFsignalPowerMeasurementState, rfIFsignalPowerValue, 
				noisePowerTestState, noisePowerEnable, noisePowerCounter, noisePowerCounterDiscontinuity, noisePowerCounterReset, 
				noisePowerLatestError, noisePowerActiveTime, noisePowerMeasurementState, noisePowerValue, merCSTestState, 
				merCSEnable, merCSCounter, merCSCounterDiscontinuity, merCSCounterReset, merCSLatestError, 
				merCSActiveTime, merCSMeasurementState, merCSValue, steMeanCSTestState, steMeanCSEnable, 
				steMeanCSCounter, steMeanCSCounterDiscontinuity, steMeanCSCounterReset, steMeanCSLatestError, steMeanCSActiveTime, 
				steMeanCSMeasurementState, steMeanCSValue, steDeviationCSTestState, steDeviationCSEnable, steDeviationCSCounter, 
				steDeviationCSCounterDiscontinuity, steDeviationCSCounterReset, steDeviationCSLatestError, steDeviationCSActiveTime, steDeviationCSMeasurementState, 
				steDeviationCSValue, csCSTestState, csCSEnable, csCSCounter, csCSCounterDiscontinuity, 
				csCSCounterReset, csCSLatestError, csCSActiveTime, csCSMeasurementState, csCSValue, 
				aiCSTestState, aiCSEnable, aiCSCounter, aiCSCounterDiscontinuity, aiCSCounterReset, 
				aiCSLatestError, aiCSActiveTime, aiCSMeasurementState, aiCSValue, qeCSTestState, 
				qeCSEnable, qeCSCounter, qeCSCounterDiscontinuity, qeCSCounterReset, qeCSLatestError, 
				qeCSActiveTime, qeCSMeasurementState, qeCSValue, rteCSTestState, rteCSEnable, 
				rteCSCounter, rteCSCounterDiscontinuity, rteCSCounterReset, rteCSLatestError, rteCSActiveTime, 
				rteCSMeasurementState, rteCSValue, ciCSTestState, ciCSEnable, ciCSCounter, 
				ciCSCounterDiscontinuity, ciCSCounterReset, ciCSLatestError, ciCSActiveTime, ciCSMeasurementState, 
				ciCSValue, pjCSTestState, pjCSEnable, pjCSCounter, pjCSCounterDiscontinuity, 
				pjCSCounterReset, pjCSLatestError, pjCSActiveTime, pjCSMeasurementState, pjCSValue, 
				snrCSTestState, snrCSEnable, snrCSCounter, snrCSCounterDiscontinuity, snrCSCounterReset, 
				snrCSLatestError, snrCSActiveTime, snrCSMeasurementState, snrCSValue, cableSatPrefCentreFrequency, 
				cableSatPrefModulation, cableSatPrefSysAvailUATMode, cableSatPrefSysAvailN, cableSatPrefSysAvailT, cableSatPrefSysAvailM, 
				cableSatPrefSysAvailTI, cableSatPrefSysAvailEBPerCent, cableSatPrefSysAvailTotalTime, cableSatPrefLinkAvailUATMode, cableSatPrefLinkAvailN, 
				cableSatPrefLinkAvailT, cableSatPrefLinkAvailM, cableSatPrefLinkAvailTI, cableSatPrefLinkAvailUPPerCent, cableSatPrefLinkAvailTotalTime, 
				cableSatPrefBERMax, cableSatPrefSignalPowerMin, cableSatPrefSignalPowerMax, cableSatPrefNoisePowerMax, cableSatPrefMerCSMin, 
				cableSatPrefSteMeanCSMax, cableSatPrefSteDeviationCSMax, cableSatPrefCsCSMin, cableSatPrefAiCSMax, cableSatPrefQeCSMax, 
				cableSatPrefRteCSMax, cableSatPrefCiCSMin, cableSatPrefPjCSMax, cableSatPrefSnrCSMin, noiseMarginTestState, 
				noiseMarginEnable, noiseMarginCounter, noiseMarginCounterDiscontinuity, noiseMarginCounterReset, noiseMarginLatestError, 
				noiseMarginActiveTime, noiseMarginMeasurementState, noiseMarginValue, estNoiseMarginTestState, estNoiseMarginEnable, 
				estNoiseMarginCounter, estNoiseMarginCounterDiscontinuity, estNoiseMarginCounterReset, estNoiseMarginLatestError, estNoiseMarginActiveTime, 
				estNoiseMarginMeasurementState, estNoiseMarginValue, signQualMarTTestState, signQualMarTEnable, signQualMarTCounter, 
				signQualMarTCounterDiscontinuity, signQualMarTCounterReset, signQualMarTLatestError, signQualMarTActiveTime, eNDCTestState, 
				eNDCEnable, eNDCCounter, eNDCCounterDiscontinuity, eNDCCounterReset, eNDCLatestError, 
				eNDCActiveTime, eNDCMeasurementState, eNDCValue, outBandEmissTestState, outBandEmissEnable, 
				outBandEmissCounter, outBandEmissCounterDiscontinuity, outBandEmissCounterReset, outBandEmissLatestError, outBandEmissActiveTime, 
				cablePrefNoiseMarginMin, cablePrefEstNoiseMarginMin, cablePrefSignQualBoxSize, cablePrefSignQualPercentMax, cablePrefENDBER, 
				cablePrefENDCtoNSpecified, cablePrefENDIdeal , cablePrefENDMax }
			STATUS current
			DESCRIPTION
				"Contains all objects relevant to cable RF measurement"
			::= { tr101290ObjectGroups 6 }
		
		groupSatellite OBJECT-GROUP
			OBJECTS { sysAvailabilityTestState, sysAvailabilityEnable, sysAvailabilityCounter, sysAvailabilityCounterDiscontinuity, sysAvailabilityCounterReset, 
				sysAvailabilityLatestError, sysAvailabilityActiveTime, sysAvailabilityMeasurementState, sysAvailabilityUnavailableTime, sysAvailabilityRatio, 
				sysAvailabilityInSETI, linkAvailabilityTestState, linkAvailabilityEnable, linkAvailabilityCounter, linkAvailabilityCounterDiscontinuity, 
				linkAvailabilityCounterReset, linkAvailabilityLatestError, linkAvailabilityActiveTime, linkAvailabilityMeasurementState, linkAvailabilityUnavailableTime, 
				linkAvailabilityRatio, linkAvailabilityInSUTI, berRSinServiceTestState, berRSinServiceEnable, berRSinServiceCounter, 
				berRSinServiceCounterDiscontinuity, berRSinServiceCounterReset, berRSinServiceLatestError, berRSinServiceActiveTime, berRSinServiceMeasurementState, 
				berRSinServiceValue, rfIFsignalPowerTestState, rfIFsignalPowerEnable, rfIFsignalPowerCounter, rfIFsignalPowerCounterDiscontinuity, 
				rfIFsignalPowerCounterReset, rfIFsignalPowerLatestError, rfIFsignalPowerActiveTime, rfIFsignalPowerMeasurementState, rfIFsignalPowerValue, 
				noisePowerTestState, noisePowerEnable, noisePowerCounter, noisePowerCounterDiscontinuity, noisePowerCounterReset, 
				noisePowerLatestError, noisePowerActiveTime, noisePowerMeasurementState, noisePowerValue, merCSTestState, 
				merCSEnable, merCSCounter, merCSCounterDiscontinuity, merCSCounterReset, merCSLatestError, 
				merCSActiveTime, merCSMeasurementState, merCSValue, steMeanCSTestState, steMeanCSEnable, 
				steMeanCSCounter, steMeanCSCounterDiscontinuity, steMeanCSCounterReset, steMeanCSLatestError, steMeanCSActiveTime, 
				steMeanCSMeasurementState, steMeanCSValue, steDeviationCSTestState, steDeviationCSEnable, steDeviationCSCounter, 
				steDeviationCSCounterDiscontinuity, steDeviationCSCounterReset, steDeviationCSLatestError, steDeviationCSActiveTime, steDeviationCSMeasurementState, 
				steDeviationCSValue, csCSTestState, csCSEnable, csCSCounter, csCSCounterDiscontinuity, 
				csCSCounterReset, csCSLatestError, csCSActiveTime, csCSMeasurementState, csCSValue, 
				aiCSTestState, aiCSEnable, aiCSCounter, aiCSCounterDiscontinuity, aiCSCounterReset, 
				aiCSLatestError, aiCSActiveTime, aiCSMeasurementState, aiCSValue, qeCSTestState, 
				qeCSEnable, qeCSCounter, qeCSCounterDiscontinuity, qeCSCounterReset, qeCSLatestError, 
				qeCSActiveTime, qeCSMeasurementState, qeCSValue, rteCSTestState, rteCSEnable, 
				rteCSCounter, rteCSCounterDiscontinuity, rteCSCounterReset, rteCSLatestError, rteCSActiveTime, 
				rteCSMeasurementState, rteCSValue, ciCSTestState, ciCSEnable, ciCSCounter, 
				ciCSCounterDiscontinuity, ciCSCounterReset, ciCSLatestError, ciCSActiveTime, ciCSMeasurementState, 
				ciCSValue, pjCSTestState, pjCSEnable, pjCSCounter, pjCSCounterDiscontinuity, 
				pjCSCounterReset, pjCSLatestError, pjCSActiveTime, pjCSMeasurementState, pjCSValue, 
				snrCSTestState, snrCSEnable, snrCSCounter, snrCSCounterDiscontinuity, snrCSCounterReset, 
				snrCSLatestError, snrCSActiveTime, snrCSMeasurementState, snrCSValue, cableSatPrefCentreFrequency, 
				cableSatPrefModulation, cableSatPrefSysAvailUATMode, cableSatPrefSysAvailN, cableSatPrefSysAvailT, cableSatPrefSysAvailM, 
				cableSatPrefSysAvailTI, cableSatPrefSysAvailEBPerCent, cableSatPrefSysAvailTotalTime, cableSatPrefLinkAvailUATMode, cableSatPrefLinkAvailN, 
				cableSatPrefLinkAvailT, cableSatPrefLinkAvailM, cableSatPrefLinkAvailTI, cableSatPrefLinkAvailUPPerCent, cableSatPrefLinkAvailTotalTime, 
				cableSatPrefBERMax, cableSatPrefSignalPowerMin, cableSatPrefSignalPowerMax, cableSatPrefNoisePowerMax, cableSatPrefMerCSMin, 
				cableSatPrefSteMeanCSMax, cableSatPrefSteDeviationCSMax, cableSatPrefCsCSMin, cableSatPrefAiCSMax, cableSatPrefQeCSMax, 
				cableSatPrefRteCSMax, cableSatPrefCiCSMin, cableSatPrefPjCSMax, cableSatPrefSnrCSMin, berViterbiSTestState, 
				berViterbiSEnable, berViterbiSCounter, berViterbiSCounterDiscontinuity, berViterbiSCounterReset, berViterbiSLatestError, 
				berViterbiSActiveTime, berViterbiSMeasurementState, berViterbiSIValue, berViterbiSQValue, berViterbiSMeasurementMethod, 
				ifSpectrumTestState, ifSpectrumEnable, ifSpectrumCounter, ifSpectrumCounterDiscontinuity, ifSpectrumCounterReset, 
				ifSpectrumLatestError, ifSpectrumActiveTime, satellitePrefBERMax }
			STATUS current
			DESCRIPTION
				"Contains all objects relevent to satellite RF measurements"
			::= { tr101290ObjectGroups 7 }
		
		groupTerrestrial OBJECT-GROUP
			OBJECTS { rfAccuracyTestState, rfAccuracyEnable, rfAccuracyCounter, rfAccuracyCounterDiscontinuity, rfAccuracyCounterReset, 
				rfAccuracyLatestError, rfAccuracyActiveTime, rfAccuracyMeasurementState, rfAccuracyValue, rfChannelWidthTestState, 
				rfChannelWidthEnable, rfChannelWidthCounter, rfChannelWidthCounterDiscontinuity, rfChannelWidthCounterReset, rfChannelWidthLatestError, 
				rfChannelWidthActiveTime, rfChannelWidthMeasurementState, rfChannelWidthValue, symbolLengthTestState, symbolLengthEnable, 
				symbolLengthCounter, symbolLengthCounterDiscontinuity, symbolLengthCounterReset, symbolLengthLatestError, symbolLengthActiveTime, 
				symbolLengthMeasurementState, symbolLengthValue, rfIfPowerTestState, rfIfPowerEnable, rfIfPowerCounter, 
				rfIfPowerCounterDiscontinuity, rfIfPowerCounterReset, rfIfPowerLatestError, rfIfPowerActiveTime, rfIfPowerMeasurementState, 
				rfIfPowerValue, rfIfSpectrumTestState, rfIfSpectrumEnable, rfIfSpectrumCounter, rfIfSpectrumCounterDiscontinuity, 
				rfIfSpectrumCounterReset, rfIfSpectrumLatestError, rfIfSpectrumActiveTime, eNDTTestState, eNDTEnable, 
				eNDTCounter, eNDTCounterDiscontinuity, eNDTCounterReset, eNDTLatestError, eNDTActiveTime, 
				eNDTMeasurementState, eNDTValue, eNFTTestState, eNFTEnable, eNFTCounter, 
				eNFTCounterDiscontinuity, eNFTCounterReset, eNFTLatestError, eNFTActiveTime, eNFTMeasurementState, 
				eNFTValue, eNDTLPTestState, eNDTLPEnable, eNDTLPCounter, eNDTLPCounterDiscontinuity, 
				eNDTLPCounterReset, eNDTLPLatestError, eNDTLPActiveTime, eNDTLPMeasurementState, eNDTLPValue, 
				eNFTLPTestState, eNFTLPEnable, eNFTLPCounter, eNFTLPCounterDiscontinuity, eNFTLPCounterReset, 
				eNFTLPLatestError, eNFTLPActiveTime, eNFTLPMeasurementState, eNFTLPValue, linearityTestState, 
				linearityEnable, linearityCounter, linearityCounterDiscontinuity, linearityCounterReset, linearityLatestError, 
				linearityActiveTime, linearityMeasurementState, linearityValue, berViterbiTTestState, berViterbiTEnable, 
				berViterbiTCounter, berViterbiTCounterDiscontinuity, berViterbiTCounterReset, berViterbiTLatestError, berViterbiTActiveTime, 
				berViterbiTMeasurementState, berViterbiTValue, berViterbiTLPTestState, berViterbiTLPEnable, berViterbiTLPCounter, 
				berViterbiTLPCounterDiscontinuity, berViterbiTLPCounterReset, berViterbiTLPLatestError, berViterbiTLPActiveTime, berViterbiTLPMeasurementState, 
				berViterbiTLPValue, berRSTestState, berRSEnable, berRSCounter, berRSCounterDiscontinuity, 
				berRSCounterReset, berRSLatestError, berRSActiveTime, berRSMeasurementState, berRSValue, 
				berRSLPTestState, berRSLPEnable, berRSLPCounter, berRSLPCounterDiscontinuity, berRSLPCounterReset, 
				berRSLPLatestError, berRSLPActiveTime, berRSLPMeasurementState, berRSLPValue, merTTestState, 
				merTEnable, merTCounter, merTCounterDiscontinuity, merTCounterReset, merTLatestError, 
				merTActiveTime, merTMeasurementState, merTValue, steMeanTTestState, steMeanTEnable, 
				steMeanTCounter, steMeanTCounterDiscontinuity, steMeanTCounterReset, steMeanTLatestError, steMeanTActiveTime, 
				steMeanTMeasurementState, steMeanTValue, steDeviationTTestState, steDeviationTEnable, steDeviationTCounter, 
				steDeviationTCounterDiscontinuity, steDeviationTCounterReset, steDeviationTLatestError, steDeviationTActiveTime, steDeviationTMeasurementState, 
				steDeviationTValue, csTTestState, csTEnable, csTCounter, csTCounterDiscontinuity, 
				csTCounterReset, csTLatestError, csTActiveTime, csTMeasurementState, csTValue, 
				aiTTestState, aiTEnable, aiTCounter, aiTCounterDiscontinuity, aiTCounterReset, 
				aiTLatestError, aiTActiveTime, aiTMeasurementState, aiTValue, qeTTestState, 
				qeTEnable, qeTCounter, qeTCounterDiscontinuity, qeTCounterReset, qeTLatestError, 
				qeTActiveTime, qeTMeasurementState, qeTValue, pjTTestState, pjTEnable, 
				pjTCounter, pjTCounterDiscontinuity, pjTCounterReset, pjTLatestError, pjTActiveTime, 
				pjTMeasurementState, pjTValue, mipSyntaxState, mipSyntaxEnable, mipSyntaxCounter, 
				mipSyntaxCounterDiscontinuity, mipSyntaxCounterReset, mipSyntaxLatestError, mipSyntaxActiveTime, sepEtiTestState, 
				sepEtiEnable, sepEtiCounter, sepEtiCounterDiscontinuity, sepEtiCounterReset, sepEtiLatestError, 
				sepEtiActiveTime, sepEtiMeasurementState, sepEtiValue, sepSetiTestState, sepSetiEnable, 
				sepSetiCounter, sepSetiCounterDiscontinuity, sepSetiCounterReset, sepSetiLatestError, sepSetiActiveTime, 
				sepSetiMeasurementState, sepSetiValue, terrestrialPrefCentreFrequency, terrestrialPrefBandwidth, terrestrialPrefModulation, 
				terrestrialPrefTransmissionMode, terrestrialPrefGuardInterval, terrestrialPrefHierarchical, terrestrialPrefCentreFreqExpected, terrestrialPrefCentreFreqLimit, 
				terrestrialPrefChannelWidthLimit, terrestrialPrefSymbolLengthLimit, terrestrialPrefPowerMin, terrestrialPrefPowerMax, terrestrialPrefENDBER, 
				terrestrialPrefENDIdeal , terrestrialPrefENDMax, terrestrialPrefENFIdeal , terrestrialPrefENFMax, terrestrialPrefENDLPIdeal , 
				terrestrialPrefENDLPMax, terrestrialPrefENFLPIdeal , terrestrialPrefENFLPMax, terrestrialPrefLinearityMin, terrestrialPrefBERViterbiMax, 
				terrestrialPrefBERViterbiLPMax, terrestrialPrefBERRSMax, terrestrialPrefBERRSLPMax, terrestrialPrefMerTMin, terrestrialPrefSteMeanMax, 
				terrestrialPrefSteDeviationMax, terrestrialPrefCsMin, terrestrialPrefAiMax, terrestrialPrefQeMax, terrestrialPrefPjMax, 
				terrestrialPrefMIPTimingLimit, terrestrialPrefMIPDeviationMax, terrestrialPrefSEPUATMode, terrestrialPrefSEPN, terrestrialPrefSEPT, 
				terrestrialPrefSEPM, terrestrialPrefSEPTI, terrestrialPrefSEPEBPerCent, terrestrialPrefSEPMeasurementInterval }
			STATUS current
			DESCRIPTION
				"Contains all objects relevant to terrestrial RF measurements"
			::= { tr101290ObjectGroups 8 }
		
	
	END

--
-- DVB-MGTR101290-MIB.my
--
