--			Ascend mibtransaction MIB
--
--			Ascend Communications, Inc
--			1275 Harbor Bay Pkwy
--			Alameda, CA 94502
--			+1 510 769 6001
--			info@ascend.com
--
-- Copyright (c) 1993-1999 Ascend Communications, Inc.
-- All rights reserved.
--
-- Do not edit this file directly.
-- It is generated automatically by mibgen for use with
-- TAOS version 10.0.1 or newer.
--

ASCEND-MIBTRANSACTION-MIB DEFINITIONS ::= BEGIN

    IMPORTS

        configuration
            FROM ASCEND-MIB
	IpAddress
	    FROM RFC1155-SMI
	OBJECT-TYPE
	    FROM RFC-1212;

	-- If any of the MIB compilers have problems with the DisplayString
	-- or PhysAddress, uncomment the next two lines.

    DisplayString	::=	OCTET STRING
    -- PhysAddress	::=	OCTET STRING

    mibtransactionProfile  OBJECT IDENTIFIER ::= { configuration 131}

	-- The mibtransactionProfile table
	--
	-- This table contains parameters for the mibtransactionProfile profile
	--

    mibtransactionProfileTable	OBJECT-TYPE
	SYNTAX		SEQUENCE OF MibtransactionProfileEntry
	ACCESS		not-accessible
	STATUS		mandatory
	DESCRIPTION	"A list of mibtransactionProfile profile entries."
	::= { mibtransactionProfile 1 }

    mibtransactionProfileEntry	OBJECT-TYPE
	SYNTAX		MibtransactionProfileEntry
	ACCESS		not-accessible
	STATUS		mandatory
	DESCRIPTION	"A mibtransactionProfile entry containing objects that
			 maps to the parameters of mibtransactionProfile profile."
	INDEX		{ transactionProfile-Index-o }
	::= { mibtransactionProfileTable 1 }

    MibtransactionProfileEntry ::=
	SEQUENCE {
	    transactionProfile-Index-o
		INTEGER,
	    transactionProfile-SelectionTimeout
		INTEGER,
	    transactionProfile-DataAckTimeout
		INTEGER,
	    transactionProfile-KeepAliveTimeout
		INTEGER,
	    transactionProfile-QtpPort
		INTEGER,
	    transactionProfile-MetricMax
		INTEGER,
	    transactionProfile-NoConnAckIncrement
		INTEGER,
	    transactionProfile-CallRejectIncrement
		INTEGER,
	    transactionProfile-CallAckDecrement
		INTEGER,
	    transactionProfile-AvailableMetric
		INTEGER,
	    transactionProfile-PartlyCongestedMetric
		INTEGER,
	    transactionProfile-CongestedMetric
		INTEGER,
	    transactionProfile-ShutdownMetric
		INTEGER,
	    transactionProfile-NoFirstStatusMetric
		INTEGER,
	    transactionProfile-NoSecondStatusMetric
		INTEGER,
	    transactionProfile-MaxQtpPduSize
		INTEGER,
	    transactionProfile-Action-o
		INTEGER
	}

    transactionProfile-Index-o	OBJECT-TYPE
	SYNTAX	INTEGER
	ACCESS	read-only
	STATUS	mandatory
	DESCRIPTION	""
	::= { mibtransactionProfileEntry 1 }

    transactionProfile-SelectionTimeout	OBJECT-TYPE
	SYNTAX	INTEGER
	ACCESS	read-write
	STATUS	mandatory
	DESCRIPTION	"Transaction Server Selection Timeout in milliseconds"
	::= { mibtransactionProfileEntry 2 }

    transactionProfile-DataAckTimeout	OBJECT-TYPE
	SYNTAX	INTEGER
	ACCESS	read-write
	STATUS	mandatory
	DESCRIPTION	"Transaction Server Ack Data message Timeout in milliseconds"
	::= { mibtransactionProfileEntry 3 }

    transactionProfile-KeepAliveTimeout	OBJECT-TYPE
	SYNTAX	INTEGER
	ACCESS	read-write
	STATUS	mandatory
	DESCRIPTION	"Transaction Server Keep Alive Timeout in seconds"
	::= { mibtransactionProfileEntry 4 }

    transactionProfile-QtpPort	OBJECT-TYPE
	SYNTAX	INTEGER
	ACCESS	read-write
	STATUS	mandatory
	DESCRIPTION	"UDP Port number for QTP"
	::= { mibtransactionProfileEntry 5 }

    transactionProfile-MetricMax	OBJECT-TYPE
	SYNTAX	INTEGER
	ACCESS	read-write
	STATUS	mandatory
	DESCRIPTION	"Metric Maximum (threshold)"
	::= { mibtransactionProfileEntry 6 }

    transactionProfile-NoConnAckIncrement	OBJECT-TYPE
	SYNTAX	INTEGER
	ACCESS	read-write
	STATUS	mandatory
	DESCRIPTION	"No Reply to QTP Connect Request metric increment"
	::= { mibtransactionProfileEntry 7 }

    transactionProfile-CallRejectIncrement	OBJECT-TYPE
	SYNTAX	INTEGER
	ACCESS	read-write
	STATUS	mandatory
	DESCRIPTION	"QTP Call Reject metric increment"
	::= { mibtransactionProfileEntry 8 }

    transactionProfile-CallAckDecrement	OBJECT-TYPE
	SYNTAX	INTEGER
	ACCESS	read-write
	STATUS	mandatory
	DESCRIPTION	"QTP Call Ack metric decrement"
	::= { mibtransactionProfileEntry 9 }

    transactionProfile-AvailableMetric	OBJECT-TYPE
	SYNTAX	INTEGER
	ACCESS	read-write
	STATUS	mandatory
	DESCRIPTION	"QTP Status Report, Flow Control Attribute: Available metric"
	::= { mibtransactionProfileEntry 10 }

    transactionProfile-PartlyCongestedMetric	OBJECT-TYPE
	SYNTAX	INTEGER
	ACCESS	read-write
	STATUS	mandatory
	DESCRIPTION	"QTP Status Report, Flow Control Attribute: Partly congested metric"
	::= { mibtransactionProfileEntry 11 }

    transactionProfile-CongestedMetric	OBJECT-TYPE
	SYNTAX	INTEGER
	ACCESS	read-write
	STATUS	mandatory
	DESCRIPTION	"QTP Status Report, Flow Control Attribute: Congested metric"
	::= { mibtransactionProfileEntry 12 }

    transactionProfile-ShutdownMetric	OBJECT-TYPE
	SYNTAX	INTEGER
	ACCESS	read-write
	STATUS	mandatory
	DESCRIPTION	"QTP Status Report, Flow Control Attribute: Shutdown metric"
	::= { mibtransactionProfileEntry 13 }

    transactionProfile-NoFirstStatusMetric	OBJECT-TYPE
	SYNTAX	INTEGER
	ACCESS	read-write
	STATUS	mandatory
	DESCRIPTION	"No QTP Status Report, First Occurence metric"
	::= { mibtransactionProfileEntry 14 }

    transactionProfile-NoSecondStatusMetric	OBJECT-TYPE
	SYNTAX	INTEGER
	ACCESS	read-write
	STATUS	mandatory
	DESCRIPTION	"No QTP Status Report, Second Occurence metric"
	::= { mibtransactionProfileEntry 15 }

    transactionProfile-MaxQtpPduSize	OBJECT-TYPE
	SYNTAX	INTEGER
	ACCESS	read-write
	STATUS	mandatory
	DESCRIPTION	"Max QTP PDU size for data forwarding"
	::= { mibtransactionProfileEntry 16 }

    transactionProfile-Action-o	OBJECT-TYPE
	SYNTAX	INTEGER {
		    noAction (1),
		    createProfile (2),
		    deleteProfile (3)
		}
	ACCESS	read-write
	STATUS	mandatory
	DESCRIPTION	""
	::= { mibtransactionProfileEntry 17 }

END
