-- SNA Link Conversion MIB

CXSnaLinkConversionModule-MIB DEFINITIONS ::= BEGIN

--#CURRENT_VERSION 2

IMPORTS
    OBJECT-TYPE     FROM RFC-1212
    cxSnalc,SapIndex,Alias
		FROM CXProduct-SMI;



--  Service Access Point Configuration Table

--     The table defining all the parameters, status, control and statistics 
--     required to manipulate an SNA Link Conversion Module Service Access 
--     Point (SAP).

snalcMibLevel OBJECT-TYPE
	SYNTAX	INTEGER
	ACCESS	read-only
	STATUS	mandatory
	DESCRIPTION
"Used to determine current MIB module release supported
by the agent. Object is in decimal."
	DEFVAL { 0 }
	--#STARTING_VERSION 1
	::= { cxSnalc 9 }

snalcSapTable OBJECT-TYPE
    SYNTAX  SEQUENCE OF SnalcSapEntry
    ACCESS  not-accessible
    STATUS  mandatory
    DESCRIPTION
"This table contains configuration information for each SNA Link 
Conversion layer SAP (service access point)."
    ::= { cxSnalc 10 }


    snalcSapEntry OBJECT-TYPE
	SYNTAX  SnalcSapEntry
	ACCESS  not-accessible
	STATUS  mandatory
	DESCRIPTION
"Defines a row in the snalcSapTable. Each row contains the objects which 
define a service access point."
	INDEX { snalcSapNumber }
	::= { snalcSapTable 1 }


    SnalcSapEntry ::=
	SEQUENCE {
-- Parameters
	    snalcSapNumber                        SapIndex,
	    snalcSapRowStatus                     INTEGER,
	    snalcSapAlias                         Alias,
	    snalcSapCompanionAlias                Alias,
-- Status
	    snalcSapState                         INTEGER
	    }


    snalcSapNumber OBJECT-TYPE
	SYNTAX  SapIndex
	ACCESS  read-only
	STATUS  mandatory
	DESCRIPTION
"Identifies this SAP (service access point) with a numerical value which 
must be unique for each SNA Link Conversion SAP."
	::= { snalcSapEntry 1 }


    snalcSapRowStatus OBJECT-TYPE
	SYNTAX  INTEGER {
		    invalid         (1),
		    valid           (2)
		    }
	ACCESS  read-write
	STATUS  mandatory
	DESCRIPTION
"Determines the status of the objects in a table row.

Options:
invalid (1): Row is flagged, after next reset the values will be disabled 
and the row is deleted from the table 

valid (2): Values are enabled

Configuration Changed: administrative"
	::= { snalcSapEntry 2 }


    snalcSapAlias OBJECT-TYPE
	SYNTAX  Alias
	ACCESS  read-write
	STATUS  mandatory
	DESCRIPTION
"Identifies this service access point by a textual name. Names must be 
unique across all service access points at all layers.

Default Value: none

Range of Values: 1 -16 alphanumeric characters (first character must be a 
letter)

Configuration Changed: administrative"
	::= { snalcSapEntry 3 }


    snalcSapCompanionAlias OBJECT-TYPE
	SYNTAX  Alias
	ACCESS  read-write
	STATUS  mandatory
	DESCRIPTION
"Determines the sub-layer SAP (service access point) this SAP communicates 
with. This object contains the textual name of the sub-layer SAP. SDLC, 
LLC-2 (LLCIM), or QLLC SAP aliases are valid.

Default Value: none

Range of Values: 1 -16 alphanumeric characters (first character must be a 
letter)

Configuration Changed: administrative"
	::= { snalcSapEntry 4 }


    snalcSapState OBJECT-TYPE
	SYNTAX  INTEGER {
		    offLine         (1),
		    unbound         (2),
		    bound           (3)
		}
	ACCESS  read-only
	STATUS  mandatory
	DESCRIPTION
"Indicates the state of this SAP (service access point).

Options:
offLine (1): Indicates that the SAP is not configured.

unbound (2): Indicates that this SAP is configured but not yet bound to 
its companion SAP.

bound (3): Indicates that this SAP is bound to its companion SAP." 
	::= { snalcSapEntry 6 }


--  Cross-Connections Configuration Table
--
--    The table defining all the parameters, status, control and statistics 
--    required to manipulate SNA Link Conversion Module's cross-connections.
--    A cross-connection associates two link connections such that SNA traffic
--    flows from one connection to the other one.


snalcCrossConnectTable OBJECT-TYPE
    SYNTAX  SEQUENCE OF SnalcCrossConnectEntry
    ACCESS  not-accessible
    STATUS  mandatory
    DESCRIPTION
"This table contains configuration information for each SNA Link 
Conversion Module cross-connection. A cross-connection associates two link 
connections so that SNA traffic can flow from one connection to the 
other."
    ::= { cxSnalc 11 }


    snalcCrossConnectEntry OBJECT-TYPE
	SYNTAX  SnalcCrossConnectEntry
	ACCESS  not-accessible
	STATUS  mandatory
	DESCRIPTION
"The parameters for a particular SNA Link Conversion Module cross- 
connection. Up to 64 cross-connect rows may exist in the table."
	INDEX { snalcCrossConnectSrcSapNumber, 
	    snalcCrossConnectSrcLinkAddrIndex,
	    snalcCrossConnectDstSapNumber,
	    snalcCrossConnectDstLinkAddrIndex } 
	::= { snalcCrossConnectTable 1 }


    SnalcCrossConnectEntry ::=
	SEQUENCE {
-- Parameters
	    snalcCrossConnectSrcSapNumber         SapIndex,
	    snalcCrossConnectSrcLinkAddrIndex     INTEGER,                        
	    snalcCrossConnectDstSapNumber         SapIndex,
	    snalcCrossConnectDstLinkAddrIndex     INTEGER,
	    snalcCrossConnectRowStatus            INTEGER,
	    snalcCrossConnectPuId                 OCTET STRING,
	    snalcCrossConnectMaxRetries           INTEGER,
	    snalcCrossConnectConnectInterval      INTEGER,  
	    snalcCrossConnectSlowConnectThreshold INTEGER,
	    snalcCrossConnectSlowConnectInterval  INTEGER,
	    snalcCrossConnectWaitContactTimer     INTEGER,
	    snalcCrossConnectConnectMethod        INTEGER,
	    snalcCrossConnectAdminStatus          INTEGER,
-- Status
	    snalcCrossConnectSrcOperStatus        INTEGER,                        
	    snalcCrossConnectDstOperStatus        INTEGER,
-- More Configurations 
	    snalcCrossConnectXidTransparent       INTEGER,
	    snalcCrossConnectDataLinkType			INTEGER
	    }
    

    snalcCrossConnectSrcSapNumber OBJECT-TYPE
	SYNTAX  SapIndex
	ACCESS  read-only
	STATUS  mandatory
	DESCRIPTION
"Identifies the source link for a cross-connection. When cross- connecting 
hierarchical SNA devices, the source link is the side which is attached to 
the SNA control unit (secondary link station). 

Related Objects: snalcSapNumber"
	 ::= { snalcCrossConnectEntry 1 }


    snalcCrossConnectSrcLinkAddrIndex OBJECT-TYPE
	SYNTAX  INTEGER (1..255)
	ACCESS  read-only
	STATUS  mandatory
	DESCRIPTION
"Identifies the link level connection for the source-side of a cross- 
connection. Many link level connections can share the same source SAP 
(service access point). This number is used to uniquely identify each 
link. The value for this object depends on the type of link level service 
the source SAP (snalcCrossConnectSrcSapNumber) is associated with 
(snalcSapCompanionAlias).

When the source SAP is associated with the LLC-2 module, this object is 
set to the value of the corresponding llcimSapNumber (lower SAP). 

When the source SAP is associated with the SDLC module, this object is set 
to the value of the corresponding sdlcCuId object.

When the source SAP is associated with the QLLC module, this object is set 
to the value of the corresponding qllcDteIndex object.

Range of Values: 1 - 255"
	::= { snalcCrossConnectEntry 2 }


    snalcCrossConnectDstSapNumber OBJECT-TYPE
	SYNTAX  SapIndex
	ACCESS  read-only
	STATUS  mandatory
	DESCRIPTION
"Identifies the destination link for a cross-connection. When cross- 
connecting hierarchical SNA devices, the destination link is the side 
which is attached to the SNA host (primary link station)."
	 ::= { snalcCrossConnectEntry 3 }


    snalcCrossConnectDstLinkAddrIndex OBJECT-TYPE
	SYNTAX  INTEGER (1..255)
	ACCESS  read-only
	STATUS  mandatory
	DESCRIPTION
"Identifies the link level connection for the destination-side of a cross- 
connection. Many link level connections can share the same destination SAP 
(service access point). This number is used to uniquely identify each 
link. The value for this object depends on the type of link level service 
the source SAP (snalcCrossConnectSrcSapNumber) is associated with 
(snalcSapCompanionAlias).

When the destination SAP is associated with the LLC-2 module, this object 
is set to the value of the corresponding llcimSapNumber (lower SAP). 

When the destination SAP is associated with the SDLC module, this object 
is set to the value of the corresponding sdlcCuId object.

When the destination SAP is associated with the QLLC module, this object 
is set to the value of the corresponding qllcDteIndex object.

Range of Values: 1 - 255"
	::= { snalcCrossConnectEntry 4 }
    

    snalcCrossConnectRowStatus OBJECT-TYPE
	SYNTAX  INTEGER {
		    invalid         (1),
		    valid           (2)
		    }
	ACCESS  read-write
	STATUS  mandatory
	DESCRIPTION
"Determines the status of the objects in a table row.

Options:
invalid (1): Row is flagged, after next reset the values will be disabled 
and the row will be deleted from the table.

valid (2): Values are enabled.

Configuration Changed: administrative"
	::= { snalcCrossConnectEntry 5 }
    

    snalcCrossConnectPuId OBJECT-TYPE
	SYNTAX  OCTET STRING (SIZE(4))
	ACCESS  read-write
	STATUS  mandatory
	DESCRIPTION
"Determines the SNA PU identifier sent to the host in an XID. The PU 
identifier is composed of the block ID and node ID. This object applies 
only when the destination-side of a cross- connection is LLC-2 (IEEE 802.2 
LLC) and when snalcCrossConnectConnectMethod is set to 'local'.

Range of Values: (eight hexadecimal digits)

Default Value: 0

Configuration Changed: administrative and operative"
	DEFVAL { '00000000'h }
	::= { snalcCrossConnectEntry 6 }


    snalcCrossConnectMaxRetries OBJECT-TYPE
	SYNTAX  INTEGER (0..255)
	ACCESS  read-write
	STATUS  mandatory
	DESCRIPTION
"Determines the maximum number of attempts to establish this cross- 
connection before it is abandoned. If set to 255, SNA Link Conversion 
retries forever until successful.

Range of Values: 1 - 255 

Default Value: 255

Configuration Changed: administrative and operative"
	DEFVAL { 255 }
	::= { snalcCrossConnectEntry 7 }


snalcCrossConnectConnectInterval OBJECT-TYPE
	SYNTAX  INTEGER (1..65535)
	ACCESS  read-write
	STATUS  mandatory
	DESCRIPTION
"Determines the delay between attempts to establish this cross-connection 
when not in slow connect mode.

Range of Values: 1 - 65535 seconds

Default Value: 10 seconds

Related Objects: snalcCrossConnectSlowConnectThreshold

Configuration Changed: administrative and operative"
	DEFVAL{ 10 }
	::= { snalcCrossConnectEntry 8 }
                 
    
    snalcCrossConnectSlowConnectThreshold OBJECT-TYPE
	SYNTAX  INTEGER (0..254)
	ACCESS  read-write
	STATUS  mandatory
	DESCRIPTION
"Determines the number of attempts that are made to establish a cross- 
connection using the snalcCrossConnectConnectInterval . When the threshold 
defined by this object is reached, slow connect mode is initialized. In 
this mode, cross- connection attempts continue, but the interval between 
attempts is set by snalcCrossConnectSlowConnectInterval.

Range of Values: 0 - 254 seconds (0 disables slow connect mode)

Default Value: 0 (disabled)

Related Objects: snalcCrossConnectConnectInterval 
snalcCrossConnectSlowConnectInterval

Configuration Changed: administrative and operative"
	DEFVAL{ 0 }
	::= { snalcCrossConnectEntry 9 }
    

snalcCrossConnectSlowConnectInterval OBJECT-TYPE
	SYNTAX  INTEGER (1..65535)
	ACCESS  read-write
	STATUS  mandatory
	DESCRIPTION
"Determines the delay between attempts to establish a cross-connection 
when in slow connect mode.

Range of Values: 1 - 65535

Default Value: 60

Related Objects: snalcCrossConnectSlowConnectThreshold

Configuration Changed: administrative and operative"
	DEFVAL{ 60 }
	::= { snalcCrossConnectEntry 10 }


snalcCrossConnectWaitContactTimer OBJECT-TYPE
	SYNTAX  INTEGER (1..65535)
	ACCESS  read-write
	STATUS  mandatory
	DESCRIPTION
"Determines the amount of time to wait for a Set Mode or SNA XID frame 
from the remote station after the link has been established.

Range of Values: 1 - 65535 seconds

Default Value: 45 seconds

Configuration Changed: administrative and operative"
	DEFVAL{ 45 }
	::= { snalcCrossConnectEntry 11 }
  
    
    snalcCrossConnectConnectMethod OBJECT-TYPE
	SYNTAX  INTEGER {
		   local     (1),
		   endToEnd  (2)
		}
	ACCESS  read-write
	STATUS  mandatory
	DESCRIPTION
"Determines how the cross-connected links are established.

This object may be set only if the value of the associated 
snalcCrossConnectAdminStatus object is 'down'.

Options:
local (1): The cross-connection is established by first attempting to 
bring up the source connection. The destination connection is only 
established after the source connection has transmitted data. This means 
that connection establishment frames are not transported between the 
source and destination links.

endToEnd (2) The cross-connection is established by first bringing up both 
the source and destination links layers. Next, connection establishment 
frames are transported (with conversion) between the source and 
destination links to establish the connection. This option must be 
selected when connecting PUs 1 or Nodes Type 2.1, or when connecting SDLC 
or QLLC switched lines. It allows XID frames to be propagated between the 
two cross-connected stations.

Default Value: endToEnd (2)

Related Objects: snalcCrossConnectWaitContactTimer 
snalcCrossConnectAdminStatus

Configuration Changed: administrative and operative
"
	DEFVAL{ endToEnd }
	::= { snalcCrossConnectEntry 12 }
    

    snalcCrossConnectAdminStatus OBJECT-TYPE
	SYNTAX  INTEGER {
		    up            (1),
		    down           (2)
		    }
	ACCESS  read-write
	STATUS  mandatory
	DESCRIPTION
"Control which allows the cross- connections to be established or 
disconnected. The order in which links are established is determined by 
object snalcCrossConnectConnectMethod.

Options:
up (1): Causes SNA Link Conversion to activate the cross-connection by 
establishing the source and destination links.

down (2): Causes SNA Link Conversion to de-activate the cross-connection 
by disconnecting the source and destination links.

Default Value: down (2)

Related Objects: snalcCrossConnectConnectMethod 

Configuration Changed: administrative and operative"
	DEFVAL{ down }
	::= { snalcCrossConnectEntry 13 }
		  

    snalcCrossConnectSrcOperStatus OBJECT-TYPE
	SYNTAX  INTEGER {
		    offLine            (1),
		    notConnected       (2),
		    connecting         (3),
		    waitXid            (4),
		    setMode            (5),
		    waitPartner        (6),
		    sendXid            (7),
		    waitSetMode        (8),
		    delayConnect       (9),
		    associated         (10),
		    disconnecting      (11),
		    linkDisconnecting  (12),
		    waitDisconnect     (13),
		    failed             (14),
		    data               (15)
		    }
	ACCESS  read-only
	STATUS  mandatory
	DESCRIPTION
"Indicates the state of the source link.

Options:
offLine (1): Indicates that this cross-connection is not defined at the 
layer or too many cross-connections have been defined.

notConnected (2): The connection is idle.

connecting (3): The connection is in the process of being established.

waitXid (4): Awaiting an incoming SNA XID frame to continue the link 
establishment process.

setMode (5): A Set Mode command was sent to the remote station.

waitPartner (6): The link is established but is waiting for establishment 
on the other cross- connected link. 

sendXid (7): Awaiting the appropriate response to an XID that was sent to 
the remote.

waitSetMode (8): Waiting for a Set Mode command from the remote.

delayConnect (9): Waiting for the connection timer 
(snalcCrossConnectDstConnectInterval) to expire in order to retry the 
connection.

associated (10): Indicates that both the source and destination link 
levels are established and that connection establishment frames may be 
exchanged.

disconnecting (11): The link is being disconnected.

linkDisconnecting (12): The link is terminating data exchange mode.

waitDisconnect (13): Waiting for the remote to clear the link.

failed (14) The cross-connection process failed. To retry, set 
snalcCrossConnectAdminStatus from 'up' to 'down' and back to 'up'.

data (15): Indicates that the cross- connection between the source and 
destination is established and that data frames may be exchanged."
	::= { snalcCrossConnectEntry 14 }


    snalcCrossConnectDstOperStatus OBJECT-TYPE
	SYNTAX  INTEGER {
		    offLine            (1),
		    notConnected       (2),
		    connecting         (3),
		    waitXid            (4),
		    setMode            (5),
		    waitPartner        (6),
		    sendXid            (7),
		    waitSetMode        (8),
		    delayConnect       (9),
		    associated         (10),
		    disconnecting      (11),
		    linkDisconnecting  (12),
		    waitDisconnect     (13),
		    failed             (14),
		    data               (15)
		    }
	ACCESS  read-only
	STATUS  mandatory
	DESCRIPTION
"Indicates the state of the destination link.

Options:
offLine (1): Indicates that this cross-connection is not defined at the 
layer or too many cross-connections have been defined.

notConnected (2): The connection is idle.

connecting (3): The connection is in the process of being established.

waitXid (4): Awaiting an incoming SNA XID frame to continue the link 
establishment process.

setMode (5): A Set Mode command was sent to the remote station.

waitPartner (6): The link is established but is waiting for establishment 
on the other cross- connected link. 

sendXid (7): Awaiting the appropriate response to an XID that was sent to 
the remote.

waitSetMode (8): Waiting for a Set Mode command from the remote.

delayConnect (9): Waiting for the connection timer 
(snalcCrossConnectDstConnectInterval) to expire in order to retry the 
connection.

associated (10): Indicates that both the source and destination link 
levels are established and that connection establishment frames may be 
exchanged.

disconnecting (11): The link is being disconnected.

linkDisconnecting (12): The link is terminating data exchange mode.

waitDisconnect (13): Waiting for the remote to clear the link.

failed (14) The cross-connection process failed. To retry, set 
snalcCrossConnectAdminStatus from 'up' to 'down' and back to 'up'.

data (15): Indicates that the cross- connection between the source and 
destination is established and that data frames may be exchanged."

	::= { snalcCrossConnectEntry 15 }
      
      
    snalcCrossConnectXidTransparent OBJECT-TYPE
	SYNTAX  INTEGER {
		    nonTransparent (1),
		    transparent    (2)
		    }
	ACCESS  read-write
	STATUS  mandatory
	DESCRIPTION
"Determines if any changes are to be made to the XID. If transparent mode 
is specified, XID information fields are not modified, and the XID's are 
passed transparently between the lower software layers (i.e.: SDLC, QLLC, 
LIM).

Options:

nonTransparent (1) 

transparent (2)

Default Value: nonTransparent (1)

Configuration Changed: administrative and operative"
	DEFVAL{ nonTransparent }
	--#STARTING_VERSION 1
	::= { snalcCrossConnectEntry 16 }
	

	snalcCrossConnectDataLinkType	OBJECT-TYPE
	SYNTAX  								INTEGER {
		    			sna 		(1),
		    			bsc   	(2)
		    			}
	ACCESS  read-write
	STATUS  mandatory
	DESCRIPTION
"Configurates the type of connection. Two types are supported :
	SNA connections, using the SDLC data link layer.
	BSC connections, using the BSC data link layer.
 
Options:

sna 			(1) 

bsc			(2)

Default Value: sna (1)

Configuration Changed: administrative and operative"
	DEFVAL{ sna }
	--#STARTING_VERSION 2
	::= { snalcCrossConnectEntry 17 }					 
	
END
