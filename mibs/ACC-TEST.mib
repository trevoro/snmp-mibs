ACC-TEST DEFINITIONS ::= BEGIN

    IMPORTS
		OBJECT-TYPE, IpAddress, TimeTicks, Gauge, Counter FROM RFC1155-SMI
		TRAP-TYPE FROM RFC-1215
 accTrapLogSeqNum FROM ACC-SYSTEM
 accBRG, DisplayString, RowStatus, IfIndex, SmdsAddress
             FROM ACC-MIB;

-- Test Group {accBRG 41 }
        accTest      OBJECT IDENTIFIER ::= { accBRG 49 }
            accDialTest      OBJECT IDENTIFIER ::= { accTest 1 }
        accDialTestAction OBJECT-TYPE
                SYNTAX INTEGER {
			   loopback (1)
		       }
                ACCESS read-write
                STATUS mandatory
                DESCRIPTION
                        " The test action to be performed."
                ::= { accDialTest 1 }
        accDialTestDialAddress OBJECT-TYPE
                SYNTAX OCTET STRING
                ACCESS read-write
                STATUS mandatory
                DESCRIPTION
                        " Dial address to use in test."
                ::= { accDialTest 2 }
        accDialTestPort OBJECT-TYPE
                SYNTAX INTEGER
                ACCESS read-write
                STATUS mandatory
                DESCRIPTION
                        " The physical port on which to perform the test."
                ::= { accDialTest 3 }
        accDialTestMessageLevel OBJECT-TYPE
                SYNTAX INTEGER (1..7)
                ACCESS read-write
                STATUS mandatory
                DESCRIPTION
                        " The message level for test traps. Message level 7
                          produces the most traps."
                ::= { accDialTest 4 }

END
