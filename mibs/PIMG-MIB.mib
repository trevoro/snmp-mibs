-- extracted from draft-thaler-idmr-multiproto-pimmib-00.txt
-- at Mon Jun 12 10:51:24 2000

   PIMG-MIB DEFINITIONS ::= BEGIN 
    
   IMPORTS 
       MODULE-IDENTITY, OBJECT-TYPE, experimental, 
       NOTIFICATION-TYPE, 
       Integer32, TimeTicks  FROM SNMPv2-SMI 
       RowStatus, TruthValue            FROM SNMPv2-TC 
       MODULE-COMPLIANCE, OBJECT-GROUP, 
       NOTIFICATION-GROUP               FROM SNMPv2-CONF 
       inetMRouteGroupType, inetMRouteGroup, inetMRouteGroupMaskLen, 
       inetMRouteSourceType, inetMRouteSource, inetMRouteSourceMaskLen, 
       inetMRouteNextHopGroupType, inetMRouteNextHopGroup, 
       inetMRouteNextHopSourceType, inetMRouteNextHopSource,  
       inetMRouteNextHopSourceMaskLen, 
       inetMRouteNextHopIfIndex, inetMRouteNextHopAddressType, 
       inetMRouteNextHopAddress         FROM INETMROUTE-STD-MIB 
       InterfaceIndex                   FROM IF-MIB 
       InetAddress, InetAddressType        FROM INET-ADDRESS-MIB; 
    
   pimgMIB MODULE-IDENTITY 
       LAST-UPDATED "200003091200Z" -- March 9, 2000 
       ORGANIZATION "IETF IDMR Working Group." 
       CONTACT-INFO 
               " Dave Thaler 
                 Microsoft Corporation 
                 One Microsoft Way 
                 Redmond, WA  98052-6399 
                 US 
    
                 Phone: +1 425 703 8835 
                 EMail: dthaler@dthaler.microsoft.com 
    
                 Andrew Adams 
                 Merit Network, Inc. 
                 4251 Plymouth Rd. 
                 Ann Arbor, MI  48105-2785 
    
                 Phone: +1 734 763-6378 
                 EMail: ala@merit.edu 
    
                 William Siadak 
                 Merit Network, Inc. 
                 4251 Plymouth Rd. 
                 Ann Arbor, MI 48105-2785 
    
                 Phone: +1 734 936 2035 
                 EMail: wfs@merit.edu" 
    
       DESCRIPTION 
               "The MIB module for management of PIM routers." 
       REVISION     "200003091200Z" -- March 9, 2000 
       DESCRIPTION 
               "Initial version, published as RFC xxxx (to be filled in 
               by RFC-Editor)." 
       ::= { experimental 1 } 
    
   pimgMIBObjects OBJECT IDENTIFIER ::= { pimgMIB 1 } 
    
   pimgTraps      OBJECT IDENTIFIER ::= { pimgMIBObjects 0 } 
    
   pimg           OBJECT IDENTIFIER ::= { pimgMIBObjects 1 } 
    
   pimgJoinPruneInterval OBJECT-TYPE 
       SYNTAX     Integer32 
       UNITS      "seconds" 
       MAX-ACCESS read-write 
       STATUS     current 
       DESCRIPTION 
               "The default interval at which periodic PIM-SM 
   Join/Prune 
               messages are to be sent." 
       ::= { pimg 1 } 
    
   -- The PIM Interface Table 
    
   pimgInterfaceTable OBJECT-TYPE 
       SYNTAX     SEQUENCE OF PimgInterfaceEntry 
       MAX-ACCESS not-accessible 
       STATUS     current 
       DESCRIPTION 
               "The (conceptual) table listing the router's PIM 
               interfaces. IGMP and PIM are enabled on all interfaces 
               listed in this table." 
       ::= { pimg 2 } 
    
   pimgInterfaceEntry OBJECT-TYPE 
       SYNTAX     PimgInterfaceEntry 
       MAX-ACCESS not-accessible 
       STATUS     current 
       DESCRIPTION 
               "An entry (conceptual row) in the pimgInterfaceTable." 
       INDEX      { pimgInterfaceIfIndex } 
       ::= { pimgInterfaceTable 1 } 
    
   PimgInterfaceEntry ::= SEQUENCE { 
       pimgInterfaceIfIndex            InterfaceIndex, 
       pimgInterfaceAddressType        InetAddressType, 
       pimgInterfaceAddress            InetAddress, 
       pimgInterfaceNetMaskLen         INTEGER, 
       pimgInterfaceMode               INTEGER, 
       pimgInterfaceDRType             InetAddressType, 
       pimgInterfaceDR                 InetAddress, 
       pimgInterfaceHelloInterval      Integer32, 
       pimgInterfaceStatus             RowStatus, 
       pimgInterfaceJoinPruneInterval  Integer32, 
       pimgInterfaceCBSRPreference     Integer32 
   } 
    
   pimgInterfaceIfIndex OBJECT-TYPE 
       SYNTAX     InterfaceIndex 
       MAX-ACCESS not-accessible 
       STATUS     current 
       DESCRIPTION 
               "The ifIndex value of this PIM interface." 
       ::= { pimgInterfaceEntry 1 } 

   pimgInterfaceAddressType OBJECT-TYPE 
       SYNTAX     InetAddressType 
       MAX-ACCESS read-only 
       STATUS     current 
       DESCRIPTION 
               "A value indicating the address family of the address 
               contained in pimgInterfaceAddress.  Legal values 
               correspond to the subset of address families for which  
               PIM routing is supported." 
       ::= { pimgInterfaceEntry 2 } 
    
   pimgInterfaceAddress OBJECT-TYPE 
       SYNTAX     InetAddress 
       MAX-ACCESS read-only 
       STATUS     current 
       DESCRIPTION 
               "The IP address of the PIM interface." 
       ::= { pimgInterfaceEntry 3 } 
    
   pimgInterfaceNetMaskLen OBJECT-TYPE 
       SYNTAX     INTEGER (0..128) 
       MAX-ACCESS read-only 
       STATUS     current 
       DESCRIPTION 
               "The length in bits of the network mask which when 
               combined with the corresponding value of 
               pimgInterfaceAddress identifies the address of the 
   network 
               to which the PIM interface is attached." 
       ::= { pimgInterfaceEntry 4 } 
    
   pimgInterfaceMode OBJECT-TYPE 
       SYNTAX     INTEGER { dense(1), sparse(2), sparseDense(3) } 
       MAX-ACCESS read-create 
       STATUS     current 
       DESCRIPTION 
               "The configured mode of this PIM interface.  A value of 
               sparseDense is only valid for PIMv1." 
       DEFVAL     { dense } 
       ::= { pimgInterfaceEntry 5 } 
    
   pimgInterfaceDRType OBJECT-TYPE 
       SYNTAX     InetAddressType 
       MAX-ACCESS read-only 
       STATUS     current 
       DESCRIPTION 
              "A value indicating the address family of the address 
              contained in pimgInterfaceDR. The value MUST be the same 
   as 
              the value of pimgInterfaceAddressType." 
       ::= { pimgInterfaceEntry 6 } 
    
   pimgInterfaceDR OBJECT-TYPE 
       SYNTAX     InetAddress 
       MAX-ACCESS read-only 
       STATUS     current 
       DESCRIPTION 
               "The Designated Router on this PIM interface.  For  
               point-to-point interfaces, pimgInterfaceDR will be 
   0.0.0.0 
               in the case of an IPv4 entry, and 0:0:0:0:0:0:0:0 in the 
               case of an IPv6 entry." 
       ::= { pimgInterfaceEntry 7 } 
    
   pimgInterfaceHelloInterval OBJECT-TYPE 
       SYNTAX     Integer32 
       UNITS      "seconds" 
       MAX-ACCESS read-create 
       STATUS     current 
       DESCRIPTION 
               "The frequency at which PIM Hello messages are 
   transmitted 
               on this interface." 
       DEFVAL     { 30 } 
       ::= { pimgInterfaceEntry 8 } 
    
   pimgInterfaceStatus OBJECT-TYPE 
       SYNTAX     RowStatus 
       MAX-ACCESS read-create 
       STATUS     current 
       DESCRIPTION 
               "The status of this entry.  Creating the entry enables 
   PIM 
               on the interface; destroying the entry disables PIM on 
   the 
               interface." 
       ::= { pimgInterfaceEntry 9 } 
    
   pimgInterfaceJoinPruneInterval OBJECT-TYPE 
       SYNTAX     Integer32 
       UNITS      "seconds" 
       MAX-ACCESS read-create 
       STATUS     current 
       DESCRIPTION 
               "The frequency at which PIM Join/Prune messages are 
               transmitted on this PIM interface.  The default value of 
               this object is the pimgJoinPruneInterval." 
       ::= { pimgInterfaceEntry 10 } 
    
   pimgInterfaceCBSRPreference OBJECT-TYPE 
       SYNTAX     Integer32 (-1..255) 
       MAX-ACCESS read-create 
       STATUS     current 
       DESCRIPTION 
               "The preference value for the local interface as a 
               candidate bootstrap router.  The value of -1 is used to 
               indicate that the local interface is not a candidate BSR 
               interface." 
       DEFVAL     { 0 } 
       ::= { pimgInterfaceEntry 11 } 
    
   -- The PIM Neighbor Table 
    
   pimgNeighborTable OBJECT-TYPE 
       SYNTAX     SEQUENCE OF PimgNeighborEntry 
       MAX-ACCESS not-accessible 
       STATUS     current 
       DESCRIPTION 
               "The (conceptual) table listing the router's PIM 
               neighbors." 
       ::= { pimg 3 } 
    
   pimgNeighborEntry OBJECT-TYPE 
       SYNTAX     PimgNeighborEntry 
       MAX-ACCESS not-accessible 
       STATUS     current 
       DESCRIPTION 
               "An entry (conceptual row) in the pimgNeighborTable." 
       INDEX      { pimgNeighborAddressType, pimgNeighborAddress } 
       ::= { pimgNeighborTable 1 } 
    
   PimgNeighborEntry ::= SEQUENCE { 
       pimgNeighborAddressType  InetAddressType, 
       pimgNeighborAddress      InetAddress, 
       pimgNeighborIfIndex      InterfaceIndex, 
       pimgNeighborUpTime       TimeTicks, 
       pimgNeighborExpiryTime   TimeTicks, 
       pimgNeighborMode         INTEGER 
   } 
    
   pimgNeighborAddressType OBJECT-TYPE 
       SYNTAX     InetAddressType 
       MAX-ACCESS not-accessible 
       STATUS     current 
       DESCRIPTION 
              "A value indicating the address family of the address 
              contained in pimgNeighborAddress.  Legal values 
   correspond 
              to the subset of  
               address families for which PIM routing is supported." 
       ::= { pimgNeighborEntry 1 } 
    
   pimgNeighborAddress OBJECT-TYPE 
       SYNTAX     InetAddress 
       MAX-ACCESS not-accessible 
       STATUS     current 
       DESCRIPTION 
               "The IP address of the PIM neighbor for which this entry 
               contains information." 
       ::= { pimgNeighborEntry 2 } 
    
   pimgNeighborIfIndex OBJECT-TYPE 
       SYNTAX     InterfaceIndex 
       MAX-ACCESS read-only 
       STATUS     current 
       DESCRIPTION 
               "The value of ifIndex for the interface used to reach 
   this 
               PIM neighbor." 
       ::= { pimgNeighborEntry 3 } 
    
   pimgNeighborUpTime OBJECT-TYPE 
       SYNTAX     TimeTicks 
       MAX-ACCESS read-only 
       STATUS     current 
       DESCRIPTION 
               "The time since this PIM neighbor (last) became a 
   neighbor 
               of the local router." 
       ::= { pimgNeighborEntry 4 } 
    
   pimgNeighborExpiryTime OBJECT-TYPE 
       SYNTAX     TimeTicks 
       MAX-ACCESS read-only 
       STATUS     current 
       DESCRIPTION 
               "The minimum time remaining before this PIM neighbor 
   will 
               be aged out." 
       ::= { pimgNeighborEntry 5 } 
    
   pimgNeighborMode OBJECT-TYPE 
       SYNTAX     INTEGER { dense(1), sparse(2) } 
       MAX-ACCESS read-only 
       STATUS     deprecated 
       DESCRIPTION 
               "The active PIM mode of this neighbor.  This object is 
               deprecated for PIMv2 routers since all neighbors on the 
               interface must be either dense or sparse as determined 
   by 
               the protocol running on the interface." 
       ::= { pimgNeighborEntry 6 } 
    
   -- 
   -- The PIM IP Multicast Route Table 
   -- 
    
   pimgInetMRouteTable OBJECT-TYPE 
       SYNTAX     SEQUENCE OF PimgInetMRouteEntry 
       MAX-ACCESS not-accessible 
       STATUS     current 
       DESCRIPTION 
               "The (conceptual) table listing PIM-specific information 
               on a subset of the rows of the inetMRouteTable defined 
   in 
               the Inet Multicast MIB." 
       ::= { pimg 4 } 
    
   pimgInetMRouteEntry OBJECT-TYPE 
       SYNTAX     PimgInetMRouteEntry 
       MAX-ACCESS not-accessible 
       STATUS     current 
       DESCRIPTION 
               "An entry (conceptual row) in the pimgInetMRouteTable. 
               There is one entry per entry in the inetMRouteTable 
   whose 
               incoming interface is running PIM." 
       INDEX      { inetMRouteGroupType, 
                    inetMRouteGroup, 
                    inetMRouteGroupMaskLen, 
                    inetMRouteSourceType,  
                    inetMRouteSource,  
                    inetMRouteSourceMaskLen } 
       ::= { pimgInetMRouteTable 1 } 
    
   PimgInetMRouteEntry ::= SEQUENCE { 
       pimgInetMRouteUpstreamAssertTimer   TimeTicks, 
       pimgInetMRouteAssertMetric          Integer32, 
       pimgInetMRouteAssertMetricPref      Integer32, 
       pimgInetMRouteAssertRPTBit          TruthValue, 
       pimgInetMRouteFlags                 BITS 
    
   } 
    
   pimgInetMRouteUpstreamAssertTimer OBJECT-TYPE 
       SYNTAX     TimeTicks 
       MAX-ACCESS read-only 
       STATUS     current 
       DESCRIPTION 
               "The time remaining before the router changes its 
   upstream 
               neighbor back to its RPF neighbor.  This timer is called 
               the Assert timer in the PIM Sparse and Dense mode 
               specification. A value of 0 indicates that no Assert has 
               changed the upstream neighbor away from the RPF 
   neighbor." 
       ::= { pimgInetMRouteEntry 1 } 
    
   pimgInetMRouteAssertMetric OBJECT-TYPE 
       SYNTAX     Integer32 
       MAX-ACCESS read-only 
       STATUS     current 
       DESCRIPTION 
               "The metric advertised by the assert winner on the 
               upstream interface, or 0 if no such assert is in 
               received." 
       ::= { pimgInetMRouteEntry 2 } 
    
   pimgInetMRouteAssertMetricPref OBJECT-TYPE 
       SYNTAX     Integer32 
       MAX-ACCESS read-only 
       STATUS     current 
       DESCRIPTION 
               "The preference advertised by the assert winner on the 
               upstream interface, or 0 if no such assert is in 
   effect." 
       ::= { pimgInetMRouteEntry 3 } 
    
   pimgInetMRouteAssertRPTBit OBJECT-TYPE 
       SYNTAX     TruthValue 
       MAX-ACCESS read-only 
       STATUS     current 
       DESCRIPTION 
               "The value of the RPT-bit advertised by the assert 
   winner 
               on the upstream interface, or false if no such assert is 
               in effect." 
       ::= { pimgInetMRouteEntry 4 } 
    
   pimgInetMRouteFlags OBJECT-TYPE 
       SYNTAX     BITS { 
                     rpt(0), 
                     spt(1) 
                  } 
       MAX-ACCESS read-only 
       STATUS     current 
       DESCRIPTION 
               "This object describes PIM-specific flags related 
               to a multicast state entry.  See the PIM Sparse 
               Mode specification for the meaning of the RPT and 
               SPT bits." 
       ::= { pimgInetMRouteEntry 5 } 
    
   -- 
   -- The PIM Next Hop Table 
   -- 
    
   pimgInetMRouteNextHopTable OBJECT-TYPE 
       SYNTAX     SEQUENCE OF PimgInetMRouteNextHopEntry 
       MAX-ACCESS not-accessible 
       STATUS     current 
       DESCRIPTION 
               "The (conceptual) table listing PIM-specific 
               information on a subset of the rows of the 
               inetMRouteNextHopTable defined in the IP Multicast 
               MIB." 
       ::= { pimg 7 } 

   pimgInetMRouteNextHopEntry OBJECT-TYPE 
       SYNTAX     PimgInetMRouteNextHopEntry 
       MAX-ACCESS not-accessible 
       STATUS     current 
       DESCRIPTION 
               "An entry (conceptual row) in the 
               pimgInetMRouteNextHopTable. There is one entry per 
               entry in the inetMRouteNextHopTable whose interface 
               is running PIM and whose inetMRouteNextHopState is 
               pruned(1)." 
       INDEX      { inetMRouteNextHopGroupType, 
                    inetMRouteNextHopGroup, 
                    inetMRouteNextHopSourceType, 
                    inetMRouteNextHopSource, 
                    inetMRouteNextHopSourceMaskLen, 
                    inetMRouteNextHopIfIndex, 
                    inetMRouteNextHopAddressType, 
                    inetMRouteNextHopAddress } 
       ::= { pimgInetMRouteNextHopTable 1 } 
    
   PimgInetMRouteNextHopEntry ::= SEQUENCE { 
       pimgInetMRouteNextHopPruneReason       INTEGER 
   } 
    
   pimgInetMRouteNextHopPruneReason OBJECT-TYPE 
       SYNTAX     INTEGER { 
                     other (1), 
                     prune (2), 
                     assert (3) 
                  } 
       MAX-ACCESS read-only 
       STATUS     current 
       DESCRIPTION 
               "This object indicates why the downstream interface 
               was pruned, whether in response to a PIM prune 
               message or due to PIM Assert processing." 
       ::= { pimgInetMRouteNextHopEntry 2 } 
    
   -- The PIM RP Table 
    
   pimgRPTable OBJECT-TYPE 
       SYNTAX     SEQUENCE OF PimgRPEntry 
       MAX-ACCESS not-accessible 
       STATUS     deprecated 
       DESCRIPTION 
               "The (conceptual) table listing PIM version 1 
               information for the Rendezvous Points (RPs) for 
               multicast groups. This table is deprecated since 
               its function is replaced by the pimgRPSetTable for 
               PIM version 2." 
       ::= { pimg 5 } 
    
   pimgRPEntry OBJECT-TYPE 
       SYNTAX     PimgRPEntry 
       MAX-ACCESS not-accessible 
       STATUS     deprecated 
       DESCRIPTION 
               "An entry (conceptual row) in the pimgRPTable. 
               There is one entry per RP address for each 
               multicast group." 
       INDEX      { pimgRPGroupAddressType, pimgRPGroupAddress,  
                    pimgRPAddressType, pimgRPAddress } 
       ::= { pimgRPTable 1 } 
    
   PimgRPEntry ::= SEQUENCE { 
       pimgRPGroupAddressType    InetAddressType, 
       pimgRPGroupAddress        InetAddress, 
       pimgRPAddressType         InetAddressType, 
       pimgRPAddress             InetAddress, 
       pimgRPState               INTEGER, 
       pimgRPStateTimer          TimeTicks, 
       pimgRPLastChange          TimeTicks, 
       pimgRPRowStatus           RowStatus 
   } 
    
   pimgRPGroupAddressType OBJECT-TYPE 
       SYNTAX     InetAddressType 
       MAX-ACCESS not-accessible 
       STATUS     deprecated 
       DESCRIPTION 
               "A value indicating the address family of the 
               address contained in pimgRPGroupAddress.  Legal 
               values are: 
               unknown(0), ipv4(1), ipv6(2), dns(16)" 
       ::= { pimgRPEntry 1 } 
    
   pimgRPGroupAddress OBJECT-TYPE 
       SYNTAX     InetAddress 
       MAX-ACCESS not-accessible 
       STATUS     deprecated 
       DESCRIPTION 
               "The multicast group address for which this entry 
               contains information about an RP." 
       ::= { pimgRPEntry 2 } 
    
   pimgRPAddressType OBJECT-TYPE 
       SYNTAX     InetAddressType 
       MAX-ACCESS not-accessible 
       STATUS     deprecated 
       DESCRIPTION 
               "A value indicating the address family of the 
               address contained in pimgRPAddress. The value MUST 
               be the same as the value of 
               pimgRPGroupAddressType." 
       ::= { pimgRPEntry 3 } 

   pimgRPAddress OBJECT-TYPE 
       SYNTAX     InetAddress 
       MAX-ACCESS not-accessible 
       STATUS     deprecated 
       DESCRIPTION 
               "The unicast address of the RP." 
       ::= { pimgRPEntry 4 } 
    
   pimgRPState OBJECT-TYPE 
       SYNTAX     INTEGER { up(1), down(2) } 
       MAX-ACCESS read-only 
       STATUS     deprecated 
       DESCRIPTION 
               "The state of the RP." 
       ::= { pimgRPEntry 5 } 
    
   pimgRPStateTimer OBJECT-TYPE 
       SYNTAX     TimeTicks 
       MAX-ACCESS read-only 
       STATUS     deprecated 
       DESCRIPTION 
               "The minimum time remaining before the next state 
               change. When pimgRPState is up, this is the minimum 
               time which must expire until it can be declared 
               down.  When pimgRPState is down, this is the time 
               until it will be declared up (in order to retry)." 
       ::= { pimgRPEntry 6 } 
    
   pimgRPLastChange OBJECT-TYPE 
       SYNTAX     TimeTicks 
       MAX-ACCESS read-only 
       STATUS     deprecated 
       DESCRIPTION 
               "The value of sysUpTime at the time when the 
               corresponding instance of pimgRPState last changed 
               its value." 
       ::= { pimgRPEntry 7 } 
    
   pimgRPRowStatus OBJECT-TYPE 
       SYNTAX     RowStatus 
       MAX-ACCESS read-create 
       STATUS     deprecated 
       DESCRIPTION 
               "The status of this row, by which new entries may 
               be created, or old entries deleted from this 
               table." 
       ::= { pimgRPEntry 8 } 
    
   -- The PIM RP-Set Table 
    
   pimgRPSetTable OBJECT-TYPE 
       SYNTAX     SEQUENCE OF PimgRPSetEntry 
       MAX-ACCESS not-accessible 
       STATUS     current 
       DESCRIPTION 
               "The (conceptual) table listing PIM information for 
               candidate Rendezvous Points (RPs) for multicast 
               groups. When the local router is the BSR, this 
               information is obtained from received Candidate-RP- 
               Advertisements.  When the local router is not the 
               BSR, this information is obtained from received RP- 
               Set messages." 
       ::= { pimg 6 } 
    
   pimgRPSetEntry OBJECT-TYPE 
       SYNTAX     PimgRPSetEntry 
       MAX-ACCESS not-accessible 
       STATUS     current 
       DESCRIPTION 
               "An entry (conceptual row) in the pimgRPSetTable." 
       INDEX      { pimgRPSetComponent,  
                    pimgRPSetGroupAddressType, 
                    pimgRPSetGroupAddress, 
                    pimgRPSetGroupMaskLen, pimgRPSetAddressType,  
                    pimgRPSetAddress } 
       ::= { pimgRPSetTable 1 } 
    
   PimgRPSetEntry ::= SEQUENCE { 
       pimgRPSetGroupAddressType    InetAddressType, 
       pimgRPSetGroupAddress        InetAddress, 
       pimgRPSetGroupMaskLen        INTEGER, 
       pimgRPSetAddressType         InetAddressType, 
       pimgRPSetAddress             InetAddress, 
       pimgRPSetHoldTime            Integer32, 
       pimgRPSetExpiryTime          TimeTicks, 
       pimgRPSetComponent           Integer32 
   } 
    
   pimgRPSetGroupAddressType OBJECT-TYPE 
       SYNTAX     InetAddressType 
       MAX-ACCESS not-accessible 
       STATUS     current 
       DESCRIPTION 
              "A value indicating the address family of the address 
              contained in pimgRPSetGroupAddress.  Legal values 
              correspond to the subset of address families for which 
   PIM 
              routing is supported." 
       ::= { pimgRPSetEntry 1 } 
    
   pimgRPSetGroupAddress OBJECT-TYPE 
       SYNTAX     InetAddress 
       MAX-ACCESS not-accessible 
       STATUS     current 
       DESCRIPTION 
               "The IP multicast group address which, when 
               combined with 
               the value of pimgRPSetGroupMaskLen, gives the group 
               prefix for which this entry contains information 
               about the Candidate-RP." 
       ::= { pimgRPSetEntry 2 } 
    
   pimgRPSetGroupMaskLen OBJECT-TYPE 
       SYNTAX     INTEGER (0..128) 
       MAX-ACCESS not-accessible 
       STATUS     current 
       DESCRIPTION 
               "The length in bits of the mask which, when 
               combined with pimgRPSetGroupAddress, gives the 
               group prefix for which this entry contains 
               information about the Candidate-RP." 
       ::= { pimgRPSetEntry 3 } 
    
   pimgRPSetAddressType OBJECT-TYPE 
       SYNTAX     InetAddressType 
       MAX-ACCESS not-accessible 
       STATUS     current 
       DESCRIPTION 
              "A value indicating the address family of the 
              address contained in pimgRPSetAddress. The value 
              MUST be the same as the value of 
              pimgRPSetGroupAddressType." 
       ::= { pimgRPSetEntry 4 } 
    
   pimgRPSetAddress OBJECT-TYPE 
       SYNTAX     InetAddress 
       MAX-ACCESS not-accessible 
       STATUS     current 
       DESCRIPTION 
               "The address of the Candidate-RP." 
       ::= { pimgRPSetEntry 5 } 
    
   pimgRPSetHoldTime OBJECT-TYPE 
       SYNTAX     Integer32 (0..255) 
       UNITS      "seconds" 
       MAX-ACCESS read-only 
       STATUS     current 
       DESCRIPTION 
               "The holdtime of a Candidate-RP.  If the local 
               router is not the BSR, this value is 0." 
       ::= { pimgRPSetEntry 6 } 
    
   pimgRPSetExpiryTime OBJECT-TYPE 
       SYNTAX     TimeTicks 
       MAX-ACCESS read-only 
       STATUS     current 
       DESCRIPTION 
               "The minimum time remaining before the Candidate-RP 
               will be declared down.  If the local router is not 
               the BSR, this value is 0." 
       ::= { pimgRPSetEntry 7 } 
    
   pimgRPSetComponent OBJECT-TYPE 
       SYNTAX     Integer32 (1..255) 
       MAX-ACCESS not-accessible 
       STATUS     current 
       DESCRIPTION 
               "A number uniquely identifying the component.  Each 
               protocol instance connected to a separate domain 
               should have a different index value." 
       ::= { pimgRPSetEntry 8 } 
    
   -- The PIM Candidate-RP Table 
    
   pimgCandidateRPTable OBJECT-TYPE 
       SYNTAX     SEQUENCE OF PimgCandidateRPEntry 
       MAX-ACCESS not-accessible 
       STATUS     current 
       DESCRIPTION 
               "The (conceptual) table listing the multicast 
               groups for which the local router is to advertise 
               itself as a Candidate-RP when the value of 
               pimgComponentCRPHoldTime is non-zero.  If this 
               table is empty, then the local router 
               will advertise itself as a Candidate-RP for all 
               groups (providing the value of 
               pimgComponentCRPHoldTime is non-zero)." 
       ::= { pimg 11 } 
    
   pimgCandidateRPEntry OBJECT-TYPE 
       SYNTAX     PimgCandidateRPEntry 
       MAX-ACCESS not-accessible 
       STATUS     current 
       DESCRIPTION 
               "An entry (conceptual row) in the 
               pimgCandidateRPTable." 
       INDEX      { pimgCandidateRPGroupAddressType, 
                    pimgCandidateRPGroupAddress, 
                    pimgCandidateRPGroupMaskLen } 
   ::= { pimgCandidateRPTable 1 } 
    
   PimgCandidateRPEntry ::= SEQUENCE { 
       pimgCandidateRPGroupAddressType InetAddressType, 
       pimgCandidateRPGroupAddress     InetAddress, 
       pimgCandidateRPGroupMaskLen     INTEGER, 
       pimgCandidateRPAddressType      InetAddressType, 
       pimgCandidateRPAddress          InetAddress, 
       pimgCandidateRPRowStatus        RowStatus 
   } 
    
   pimgCandidateRPGroupAddressType OBJECT-TYPE 
       SYNTAX     InetAddressType 
       MAX-ACCESS not-accessible 
       STATUS     current 
       DESCRIPTION 
              "A value indicating the address family of the 
              address contained in pimgCandidateRPGroupAddress. 
              Legal values correspond to the subset of address 
              families for which PIM routing is supported." 
       ::= { pimgCandidateRPEntry 1 } 
    
   pimgCandidateRPGroupAddress OBJECT-TYPE 
       SYNTAX     InetAddress 
       MAX-ACCESS not-accessible 
       STATUS     current 
       DESCRIPTION 
               "The multicast group address which, when combined 
               with the corresponding value of 
               pimgCandidateRPGroupMaskLen, identifies a group 
               prefix for which the local router will advertise 
               itself as a Candidate-RP." 
       ::= { pimgCandidateRPEntry 2 } 
    
   pimgCandidateRPGroupMaskLen OBJECT-TYPE 
       SYNTAX     INTEGER (0..128) 
       MAX-ACCESS not-accessible 
       STATUS     current 
       DESCRIPTION 
               "The length in bits of the mask which, when 
               combined with pimgCandidateRPGroupAddress, 
               identifies a group prefix for which the local 
               router will advertise itself as a Candidate-RP." 
       ::= { pimgCandidateRPEntry 3 } 
    
   pimgCandidateRPAddressType OBJECT-TYPE 
       SYNTAX     InetAddressType 
       MAX-ACCESS read-create 
       STATUS     current 
       DESCRIPTION 
              "A value indicating the address family of the 
              address contained in pimgCandidateRPAddress. The 
              value MUST be the same as the value of 
              pimgCandidateRPGroupAddressType." 
       ::= { pimgCandidateRPEntry 4 } 
    
   pimgCandidateRPAddress OBJECT-TYPE 
       SYNTAX     InetAddress 
       MAX-ACCESS read-create 
       STATUS     current 
       DESCRIPTION 
               "The (unicast) address of the interface which will 
               be advertised as a Candidate-RP." 
       ::= { pimgCandidateRPEntry 5 } 
    
   pimgCandidateRPRowStatus OBJECT-TYPE 
       SYNTAX     RowStatus 
       MAX-ACCESS read-create 
       STATUS     current 
       DESCRIPTION 
               "The status of this row, by which new entries may 
               be created, or old entries deleted from this 
               table." 
       ::= { pimgCandidateRPEntry 6 } 
    
   -- The PIM Component Table 
    
   pimgComponentTable OBJECT-TYPE 
       SYNTAX     SEQUENCE OF PimgComponentEntry 
       MAX-ACCESS not-accessible 
       STATUS     current 
       DESCRIPTION 
               "The (conceptual) table containing objects specific 
               to a PIM domain.  One row exists for each domain to 
               which the router is connected.  A PIM-SM domain is 
               defined as an area of the network over which 
               Bootstrap messages are forwarded. Typically, a PIM- 
               SM router will be a member of exactly one domain. 
               This table also supports, however, routers which 
               may form a border between two PIM-SM domains and do 
               not forward Bootstrap messages between them." 
       ::= { pimg 12 } 
    
   pimgComponentEntry OBJECT-TYPE 
       SYNTAX     PimgComponentEntry 
       MAX-ACCESS not-accessible 
       STATUS     current 
       DESCRIPTION 
               "An entry (conceptual row) in the 
               pimgComponentTable." 
       INDEX      { pimgComponentIndex } 
       ::= { pimgComponentTable 1 } 
    
   PimgComponentEntry ::= SEQUENCE { 
       pimgComponentIndex              Integer32, 
       pimgComponentBSRAddressType     InetAddressType, 
       pimgComponentBSRAddress         InetAddress, 
       pimgComponentBSRExpiryTime      TimeTicks, 
       pimgComponentCRPHoldTime        Integer32, 
       pimgComponentStatus             RowStatus 
   } 
    
   pimgComponentIndex OBJECT-TYPE 
       SYNTAX     Integer32 (1..255) 
       MAX-ACCESS not-accessible 
       STATUS     current 
       DESCRIPTION 
               "A number uniquely identifying the component.  Each 
               protocol instance connected to a separate domain 
               should have a different index value.  Routers that 
               only support membership in a single PIM-SM domain 
               should use a pimgComponentIndex value of 1." 
       ::= { pimgComponentEntry 1 } 
    
   pimgComponentBSRAddressType OBJECT-TYPE 
       SYNTAX     InetAddressType 
       MAX-ACCESS read-only 
       STATUS     current 
       DESCRIPTION 
              "A value indicating the address family of the 
              address contained in pimgComponentBSRAddress.  Legal 
              values correspond to the subset of address families 
              for which PIM routing is supported." 
       ::= { pimgComponentEntry 2 } 
    
   pimgComponentBSRAddress OBJECT-TYPE 
       SYNTAX     InetAddress 
       MAX-ACCESS read-only 
       STATUS     current 
       DESCRIPTION 
               "The address of the bootstrap router (BSR) for the 
               local PIM region." 
       ::= { pimgComponentEntry 3 } 
    
   pimgComponentBSRExpiryTime OBJECT-TYPE 
       SYNTAX     TimeTicks 
       MAX-ACCESS read-only 
       STATUS     current 
       DESCRIPTION 
               "The minimum time remaining before the bootstrap 
               router in the local domain will be declared down. 
               For candidate BSRs, this is the time until the 
               component sends an RP-Set message.  For other 
               routers, this is the time until it may accept an 
               RP-Set message from a lower candidate BSR." 
       ::= { pimgComponentEntry 4 } 
    
   pimgComponentCRPHoldTime OBJECT-TYPE 
       SYNTAX     Integer32 (0..255) 
       UNITS      "seconds" 
       MAX-ACCESS read-create 
       STATUS     current 
       DESCRIPTION 
               "The holdtime of the component when it is a 
               candidate RP in the local domain.  The value of 0 
               is used to indicate that the local system is not a 
               Candidate-RP." 
       DEFVAL     { 0 } 
       ::= { pimgComponentEntry 5 } 
    
   pimgComponentStatus OBJECT-TYPE 
       SYNTAX     RowStatus 
       MAX-ACCESS read-create 
       STATUS     current 
       DESCRIPTION 
               "The status of this entry.  Creating the entry 
               creates another protocol instance; destroying the 
               entry disables a protocol instance." 
       ::= { pimgComponentEntry 6 } 
    
   -- PIM Traps 
    
   pimgNeighborLoss NOTIFICATION-TYPE 
       OBJECTS { 
          pimgNeighborIfIndex 
       } 
       STATUS             current 
       DESCRIPTION 
               "A pimgNeighborLoss trap signifies the loss of an 
               adjacency with a neighbor.  This trap should be 
               generated when the neighbor timer expires, and the 
               router has no other neighbors on the same interface 
               with a lower IP address than itself." 
       ::= { pimgTraps 1 } 
    
   -- conformance information 
    
   pimgMIBConformance OBJECT IDENTIFIER ::= { pimgMIB 2 } 
   pimgMIBCompliances OBJECT IDENTIFIER ::= { pimgMIBConformance 1 } 
   pimgMIBGroups      OBJECT IDENTIFIER ::= { pimgMIBConformance 2 } 
    
   -- compliance statements 
    
   pimgV1MIBCompliance MODULE-COMPLIANCE 
       STATUS  deprecated 
       DESCRIPTION 
               "The compliance statement for routers running PIMv1 
               and implementing the PIM MIB." 
       MODULE  -- this module 
           MANDATORY-GROUPS { pimgV1MIBGroup } 
    
       ::= { pimgMIBCompliances 1 } 
    
   pimgSparseV2MIBCompliance MODULE-COMPLIANCE 
       STATUS  current 
       DESCRIPTION 
               "The compliance statement for routers running PIM 
               Sparse Mode and implementing the PIM MIB." 
       MODULE  -- this module 
       MANDATORY-GROUPS { pimgV2MIBGroup } 
    
       GROUP      pimgV2CandidateRPMIBGroup 
       DESCRIPTION 
               "This group is mandatory if the router is capable 
               of being a Candidate RP." 

       OBJECT     pimgInterfaceStatus 
       MIN-ACCESS read-only 
       DESCRIPTION 
                "Write access is not required." 
    
       ::= { pimgMIBCompliances 2 } 
    
   pimgDenseV2MIBCompliance MODULE-COMPLIANCE 
       STATUS  current 
       DESCRIPTION 
               "The compliance statement for routers running PIM 
               Dense Mode and implementing the PIM MIB." 
       MODULE  -- this module 
       MANDATORY-GROUPS { pimgDenseV2MIBGroup } 
    
       OBJECT     pimgInterfaceStatus 
       MIN-ACCESS read-only 
       DESCRIPTION 
                "Write access is not required." 
    
       ::= { pimgMIBCompliances 3 } 
    
   -- units of conformance 
    
   pimgNotificationGroup NOTIFICATION-GROUP 
       NOTIFICATIONS { pimgNeighborLoss } 
       STATUS  current 
       DESCRIPTION 
               "A collection of notifications for signaling 
               important PIM events." 
       ::= { pimgMIBGroups 1 } 
    
   pimgV2MIBGroup OBJECT-GROUP 
       OBJECTS { pimgJoinPruneInterval, pimgNeighborIfIndex, 
                 pimgNeighborUpTime, pimgNeighborExpiryTime, 
                 pimgInterfaceAddressType, pimgInterfaceAddress,  
                 pimgInterfaceNetMaskLen, 
                 pimgInterfaceDRType, pimgInterfaceDR,  
                 pimgInterfaceHelloInterval, 
                 pimgInterfaceStatus, 
                 pimgInterfaceJoinPruneInterval, 
                 pimgInterfaceCBSRPreference, pimgInterfaceMode, 
                 pimgRPSetHoldTime, pimgRPSetExpiryTime, 
                 pimgComponentBSRAddressType, 
                 pimgComponentBSRAddress, 
                 pimgComponentBSRExpiryTime, 
                 pimgComponentCRPHoldTime, pimgComponentStatus, 
                 pimgInetMRouteFlags, 
                 pimgInetMRouteUpstreamAssertTimer 
               } 
       STATUS  current 
       DESCRIPTION 
               "A collection of objects to support management of PIM 
   Sparse 
               Mode (version 2) routers." 
       ::= { pimgMIBGroups 2 } 
    
   pimgDenseV2MIBGroup OBJECT-GROUP 
       OBJECTS { pimgNeighborIfIndex, 
                 pimgNeighborUpTime, pimgNeighborExpiryTime, 
                 pimgInterfaceAddressType, pimgInterfaceAddress,  
                 pimgInterfaceNetMaskLen, 
                 pimgInterfaceDRType, pimgInterfaceDR,  
                 pimgInterfaceHelloInterval, 
                 pimgInterfaceStatus, pimgInterfaceMode 
               } 
       STATUS  current 
       DESCRIPTION 
               "A collection of objects to support management of 
               PIM Dense Mode (version 2) routers." 
       ::= { pimgMIBGroups 7 } 
    
   pimgV2CandidateRPMIBGroup OBJECT-GROUP 
       OBJECTS { pimgCandidateRPAddressType, 
                 pimgCandidateRPAddress, 
                 pimgCandidateRPRowStatus 
               } 
       STATUS  current 
       DESCRIPTION 
               "A collection of objects to support configuration 
               of which groups a router is to advertise itself as 
               a Candidate-RP." 
       ::= { pimgMIBGroups 3 } 
    
   pimgV1MIBGroup OBJECT-GROUP 
       OBJECTS { pimgJoinPruneInterval, pimgNeighborIfIndex, 
                 pimgNeighborUpTime, pimgNeighborExpiryTime, 
                 pimgNeighborMode, 
                 pimgInterfaceAddressType, pimgInterfaceAddress,  
                 pimgInterfaceNetMaskLen, 
                 pimgInterfaceJoinPruneInterval, 
                 pimgInterfaceStatus, 
                 pimgInterfaceMode,  
                 pimgInterfaceDRType, pimgInterfaceDR, 
                 pimgInterfaceHelloInterval, 
                 pimgRPState, pimgRPStateTimer, 
                 pimgRPLastChange, pimgRPRowStatus 
               } 
       STATUS  deprecated 
       DESCRIPTION 
               "A collection of objects to support management of 
               PIM (version 1) routers." 
       ::= { pimgMIBGroups 4 } 
    
   pimgNextHopGroup OBJECT-GROUP 
       OBJECTS { pimgInetMRouteNextHopPruneReason } 
       STATUS  current 
       DESCRIPTION 
               "A collection of optional objects to provide per- 
               next hop information for diagnostic purposes. 
               Supporting this group may add a large number of 
               instances to a tree walk, but the information in 
               this group can be extremely useful in tracking down 
               multicast connectivity problems." 
       ::= { pimgMIBGroups 5 } 
    
   pimgAssertGroup OBJECT-GROUP 
       OBJECTS { pimgInetMRouteAssertMetric, 
   pimgInetMRouteAssertMetricPref, 
                 pimgInetMRouteAssertRPTBit } 
       STATUS  current 
       DESCRIPTION 
               "A collection of optional objects to provide extra 
               information about the assert election process. 
               There is no protocol reason to keep such 
               information, but some implementations may already 
               keep this information and make it available.  These 
               objects can also be very useful in debugging 
               connectivity or duplicate packet problems, 
               especially if the assert winner does not support 
               the PIM and Inet Multicast MIBs." 
       ::= { pimgMIBGroups 6 } 
    
   END 

--     
--    Copyright (C) The Internet Society (2000).  All Rights Reserved. 
--     
--    This document and translations of it may be copied and furnished to 
--    others, and derivative works that comment on or otherwise explain it 
--    or assist in its implementation may be prepared, copied, published 
--    and distributed, in whole or in part, without restriction of any 
--  
-- Thaler,Adams,Siadak Experimental/Expires Dec 2000                   27 
--                 draft-thaler-idmr-multiproto-pimmib-1       June, 2000 
-- 
-- 
--    kind, provided that the above copyright notice and this paragraph 
--    are included on all such copies and derivative works.  However, this 
--    document itself may not be modified in any way, such as by removing 
--    the copyright notice or references to the Internet Society or other 
--    Internet organizations, except as needed for the purpose of 
--    developing Internet standards in which case the procedures for 
--    copyrights defined in the Internet Standards process must be 
--    followed, or as required to translate it into languages other than 
--    English. 
--     
--    The limited permissions granted above are perpetual and will not be 
--    revoked by the Internet Society or its successors or assigns. 
--     
--    This document and the information contained herein is provided on an 
--    "AS IS" basis and THE INTERNET SOCIETY AND THE INTERNET ENGINEERING 
--    TASK FORCE DISCLAIMS ALL WARRANTIES, EXPRESS OR IMPLIED, INCLUDING 
--    BUT NOT LIMITED TO ANY WARRANTY THAT THE USE OF THE INFORMATION 
--    HEREIN WILL NOT INFRINGE ANY RIGHTS OR ANY IMPLIED WARRANTIES OF 
--    MERCHANTABILITY OR FITNESS FOR A PARTICULAR PURPOSE. 
--     
--
