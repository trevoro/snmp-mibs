TERAWAVE-teraPonConfig-MIB DEFINITIONS ::= BEGIN
        -- Created by sml2mib compiler 
        IMPORTS

 IpAddress,  OBJECT-TYPE,  Counter,  Gauge,  TimeTicks, enterprises
        FROM RFC1155-SMI
		  Counter64, Gauge32 FROM SNMPv2-SMI;

terawave OBJECT IDENTIFIER ::=  { enterprises 4513 }

     -- teraAPONTable (special)

teraAPON OBJECT IDENTIFIER ::=  { terawave 4 }

teraPonIndex OBJECT-TYPE
          SYNTAX INTEGER (1..33)
          ACCESS read-only
          STATUS mandatory
          DESCRIPTION
               ""
          ::= { teraAPON 2 }

teraAPONConfig OBJECT IDENTIFIER ::=  { teraAPON 1 }

     -- teraAPONConfigTable

teraAPONConfigTable OBJECT-TYPE
     SYNTAX SEQUENCE OF TeraAPONConfigTableEntryType
     ACCESS not-accessible
     STATUS mandatory
     DESCRIPTION
          " table teraAPONConfigTable"
     ::= { teraAPONConfig 1 }

teraAPONConfigTableEntry OBJECT-TYPE
          SYNTAX TeraAPONConfigTableEntryType
          ACCESS not-accessible
          STATUS mandatory
          DESCRIPTION
               " table entry teraAPONConfigTableEntry "
          INDEX {                   teraAPONConfigIndex }
     ::= { teraAPONConfigTable 1 }

TeraAPONConfigTableEntryType ::= SEQUENCE {
          teraAPONConfigIndex   
             INTEGER (1..7),
          teraAPONSystemMode   
             INTEGER,
          teraAPONLaserMode   
             INTEGER,
          teraAPONMinUpCps   
             INTEGER (0..65535),
          teraAPONMaxUpCps   
             INTEGER,
          teraAPONMinUpKbps   
             INTEGER (0..65535),
          teraAPONMaxUpKbps   
             INTEGER,
          teraAPONMaxDwnCps   
             INTEGER,
          teraAPONMaxDwnKbps   
             INTEGER,
          teraAPONLsbStatus   
             INTEGER
}

teraAPONConfigIndex OBJECT-TYPE
          SYNTAX INTEGER (1..7)
          ACCESS read-only
          STATUS mandatory
          DESCRIPTION
               ""
          ::= { teraAPONConfigTableEntry 1 }

teraAPONSystemMode OBJECT-TYPE
          SYNTAX INTEGER
                  {
                  mode155(0),
                  mode622(1)
                  }
          ACCESS read-only
          STATUS mandatory
          DESCRIPTION
               ""
          ::= { teraAPONConfigTableEntry 2 }

teraAPONLaserMode OBJECT-TYPE
          SYNTAX INTEGER
                  {
                  laserOn(0),
                  laserOff(1)
                  }
          ACCESS read-write
          STATUS mandatory
          DESCRIPTION
               ""
          ::= { teraAPONConfigTableEntry 3 }

teraAPONMinUpCps OBJECT-TYPE
          SYNTAX INTEGER (0..65535)
          ACCESS read-only
          STATUS mandatory
          DESCRIPTION
               ""
          ::= { teraAPONConfigTableEntry 4 }

teraAPONMaxUpCps OBJECT-TYPE
          SYNTAX INTEGER
          ACCESS read-only
          STATUS mandatory
          DESCRIPTION
               ""
          ::= { teraAPONConfigTableEntry 5 }

teraAPONMinUpKbps OBJECT-TYPE
          SYNTAX INTEGER (0..65535)
          ACCESS read-only
          STATUS mandatory
          DESCRIPTION
               ""
          ::= { teraAPONConfigTableEntry 6 }

teraAPONMaxUpKbps OBJECT-TYPE
          SYNTAX INTEGER
          ACCESS read-only
          STATUS mandatory
          DESCRIPTION
               ""
          ::= { teraAPONConfigTableEntry 7 }

teraAPONMaxDwnCps OBJECT-TYPE
          SYNTAX INTEGER
          ACCESS read-only
          STATUS mandatory
          DESCRIPTION
               ""
          ::= { teraAPONConfigTableEntry 8 }

teraAPONMaxDwnKbps OBJECT-TYPE
          SYNTAX INTEGER
          ACCESS read-only
          STATUS mandatory
          DESCRIPTION
               ""
          ::= { teraAPONConfigTableEntry 9 }

teraAPONLsbStatus OBJECT-TYPE
          SYNTAX INTEGER
                  {
                  none(0),
                  master(1),
                  slave(2)
                  }
          ACCESS read-only
          STATUS mandatory
          DESCRIPTION
               ""
          ::= { teraAPONConfigTableEntry 10 }

     -- teraLiteAPONCurrentTable

teraLiteAPONCurrentTable OBJECT-TYPE
     SYNTAX SEQUENCE OF TeraLiteAPONCurrentTableEntryType
     ACCESS not-accessible
     STATUS mandatory
     DESCRIPTION
          " table teraLiteAPONCurrentTable"
     ::= { teraAPONConfig 2 }

teraLiteAPONCurrentTableEntry OBJECT-TYPE
          SYNTAX TeraLiteAPONCurrentTableEntryType
          ACCESS not-accessible
          STATUS mandatory
          DESCRIPTION
               " table entry teraLiteAPONCurrentTableEntry "
          INDEX {                   ifIndex }
     ::= { teraLiteAPONCurrentTable 1 }

TeraLiteAPONCurrentTableEntryType ::= SEQUENCE {
          teraLiteAPONCurrentESs   
             Gauge32,
          teraLiteAPONCurrentSESs   
             Gauge32,
          teraLiteAPONCurrentCVs   
             Gauge32,
          teraLiteAPONCurrentUASs   
             Gauge32
}

teraLiteAPONCurrentESs OBJECT-TYPE
          SYNTAX Gauge32
          ACCESS read-only
          STATUS mandatory
          DESCRIPTION
               ""
          ::= { teraLiteAPONCurrentTableEntry 1 }

teraLiteAPONCurrentSESs OBJECT-TYPE
          SYNTAX Gauge32
          ACCESS read-only
          STATUS mandatory
          DESCRIPTION
               ""
          ::= { teraLiteAPONCurrentTableEntry 2 }

teraLiteAPONCurrentCVs OBJECT-TYPE
          SYNTAX Gauge32
          ACCESS read-only
          STATUS mandatory
          DESCRIPTION
               ""
          ::= { teraLiteAPONCurrentTableEntry 3 }

teraLiteAPONCurrentUASs OBJECT-TYPE
          SYNTAX Gauge32
          ACCESS read-only
          STATUS mandatory
          DESCRIPTION
               ""
          ::= { teraLiteAPONCurrentTableEntry 4 }

     -- teraLiteAPONIntervalTable

teraLiteAPONIntervalTable OBJECT-TYPE
     SYNTAX SEQUENCE OF TeraLiteAPONIntervalTableEntryType
     ACCESS not-accessible
     STATUS mandatory
     DESCRIPTION
          " table teraLiteAPONIntervalTable"
     ::= { teraAPONConfig 3 }

teraLiteAPONIntervalTableEntry OBJECT-TYPE
          SYNTAX TeraLiteAPONIntervalTableEntryType
          ACCESS not-accessible
          STATUS mandatory
          DESCRIPTION
               " table entry teraLiteAPONIntervalTableEntry "
          INDEX {                   ifIndex,                  teraLiteAPONIntervalNumber }
     ::= { teraLiteAPONIntervalTable 1 }

TeraLiteAPONIntervalTableEntryType ::= SEQUENCE {
          teraLiteAPONIntervalNumber   
             INTEGER (1..96),
          teraLiteAPONIntervalESs   
             Gauge32,
          teraLiteAPONIntervalSESs   
             Gauge32,
          teraLiteAPONIntervalCVs   
             Gauge32,
          teraLiteAPONIntervalUASs   
             Gauge32,
          teraLiteAPONIntervalValidData   
             INTEGER
}

teraLiteAPONIntervalNumber OBJECT-TYPE
          SYNTAX INTEGER (1..96)
          ACCESS read-only
          STATUS mandatory
          DESCRIPTION
               ""
          ::= { teraLiteAPONIntervalTableEntry 1 }

teraLiteAPONIntervalESs OBJECT-TYPE
          SYNTAX Gauge32
          ACCESS read-only
          STATUS mandatory
          DESCRIPTION
               ""
          ::= { teraLiteAPONIntervalTableEntry 2 }

teraLiteAPONIntervalSESs OBJECT-TYPE
          SYNTAX Gauge32
          ACCESS read-only
          STATUS mandatory
          DESCRIPTION
               ""
          ::= { teraLiteAPONIntervalTableEntry 3 }

teraLiteAPONIntervalCVs OBJECT-TYPE
          SYNTAX Gauge32
          ACCESS read-only
          STATUS mandatory
          DESCRIPTION
               ""
          ::= { teraLiteAPONIntervalTableEntry 4 }

teraLiteAPONIntervalUASs OBJECT-TYPE
          SYNTAX Gauge32
          ACCESS read-only
          STATUS mandatory
          DESCRIPTION
               ""
          ::= { teraLiteAPONIntervalTableEntry 5 }

teraLiteAPONIntervalValidData OBJECT-TYPE
          SYNTAX INTEGER
          ACCESS read-only
          STATUS mandatory
          DESCRIPTION
               ""
          ::= { teraLiteAPONIntervalTableEntry 6 }

     -- teraLiteAPONCurrTotalTable

teraLiteAPONCurrTotalTable OBJECT-TYPE
     SYNTAX SEQUENCE OF TeraLiteAPONCurrTotalTableEntryType
     ACCESS not-accessible
     STATUS mandatory
     DESCRIPTION
          " table teraLiteAPONCurrTotalTable"
     ::= { teraAPONConfig 4 }

teraLiteAPONCurrTotalTableEntry OBJECT-TYPE
          SYNTAX TeraLiteAPONCurrTotalTableEntryType
          ACCESS not-accessible
          STATUS mandatory
          DESCRIPTION
               " table entry teraLiteAPONCurrTotalTableEntry "
          INDEX {                   ifIndex }
     ::= { teraLiteAPONCurrTotalTable 1 }

TeraLiteAPONCurrTotalTableEntryType ::= SEQUENCE {
          teraLiteAPONCurrTotalESs   
             Gauge32,
          teraLiteAPONCurrTotalSESs   
             Gauge32,
          teraLiteAPONCurrTotalCVs   
             Gauge32,
          teraLiteAPONCurrTotalUASs   
             Gauge32,
          teraLiteAPONTotalPerfStat   
             INTEGER
}

teraLiteAPONCurrTotalESs OBJECT-TYPE
          SYNTAX Gauge32
          ACCESS read-only
          STATUS mandatory
          DESCRIPTION
               ""
          ::= { teraLiteAPONCurrTotalTableEntry 1 }

teraLiteAPONCurrTotalSESs OBJECT-TYPE
          SYNTAX Gauge32
          ACCESS read-only
          STATUS mandatory
          DESCRIPTION
               ""
          ::= { teraLiteAPONCurrTotalTableEntry 2 }

teraLiteAPONCurrTotalCVs OBJECT-TYPE
          SYNTAX Gauge32
          ACCESS read-only
          STATUS mandatory
          DESCRIPTION
               ""
          ::= { teraLiteAPONCurrTotalTableEntry 3 }

teraLiteAPONCurrTotalUASs OBJECT-TYPE
          SYNTAX Gauge32
          ACCESS read-only
          STATUS mandatory
          DESCRIPTION
               ""
          ::= { teraLiteAPONCurrTotalTableEntry 4 }

teraLiteAPONTotalPerfStat OBJECT-TYPE
          SYNTAX INTEGER
                  {
                  ok(1),
                  clear(2)
                  }
          ACCESS read-write
          STATUS mandatory
          DESCRIPTION
               ""
          ::= { teraLiteAPONCurrTotalTableEntry 5 }

     -- teraLiteAPONTotalTable

teraLiteAPONTotalTable OBJECT-TYPE
     SYNTAX SEQUENCE OF TeraLiteAPONTotalTableEntryType
     ACCESS not-accessible
     STATUS mandatory
     DESCRIPTION
          " table teraLiteAPONTotalTable"
     ::= { teraAPONConfig 5 }

teraLiteAPONTotalTableEntry OBJECT-TYPE
          SYNTAX TeraLiteAPONTotalTableEntryType
          ACCESS not-accessible
          STATUS mandatory
          DESCRIPTION
               " table entry teraLiteAPONTotalTableEntry "
          INDEX {                   ifIndex,                  teraLiteAPONTotalNumber }
     ::= { teraLiteAPONTotalTable 1 }

TeraLiteAPONTotalTableEntryType ::= SEQUENCE {
          teraLiteAPONTotalNumber   
             INTEGER (0..7),
          teraLiteAPONTotalESs   
             Gauge32,
          teraLiteAPONTotalSESs   
             Gauge32,
          teraLiteAPONTotalCVs   
             Gauge32,
          teraLiteAPONTotalUASs   
             Gauge32,
          teraLiteAPONTotalValidData   
             INTEGER
}

teraLiteAPONTotalNumber OBJECT-TYPE
          SYNTAX INTEGER (0..7)
          ACCESS read-only
          STATUS mandatory
          DESCRIPTION
               ""
          ::= { teraLiteAPONTotalTableEntry 1 }

teraLiteAPONTotalESs OBJECT-TYPE
          SYNTAX Gauge32
          ACCESS read-only
          STATUS mandatory
          DESCRIPTION
               ""
          ::= { teraLiteAPONTotalTableEntry 2 }

teraLiteAPONTotalSESs OBJECT-TYPE
          SYNTAX Gauge32
          ACCESS read-only
          STATUS mandatory
          DESCRIPTION
               ""
          ::= { teraLiteAPONTotalTableEntry 3 }

teraLiteAPONTotalCVs OBJECT-TYPE
          SYNTAX Gauge32
          ACCESS read-only
          STATUS mandatory
          DESCRIPTION
               ""
          ::= { teraLiteAPONTotalTableEntry 4 }

teraLiteAPONTotalUASs OBJECT-TYPE
          SYNTAX Gauge32
          ACCESS read-only
          STATUS mandatory
          DESCRIPTION
               ""
          ::= { teraLiteAPONTotalTableEntry 5 }

teraLiteAPONTotalValidData OBJECT-TYPE
          SYNTAX INTEGER
          ACCESS read-only
          STATUS mandatory
          DESCRIPTION
               ""
          ::= { teraLiteAPONTotalTableEntry 6 }

     -- teraVpiVciTable

teraVpiVciTable OBJECT-TYPE
     SYNTAX SEQUENCE OF TeraVpiVciTableEntryType
     ACCESS not-accessible
     STATUS mandatory
     DESCRIPTION
          " table teraVpiVciTable"
     ::= { teraAPONConfig 14 }

teraVpiVciTableEntry OBJECT-TYPE
          SYNTAX TeraVpiVciTableEntryType
          ACCESS not-accessible
          STATUS mandatory
          DESCRIPTION
               " table entry teraVpiVciTableEntry "
          INDEX {                   teraVci,                  teraVpi }
     ::= { teraVpiVciTable 1 }

TeraVpiVciTableEntryType ::= SEQUENCE {
          teraVci   
             INTEGER,
          teraVpi   
             INTEGER
}

teraVci OBJECT-TYPE
          SYNTAX INTEGER
          ACCESS read-only
          STATUS mandatory
          DESCRIPTION
               ""
          ::= { teraVpiVciTableEntry 1 }

teraVpi OBJECT-TYPE
          SYNTAX INTEGER
          ACCESS read-only
          STATUS mandatory
          DESCRIPTION
               ""
          ::= { teraVpiVciTableEntry 2 }

     -- teraPONInstallCfgTable

teraPONInstallCfgTable OBJECT-TYPE
     SYNTAX SEQUENCE OF TeraPONInstallCfgTableEntryType
     ACCESS not-accessible
     STATUS mandatory
     DESCRIPTION
          " table teraPONInstallCfgTable"
     ::= { teraAPONConfig 15 }

teraPONInstallCfgTableEntry OBJECT-TYPE
          SYNTAX TeraPONInstallCfgTableEntryType
          ACCESS not-accessible
          STATUS mandatory
          DESCRIPTION
               " table entry teraPONInstallCfgTableEntry "
          INDEX {                   teraInstallSlotNumber }
     ::= { teraPONInstallCfgTable 1 }

TeraPONInstallCfgTableEntryType ::= SEQUENCE {
          teraPONInstallNEDiscoveryInterval   
             INTEGER (500..4320000),
          teraPONInstallNEChurningKeyChangeTime   
             INTEGER (500..4320000),
          teraPONInstallNERangingPollingInterval   
             INTEGER (360000..4320000),
          teraPONInstallNERangingInterval   
             INTEGER (1..10000),
          teraPONInstallNEMinDistance   
             INTEGER (0..100),
          teraPONInstallNEMaxDistance   
             INTEGER (0..100),
          teraPONInstallNEForceDistanceChange   
             INTEGER,
          teraPONInstallNEDistanceChangeResult   
             INTEGER
}

teraPONInstallNEDiscoveryInterval OBJECT-TYPE
          SYNTAX INTEGER (500..4320000)
          ACCESS read-write
          STATUS mandatory
          DESCRIPTION
               ""
          ::= { teraPONInstallCfgTableEntry 1 }

teraPONInstallNEChurningKeyChangeTime OBJECT-TYPE
          SYNTAX INTEGER (500..4320000)
          ACCESS read-write
          STATUS mandatory
          DESCRIPTION
               ""
          ::= { teraPONInstallCfgTableEntry 2 }

teraPONInstallNERangingPollingInterval OBJECT-TYPE
          SYNTAX INTEGER (360000..4320000)
          ACCESS read-write
          STATUS mandatory
          DESCRIPTION
               ""
          ::= { teraPONInstallCfgTableEntry 3 }

teraPONInstallNERangingInterval OBJECT-TYPE
          SYNTAX INTEGER (1..10000)
          ACCESS read-write
          STATUS mandatory
          DESCRIPTION
               ""
          ::= { teraPONInstallCfgTableEntry 4 }

teraPONInstallNEMinDistance OBJECT-TYPE
          SYNTAX INTEGER (0..100)
          ACCESS read-write
          STATUS mandatory
          DESCRIPTION
               ""
          ::= { teraPONInstallCfgTableEntry 5 }

teraPONInstallNEMaxDistance OBJECT-TYPE
          SYNTAX INTEGER (0..100)
          ACCESS read-write
          STATUS mandatory
          DESCRIPTION
               ""
          ::= { teraPONInstallCfgTableEntry 6 }

teraPONInstallNEForceDistanceChange OBJECT-TYPE
          SYNTAX INTEGER
                  {
                  no(0),
                  yes(1)
                  }
          ACCESS read-write
          STATUS mandatory
          DESCRIPTION
               ""
          ::= { teraPONInstallCfgTableEntry 7 }

teraPONInstallNEDistanceChangeResult OBJECT-TYPE
          SYNTAX INTEGER
                  {
                  success(0),
                  oNT-ReRanged(1),
                  fail(2)
                  }
          ACCESS read-only
          STATUS mandatory
          DESCRIPTION
               ""
          ::= { teraPONInstallCfgTableEntry 8 }

     -- teraLiteAPONBWUsageCurrentTable

teraLiteAPONBWUsageCurrentTable OBJECT-TYPE
     SYNTAX SEQUENCE OF TeraLiteAPONBWUsageCurrentTableEntryType
     ACCESS not-accessible
     STATUS mandatory
     DESCRIPTION
          " table teraLiteAPONBWUsageCurrentTable"
     ::= { teraAPONConfig 16 }

teraLiteAPONBWUsageCurrentTableEntry OBJECT-TYPE
          SYNTAX TeraLiteAPONBWUsageCurrentTableEntryType
          ACCESS not-accessible
          STATUS mandatory
          DESCRIPTION
               " table entry teraLiteAPONBWUsageCurrentTableEntry "
          INDEX {                   ifIndex }
     ::= { teraLiteAPONBWUsageCurrentTable 1 }

TeraLiteAPONBWUsageCurrentTableEntryType ::= SEQUENCE {
          teraLiteAPONBWUsageCurrentUpCellCnt   
             Counter64,
          teraLiteAPONBWUsageCurrentBIPErrCnt   
             Gauge32,
          teraLiteAPONBWUsageCurrentHECErrCnt   
             Gauge32,
          teraLiteAPONBWUsageCurrentCRC8ErrCnt   
             Gauge32,
          teraLiteAPONBWUsageCurrentDwnCellCnt   
             Counter64
}

teraLiteAPONBWUsageCurrentUpCellCnt OBJECT-TYPE
          SYNTAX Counter64
          ACCESS read-only
          STATUS mandatory
          DESCRIPTION
               ""
          ::= { teraLiteAPONBWUsageCurrentTableEntry 1 }

teraLiteAPONBWUsageCurrentBIPErrCnt OBJECT-TYPE
          SYNTAX Gauge32
          ACCESS read-only
          STATUS mandatory
          DESCRIPTION
               ""
          ::= { teraLiteAPONBWUsageCurrentTableEntry 2 }

teraLiteAPONBWUsageCurrentHECErrCnt OBJECT-TYPE
          SYNTAX Gauge32
          ACCESS read-only
          STATUS mandatory
          DESCRIPTION
               ""
          ::= { teraLiteAPONBWUsageCurrentTableEntry 3 }

teraLiteAPONBWUsageCurrentCRC8ErrCnt OBJECT-TYPE
          SYNTAX Gauge32
          ACCESS read-only
          STATUS mandatory
          DESCRIPTION
               ""
          ::= { teraLiteAPONBWUsageCurrentTableEntry 4 }

teraLiteAPONBWUsageCurrentDwnCellCnt OBJECT-TYPE
          SYNTAX Counter64
          ACCESS read-only
          STATUS mandatory
          DESCRIPTION
               ""
          ::= { teraLiteAPONBWUsageCurrentTableEntry 5 }

     -- teraLiteAPONBWUsageIntervalTable

teraLiteAPONBWUsageIntervalTable OBJECT-TYPE
     SYNTAX SEQUENCE OF TeraLiteAPONBWUsageIntervalTableEntryType
     ACCESS not-accessible
     STATUS mandatory
     DESCRIPTION
          " table teraLiteAPONBWUsageIntervalTable"
     ::= { teraAPONConfig 17 }

teraLiteAPONBWUsageIntervalTableEntry OBJECT-TYPE
          SYNTAX TeraLiteAPONBWUsageIntervalTableEntryType
          ACCESS not-accessible
          STATUS mandatory
          DESCRIPTION
               " table entry teraLiteAPONBWUsageIntervalTableEntry "
          INDEX {                   ifIndex,                  teraLiteAPONBWUsageIntervalNumber }
     ::= { teraLiteAPONBWUsageIntervalTable 1 }

TeraLiteAPONBWUsageIntervalTableEntryType ::= SEQUENCE {
          teraLiteAPONBWUsageIntervalNumber   
             INTEGER (1..96),
          teraLiteAPONBWUsageIntervalUpCellCnt   
             Counter64,
          teraLiteAPONBWUsageIntervalBIPErrCnt   
             Gauge32,
          teraLiteAPONBWUsageIntervalHECErrCnt   
             Gauge32,
          teraLiteAPONBWUsageIntervalCRC8ErrCnt   
             Gauge32,
          teraLiteAPONBWUsageIntervalDwnCellCnt   
             Counter64,
          teraLiteAPONBWUsageIntervalValidData   
             INTEGER
}

teraLiteAPONBWUsageIntervalNumber OBJECT-TYPE
          SYNTAX INTEGER (1..96)
          ACCESS read-only
          STATUS mandatory
          DESCRIPTION
               ""
          ::= { teraLiteAPONBWUsageIntervalTableEntry 1 }

teraLiteAPONBWUsageIntervalUpCellCnt OBJECT-TYPE
          SYNTAX Counter64
          ACCESS read-only
          STATUS mandatory
          DESCRIPTION
               ""
          ::= { teraLiteAPONBWUsageIntervalTableEntry 2 }

teraLiteAPONBWUsageIntervalBIPErrCnt OBJECT-TYPE
          SYNTAX Gauge32
          ACCESS read-only
          STATUS mandatory
          DESCRIPTION
               ""
          ::= { teraLiteAPONBWUsageIntervalTableEntry 3 }

teraLiteAPONBWUsageIntervalHECErrCnt OBJECT-TYPE
          SYNTAX Gauge32
          ACCESS read-only
          STATUS mandatory
          DESCRIPTION
               ""
          ::= { teraLiteAPONBWUsageIntervalTableEntry 4 }

teraLiteAPONBWUsageIntervalCRC8ErrCnt OBJECT-TYPE
          SYNTAX Gauge32
          ACCESS read-only
          STATUS mandatory
          DESCRIPTION
               ""
          ::= { teraLiteAPONBWUsageIntervalTableEntry 5 }

teraLiteAPONBWUsageIntervalDwnCellCnt OBJECT-TYPE
          SYNTAX Counter64
          ACCESS read-only
          STATUS mandatory
          DESCRIPTION
               ""
          ::= { teraLiteAPONBWUsageIntervalTableEntry 6 }

teraLiteAPONBWUsageIntervalValidData OBJECT-TYPE
          SYNTAX INTEGER
          ACCESS read-only
          STATUS mandatory
          DESCRIPTION
               ""
          ::= { teraLiteAPONBWUsageIntervalTableEntry 7 }

     -- teraLiteAPONBWUsageCurrTotalTable

teraLiteAPONBWUsageCurrTotalTable OBJECT-TYPE
     SYNTAX SEQUENCE OF TeraLiteAPONBWUsageCurrTotalTableEntryType
     ACCESS not-accessible
     STATUS mandatory
     DESCRIPTION
          " table teraLiteAPONBWUsageCurrTotalTable"
     ::= { teraAPONConfig 18 }

teraLiteAPONBWUsageCurrTotalTableEntry OBJECT-TYPE
          SYNTAX TeraLiteAPONBWUsageCurrTotalTableEntryType
          ACCESS not-accessible
          STATUS mandatory
          DESCRIPTION
               " table entry teraLiteAPONBWUsageCurrTotalTableEntry "
          INDEX {                   ifIndex }
     ::= { teraLiteAPONBWUsageCurrTotalTable 1 }

TeraLiteAPONBWUsageCurrTotalTableEntryType ::= SEQUENCE {
          teraLiteAPONBWUsageCurrTotalUpCellCnt   
             Counter64,
          teraLiteAPONBWUsageCurrTotalBIPErrCnt   
             Gauge32,
          teraLiteAPONBWUsageCurrTotalHECErrCnt   
             Gauge32,
          teraLiteAPONBWUsageCurrTotalCRC8ErrCnt   
             Gauge32,
          teraLiteAPONBWUsageCurrTotalDwnCellCnt   
             Counter64,
          teraLiteAPONBWTotalPerfStat   
             INTEGER
}

teraLiteAPONBWUsageCurrTotalUpCellCnt OBJECT-TYPE
          SYNTAX Counter64
          ACCESS read-only
          STATUS mandatory
          DESCRIPTION
               ""
          ::= { teraLiteAPONBWUsageCurrTotalTableEntry 1 }

teraLiteAPONBWUsageCurrTotalBIPErrCnt OBJECT-TYPE
          SYNTAX Gauge32
          ACCESS read-only
          STATUS mandatory
          DESCRIPTION
               ""
          ::= { teraLiteAPONBWUsageCurrTotalTableEntry 2 }

teraLiteAPONBWUsageCurrTotalHECErrCnt OBJECT-TYPE
          SYNTAX Gauge32
          ACCESS read-only
          STATUS mandatory
          DESCRIPTION
               ""
          ::= { teraLiteAPONBWUsageCurrTotalTableEntry 3 }

teraLiteAPONBWUsageCurrTotalCRC8ErrCnt OBJECT-TYPE
          SYNTAX Gauge32
          ACCESS read-only
          STATUS mandatory
          DESCRIPTION
               ""
          ::= { teraLiteAPONBWUsageCurrTotalTableEntry 4 }

teraLiteAPONBWUsageCurrTotalDwnCellCnt OBJECT-TYPE
          SYNTAX Counter64
          ACCESS read-only
          STATUS mandatory
          DESCRIPTION
               ""
          ::= { teraLiteAPONBWUsageCurrTotalTableEntry 5 }

teraLiteAPONBWTotalPerfStat OBJECT-TYPE
          SYNTAX INTEGER
                  {
                  ok(1),
                  clear(2)
                  }
          ACCESS read-write
          STATUS mandatory
          DESCRIPTION
               ""
          ::= { teraLiteAPONBWUsageCurrTotalTableEntry 6 }

     -- teraLiteAPONBWUsageTotalTable

teraLiteAPONBWUsageTotalTable OBJECT-TYPE
     SYNTAX SEQUENCE OF TeraLiteAPONBWUsageTotalTableEntryType
     ACCESS not-accessible
     STATUS mandatory
     DESCRIPTION
          " table teraLiteAPONBWUsageTotalTable"
     ::= { teraAPONConfig 19 }

teraLiteAPONBWUsageTotalTableEntry OBJECT-TYPE
          SYNTAX TeraLiteAPONBWUsageTotalTableEntryType
          ACCESS not-accessible
          STATUS mandatory
          DESCRIPTION
               " table entry teraLiteAPONBWUsageTotalTableEntry "
          INDEX {                   ifIndex,                  teraLiteAPONBWUsageTotalNumber }
     ::= { teraLiteAPONBWUsageTotalTable 1 }

TeraLiteAPONBWUsageTotalTableEntryType ::= SEQUENCE {
          teraLiteAPONBWUsageTotalNumber   
             INTEGER (1..7),
          teraLiteAPONBWUsageTotalUpCellCnt   
             Counter64,
          teraLiteAPONBWUsageTotalBIPErrCnt   
             Gauge32,
          teraLiteAPONBWUsageTotalHECErrCnt   
             Gauge32,
          teraLiteAPONBWUsageTotalCRC8ErrCnt   
             Gauge32,
          teraLiteAPONBWUsageTotalDwnCellCnt   
             Counter64,
          teraLiteAPONBWUsageTotalValidData   
             INTEGER
}

teraLiteAPONBWUsageTotalNumber OBJECT-TYPE
          SYNTAX INTEGER (1..7)
          ACCESS read-only
          STATUS mandatory
          DESCRIPTION
               ""
          ::= { teraLiteAPONBWUsageTotalTableEntry 1 }

teraLiteAPONBWUsageTotalUpCellCnt OBJECT-TYPE
          SYNTAX Counter64
          ACCESS read-only
          STATUS mandatory
          DESCRIPTION
               ""
          ::= { teraLiteAPONBWUsageTotalTableEntry 2 }

teraLiteAPONBWUsageTotalBIPErrCnt OBJECT-TYPE
          SYNTAX Gauge32
          ACCESS read-only
          STATUS mandatory
          DESCRIPTION
               ""
          ::= { teraLiteAPONBWUsageTotalTableEntry 3 }

teraLiteAPONBWUsageTotalHECErrCnt OBJECT-TYPE
          SYNTAX Gauge32
          ACCESS read-only
          STATUS mandatory
          DESCRIPTION
               ""
          ::= { teraLiteAPONBWUsageTotalTableEntry 4 }

teraLiteAPONBWUsageTotalCRC8ErrCnt OBJECT-TYPE
          SYNTAX Gauge32
          ACCESS read-only
          STATUS mandatory
          DESCRIPTION
               ""
          ::= { teraLiteAPONBWUsageTotalTableEntry 5 }

teraLiteAPONBWUsageTotalDwnCellCnt OBJECT-TYPE
          SYNTAX Counter64
          ACCESS read-only
          STATUS mandatory
          DESCRIPTION
               ""
          ::= { teraLiteAPONBWUsageTotalTableEntry 6 }

teraLiteAPONBWUsageTotalValidData OBJECT-TYPE
          SYNTAX INTEGER
          ACCESS read-only
          STATUS mandatory
          DESCRIPTION
               ""
          ::= { teraLiteAPONBWUsageTotalTableEntry 7 }

END
