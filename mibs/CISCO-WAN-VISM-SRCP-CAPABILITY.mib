-- *****************************************************************
-- ciscoWanVismSrcpCapabilities MIB
--
-- AGENT-CAPABILITIES mib for CISCO-WAN-SRCP-MIB in the VISM product
--
-- Copyright(c) 2000 by Cisco Systems,Inc.
--
-- Author: Ganga Purlupady

-- Modified based on vism 2.0.3 release - Sushma Srikanth
-- *****************************************************************

CISCO-WAN-VISM-SRCP-CAPABILITY DEFINITIONS ::= BEGIN

IMPORTS
        MODULE-IDENTITY,
        Integer32
                FROM SNMPv2-SMI
        AGENT-CAPABILITIES
                FROM SNMPv2-CONF
        ciscoWanAgentCapability
                FROM CISCOWAN-SMI;   

ciscoWanVismSrcpCapability MODULE-IDENTITY
        LAST-UPDATED    "200109080000Z"
        ORGANIZATION    "Cisco Systems, Inc."
        CONTACT-INFO
                "       Cisco Systems
                        Customer Service

                Postal: 170 W Tasman Drive
                        San Jose, CA  95134
                        USA

                        Tel: +1 800 553-NETS

                E-mail: cs-vism@cisco.com"
        DESCRIPTION
                "The Agent Capabilities for CISCO-WAN-SRCP-MIB."

        REVISION   "200007210000Z"
        DESCRIPTION  
                "added ciscoWanVismSrcpCapabilityV2R01 macro
                "
        ::= { ciscoWanAgentCapability 321 }

ciscoWanVismSrcpCapabilityV2R00 AGENT-CAPABILITIES
    PRODUCT-RELEASE      "VISM Release1.5,VISM Release2.0"
    STATUS                current
    DESCRIPTION          "SRCP MIB Capabilities"

    SUPPORTS CISCO-WAN-SRCP-MIB
    INCLUDES { srcpConfigurationGroup3, srcpStatisticsGroup2 }

	VARIATION   srcpPortNumber
	ACCESS      read-only
	DESCRIPTION "Write access is not supported."

	VARIATION   srcpPeerId
	SYNTAX      Integer32(1..8)
	DESCRIPTION "Supports range 1-8 only."

    ::= { ciscoWanVismSrcpCapability 1 }

ciscoWanVismSrcpCapabilityV2R01 AGENT-CAPABILITIES
     PRODUCT-RELEASE  "VISM release 2.0.3"
     STATUS            current
     DESCRIPTION      "SRCP MIB Capabilities"

     SUPPORTS   CISCO-WAN-SRCP-MIB
     INCLUDES   { srcpConfigurationGroup3, srcpStatisticsGroup2 }

--   VARIATION   srcpRequestTimeOut
--   SYNTAX      Integer32 (1..10000)
--   ACCESS      read-write
--   DESCRIPTION
--            "write supported with the above restricted range"

--   VARIATION   srcpRequestRetries
--   SYNTAX       Integer32 (0..10)
--   DESCRIPTION
--            "write supported with the above restricted range"  

--   VARIATION   srcpRequestMaxTimeout
--   SYNTAX      Integer32 (1..10000)
--   DESCRIPTION
--             "write supported with the above restricted range"

     ::= {ciscoWanVismSrcpCapability 2}

END
