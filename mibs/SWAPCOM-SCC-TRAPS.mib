SWAPCOM-SCC-TRAPS	DEFINITIONS ::= BEGIN

	IMPORTS
		NOTIFICATION-TYPE, enterprises, MODULE-IDENTITY, OBJECT-TYPE, TimeTicks,
		IpAddress, Gauge32, Counter32, Counter64
			FROM SNMPv2-SMI
		MacAddress, TimeInterval, TruthValue, TestAndIncr,
		RowStatus, DisplayString, StorageType, DateAndTime
			FROM SNMPv2-TC
		IpAddress
			FROM RFC1155-SMI
		DisplayString
			FROM RFC1213-MIB
		alarmProbeSeverity, alarmProbeAlertSource, alarmProbeAlertType
			FROM SWAPCOM-SCC;

swapcom	MODULE-IDENTITY
LAST-UPDATED	"2007381648Z"
ORGANIZATION	"Organization name"
CONTACT-INFO	"Contact information"
DESCRIPTION	"Description"
REVISION	"2007381648Z"
DESCRIPTION	"Revision Description"
::=	{	enterprises	11308
	 }

org	OBJECT IDENTIFIER
::=	{	iso	3
	}

dod	OBJECT IDENTIFIER
::=	{	org	6
	}

internet	OBJECT IDENTIFIER
::=	{	dod	1
	}

private	OBJECT IDENTIFIER
::=	{	internet	4
	}

enterprises	OBJECT IDENTIFIER
::=	{	private	1
	}

sccTraps	OBJECT IDENTIFIER
::=	{	swapcom	4
	}


sqlPoolUnavailable NOTIFICATION-TYPE
  OBJECTS
    { alarmProbeAlertType,
      alarmProbeAlertSource,
      alarmProbeSeverity }
  STATUS current
  DESCRIPTION ""
::= { sccTraps 1 }

sqlPoolHighCheckedOutConnections NOTIFICATION-TYPE
  OBJECTS
    { alarmProbeAlertType,
      alarmProbeAlertSource,
      alarmProbeSeverity }
  STATUS current
  DESCRIPTION ""
::= { sccTraps 2 }

slsUnavailable NOTIFICATION-TYPE
  OBJECTS
    { alarmProbeAlertType,
      alarmProbeAlertSource,
      alarmProbeSeverity }
  STATUS current
  DESCRIPTION ""
::= { sccTraps 3 }

remotePlatformUnavailable NOTIFICATION-TYPE
  OBJECTS
    { alarmProbeAlertType,
      alarmProbeAlertSource,
      alarmProbeSeverity }
  STATUS current
  DESCRIPTION ""
::= { sccTraps 4 }

schedulerTaskError NOTIFICATION-TYPE
  OBJECTS
    { alarmProbeAlertType,
      alarmProbeAlertSource,
      alarmProbeSeverity }
  STATUS current
  DESCRIPTION ""
::= { sccTraps 5 }

END
