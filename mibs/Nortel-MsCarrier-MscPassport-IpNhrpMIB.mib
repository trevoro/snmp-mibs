Nortel-MsCarrier-MscPassport-IpNhrpMIB
DEFINITIONS ::= BEGIN



IMPORTS

      OBJECT-TYPE
   FROM RFC-1212

      IpAddress
   FROM RFC1155-SMI

      mscPassportMIBs
   FROM Nortel-MsCarrier-MscPassport-UsefulDefinitionsMIB

      Counter32,
      RowPointer,
      DisplayString,
      StorageType,
      RowStatus,
      Integer32,
      Unsigned32
   FROM Nortel-MsCarrier-MscPassport-StandardTextualConventionsMIB

      NonReplicated,
      HexString
   FROM Nortel-MsCarrier-MscPassport-TextualConventionsMIB

      mscVrIpIndex,
      mscVrPpIpPortIndex,
      mscVrIp,
      mscVrPpIpPortLogicalIf,
      mscVrPpIpPortLogicalIfAddressIndex
   FROM Nortel-MsCarrier-MscPassport-IpMIB

      mscVrIndex,
      mscVrPpIndex
   FROM Nortel-MsCarrier-MscPassport-VirtualRouterMIB;




-- LAST-UPDATED   "9909010000Z"
-- ORGANIZATION   "Nortel Networks"
-- CONTACT-INFO   "
--         Nortel Carrier Data Network Management
--         
--         Postal:       P.O. Box 3511, Station C 
--                       Ottawa, Ontario 
--                       Canada  K1Y 4H7
--         
--         via the WEB:  http://www.nortelnetworks.com  
--                       select 'Contact Us' from the menu
--          
--         via phone:    1-800-4NORTEL"
-- DESCRIPTION
--    "The module describing the Nortel MsCarrier MscPassport
--     IpNhrp Enterprise MIB."

ipNhrpMIB OBJECT IDENTIFIER ::= { mscPassportMIBs 77 }










-- Vr/x Pp/x IpPort LogicalIf/<ipAddress> NhrpInterface
-- This component is used to configure a LogicalIf to run NHRP 
-- protocol.

mscVrPpIpPortLogicalIfNhrpIf OBJECT IDENTIFIER ::= { mscVrPpIpPortLogicalIf 4 }



mscVrPpIpPortLogicalIfNhrpIfRowStatusTable OBJECT-TYPE
   SYNTAX     SEQUENCE OF MscVrPpIpPortLogicalIfNhrpIfRowStatusEntry
   ACCESS     not-accessible
   STATUS     mandatory
   DESCRIPTION
     "This entry controls the addition and deletion of 
      mscVrPpIpPortLogicalIfNhrpIf components."
::= { mscVrPpIpPortLogicalIfNhrpIf 1 }

mscVrPpIpPortLogicalIfNhrpIfRowStatusEntry OBJECT-TYPE
   SYNTAX     MscVrPpIpPortLogicalIfNhrpIfRowStatusEntry
   ACCESS     not-accessible
   STATUS     mandatory
   DESCRIPTION
     "A single entry in the table represents a single 
      mscVrPpIpPortLogicalIfNhrpIf component."
   INDEX {
      mscVrIndex,
      mscVrPpIndex,
      mscVrPpIpPortIndex,
      mscVrPpIpPortLogicalIfAddressIndex,
      mscVrPpIpPortLogicalIfNhrpIfIndex }
::= { mscVrPpIpPortLogicalIfNhrpIfRowStatusTable 1 }

MscVrPpIpPortLogicalIfNhrpIfRowStatusEntry ::= SEQUENCE {
   mscVrPpIpPortLogicalIfNhrpIfRowStatus
      RowStatus,
   mscVrPpIpPortLogicalIfNhrpIfComponentName
      DisplayString,
   mscVrPpIpPortLogicalIfNhrpIfStorageType
      StorageType,
   mscVrPpIpPortLogicalIfNhrpIfIndex
      NonReplicated }

mscVrPpIpPortLogicalIfNhrpIfRowStatus OBJECT-TYPE
   SYNTAX     RowStatus 
   ACCESS     read-write
   STATUS     mandatory
   DESCRIPTION
     "This variable is used as the basis for SNMP naming of
      mscVrPpIpPortLogicalIfNhrpIf components.
      These components can be added and deleted."
::= { mscVrPpIpPortLogicalIfNhrpIfRowStatusEntry 1 }

mscVrPpIpPortLogicalIfNhrpIfComponentName OBJECT-TYPE
   SYNTAX     DisplayString 
   ACCESS     read-only
   STATUS     mandatory
   DESCRIPTION
     "This variable provides the component's string name for
      use with the ASCII Console Interface"
::= { mscVrPpIpPortLogicalIfNhrpIfRowStatusEntry 2 }

mscVrPpIpPortLogicalIfNhrpIfStorageType OBJECT-TYPE
   SYNTAX     StorageType 
   ACCESS     read-only
   STATUS     mandatory
   DESCRIPTION
     "This variable represents the storage type value for the
      mscVrPpIpPortLogicalIfNhrpIf tables."
::= { mscVrPpIpPortLogicalIfNhrpIfRowStatusEntry 4 }

mscVrPpIpPortLogicalIfNhrpIfIndex OBJECT-TYPE
   SYNTAX     NonReplicated 
   ACCESS     not-accessible
   STATUS     mandatory
   DESCRIPTION
     "This variable represents the index for the mscVrPpIpPortLogicalIfNhrpIf tables."
::= { mscVrPpIpPortLogicalIfNhrpIfRowStatusEntry 10 }


-- Vr/<string> Ip NextHopResolutionProtocol
-- This component represents a co-located NHRP Client and Server as 
-- specified in RFC2332. NHRP provides a method for a station 
-- connected to a Non-Broadcast Multiple Access (NBMA) 
-- subnetwork to determine the internetworking layer address and 
-- NBMA subnetwork address of the "next hop" towards a destination 
-- station. NHRP reduces or eliminates the extra hops required by the 
-- existing logically independent IP subnet (LIS) model.

mscVrIpNhrp OBJECT IDENTIFIER ::= { mscVrIp 19 }



mscVrIpNhrpRowStatusTable OBJECT-TYPE
   SYNTAX     SEQUENCE OF MscVrIpNhrpRowStatusEntry
   ACCESS     not-accessible
   STATUS     mandatory
   DESCRIPTION
     "This entry controls the addition and deletion of 
      mscVrIpNhrp components."
::= { mscVrIpNhrp 1 }

mscVrIpNhrpRowStatusEntry OBJECT-TYPE
   SYNTAX     MscVrIpNhrpRowStatusEntry
   ACCESS     not-accessible
   STATUS     mandatory
   DESCRIPTION
     "A single entry in the table represents a single 
      mscVrIpNhrp component."
   INDEX {
      mscVrIndex,
      mscVrIpIndex,
      mscVrIpNhrpIndex }
::= { mscVrIpNhrpRowStatusTable 1 }

MscVrIpNhrpRowStatusEntry ::= SEQUENCE {
   mscVrIpNhrpRowStatus
      RowStatus,
   mscVrIpNhrpComponentName
      DisplayString,
   mscVrIpNhrpStorageType
      StorageType,
   mscVrIpNhrpIndex
      NonReplicated }

mscVrIpNhrpRowStatus OBJECT-TYPE
   SYNTAX     RowStatus 
   ACCESS     read-write
   STATUS     mandatory
   DESCRIPTION
     "This variable is used as the basis for SNMP naming of
      mscVrIpNhrp components.
      These components can be added and deleted."
::= { mscVrIpNhrpRowStatusEntry 1 }

mscVrIpNhrpComponentName OBJECT-TYPE
   SYNTAX     DisplayString 
   ACCESS     read-only
   STATUS     mandatory
   DESCRIPTION
     "This variable provides the component's string name for
      use with the ASCII Console Interface"
::= { mscVrIpNhrpRowStatusEntry 2 }

mscVrIpNhrpStorageType OBJECT-TYPE
   SYNTAX     StorageType 
   ACCESS     read-only
   STATUS     mandatory
   DESCRIPTION
     "This variable represents the storage type value for the
      mscVrIpNhrp tables."
::= { mscVrIpNhrpRowStatusEntry 4 }

mscVrIpNhrpIndex OBJECT-TYPE
   SYNTAX     NonReplicated 
   ACCESS     not-accessible
   STATUS     mandatory
   DESCRIPTION
     "This variable represents the index for the mscVrIpNhrp tables."
::= { mscVrIpNhrpRowStatusEntry 10 }

mscVrIpNhrpAdminControlTable OBJECT-TYPE
   SYNTAX     SEQUENCE OF MscVrIpNhrpAdminControlEntry
   ACCESS     not-accessible
   STATUS     mandatory
   DESCRIPTION
     "This group includes the Administrative Control attribute. This 
      attribute defines the current administrative state of this component."
::= { mscVrIpNhrp 10 }

mscVrIpNhrpAdminControlEntry OBJECT-TYPE
   SYNTAX     MscVrIpNhrpAdminControlEntry
   ACCESS     not-accessible
   STATUS     mandatory
   DESCRIPTION
     "An entry in the mscVrIpNhrpAdminControlTable."
   INDEX {
      mscVrIndex,
      mscVrIpIndex,
      mscVrIpNhrpIndex }
::= { mscVrIpNhrpAdminControlTable 1 }

MscVrIpNhrpAdminControlEntry ::= SEQUENCE {
   mscVrIpNhrpSnmpAdminStatus
      INTEGER }

mscVrIpNhrpSnmpAdminStatus OBJECT-TYPE
   SYNTAX     INTEGER  {
                 up(1),
                 down(2),
                 testing(3) }
   ACCESS     read-write
   STATUS     mandatory
   DESCRIPTION
     "The desired state of the interface. The up state indicates the 
      interface is operational and packet forwarding is allowed. The down 
      state indicates the interface is not operational and packet forwarding 
      is unavailable. The testing state indicates that no operational 
      packets can be passed."
   DEFVAL     { up }
::= { mscVrIpNhrpAdminControlEntry 1 }

mscVrIpNhrpProvTable OBJECT-TYPE
   SYNTAX     SEQUENCE OF MscVrIpNhrpProvEntry
   ACCESS     not-accessible
   STATUS     mandatory
   DESCRIPTION
     "This group contains the provisionable attributes of the Nhrp 
      component."
::= { mscVrIpNhrp 11 }

mscVrIpNhrpProvEntry OBJECT-TYPE
   SYNTAX     MscVrIpNhrpProvEntry
   ACCESS     not-accessible
   STATUS     mandatory
   DESCRIPTION
     "An entry in the mscVrIpNhrpProvTable."
   INDEX {
      mscVrIndex,
      mscVrIpIndex,
      mscVrIpNhrpIndex }
::= { mscVrIpNhrpProvTable 1 }

MscVrIpNhrpProvEntry ::= SEQUENCE {
   mscVrIpNhrpMaxResCacheEntries
      Unsigned32,
   mscVrIpNhrpFwdTransitRecord
      INTEGER,
   mscVrIpNhrpRevTransitRecord
      INTEGER }

mscVrIpNhrpMaxResCacheEntries OBJECT-TYPE
   SYNTAX     Unsigned32 (32..1024)
   ACCESS     read-write
   STATUS     mandatory
   DESCRIPTION
     "This attribute specifies the maximum number of ResCacheEntry 
      components which may exist under the Nhrp component at any one 
      time. Reducing the value of this attribute will not clear existing 
      entries."
   DEFVAL     { 512 }
::= { mscVrIpNhrpProvEntry 1 }

mscVrIpNhrpFwdTransitRecord OBJECT-TYPE
   SYNTAX     INTEGER  {
                 enabled(1),
                 disabled(2) }
   ACCESS     read-write
   STATUS     mandatory
   DESCRIPTION
     "This attribute specifies whether to attach a forward transit record 
      extension to NHRP packets (Resolution and Purge requests) that 
      Passport originates. This extension along with NHRP debug tracing 
      set to 'verbose' can be used in tracing the path the NHRP packet 
      takes from source to destination."
   DEFVAL     { disabled }
::= { mscVrIpNhrpProvEntry 2 }

mscVrIpNhrpRevTransitRecord OBJECT-TYPE
   SYNTAX     INTEGER  {
                 enabled(1),
                 disabled(2) }
   ACCESS     read-write
   STATUS     mandatory
   DESCRIPTION
     "This attribute specifies whether to attach a reverse transit record 
      extension to Resolution Request packets that Passport originates. 
      This extension along with NHRP debug tracing set to 'verbose' can 
      be used in tracing the path the NHRP packet takes from destination 
      to source."
   DEFVAL     { disabled }
::= { mscVrIpNhrpProvEntry 3 }

mscVrIpNhrpStateTable OBJECT-TYPE
   SYNTAX     SEQUENCE OF MscVrIpNhrpStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { mscVrIpNhrp 13 }

mscVrIpNhrpStateEntry OBJECT-TYPE
   SYNTAX     MscVrIpNhrpStateEntry
   ACCESS     not-accessible
   STATUS     mandatory
   DESCRIPTION
     "An entry in the mscVrIpNhrpStateTable."
   INDEX {
      mscVrIndex,
      mscVrIpIndex,
      mscVrIpNhrpIndex }
::= { mscVrIpNhrpStateTable 1 }

MscVrIpNhrpStateEntry ::= SEQUENCE {
   mscVrIpNhrpAdminState
      INTEGER,
   mscVrIpNhrpOperationalState
      INTEGER,
   mscVrIpNhrpUsageState
      INTEGER }

mscVrIpNhrpAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { mscVrIpNhrpStateEntry 1 }

mscVrIpNhrpOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { mscVrIpNhrpStateEntry 2 }

mscVrIpNhrpUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { mscVrIpNhrpStateEntry 3 }

mscVrIpNhrpOperStatusTable OBJECT-TYPE
   SYNTAX     SEQUENCE OF MscVrIpNhrpOperStatusEntry
   ACCESS     not-accessible
   STATUS     mandatory
   DESCRIPTION
     "This group includes the Operational Status attribute. This attribute 
      defines the current operational state of this component."
::= { mscVrIpNhrp 14 }

mscVrIpNhrpOperStatusEntry OBJECT-TYPE
   SYNTAX     MscVrIpNhrpOperStatusEntry
   ACCESS     not-accessible
   STATUS     mandatory
   DESCRIPTION
     "An entry in the mscVrIpNhrpOperStatusTable."
   INDEX {
      mscVrIndex,
      mscVrIpIndex,
      mscVrIpNhrpIndex }
::= { mscVrIpNhrpOperStatusTable 1 }

MscVrIpNhrpOperStatusEntry ::= SEQUENCE {
   mscVrIpNhrpSnmpOperStatus
      INTEGER }

mscVrIpNhrpSnmpOperStatus OBJECT-TYPE
   SYNTAX     INTEGER  {
                 up(1),
                 down(2),
                 testing(3) }
   ACCESS     read-only
   STATUS     mandatory
   DESCRIPTION
     "The current state of the interface. The up state indicates the 
      interface is operational and capable of forwarding packets. The 
      down state indicates the interface is not operational, thus unable to 
      forward packets. testing state indicates that no operational packets 
      can be passed."
   DEFVAL     { up }
::= { mscVrIpNhrpOperStatusEntry 1 }

mscVrIpNhrpOperTable OBJECT-TYPE
   SYNTAX     SEQUENCE OF MscVrIpNhrpOperEntry
   ACCESS     not-accessible
   STATUS     mandatory
   DESCRIPTION
     "This group contains the operational attributes of the Nhrp 
      component."
::= { mscVrIpNhrp 15 }

mscVrIpNhrpOperEntry OBJECT-TYPE
   SYNTAX     MscVrIpNhrpOperEntry
   ACCESS     not-accessible
   STATUS     mandatory
   DESCRIPTION
     "An entry in the mscVrIpNhrpOperTable."
   INDEX {
      mscVrIndex,
      mscVrIpIndex,
      mscVrIpNhrpIndex }
::= { mscVrIpNhrpOperTable 1 }

MscVrIpNhrpOperEntry ::= SEQUENCE {
   mscVrIpNhrpCurrResCacheEntries
      Unsigned32,
   mscVrIpNhrpPeakResCacheEntries
      Unsigned32 }

mscVrIpNhrpCurrResCacheEntries OBJECT-TYPE
   SYNTAX     Unsigned32 (0..4292967295)
   ACCESS     read-only
   STATUS     mandatory
   DESCRIPTION
     "This attribute indicates the current number of entries in the NHRP 
      resolution cache table."
::= { mscVrIpNhrpOperEntry 1 }

mscVrIpNhrpPeakResCacheEntries OBJECT-TYPE
   SYNTAX     Unsigned32 (0..4292967295)
   ACCESS     read-only
   STATUS     mandatory
   DESCRIPTION
     "This attribute indicates the peak value of currResCacheEntries 
      since the Nhrp snmpOperStatus attribute last became up."
::= { mscVrIpNhrpOperEntry 2 }


-- Vr/<string> Ip Nhrp NextHopServer
-- This component represents the NHRP server. The server performs 
-- the NHRP service within the NBMA cloud.

mscVrIpNhrpNhs OBJECT IDENTIFIER ::= { mscVrIpNhrp 2 }



mscVrIpNhrpNhsRowStatusTable OBJECT-TYPE
   SYNTAX     SEQUENCE OF MscVrIpNhrpNhsRowStatusEntry
   ACCESS     not-accessible
   STATUS     mandatory
   DESCRIPTION
     "This entry controls the addition and deletion of 
      mscVrIpNhrpNhs components."
::= { mscVrIpNhrpNhs 1 }

mscVrIpNhrpNhsRowStatusEntry OBJECT-TYPE
   SYNTAX     MscVrIpNhrpNhsRowStatusEntry
   ACCESS     not-accessible
   STATUS     mandatory
   DESCRIPTION
     "A single entry in the table represents a single 
      mscVrIpNhrpNhs component."
   INDEX {
      mscVrIndex,
      mscVrIpIndex,
      mscVrIpNhrpIndex,
      mscVrIpNhrpNhsIndex }
::= { mscVrIpNhrpNhsRowStatusTable 1 }

MscVrIpNhrpNhsRowStatusEntry ::= SEQUENCE {
   mscVrIpNhrpNhsRowStatus
      RowStatus,
   mscVrIpNhrpNhsComponentName
      DisplayString,
   mscVrIpNhrpNhsStorageType
      StorageType,
   mscVrIpNhrpNhsIndex
      NonReplicated }

mscVrIpNhrpNhsRowStatus OBJECT-TYPE
   SYNTAX     RowStatus 
   ACCESS     read-only
   STATUS     mandatory
   DESCRIPTION
     "This variable is used as the basis for SNMP naming of
      mscVrIpNhrpNhs components.
      These components cannot be added nor deleted."
::= { mscVrIpNhrpNhsRowStatusEntry 1 }

mscVrIpNhrpNhsComponentName OBJECT-TYPE
   SYNTAX     DisplayString 
   ACCESS     read-only
   STATUS     mandatory
   DESCRIPTION
     "This variable provides the component's string name for
      use with the ASCII Console Interface"
::= { mscVrIpNhrpNhsRowStatusEntry 2 }

mscVrIpNhrpNhsStorageType OBJECT-TYPE
   SYNTAX     StorageType 
   ACCESS     read-only
   STATUS     mandatory
   DESCRIPTION
     "This variable represents the storage type value for the
      mscVrIpNhrpNhs tables."
::= { mscVrIpNhrpNhsRowStatusEntry 4 }

mscVrIpNhrpNhsIndex OBJECT-TYPE
   SYNTAX     NonReplicated 
   ACCESS     not-accessible
   STATUS     mandatory
   DESCRIPTION
     "This variable represents the index for the mscVrIpNhrpNhs tables."
::= { mscVrIpNhrpNhsRowStatusEntry 10 }

mscVrIpNhrpNhsStatsTable OBJECT-TYPE
   SYNTAX     SEQUENCE OF MscVrIpNhrpNhsStatsEntry
   ACCESS     not-accessible
   STATUS     mandatory
   DESCRIPTION
     "This group contains the statistics attributes of the Nhs component."
::= { mscVrIpNhrpNhs 10 }

mscVrIpNhrpNhsStatsEntry OBJECT-TYPE
   SYNTAX     MscVrIpNhrpNhsStatsEntry
   ACCESS     not-accessible
   STATUS     mandatory
   DESCRIPTION
     "An entry in the mscVrIpNhrpNhsStatsTable."
   INDEX {
      mscVrIndex,
      mscVrIpIndex,
      mscVrIpNhrpIndex,
      mscVrIpNhrpNhsIndex }
::= { mscVrIpNhrpNhsStatsTable 1 }

MscVrIpNhrpNhsStatsEntry ::= SEQUENCE {
   mscVrIpNhrpNhsRxResolveReq
      Counter32,
   mscVrIpNhrpNhsTxResolveReplyAck
      Counter32,
   mscVrIpNhrpNhsTxResolveReplyNakProhibited
      Counter32,
   mscVrIpNhrpNhsTxResolveReplyNakInsufResources
      Counter32,
   mscVrIpNhrpNhsTxResolveReplyNakNoBinding
      Counter32,
   mscVrIpNhrpNhsTxResolveReplyNakNotUnique
      Counter32,
   mscVrIpNhrpNhsRxRegisterReq
      Counter32,
   mscVrIpNhrpNhsRxPurgeReq
      Counter32,
   mscVrIpNhrpNhsTxPurgeReq
      Counter32,
   mscVrIpNhrpNhsRxPurgeReply
      Counter32,
   mscVrIpNhrpNhsTxPurgeReply
      Counter32,
   mscVrIpNhrpNhsRxErrUnrecognizedExtension
      Counter32,
   mscVrIpNhrpNhsRxErrLoopDetected
      Counter32,
   mscVrIpNhrpNhsRxErrProtoAddrUnreachable
      Counter32,
   mscVrIpNhrpNhsRxErrProtoError
      Counter32,
   mscVrIpNhrpNhsRxErrSduSizeExceeded
      Counter32,
   mscVrIpNhrpNhsRxErrInvalidExtension
      Counter32,
   mscVrIpNhrpNhsRxErrInvalidResReplyReceived
      Counter32,
   mscVrIpNhrpNhsRxErrAuthenticationFailure
      Counter32,
   mscVrIpNhrpNhsRxErrHopCountExceeded
      Counter32,
   mscVrIpNhrpNhsTxErrUnrecognizedExtension
      Counter32,
   mscVrIpNhrpNhsTxErrLoopDetected
      Counter32,
   mscVrIpNhrpNhsTxErrProtoAddrUnreachable
      Counter32,
   mscVrIpNhrpNhsTxErrProtoError
      Counter32,
   mscVrIpNhrpNhsTxErrSduSizeExceeded
      Counter32,
   mscVrIpNhrpNhsTxErrInvalidExtension
      Counter32,
   mscVrIpNhrpNhsTxErrAuthenticationFailure
      Counter32,
   mscVrIpNhrpNhsTxErrHopCountExceeded
      Counter32,
   mscVrIpNhrpNhsFwdResolveReq
      Counter32,
   mscVrIpNhrpNhsFwdResolveReply
      Counter32,
   mscVrIpNhrpNhsFwdRegisterReq
      Counter32,
   mscVrIpNhrpNhsFwdRegisterReply
      Counter32,
   mscVrIpNhrpNhsFwdPurgeReq
      Counter32,
   mscVrIpNhrpNhsFwdPurgeReply
      Counter32,
   mscVrIpNhrpNhsFwdErrorIndication
      Counter32 }

mscVrIpNhrpNhsRxResolveReq OBJECT-TYPE
   SYNTAX     Counter32 
   ACCESS     read-only
   STATUS     mandatory
   DESCRIPTION
     "This attribute counts the NHRP Resolution Requests received by 
      this server. 
      This counter wraps to zero when the maximum value is exceeded."
::= { mscVrIpNhrpNhsStatsEntry 1 }

mscVrIpNhrpNhsTxResolveReplyAck OBJECT-TYPE
   SYNTAX     Counter32 
   ACCESS     read-only
   STATUS     mandatory
   DESCRIPTION
     "This attribute counts the positively acknowledged NHRP Resolution 
      Replies transmitted by this server. 
      This counter wraps to zero when the maximum value is exceeded."
::= { mscVrIpNhrpNhsStatsEntry 2 }

mscVrIpNhrpNhsTxResolveReplyNakProhibited OBJECT-TYPE
   SYNTAX     Counter32 
   ACCESS     read-only
   STATUS     mandatory
   DESCRIPTION
     "This attribute counts the NAK NHRP Resolution Replies 
      transmitted by this server with the code 'Administratively 
      Prohibited'. 
      This counter wraps to zero when the maximum value is exceeded."
::= { mscVrIpNhrpNhsStatsEntry 3 }

mscVrIpNhrpNhsTxResolveReplyNakInsufResources OBJECT-TYPE
   SYNTAX     Counter32 
   ACCESS     read-only
   STATUS     mandatory
   DESCRIPTION
     "This attribute counts the NAK NHRP Resolution Replies 
      transmitted by this server with the code 'Insufficient Resources'. 
      This counter wraps to zero when the maximum value is exceeded."
::= { mscVrIpNhrpNhsStatsEntry 4 }

mscVrIpNhrpNhsTxResolveReplyNakNoBinding OBJECT-TYPE
   SYNTAX     Counter32 
   ACCESS     read-only
   STATUS     mandatory
   DESCRIPTION
     "This attribute counts the NAK NHRP Resolution Replies 
      transmitted by this server with the code 'No Internetworking Layer 
      Address to NBMA Address Binding Exists'. 
      This counter wraps to zero when the maximum value is exceeded."
::= { mscVrIpNhrpNhsStatsEntry 5 }

mscVrIpNhrpNhsTxResolveReplyNakNotUnique OBJECT-TYPE
   SYNTAX     Counter32 
   ACCESS     read-only
   STATUS     mandatory
   DESCRIPTION
     "This attribute counts the NAK NHRP Resolution Replies 
      transmitted by this server with the code 'Binding Exists But Is Not 
      Unique'. 
      This counter wraps to zero when the maximum value is exceeded."
::= { mscVrIpNhrpNhsStatsEntry 6 }

mscVrIpNhrpNhsRxRegisterReq OBJECT-TYPE
   SYNTAX     Counter32 
   ACCESS     read-only
   STATUS     mandatory
   DESCRIPTION
     "This attribute counts the NHRP Registration Requests received by 
      this server. Registration is not supported, therefore all NHRP 
      Registration Requests are silently dropped.
      This counter wraps to zero when the maximum value is exceeded."
::= { mscVrIpNhrpNhsStatsEntry 7 }

mscVrIpNhrpNhsRxPurgeReq OBJECT-TYPE
   SYNTAX     Counter32 
   ACCESS     read-only
   STATUS     mandatory
   DESCRIPTION
     "This attribute counts the NHRP Purge Requests received by this 
      server.
      This counter wraps to zero when the maximum value is exceeded."
::= { mscVrIpNhrpNhsStatsEntry 12 }

mscVrIpNhrpNhsTxPurgeReq OBJECT-TYPE
   SYNTAX     Counter32 
   ACCESS     read-only
   STATUS     mandatory
   DESCRIPTION
     "This attribute counts the NHRP Purge Requests transmitted by this 
      server. 
      This counter wraps to zero when the maximum value is exceeded."
::= { mscVrIpNhrpNhsStatsEntry 13 }

mscVrIpNhrpNhsRxPurgeReply OBJECT-TYPE
   SYNTAX     Counter32 
   ACCESS     read-only
   STATUS     mandatory
   DESCRIPTION
     "This attribute counts the NHRP Purge Replies received by this 
      server. 
      This counter wraps to zero when the maximum value is exceeded."
::= { mscVrIpNhrpNhsStatsEntry 14 }

mscVrIpNhrpNhsTxPurgeReply OBJECT-TYPE
   SYNTAX     Counter32 
   ACCESS     read-only
   STATUS     mandatory
   DESCRIPTION
     "This attribute counts the NHRP Purge Replies transmitted by this 
      server. 
      This counter wraps to zero when the maximum value is exceeded."
::= { mscVrIpNhrpNhsStatsEntry 15 }

mscVrIpNhrpNhsRxErrUnrecognizedExtension OBJECT-TYPE
   SYNTAX     Counter32 
   ACCESS     read-only
   STATUS     mandatory
   DESCRIPTION
     "This attribute counts the NHRP Error Indication packets received by 
      this server with the error code 'Unrecognized Extension'. 
      This counter wraps to zero when the maximum value is exceeded."
::= { mscVrIpNhrpNhsStatsEntry 16 }

mscVrIpNhrpNhsRxErrLoopDetected OBJECT-TYPE
   SYNTAX     Counter32 
   ACCESS     read-only
   STATUS     mandatory
   DESCRIPTION
     "This attribute counts the NHRP Error Indication packets received by 
      this server with the error code 'NHRP Loop Detected'. 
      This counter wraps to zero when the maximum value is exceeded."
::= { mscVrIpNhrpNhsStatsEntry 17 }

mscVrIpNhrpNhsRxErrProtoAddrUnreachable OBJECT-TYPE
   SYNTAX     Counter32 
   ACCESS     read-only
   STATUS     mandatory
   DESCRIPTION
     "This attribute counts the NHRP Error Indication packets received by 
      this server with the error code 'Protocol Address Unreachable'. 
      This counter wraps to zero when the maximum value is exceeded."
::= { mscVrIpNhrpNhsStatsEntry 18 }

mscVrIpNhrpNhsRxErrProtoError OBJECT-TYPE
   SYNTAX     Counter32 
   ACCESS     read-only
   STATUS     mandatory
   DESCRIPTION
     "This attribute counts the NHRP Error Indication packets received by 
      this server with the error code 'Protocol Error'.
      This counter wraps to zero when the maximum value is exceeded."
::= { mscVrIpNhrpNhsStatsEntry 19 }

mscVrIpNhrpNhsRxErrSduSizeExceeded OBJECT-TYPE
   SYNTAX     Counter32 
   ACCESS     read-only
   STATUS     mandatory
   DESCRIPTION
     "This attribute counts the NHRP Error Indication packets received by 
      this server with the error code 'NHRP SDU Size Exceeded'. 
      This counter wraps to zero when the maximum value is exceeded."
::= { mscVrIpNhrpNhsStatsEntry 20 }

mscVrIpNhrpNhsRxErrInvalidExtension OBJECT-TYPE
   SYNTAX     Counter32 
   ACCESS     read-only
   STATUS     mandatory
   DESCRIPTION
     "This attribute counts the NHRP Error Indication packets received by 
      this server with the error code 'Invalid Extension'. 
      This counter wraps to zero when the maximum value is exceeded."
::= { mscVrIpNhrpNhsStatsEntry 21 }

mscVrIpNhrpNhsRxErrInvalidResReplyReceived OBJECT-TYPE
   SYNTAX     Counter32 
   ACCESS     read-only
   STATUS     mandatory
   DESCRIPTION
     "This attribute counts the NHRP Error Indication packets received by 
      this server with the error code 'Invalid Resolution Reply Received'. 
      This counter wraps to zero when the maximum value is exceeded."
::= { mscVrIpNhrpNhsStatsEntry 22 }

mscVrIpNhrpNhsRxErrAuthenticationFailure OBJECT-TYPE
   SYNTAX     Counter32 
   ACCESS     read-only
   STATUS     mandatory
   DESCRIPTION
     "This attribute counts the NHRP Error Indication packets received by 
      this server with the error code 'Authentication Failure'. 
      This counter wraps to zero when the maximum value is exceeded."
::= { mscVrIpNhrpNhsStatsEntry 23 }

mscVrIpNhrpNhsRxErrHopCountExceeded OBJECT-TYPE
   SYNTAX     Counter32 
   ACCESS     read-only
   STATUS     mandatory
   DESCRIPTION
     "This attribute counts the NHRP Error Indication packets received by 
      this server with the error code 'Hop Count Exceeded'.
      This counter wraps to zero when the maximum value is exceeded."
::= { mscVrIpNhrpNhsStatsEntry 24 }

mscVrIpNhrpNhsTxErrUnrecognizedExtension OBJECT-TYPE
   SYNTAX     Counter32 
   ACCESS     read-only
   STATUS     mandatory
   DESCRIPTION
     "This attribute counts the NHRP Error Indication packets transmitted 
      by this server with the error code 'Unrecognized Extension'. 
      This counter wraps to zero when the maximum value is exceeded."
::= { mscVrIpNhrpNhsStatsEntry 25 }

mscVrIpNhrpNhsTxErrLoopDetected OBJECT-TYPE
   SYNTAX     Counter32 
   ACCESS     read-only
   STATUS     mandatory
   DESCRIPTION
     "This attribute counts the NHRP Error Indication packets transmitted 
      by this server with the error code 'NHRP Loop Detected'. 
      This counter wraps to zero when the maximum value is exceeded."
::= { mscVrIpNhrpNhsStatsEntry 26 }

mscVrIpNhrpNhsTxErrProtoAddrUnreachable OBJECT-TYPE
   SYNTAX     Counter32 
   ACCESS     read-only
   STATUS     mandatory
   DESCRIPTION
     "This attribute counts the NHRP Error Indication packets transmitted 
      by this server with the error code 'Protocol Address Unreachable'. 
      This counter wraps to zero when the maximum value is exceeded."
::= { mscVrIpNhrpNhsStatsEntry 27 }

mscVrIpNhrpNhsTxErrProtoError OBJECT-TYPE
   SYNTAX     Counter32 
   ACCESS     read-only
   STATUS     mandatory
   DESCRIPTION
     "This attribute counts the NHRP Error Indication packets transmitted 
      by this server with the error code 'Protocol Error'.
      This counter wraps to zero when the maximum value is exceeded."
::= { mscVrIpNhrpNhsStatsEntry 28 }

mscVrIpNhrpNhsTxErrSduSizeExceeded OBJECT-TYPE
   SYNTAX     Counter32 
   ACCESS     read-only
   STATUS     mandatory
   DESCRIPTION
     "This attribute counts the NHRP Error Indication packets transmitted 
      by this server with the error code 'NHRP SDU Size Exceeded'. 
      This counter wraps to zero when the maximum value is exceeded."
::= { mscVrIpNhrpNhsStatsEntry 29 }

mscVrIpNhrpNhsTxErrInvalidExtension OBJECT-TYPE
   SYNTAX     Counter32 
   ACCESS     read-only
   STATUS     mandatory
   DESCRIPTION
     "This attribute counts the NHRP Error Indication packets transmitted 
      by this server with the error code 'Invalid Extension'. 
      This counter wraps to zero when the maximum value is exceeded."
::= { mscVrIpNhrpNhsStatsEntry 30 }

mscVrIpNhrpNhsTxErrAuthenticationFailure OBJECT-TYPE
   SYNTAX     Counter32 
   ACCESS     read-only
   STATUS     mandatory
   DESCRIPTION
     "This attribute counts the NHRP Error Indication packets transmitted 
      by this server with the error code 'Authentication Failure'. 
      This counter wraps to zero when the maximum value is exceeded."
::= { mscVrIpNhrpNhsStatsEntry 31 }

mscVrIpNhrpNhsTxErrHopCountExceeded OBJECT-TYPE
   SYNTAX     Counter32 
   ACCESS     read-only
   STATUS     mandatory
   DESCRIPTION
     "This attribute counts the NHRP Error Indication packets transmitted 
      by this server with the error code 'Hop Count Exceeded'. 
      This counter wraps to zero when the maximum value is exceeded."
::= { mscVrIpNhrpNhsStatsEntry 32 }

mscVrIpNhrpNhsFwdResolveReq OBJECT-TYPE
   SYNTAX     Counter32 
   ACCESS     read-only
   STATUS     mandatory
   DESCRIPTION
     "This attribute counts the NHRP Resolution Requests forwarded by 
      this server acting as a transit NHS. 
      This counter wraps to zero when the maximum value is exceeded."
::= { mscVrIpNhrpNhsStatsEntry 33 }

mscVrIpNhrpNhsFwdResolveReply OBJECT-TYPE
   SYNTAX     Counter32 
   ACCESS     read-only
   STATUS     mandatory
   DESCRIPTION
     "This attribute counts the NHRP Resolution Replies forwarded by 
      this server acting as a transit NHS. 
      This counter wraps to zero when the maximum value is exceeded."
::= { mscVrIpNhrpNhsStatsEntry 34 }

mscVrIpNhrpNhsFwdRegisterReq OBJECT-TYPE
   SYNTAX     Counter32 
   ACCESS     read-only
   STATUS     mandatory
   DESCRIPTION
     "This attribute counts the NHRP Registration Requests forwarded by 
      this server acting as a transit NHS. 
      This counter wraps to zero when the maximum value is exceeded."
::= { mscVrIpNhrpNhsStatsEntry 35 }

mscVrIpNhrpNhsFwdRegisterReply OBJECT-TYPE
   SYNTAX     Counter32 
   ACCESS     read-only
   STATUS     mandatory
   DESCRIPTION
     "This attribute counts the NHRP Registration Replies forwarded by 
      this server acting as a transit NHS. 
      This counter wraps to zero when the maximum value is exceeded."
::= { mscVrIpNhrpNhsStatsEntry 36 }

mscVrIpNhrpNhsFwdPurgeReq OBJECT-TYPE
   SYNTAX     Counter32 
   ACCESS     read-only
   STATUS     mandatory
   DESCRIPTION
     "This attribute counts the NHRP Purge Requests forwarded by this 
      server acting as a transit NHS. 
      This counter wraps to zero when the maximum value is exceeded."
::= { mscVrIpNhrpNhsStatsEntry 37 }

mscVrIpNhrpNhsFwdPurgeReply OBJECT-TYPE
   SYNTAX     Counter32 
   ACCESS     read-only
   STATUS     mandatory
   DESCRIPTION
     "This attribute counts the NHRP Purge Replies forwarded by this 
      server acting as a transit NHS. 
      This counter wraps to zero when the maximum value is exceeded."
::= { mscVrIpNhrpNhsStatsEntry 38 }

mscVrIpNhrpNhsFwdErrorIndication OBJECT-TYPE
   SYNTAX     Counter32 
   ACCESS     read-only
   STATUS     mandatory
   DESCRIPTION
     "This attribute counts the NHRP Error Indication packets forwarded 
      by this server acting as a transit NHS. 
      This counter wraps to zero when the maximum value is exceeded."
::= { mscVrIpNhrpNhsStatsEntry 39 }


-- Vr/<string> Ip Nhrp Nhs EgressPolicy/n
-- This component represents an egress policy on this server.
-- The server has the following default egress policies which may be 
-- overridden by any provisioned egress policies: 1. NAK resolution 
-- request for any remotely attached destination regardless of source, 
-- 2. ACK resolution request for any locally attached destination 
-- regardless of source.

mscVrIpNhrpNhsEp OBJECT IDENTIFIER ::= { mscVrIpNhrpNhs 2 }



mscVrIpNhrpNhsEpRowStatusTable OBJECT-TYPE
   SYNTAX     SEQUENCE OF MscVrIpNhrpNhsEpRowStatusEntry
   ACCESS     not-accessible
   STATUS     mandatory
   DESCRIPTION
     "This entry controls the addition and deletion of 
      mscVrIpNhrpNhsEp components."
::= { mscVrIpNhrpNhsEp 1 }

mscVrIpNhrpNhsEpRowStatusEntry OBJECT-TYPE
   SYNTAX     MscVrIpNhrpNhsEpRowStatusEntry
   ACCESS     not-accessible
   STATUS     mandatory
   DESCRIPTION
     "A single entry in the table represents a single 
      mscVrIpNhrpNhsEp component."
   INDEX {
      mscVrIndex,
      mscVrIpIndex,
      mscVrIpNhrpIndex,
      mscVrIpNhrpNhsIndex,
      mscVrIpNhrpNhsEpIndex }
::= { mscVrIpNhrpNhsEpRowStatusTable 1 }

MscVrIpNhrpNhsEpRowStatusEntry ::= SEQUENCE {
   mscVrIpNhrpNhsEpRowStatus
      RowStatus,
   mscVrIpNhrpNhsEpComponentName
      DisplayString,
   mscVrIpNhrpNhsEpStorageType
      StorageType,
   mscVrIpNhrpNhsEpIndex
      Integer32 }

mscVrIpNhrpNhsEpRowStatus OBJECT-TYPE
   SYNTAX     RowStatus 
   ACCESS     read-write
   STATUS     mandatory
   DESCRIPTION
     "This variable is used as the basis for SNMP naming of
      mscVrIpNhrpNhsEp components.
      These components can be added and deleted."
::= { mscVrIpNhrpNhsEpRowStatusEntry 1 }

mscVrIpNhrpNhsEpComponentName OBJECT-TYPE
   SYNTAX     DisplayString 
   ACCESS     read-only
   STATUS     mandatory
   DESCRIPTION
     "This variable provides the component's string name for
      use with the ASCII Console Interface"
::= { mscVrIpNhrpNhsEpRowStatusEntry 2 }

mscVrIpNhrpNhsEpStorageType OBJECT-TYPE
   SYNTAX     StorageType 
   ACCESS     read-only
   STATUS     mandatory
   DESCRIPTION
     "This variable represents the storage type value for the
      mscVrIpNhrpNhsEp tables."
::= { mscVrIpNhrpNhsEpRowStatusEntry 4 }

mscVrIpNhrpNhsEpIndex OBJECT-TYPE
   SYNTAX     Integer32 (0..65535)
   ACCESS     not-accessible
   STATUS     mandatory
   DESCRIPTION
     "This variable represents the index for the mscVrIpNhrpNhsEp tables."
::= { mscVrIpNhrpNhsEpRowStatusEntry 10 }

mscVrIpNhrpNhsEpProvTable OBJECT-TYPE
   SYNTAX     SEQUENCE OF MscVrIpNhrpNhsEpProvEntry
   ACCESS     not-accessible
   STATUS     mandatory
   DESCRIPTION
     "This group contains the provisionable attributes of the EgressPolicy 
      component."
::= { mscVrIpNhrpNhsEp 10 }

mscVrIpNhrpNhsEpProvEntry OBJECT-TYPE
   SYNTAX     MscVrIpNhrpNhsEpProvEntry
   ACCESS     not-accessible
   STATUS     mandatory
   DESCRIPTION
     "An entry in the mscVrIpNhrpNhsEpProvTable."
   INDEX {
      mscVrIndex,
      mscVrIpIndex,
      mscVrIpNhrpIndex,
      mscVrIpNhrpNhsIndex,
      mscVrIpNhrpNhsEpIndex }
::= { mscVrIpNhrpNhsEpProvTable 1 }

MscVrIpNhrpNhsEpProvEntry ::= SEQUENCE {
   mscVrIpNhrpNhsEpAction
      INTEGER,
   mscVrIpNhrpNhsEpProtocol
      INTEGER }

mscVrIpNhrpNhsEpAction OBJECT-TYPE
   SYNTAX     INTEGER  {
                 ack(1),
                 nak(2) }
   ACCESS     read-write
   STATUS     mandatory
   DESCRIPTION
     "This attribute specifies how the server should handle the NHRP 
      Resolution Request if it matches this policy. The possible actions 
      are:
      ack - Send a positive acknowledgement (ACK Reply) for the 
      request.
      nak - Send a negative acknowledgement (NAK Reply) for the 
      request."
   DEFVAL     { nak }
::= { mscVrIpNhrpNhsEpProvEntry 1 }

mscVrIpNhrpNhsEpProtocol OBJECT-TYPE
   SYNTAX     INTEGER  {
                 default(0),
                 staticLocal(1) }
   ACCESS     read-write
   STATUS     mandatory
   DESCRIPTION
     "This attribute species the reachability type (that is, protocol) of the 
      destination in the NHRP Resolution Request. The possible 
      protocols:
      default - This value is a 'wildcard' and matches any protocol. A 
      policy with a 'wildcard' protocol is less preferred than a policy with 
      a protocol which matches exactly.
      staticLocal - The destination is on a locally attached network."
   DEFVAL     { default }
::= { mscVrIpNhrpNhsEpProvEntry 2 }


-- Vr/<string> Ip Nhrp Nhs Ep/n NetworkAddress/n
-- This component represents the source and destination address pairs 
-- for an NHRP egress policy.

mscVrIpNhrpNhsEpNetAddr OBJECT IDENTIFIER ::= { mscVrIpNhrpNhsEp 2 }



mscVrIpNhrpNhsEpNetAddrRowStatusTable OBJECT-TYPE
   SYNTAX     SEQUENCE OF MscVrIpNhrpNhsEpNetAddrRowStatusEntry
   ACCESS     not-accessible
   STATUS     mandatory
   DESCRIPTION
     "This entry controls the addition and deletion of 
      mscVrIpNhrpNhsEpNetAddr components."
::= { mscVrIpNhrpNhsEpNetAddr 1 }

mscVrIpNhrpNhsEpNetAddrRowStatusEntry OBJECT-TYPE
   SYNTAX     MscVrIpNhrpNhsEpNetAddrRowStatusEntry
   ACCESS     not-accessible
   STATUS     mandatory
   DESCRIPTION
     "A single entry in the table represents a single 
      mscVrIpNhrpNhsEpNetAddr component."
   INDEX {
      mscVrIndex,
      mscVrIpIndex,
      mscVrIpNhrpIndex,
      mscVrIpNhrpNhsIndex,
      mscVrIpNhrpNhsEpIndex,
      mscVrIpNhrpNhsEpNetAddrIndex }
::= { mscVrIpNhrpNhsEpNetAddrRowStatusTable 1 }

MscVrIpNhrpNhsEpNetAddrRowStatusEntry ::= SEQUENCE {
   mscVrIpNhrpNhsEpNetAddrRowStatus
      RowStatus,
   mscVrIpNhrpNhsEpNetAddrComponentName
      DisplayString,
   mscVrIpNhrpNhsEpNetAddrStorageType
      StorageType,
   mscVrIpNhrpNhsEpNetAddrIndex
      Integer32 }

mscVrIpNhrpNhsEpNetAddrRowStatus OBJECT-TYPE
   SYNTAX     RowStatus 
   ACCESS     read-write
   STATUS     mandatory
   DESCRIPTION
     "This variable is used as the basis for SNMP naming of
      mscVrIpNhrpNhsEpNetAddr components.
      These components can be added and deleted."
::= { mscVrIpNhrpNhsEpNetAddrRowStatusEntry 1 }

mscVrIpNhrpNhsEpNetAddrComponentName OBJECT-TYPE
   SYNTAX     DisplayString 
   ACCESS     read-only
   STATUS     mandatory
   DESCRIPTION
     "This variable provides the component's string name for
      use with the ASCII Console Interface"
::= { mscVrIpNhrpNhsEpNetAddrRowStatusEntry 2 }

mscVrIpNhrpNhsEpNetAddrStorageType OBJECT-TYPE
   SYNTAX     StorageType 
   ACCESS     read-only
   STATUS     mandatory
   DESCRIPTION
     "This variable represents the storage type value for the
      mscVrIpNhrpNhsEpNetAddr tables."
::= { mscVrIpNhrpNhsEpNetAddrRowStatusEntry 4 }

mscVrIpNhrpNhsEpNetAddrIndex OBJECT-TYPE
   SYNTAX     Integer32 (0..65535)
   ACCESS     not-accessible
   STATUS     mandatory
   DESCRIPTION
     "This variable represents the index for the mscVrIpNhrpNhsEpNetAddr tables."
::= { mscVrIpNhrpNhsEpNetAddrRowStatusEntry 10 }

mscVrIpNhrpNhsEpNetAddrProvTable OBJECT-TYPE
   SYNTAX     SEQUENCE OF MscVrIpNhrpNhsEpNetAddrProvEntry
   ACCESS     not-accessible
   STATUS     mandatory
   DESCRIPTION
     "This group contains the provisionable attributes of the 
      NetworkAddress component."
::= { mscVrIpNhrpNhsEpNetAddr 10 }

mscVrIpNhrpNhsEpNetAddrProvEntry OBJECT-TYPE
   SYNTAX     MscVrIpNhrpNhsEpNetAddrProvEntry
   ACCESS     not-accessible
   STATUS     mandatory
   DESCRIPTION
     "An entry in the mscVrIpNhrpNhsEpNetAddrProvTable."
   INDEX {
      mscVrIndex,
      mscVrIpIndex,
      mscVrIpNhrpIndex,
      mscVrIpNhrpNhsIndex,
      mscVrIpNhrpNhsEpIndex,
      mscVrIpNhrpNhsEpNetAddrIndex }
::= { mscVrIpNhrpNhsEpNetAddrProvTable 1 }

MscVrIpNhrpNhsEpNetAddrProvEntry ::= SEQUENCE {
   mscVrIpNhrpNhsEpNetAddrSourceAddress
      IpAddress,
   mscVrIpNhrpNhsEpNetAddrSourceMask
      IpAddress,
   mscVrIpNhrpNhsEpNetAddrDestinationAddress
      IpAddress,
   mscVrIpNhrpNhsEpNetAddrDestinationMask
      IpAddress }

mscVrIpNhrpNhsEpNetAddrSourceAddress OBJECT-TYPE
   SYNTAX     IpAddress 
   ACCESS     read-write
   STATUS     mandatory
   DESCRIPTION
     "This attribute specifies the internetwork address of the source. This 
      is used to match a source internetwork address in an NHRP 
      Resolution Request."
   DEFVAL     { '00000000'H }  -- "0.0.0.0"
::= { mscVrIpNhrpNhsEpNetAddrProvEntry 1 }

mscVrIpNhrpNhsEpNetAddrSourceMask OBJECT-TYPE
   SYNTAX     IpAddress 
   ACCESS     read-write
   STATUS     mandatory
   DESCRIPTION
     "This attribute specifies the netmask for the source internetwork 
      address."
   DEFVAL     { '00000000'H }  -- "0.0.0.0"
::= { mscVrIpNhrpNhsEpNetAddrProvEntry 2 }

mscVrIpNhrpNhsEpNetAddrDestinationAddress OBJECT-TYPE
   SYNTAX     IpAddress 
   ACCESS     read-write
   STATUS     mandatory
   DESCRIPTION
     "This attribute specifies the internetwork address of the destination. 
      This is used to match a destination internetwork address in an 
      NHRP Resolution Request."
   DEFVAL     { '00000000'H }  -- "0.0.0.0"
::= { mscVrIpNhrpNhsEpNetAddrProvEntry 3 }

mscVrIpNhrpNhsEpNetAddrDestinationMask OBJECT-TYPE
   SYNTAX     IpAddress 
   ACCESS     read-write
   STATUS     mandatory
   DESCRIPTION
     "This attribute specifies the netmask for the destination internetwork 
      address."
   DEFVAL     { '00000000'H }  -- "0.0.0.0"
::= { mscVrIpNhrpNhsEpNetAddrProvEntry 4 }


-- Vr/<string> Ip Nhrp NextHopClient
-- This component represents the NHRP client. The client initiates 
-- NHRP requests of various types in order to obtain access to the 
-- NHRP service.

mscVrIpNhrpNhc OBJECT IDENTIFIER ::= { mscVrIpNhrp 3 }



mscVrIpNhrpNhcRowStatusTable OBJECT-TYPE
   SYNTAX     SEQUENCE OF MscVrIpNhrpNhcRowStatusEntry
   ACCESS     not-accessible
   STATUS     mandatory
   DESCRIPTION
     "This entry controls the addition and deletion of 
      mscVrIpNhrpNhc components."
::= { mscVrIpNhrpNhc 1 }

mscVrIpNhrpNhcRowStatusEntry OBJECT-TYPE
   SYNTAX     MscVrIpNhrpNhcRowStatusEntry
   ACCESS     not-accessible
   STATUS     mandatory
   DESCRIPTION
     "A single entry in the table represents a single 
      mscVrIpNhrpNhc component."
   INDEX {
      mscVrIndex,
      mscVrIpIndex,
      mscVrIpNhrpIndex,
      mscVrIpNhrpNhcIndex }
::= { mscVrIpNhrpNhcRowStatusTable 1 }

MscVrIpNhrpNhcRowStatusEntry ::= SEQUENCE {
   mscVrIpNhrpNhcRowStatus
      RowStatus,
   mscVrIpNhrpNhcComponentName
      DisplayString,
   mscVrIpNhrpNhcStorageType
      StorageType,
   mscVrIpNhrpNhcIndex
      NonReplicated }

mscVrIpNhrpNhcRowStatus OBJECT-TYPE
   SYNTAX     RowStatus 
   ACCESS     read-only
   STATUS     mandatory
   DESCRIPTION
     "This variable is used as the basis for SNMP naming of
      mscVrIpNhrpNhc components.
      These components cannot be added nor deleted."
::= { mscVrIpNhrpNhcRowStatusEntry 1 }

mscVrIpNhrpNhcComponentName OBJECT-TYPE
   SYNTAX     DisplayString 
   ACCESS     read-only
   STATUS     mandatory
   DESCRIPTION
     "This variable provides the component's string name for
      use with the ASCII Console Interface"
::= { mscVrIpNhrpNhcRowStatusEntry 2 }

mscVrIpNhrpNhcStorageType OBJECT-TYPE
   SYNTAX     StorageType 
   ACCESS     read-only
   STATUS     mandatory
   DESCRIPTION
     "This variable represents the storage type value for the
      mscVrIpNhrpNhc tables."
::= { mscVrIpNhrpNhcRowStatusEntry 4 }

mscVrIpNhrpNhcIndex OBJECT-TYPE
   SYNTAX     NonReplicated 
   ACCESS     not-accessible
   STATUS     mandatory
   DESCRIPTION
     "This variable represents the index for the mscVrIpNhrpNhc tables."
::= { mscVrIpNhrpNhcRowStatusEntry 10 }

mscVrIpNhrpNhcProvTable OBJECT-TYPE
   SYNTAX     SEQUENCE OF MscVrIpNhrpNhcProvEntry
   ACCESS     not-accessible
   STATUS     mandatory
   DESCRIPTION
     "This group contains the provisionable attributes of the Nhc 
      component."
::= { mscVrIpNhrpNhc 10 }

mscVrIpNhrpNhcProvEntry OBJECT-TYPE
   SYNTAX     MscVrIpNhrpNhcProvEntry
   ACCESS     not-accessible
   STATUS     mandatory
   DESCRIPTION
     "An entry in the mscVrIpNhrpNhcProvTable."
   INDEX {
      mscVrIndex,
      mscVrIpIndex,
      mscVrIpNhrpIndex,
      mscVrIpNhrpNhcIndex }
::= { mscVrIpNhrpNhcProvTable 1 }

MscVrIpNhrpNhcProvEntry ::= SEQUENCE {
   mscVrIpNhrpNhcFlowDetectPacketCount
      Unsigned32,
   mscVrIpNhrpNhcFlowDetectTimePeriod
      INTEGER,
   mscVrIpNhrpNhcIdleDetectPacketCount
      Unsigned32,
   mscVrIpNhrpNhcIdleDetectTimePeriod
      Unsigned32,
   mscVrIpNhrpNhcAtmFlowDetection
      INTEGER }

mscVrIpNhrpNhcFlowDetectPacketCount OBJECT-TYPE
   SYNTAX     Unsigned32 (1..4292967295)
   ACCESS     read-write
   STATUS     mandatory
   DESCRIPTION
     "This attribute, along with flowDetectTimePeriod, specifies the IP 
      traffic flow detection threshold; If the number of IP packets sent to a 
      particular destination within the time interval specified by 
      flowDetectTimePeriod exceeds the value specified by 
      flowDetectPacketCount, then an NHRP Resolution Request will be 
      triggerred. If successful, a shortcut will be set up."
   DEFVAL     { 600 }
::= { mscVrIpNhrpNhcProvEntry 1 }

mscVrIpNhrpNhcFlowDetectTimePeriod OBJECT-TYPE
   SYNTAX     INTEGER (10 | 20 | 30 | 40 | 50 | 60)
   ACCESS     read-write
   STATUS     mandatory
   DESCRIPTION
     "This attribute, along with flowDetectPacketCount, specifies the IP 
      traffic flow detection threshold; If the number of IP packets sent to a 
      particular destination within the time interval specified by 
      flowDetectTimePeriod exceeds the value specified by 
      flowDetectPacketCount, then an NHRP Resolution Request will be 
      triggerred. If successful, a shortcut will be set up."
   DEFVAL     { 60 }
::= { mscVrIpNhrpNhcProvEntry 2 }

mscVrIpNhrpNhcIdleDetectPacketCount OBJECT-TYPE
   SYNTAX     Unsigned32 (1..4292967295)
   ACCESS     read-write
   STATUS     mandatory
   DESCRIPTION
     "This attribute, along with idleDetectTimePeriod, specifies the idle 
      shortcut threshold; If the number of frames transmitted over an 
      outgoing shortcut, or received over an incoming shortcut, within the 
      time interval specified by idleDetectTimePeriod falls below the 
      value specified by idleDetectPacketCount, then the shortcut 
      connection will be released."
   DEFVAL     { 900 }
::= { mscVrIpNhrpNhcProvEntry 3 }

mscVrIpNhrpNhcIdleDetectTimePeriod OBJECT-TYPE
   SYNTAX     Unsigned32 (1..30)
   ACCESS     read-write
   STATUS     mandatory
   DESCRIPTION
     "This attribute, along with idleDetectPacketCount, specifies the idle 
      shortcut threshold; If the number of frames transmitted over an 
      outgoing shortcut, or received over an incoming shortcut, within the 
      time interval specified by idleDetectTimePeriod falls below the 
      value specified by idleDetectPacketCount, then the shortcut 
      connection will be released."
   DEFVAL     { 3 }
::= { mscVrIpNhrpNhcProvEntry 4 }

mscVrIpNhrpNhcAtmFlowDetection OBJECT-TYPE
   SYNTAX     INTEGER  {
                 enabled(1),
                 disabled(2) }
   ACCESS     read-write
   STATUS     mandatory
   DESCRIPTION
     "This attribute specifies whether flow detection should be performed 
      for IP traffic received on ATM cards. This attribute does not apply 
      to IP traffic received on LAN or non-ATM WAN cards."
   DEFVAL     { disabled }
::= { mscVrIpNhrpNhcProvEntry 5 }

mscVrIpNhrpNhcStatsTable OBJECT-TYPE
   SYNTAX     SEQUENCE OF MscVrIpNhrpNhcStatsEntry
   ACCESS     not-accessible
   STATUS     mandatory
   DESCRIPTION
     "This group contains the statistics attributes of the Nhc component."
::= { mscVrIpNhrpNhc 11 }

mscVrIpNhrpNhcStatsEntry OBJECT-TYPE
   SYNTAX     MscVrIpNhrpNhcStatsEntry
   ACCESS     not-accessible
   STATUS     mandatory
   DESCRIPTION
     "An entry in the mscVrIpNhrpNhcStatsTable."
   INDEX {
      mscVrIndex,
      mscVrIpIndex,
      mscVrIpNhrpIndex,
      mscVrIpNhrpNhcIndex }
::= { mscVrIpNhrpNhcStatsTable 1 }

MscVrIpNhrpNhcStatsEntry ::= SEQUENCE {
   mscVrIpNhrpNhcTxResolveReq
      Counter32,
   mscVrIpNhrpNhcRxResolveReplyAck
      Counter32,
   mscVrIpNhrpNhcRxResolveReplyNakProhibited
      Counter32,
   mscVrIpNhrpNhcRxResolveReplyNakInsufResources
      Counter32,
   mscVrIpNhrpNhcRxResolveReplyNakNoBinding
      Counter32,
   mscVrIpNhrpNhcRxResolveReplyNakNotUnique
      Counter32,
   mscVrIpNhrpNhcRxPurgeReq
      Counter32,
   mscVrIpNhrpNhcTxPurgeReq
      Counter32,
   mscVrIpNhrpNhcRxPurgeReply
      Counter32,
   mscVrIpNhrpNhcTxPurgeReply
      Counter32,
   mscVrIpNhrpNhcTxErrIndication
      Counter32,
   mscVrIpNhrpNhcRxErrUnrecognizedExtension
      Counter32,
   mscVrIpNhrpNhcRxErrLoopDetected
      Counter32,
   mscVrIpNhrpNhcRxErrProtoAddrUnreachable
      Counter32,
   mscVrIpNhrpNhcRxErrProtoError
      Counter32,
   mscVrIpNhrpNhcRxErrSduSizeExceeded
      Counter32,
   mscVrIpNhrpNhcRxErrInvalidExtension
      Counter32,
   mscVrIpNhrpNhcRxErrAuthenticationFailure
      Counter32,
   mscVrIpNhrpNhcRxErrHopCountExceeded
      Counter32 }

mscVrIpNhrpNhcTxResolveReq OBJECT-TYPE
   SYNTAX     Counter32 
   ACCESS     read-only
   STATUS     mandatory
   DESCRIPTION
     "This attribute counts the NHRP Resolution Requests transmitted by 
      this client. 
      This counter wraps to zero when the maximum value is exceeded."
::= { mscVrIpNhrpNhcStatsEntry 1 }

mscVrIpNhrpNhcRxResolveReplyAck OBJECT-TYPE
   SYNTAX     Counter32 
   ACCESS     read-only
   STATUS     mandatory
   DESCRIPTION
     "This attribute counts the positively acknowledged NHRP Resolution 
      Replies received by this client.
      This counter wraps to zero when the maximum value is exceeded."
::= { mscVrIpNhrpNhcStatsEntry 2 }

mscVrIpNhrpNhcRxResolveReplyNakProhibited OBJECT-TYPE
   SYNTAX     Counter32 
   ACCESS     read-only
   STATUS     mandatory
   DESCRIPTION
     "This attribute counts the NAK NHRP Resolution Replies received 
      by this client that contained the code indicating 'Administratively 
      Prohibited'. 
      This counter wraps to zero when the maximum value is exceeded."
::= { mscVrIpNhrpNhcStatsEntry 3 }

mscVrIpNhrpNhcRxResolveReplyNakInsufResources OBJECT-TYPE
   SYNTAX     Counter32 
   ACCESS     read-only
   STATUS     mandatory
   DESCRIPTION
     "This attribute counts the NAK NHRP Resolution Replies received 
      by this client that contained the code indicating 'Insufficient 
      Resources'. 
      This counter wraps to zero when the maximum value is exceeded."
::= { mscVrIpNhrpNhcStatsEntry 4 }

mscVrIpNhrpNhcRxResolveReplyNakNoBinding OBJECT-TYPE
   SYNTAX     Counter32 
   ACCESS     read-only
   STATUS     mandatory
   DESCRIPTION
     "This attribute counts the NAK NHRP Resolution Replies received 
      by this client that contained the code indicating 'No 
      Internetworking Layer Address to NBMA Address Binding Exists'. 
      This counter wraps to zero when the maximum value is exceeded."
::= { mscVrIpNhrpNhcStatsEntry 5 }

mscVrIpNhrpNhcRxResolveReplyNakNotUnique OBJECT-TYPE
   SYNTAX     Counter32 
   ACCESS     read-only
   STATUS     mandatory
   DESCRIPTION
     "This attribute counts the NAK NHRP Resolution Replies received 
      by this client that contained the code indicating 'Binding Exists But 
      Is Not Unique'. 
      This counter wraps to zero when the maximum value is exceeded."
::= { mscVrIpNhrpNhcStatsEntry 6 }

mscVrIpNhrpNhcRxPurgeReq OBJECT-TYPE
   SYNTAX     Counter32 
   ACCESS     read-only
   STATUS     mandatory
   DESCRIPTION
     "This attribute counts the NHRP Purge Requests received by this 
      client. 
      This counter wraps to zero when the maximum value is exceeded."
::= { mscVrIpNhrpNhcStatsEntry 12 }

mscVrIpNhrpNhcTxPurgeReq OBJECT-TYPE
   SYNTAX     Counter32 
   ACCESS     read-only
   STATUS     mandatory
   DESCRIPTION
     "This attribute counts the NHRP Purge Requests transmitted by this 
      client.
      This counter wraps to zero when the maximum value is exceeded."
::= { mscVrIpNhrpNhcStatsEntry 13 }

mscVrIpNhrpNhcRxPurgeReply OBJECT-TYPE
   SYNTAX     Counter32 
   ACCESS     read-only
   STATUS     mandatory
   DESCRIPTION
     "This attribute counts the NHRP Purge Replies received by this 
      client.
      This counter wraps to zero when the maximum value is exceeded."
::= { mscVrIpNhrpNhcStatsEntry 14 }

mscVrIpNhrpNhcTxPurgeReply OBJECT-TYPE
   SYNTAX     Counter32 
   ACCESS     read-only
   STATUS     mandatory
   DESCRIPTION
     "This attribute counts the NHRP Purge Replies transmitted by this 
      client.
      This counter wraps to zero when the maximum value is exceeded."
::= { mscVrIpNhrpNhcStatsEntry 15 }

mscVrIpNhrpNhcTxErrIndication OBJECT-TYPE
   SYNTAX     Counter32 
   ACCESS     read-only
   STATUS     mandatory
   DESCRIPTION
     "This attribute counts the NHRP Error Indication packets transmitted 
      by this client.
      This counter wraps to zero when the maximum value is exceeded."
::= { mscVrIpNhrpNhcStatsEntry 16 }

mscVrIpNhrpNhcRxErrUnrecognizedExtension OBJECT-TYPE
   SYNTAX     Counter32 
   ACCESS     read-only
   STATUS     mandatory
   DESCRIPTION
     "This attribute counts the NHRP Error Indication packets received by 
      this client with the error code 'Unrecognized Extension'. 
      This counter wraps to zero when the maximum value is exceeded."
::= { mscVrIpNhrpNhcStatsEntry 17 }

mscVrIpNhrpNhcRxErrLoopDetected OBJECT-TYPE
   SYNTAX     Counter32 
   ACCESS     read-only
   STATUS     mandatory
   DESCRIPTION
     "This attribute counts the NHRP Error Indication packets received by 
      this client with the error code 'NHRP Loop Detected'. 
      This counter wraps to zero when the maximum value is exceeded."
::= { mscVrIpNhrpNhcStatsEntry 18 }

mscVrIpNhrpNhcRxErrProtoAddrUnreachable OBJECT-TYPE
   SYNTAX     Counter32 
   ACCESS     read-only
   STATUS     mandatory
   DESCRIPTION
     "This attribute counts the NHRP Error Indication packets received by 
      this client with the error code 'Protocol Address Unreachable'. 
      This counter wraps to zero when the maximum value is exceeded."
::= { mscVrIpNhrpNhcStatsEntry 19 }

mscVrIpNhrpNhcRxErrProtoError OBJECT-TYPE
   SYNTAX     Counter32 
   ACCESS     read-only
   STATUS     mandatory
   DESCRIPTION
     "This attribute counts the NHRP Error Indication packets received by 
      this client with the error code 'Protocol Error'. 
      This counter wraps to zero when the maximum value is exceeded."
::= { mscVrIpNhrpNhcStatsEntry 20 }

mscVrIpNhrpNhcRxErrSduSizeExceeded OBJECT-TYPE
   SYNTAX     Counter32 
   ACCESS     read-only
   STATUS     mandatory
   DESCRIPTION
     "This attribute counts the NHRP Error Indication packets received by 
      this client with the error code 'NHRP SDU Size Exceeded'. 
      This counter wraps to zero when the maximum value is exceeded."
::= { mscVrIpNhrpNhcStatsEntry 21 }

mscVrIpNhrpNhcRxErrInvalidExtension OBJECT-TYPE
   SYNTAX     Counter32 
   ACCESS     read-only
   STATUS     mandatory
   DESCRIPTION
     "This attribute counts the NHRP Error Indication packets received by 
      this client with the error code 'Invalid Extension'.
      This counter wraps to zero when the maximum value is exceeded."
::= { mscVrIpNhrpNhcStatsEntry 22 }

mscVrIpNhrpNhcRxErrAuthenticationFailure OBJECT-TYPE
   SYNTAX     Counter32 
   ACCESS     read-only
   STATUS     mandatory
   DESCRIPTION
     "This attribute counts the NHRP Error Indication packets received by 
      this client with the error code 'Authentication Failure'. 
      This counter wraps to zero when the maximum value is exceeded."
::= { mscVrIpNhrpNhcStatsEntry 23 }

mscVrIpNhrpNhcRxErrHopCountExceeded OBJECT-TYPE
   SYNTAX     Counter32 
   ACCESS     read-only
   STATUS     mandatory
   DESCRIPTION
     "This attribute counts the NHRP Error Indication packets received by 
      this client with the error code 'Hop Count Exceeded'. 
      This counter wraps to zero when the maximum value is exceeded."
::= { mscVrIpNhrpNhcStatsEntry 24 }

-- 
-- *** THIS SUBTREE CURRENTLY NOT IMPLEMENTED ***
-- 

-- Vr/<string> Ip Nhrp ResCacheEntry/<ipAddress>,<mask>
-- This component represents an entry in the NHRP resolution cache 
-- table.

mscVrIpNhrpRce OBJECT IDENTIFIER ::= { mscVrIpNhrp 4 }



mscVrIpNhrpRceRowStatusTable OBJECT-TYPE
   SYNTAX     SEQUENCE OF MscVrIpNhrpRceRowStatusEntry
   ACCESS     not-accessible
   STATUS     mandatory
   DESCRIPTION
     "*** THIS TABLE CURRENTLY NOT IMPLEMENTED ***

      This entry controls the addition and deletion of 
      mscVrIpNhrpRce components."
::= { mscVrIpNhrpRce 1 }

mscVrIpNhrpRceRowStatusEntry OBJECT-TYPE
   SYNTAX     MscVrIpNhrpRceRowStatusEntry
   ACCESS     not-accessible
   STATUS     mandatory
   DESCRIPTION
     "A single entry in the table represents a single 
      mscVrIpNhrpRce component."
   INDEX {
      mscVrIndex,
      mscVrIpIndex,
      mscVrIpNhrpIndex,
      mscVrIpNhrpRceDestAddrIndex,
      mscVrIpNhrpRceDestMaskIndex }
::= { mscVrIpNhrpRceRowStatusTable 1 }

MscVrIpNhrpRceRowStatusEntry ::= SEQUENCE {
   mscVrIpNhrpRceRowStatus
      RowStatus,
   mscVrIpNhrpRceComponentName
      DisplayString,
   mscVrIpNhrpRceStorageType
      StorageType,
   mscVrIpNhrpRceDestAddrIndex
      IpAddress,
   mscVrIpNhrpRceDestMaskIndex
      IpAddress }

mscVrIpNhrpRceRowStatus OBJECT-TYPE
   SYNTAX     RowStatus 
   ACCESS     read-only
   STATUS     mandatory
   DESCRIPTION
     "This variable is used as the basis for SNMP naming of
      mscVrIpNhrpRce components.
      These components cannot be added nor deleted."
::= { mscVrIpNhrpRceRowStatusEntry 1 }

mscVrIpNhrpRceComponentName OBJECT-TYPE
   SYNTAX     DisplayString 
   ACCESS     read-only
   STATUS     mandatory
   DESCRIPTION
     "This variable provides the component's string name for
      use with the ASCII Console Interface"
::= { mscVrIpNhrpRceRowStatusEntry 2 }

mscVrIpNhrpRceStorageType OBJECT-TYPE
   SYNTAX     StorageType 
   ACCESS     read-only
   STATUS     mandatory
   DESCRIPTION
     "This variable represents the storage type value for the
      mscVrIpNhrpRce tables."
::= { mscVrIpNhrpRceRowStatusEntry 4 }

mscVrIpNhrpRceDestAddrIndex OBJECT-TYPE
   SYNTAX     IpAddress 
   ACCESS     not-accessible
   STATUS     mandatory
   DESCRIPTION
     "This variable represents an index for the mscVrIpNhrpRce tables."
::= { mscVrIpNhrpRceRowStatusEntry 10 }

mscVrIpNhrpRceDestMaskIndex OBJECT-TYPE
   SYNTAX     IpAddress 
   ACCESS     not-accessible
   STATUS     mandatory
   DESCRIPTION
     "This variable represents an index for the mscVrIpNhrpRce tables."
::= { mscVrIpNhrpRceRowStatusEntry 11 }

mscVrIpNhrpRceOperTable OBJECT-TYPE
   SYNTAX     SEQUENCE OF MscVrIpNhrpRceOperEntry
   ACCESS     not-accessible
   STATUS     mandatory
   DESCRIPTION
     "*** THIS TABLE CURRENTLY NOT IMPLEMENTED ***

      This group contains the operational attributes of the ResCacheEntry 
      component."
::= { mscVrIpNhrpRce 10 }

mscVrIpNhrpRceOperEntry OBJECT-TYPE
   SYNTAX     MscVrIpNhrpRceOperEntry
   ACCESS     not-accessible
   STATUS     mandatory
   DESCRIPTION
     "An entry in the mscVrIpNhrpRceOperTable."
   INDEX {
      mscVrIndex,
      mscVrIpIndex,
      mscVrIpNhrpIndex,
      mscVrIpNhrpRceDestAddrIndex,
      mscVrIpNhrpRceDestMaskIndex }
::= { mscVrIpNhrpRceOperTable 1 }

MscVrIpNhrpRceOperEntry ::= SEQUENCE {
   mscVrIpNhrpRceNbmaAddress
      HexString,
   mscVrIpNhrpRceEntryState
      INTEGER,
   mscVrIpNhrpRceHoldingTime
      Unsigned32,
   mscVrIpNhrpRceShortcut
      RowPointer }

mscVrIpNhrpRceNbmaAddress OBJECT-TYPE
   SYNTAX     HexString (SIZE (0..20))
   ACCESS     read-only
   STATUS     mandatory
   DESCRIPTION
     "This attribute indicates the NBMA subnetwork address of the next 
      hop."
::= { mscVrIpNhrpRceOperEntry 3 }

mscVrIpNhrpRceEntryState OBJECT-TYPE
   SYNTAX     INTEGER  {
                 incomplete(1),
                 ackReply(2),
                 nakReply(3),
                 noReply(10),
                 localReply(11) }
   ACCESS     read-only
   STATUS     mandatory
   DESCRIPTION
     "This attribute indicates the state of this resolution cache entry. The 
      possible states are:
      incomplete - The client sent the resolution request and is waiting for 
      a reply.
      ackReply - The client sent the resolution request and received an 
      ACK reply.
      nakReply - The client sent the resolution request and received a 
      NAK reply. This entry remains in the cache for 20 minutes thereby 
      preventing subsequent requests during that time period.
      noReply - The client sent the resolution request but did not receive a 
      reply. This entry remains in the cache for 20 minutes thereby 
      preventing subsequent requests during that time period.
      localReply - The client sent the resolution request and received an 
      ACK reply from a locally-attached responder. This entry remains in 
      the cache for 20 minutes thereby preventing subsequent requests 
      during that time period."
::= { mscVrIpNhrpRceOperEntry 6 }

mscVrIpNhrpRceHoldingTime OBJECT-TYPE
   SYNTAX     Unsigned32 (0..4294967295)
   ACCESS     read-only
   STATUS     mandatory
   DESCRIPTION
     "This attribute indicates the number of seconds that this entry will 
      remain in the resolution cache table. If the entry has not been 
      refreshed before this time it will be removed from the cache."
::= { mscVrIpNhrpRceOperEntry 7 }

mscVrIpNhrpRceShortcut OBJECT-TYPE
   SYNTAX     RowPointer 
   ACCESS     read-only
   STATUS     mandatory
   DESCRIPTION
     "This attribute indicates the component name of the shortcut 
      connection associated with this resolution cache entry. If the 
      component name is empty then no shortcut currently exists."
::= { mscVrIpNhrpRceOperEntry 8 }




-- 
-- Version and Compliance statements
-- 



-- Object-Group Statement:
-- A list of all current accessible leaf objects.

-- OBJECTS { mscVrIpNhrpNhsTxPurgeReply,
--           mscVrIpNhrpNhsEpNetAddrDestinationMask,
--           mscVrIpNhrpNhcRxPurgeReply,
--           mscVrIpNhrpNhsEpNetAddrComponentName,
--           mscVrIpNhrpSnmpAdminStatus,
--           mscVrIpNhrpNhcRxErrAuthenticationFailure,
--           mscVrIpNhrpNhcTxPurgeReply,
--           mscVrIpNhrpNhsRxRegisterReq,
--           mscVrIpNhrpNhsRowStatus,
--           mscVrIpNhrpNhsFwdPurgeReply,
--           mscVrIpNhrpMaxResCacheEntries,
--           mscVrIpNhrpNhsRxErrHopCountExceeded,
--           mscVrIpNhrpNhsEpStorageType,
--           mscVrIpNhrpNhsFwdErrorIndication,
--           mscVrIpNhrpNhsFwdResolveReq,
--           mscVrIpNhrpNhcIdleDetectTimePeriod,
--           mscVrIpNhrpNhsTxErrProtoError,
--           mscVrIpNhrpNhcStorageType,
--           mscVrIpNhrpNhsTxErrLoopDetected,
--           mscVrIpNhrpNhsEpNetAddrDestinationAddress,
--           mscVrIpNhrpRceHoldingTime,
--           mscVrIpNhrpNhsEpRowStatus,
--           mscVrIpNhrpSnmpOperStatus,
--           mscVrIpNhrpNhsComponentName,
--           mscVrIpNhrpNhsRxPurgeReply,
--           mscVrIpNhrpRceStorageType,
--           mscVrPpIpPortLogicalIfNhrpIfRowStatus,
--           mscVrIpNhrpNhsRxErrInvalidResReplyReceived,
--           mscVrIpNhrpNhsRxResolveReq,
--           mscVrIpNhrpNhsTxPurgeReq,
--           mscVrIpNhrpNhcRxErrInvalidExtension,
--           mscVrIpNhrpNhsStorageType,
--           mscVrIpNhrpNhcRxErrSduSizeExceeded,
--           mscVrIpNhrpCurrResCacheEntries,
--           mscVrIpNhrpPeakResCacheEntries,
--           mscVrIpNhrpOperationalState,
--           mscVrIpNhrpNhcTxResolveReq,
--           mscVrIpNhrpNhcFlowDetectTimePeriod,
--           mscVrIpNhrpStorageType,
--           mscVrIpNhrpNhsEpAction,
--           mscVrIpNhrpNhcRxResolveReplyNakNoBinding,
--           mscVrIpNhrpNhsEpNetAddrStorageType,
--           mscVrIpNhrpRceEntryState,
--           mscVrIpNhrpNhcTxErrIndication,
--           mscVrIpNhrpNhsFwdPurgeReq,
--           mscVrIpNhrpNhsRxErrProtoError,
--           mscVrIpNhrpNhcRxPurgeReq,
--           mscVrIpNhrpRceShortcut,
--           mscVrIpNhrpNhsEpNetAddrSourceAddress,
--           mscVrIpNhrpFwdTransitRecord,
--           mscVrIpNhrpNhcRxErrHopCountExceeded,
--           mscVrIpNhrpNhsRxErrLoopDetected,
--           mscVrIpNhrpRowStatus,
--           mscVrIpNhrpNhsTxErrInvalidExtension,
--           mscVrIpNhrpNhsRxErrAuthenticationFailure,
--           mscVrIpNhrpNhcRxResolveReplyNakInsufResources,
--           mscVrIpNhrpNhsEpNetAddrRowStatus,
--           mscVrIpNhrpNhsEpNetAddrSourceMask,
--           mscVrIpNhrpNhsFwdRegisterReply,
--           mscVrIpNhrpNhsTxResolveReplyNakProhibited,
--           mscVrIpNhrpAdminState,
--           mscVrIpNhrpNhcIdleDetectPacketCount,
--           mscVrIpNhrpRceRowStatus,
--           mscVrIpNhrpNhsRxPurgeReq,
--           mscVrIpNhrpNhsTxResolveReplyNakNotUnique,
--           mscVrIpNhrpNhsTxErrUnrecognizedExtension,
--           mscVrIpNhrpNhcComponentName,
--           mscVrIpNhrpNhcAtmFlowDetection,
--           mscVrIpNhrpNhcRowStatus,
--           mscVrIpNhrpNhsTxErrSduSizeExceeded,
--           mscVrIpNhrpNhsTxErrAuthenticationFailure,
--           mscVrIpNhrpUsageState,
--           mscVrIpNhrpNhsEpProtocol,
--           mscVrPpIpPortLogicalIfNhrpIfStorageType,
--           mscVrIpNhrpNhsEpComponentName,
--           mscVrIpNhrpRevTransitRecord,
--           mscVrIpNhrpNhcRxErrProtoAddrUnreachable,
--           mscVrIpNhrpNhsTxResolveReplyNakNoBinding,
--           mscVrPpIpPortLogicalIfNhrpIfComponentName,
--           mscVrIpNhrpNhcFlowDetectPacketCount,
--           mscVrIpNhrpNhsTxErrProtoAddrUnreachable,
--           mscVrIpNhrpRceNbmaAddress,
--           mscVrIpNhrpNhsFwdResolveReply,
--           mscVrIpNhrpNhsTxResolveReplyNakInsufResources,
--           mscVrIpNhrpNhsRxErrInvalidExtension,
--           mscVrIpNhrpNhsTxErrHopCountExceeded,
--           mscVrIpNhrpNhcRxErrProtoError,
--           mscVrIpNhrpComponentName,
--           mscVrIpNhrpNhcTxPurgeReq,
--           mscVrIpNhrpRceComponentName,
--           mscVrIpNhrpNhcRxErrLoopDetected,
--           mscVrIpNhrpNhcRxErrUnrecognizedExtension,
--           mscVrIpNhrpNhcRxResolveReplyNakProhibited,
--           mscVrIpNhrpNhsFwdRegisterReq,
--           mscVrIpNhrpNhcRxResolveReplyNakNotUnique,
--           mscVrIpNhrpNhsRxErrUnrecognizedExtension,
--           mscVrIpNhrpNhcRxResolveReplyAck,
--           mscVrIpNhrpNhsTxResolveReplyAck,
--           mscVrIpNhrpNhsRxErrSduSizeExceeded,
--           mscVrIpNhrpNhsRxErrProtoAddrUnreachable }
-- STATUS  mandatory
-- DESCRIPTION
--   "A list of all current accessible leaf objects."

ipNhrpGroup OBJECT IDENTIFIER ::= { ipNhrpMIB 1 }
ipNhrpGroupCA OBJECT IDENTIFIER ::= { ipNhrpGroup 1 }
ipNhrpGroupCA02 OBJECT IDENTIFIER ::= { ipNhrpGroupCA 3 }
ipNhrpGroupCA02A OBJECT IDENTIFIER ::= { ipNhrpGroupCA02 2 }



-- Agent-Capabilities Statement:

-- PRODUCT-RELEASE "MscPassport Release 1.2 IpNhrp."
-- STATUS          mandatory
-- DESCRIPTION     "Carrier Passport IpNhrp MIB: MIB Version CA02A,
--                  Software Version CA02S9C."
-- SUPPORTS        Nortel-MsCarrier-MscPassport-IpNhrpMIB
--    INCLUDES     { ipNhrpGroupCA02A }

ipNhrpCapabilities OBJECT IDENTIFIER ::= { ipNhrpMIB 3 }
ipNhrpCapabilitiesCA OBJECT IDENTIFIER ::= { ipNhrpCapabilities 1 }
ipNhrpCapabilitiesCA02 OBJECT IDENTIFIER ::= { ipNhrpCapabilitiesCA 3 }
ipNhrpCapabilitiesCA02A OBJECT IDENTIFIER ::= { ipNhrpCapabilitiesCA02 2 }





END
