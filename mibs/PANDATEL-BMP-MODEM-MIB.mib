PANDATEL-BMP-MODEM-MIB DEFINITIONS ::= BEGIN

 -- This is the private mib group section for the BM-P modems.
 -- Because these modems must be installed in the PANDATEL modem rack
 -- the PANDATEL-MODEM-MIB also applies.

 -- Ver.1.06    Sep.19.2000

        IMPORTS
                enterprises
                        FROM RFC1155-SMI
                DisplayString
                        FROM RFC1213-MIB
                OBJECT-TYPE
                        FROM RFC-1212
                mdmSpecifics, device-id
                        FROM PANDATEL-MODEM-MIB;

-- ********************** THE MDM-BMP SUBTREE ******************************

-- the specific identifier is identical to the modem type integer
-- of the BM-P modem entries in the PANDATEL-MODEM-MIB mdmModemTable.

bmp-modem      OBJECT IDENTIFIER ::= { device-id 301 }     -- chassis-mib

bmp            OBJECT IDENTIFIER ::= { mdmSpecifics 301 }  -- this subtree

bmpModemTable OBJECT-TYPE
        SYNTAX  SEQUENCE OF BmpTableEntry
        ACCESS  not-accessible
        STATUS  mandatory
        DESCRIPTION
                "This table contains information about all BM-P modems in all racks."
        ::= { bmp 1 }

bmpTableEntry OBJECT-TYPE
        SYNTAX  BmpTableEntry
        ACCESS  not-accessible
        STATUS  mandatory
        DESCRIPTION
                "The index of the table."
        INDEX   { mdmRack, mdmModem, mdmPosition }
        ::= { bmpModemTable 1 }

BmpTableEntry ::= SEQUENCE {
        mdmRack
                INTEGER,
        mdmModem
                INTEGER,
        mdmPosition
                INTEGER,
        mdmModemName
                DisplayString,
        mdmDataEquipmentEmulation
                INTEGER,
        mdmClockMode
                INTEGER,
        mdmDistance
                INTEGER,
        mdmDataRateAdaptation
                INTEGER,
        mdmClockSource
                INTEGER,
        mdmDataRate
                INTEGER,
        mdmLocalCarrierDetect1
                INTEGER,
        mdmLocalCarrierDetect2
                INTEGER
        }

mdmRack OBJECT-TYPE
        SYNTAX  INTEGER
        ACCESS  read-only
        STATUS  mandatory
        DESCRIPTION
                "The index of the rack where the modem is installed."
        ::= { bmpTableEntry 1 }

mdmModem OBJECT-TYPE
        SYNTAX  INTEGER
        ACCESS  read-only
        STATUS  mandatory
        DESCRIPTION
                "This variable displays the slot number where the
                 corresponding modem is installed in the rack."
        ::= { bmpTableEntry 2 }

mdmPosition OBJECT-TYPE
        SYNTAX  INTEGER {
                local       (1),
                remote      (2)
                }
        ACCESS  read-only
        STATUS  mandatory
        DESCRIPTION
                "This variable displays the location of the corresponding
                 modem: 'local' or 'remote'. The modem which is plugged
                 into a managed rack is 'local', the counterpart is 'remote'."
        ::= { bmpTableEntry 3 }

mdmModemName OBJECT-TYPE
        SYNTAX  DisplayString
        ACCESS  read-only
        STATUS  mandatory
        DESCRIPTION
                "The verbal name of this modem."
        ::= { bmpTableEntry 5 }

mdmDataEquipmentEmulation OBJECT-TYPE
        SYNTAX  INTEGER {
                other       (1),
                dte         (2),
                dce         (3),
                te          (4),
                nt          (5),
                unknown     (99)
        }
        ACCESS  read-only
        STATUS  mandatory
        DESCRIPTION
                "Interface mode of the unit: 'dte' or 'dce', 'te' or 'nt'."
        ::= { bmpTableEntry 6 }

mdmClockMode OBJECT-TYPE
        SYNTAX  INTEGER {
                other       (1),
                slave       (2),
                master      (3)
        }
        ACCESS  read-write
        STATUS  mandatory
        DESCRIPTION
                "The clock mode of the unit: 'master' or 'slave'."
        ::= { bmpTableEntry 20 }

mdmDistance OBJECT-TYPE
        SYNTAX  INTEGER {
                other       (1),
                short       (3),
                long        (4)
        }
        ACCESS  read-write
        STATUS  mandatory
        DESCRIPTION
                "The transmission distance of the unit: 'long' or 'short'.
                 'Long' is valid for link data rates of up to 64 Kbps. For
                 data rates higher than 64 Kbps this entry must be set to
                 'short'."
        ::= { bmpTableEntry 21 }

mdmDataRateAdaptation OBJECT-TYPE
        SYNTAX  INTEGER {
                other       (1),
                disable     (2),
                enable      (3)
        }
        ACCESS  read-write
        STATUS  mandatory
        DESCRIPTION
                "This entry enables or disables data rate adaptation, i.e. one
                 unit operates at line speed and the other one at lower speeds
                 (1.2, 2.4, 4.8 or 9.6 Kbps at 64 Kbps line speed and 1.2, 2.4,
                 4.8, 9.6 or 19.2 Kbps at 128 Kbps line speed)."
        ::= { bmpTableEntry 22 }

mdmClockSource OBJECT-TYPE
        SYNTAX  INTEGER {
                other       (1),
                internal    (2),
                external    (4),
                async       (5)
        }
        ACCESS  read-write
        STATUS  mandatory
        DESCRIPTION
                "The clock source of the link: 'internal', 'external', or
                 'async'."
        ::= { bmpTableEntry 24 }

mdmDataRate OBJECT-TYPE
        SYNTAX  INTEGER {
                other       (1)
        }
        ACCESS  read-write
        STATUS  mandatory
        DESCRIPTION
                "The data rate at the interface in bits per seconds. If
                 dataRateAdaptation is disabled, the data rate at the remote
                 counterpart changes simultaneously. Otherwise the data rate
                 at one unit is fixed to line speed and the data rate at the
                 other unit must be set to speeds lower than line speed."
        ::= { bmpTableEntry 25 }

mdmLocalCarrierDetect1 OBJECT-TYPE
        SYNTAX  INTEGER {
                other                           (1),
                fo-link-and-remote-handshake    (2),
                fo-link                         (3)
        }
        ACCESS  read-write
        STATUS  mandatory
        DESCRIPTION
                "The data carrier detect mode at the interface: if set to
                 'fo-link-and-remote-handshake' the DCD signal (resp. I for
                 X.21, etc.) follows link status and remote RTS (resp. C for
                 X.21, etc.), if set to 'fo-link' the DCD signal follows link
                 status only."
        ::= { bmpTableEntry 60 }

mdmLocalCarrierDetect2 OBJECT-TYPE
        SYNTAX  INTEGER {
                other                           (1),
                fo-link-and-remote-handshake    (2),
                fo-link                         (3)
        }
        ACCESS  read-write
        STATUS  mandatory
        DESCRIPTION
                "The data carrier detect mode 2 at the interface: if set to
                 'fo-link-and-remote-handshake' the DSR signal  follows link
                 status and remote RTS (resp. C for X.21, etc.), if set to
                 'fo-link' the DSR signal follows link status only."
        ::= { bmpTableEntry 61 }

END
