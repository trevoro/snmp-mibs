--			Ascend mibts MIB
--
--			Ascend Communications, Inc
--			1275 Harbor Bay Pkwy
--			Alameda, CA 94502
--			+1 510 769 6001
--			info@ascend.com
--
-- Copyright (c) 1993-1999 Ascend Communications, Inc.
-- All rights reserved.
--
-- Do not edit this file directly.
-- It is generated automatically by mibgen for use with
-- TAOS version 10.0.1 or newer.
--

ASCEND-MIBTS-MIB DEFINITIONS ::= BEGIN

    IMPORTS

        configuration
            FROM ASCEND-MIB
	IpAddress
	    FROM RFC1155-SMI
	OBJECT-TYPE
	    FROM RFC-1212;

	-- If any of the MIB compilers have problems with the DisplayString
	-- or PhysAddress, uncomment the next two lines.

    DisplayString	::=	OCTET STRING
    -- PhysAddress	::=	OCTET STRING

    mibtermSrvProfile  OBJECT IDENTIFIER ::= { configuration 133}

	-- The mibtermSrvProfile table
	--
	-- This table contains parameters for the mibtermSrvProfile profile
	--

    mibtermSrvProfileTable	OBJECT-TYPE
	SYNTAX		SEQUENCE OF MibtermSrvProfileEntry
	ACCESS		not-accessible
	STATUS		mandatory
	DESCRIPTION	"A list of mibtermSrvProfile profile entries."
	::= { mibtermSrvProfile 1 }

    mibtermSrvProfileEntry	OBJECT-TYPE
	SYNTAX		MibtermSrvProfileEntry
	ACCESS		not-accessible
	STATUS		mandatory
	DESCRIPTION	"A mibtermSrvProfile entry containing objects that
			 maps to the parameters of mibtermSrvProfile profile."
	INDEX		{ termSrvProfile-Index-o }
	::= { mibtermSrvProfileTable 1 }

    MibtermSrvProfileEntry ::=
	SEQUENCE {
	    termSrvProfile-Index-o
		INTEGER,
	    termSrvProfile-Enabled
		INTEGER,
	    termSrvProfile-SecurityMode
		INTEGER,
	    termSrvProfile-ModemConfiguration-V42-mnp
		INTEGER,
	    termSrvProfile-ModemConfiguration-MaxBaudRate
		INTEGER,
	    termSrvProfile-ModemConfiguration-ModemTransmitLevel
		INTEGER,
	    termSrvProfile-ModemConfiguration-CellModeFirst
		INTEGER,
	    termSrvProfile-ModemConfiguration-CellLevel
		INTEGER,
	    termSrvProfile-ModemConfiguration-o7Even
		INTEGER,
	    termSrvProfile-ModemConfiguration-ModemMod
		INTEGER,
	    termSrvProfile-ModemConfiguration-oATAnswerString
		DisplayString,
	    termSrvProfile-ModemConfiguration-ModemOnHoldTimeout
		INTEGER,
	    termSrvProfile-ModemConfiguration-QuickConnectEnabled
		INTEGER,
	    termSrvProfile-ModemConfiguration-MaxV92ReceiveBaudRate
		INTEGER,
	    termSrvProfile-ModemConfiguration-V44Enabled
		INTEGER,
	    termSrvProfile-TerminalModeConfiguration-SilentMode
		INTEGER,
	    termSrvProfile-TerminalModeConfiguration-ClearScreen
		INTEGER,
	    termSrvProfile-TerminalModeConfiguration-SystemPassword
		DisplayString,
	    termSrvProfile-TerminalModeConfiguration-Banner
		DisplayString,
	    termSrvProfile-TerminalModeConfiguration-LoginPrompt
		DisplayString,
	    termSrvProfile-TerminalModeConfiguration-PasswordPrompt
		DisplayString,
	    termSrvProfile-TerminalModeConfiguration-ThirdLoginPrompt
		DisplayString,
	    termSrvProfile-TerminalModeConfiguration-ThirdPromptSequence
		INTEGER,
	    termSrvProfile-TerminalModeConfiguration-Prompt
		DisplayString,
	    termSrvProfile-TerminalModeConfiguration-TerminalType
		DisplayString,
	    termSrvProfile-TerminalModeConfiguration-ClearCall
		INTEGER,
	    termSrvProfile-TerminalModeConfiguration-BufferChars
		INTEGER,
	    termSrvProfile-TerminalModeConfiguration-Ping
		INTEGER,
	    termSrvProfile-TerminalModeConfiguration-Traceroute
		INTEGER,
	    termSrvProfile-TerminalModeConfiguration-Tcp
		INTEGER,
	    termSrvProfile-TerminalModeConfiguration-TsAraEnabled
		INTEGER,
	    termSrvProfile-TerminalModeConfiguration-RloginOptions-Rlogin
		INTEGER,
	    termSrvProfile-TerminalModeConfiguration-RloginOptions-MaxSourcePort
		INTEGER,
	    termSrvProfile-TerminalModeConfiguration-RloginOptions-MinSourcePort
		INTEGER,
	    termSrvProfile-TerminalModeConfiguration-TelnetOptions-Telnet
		INTEGER,
	    termSrvProfile-TerminalModeConfiguration-TelnetOptions-TelnetMode
		INTEGER,
	    termSrvProfile-TerminalModeConfiguration-TelnetOptions-AutoTelnet
		INTEGER,
	    termSrvProfile-TerminalModeConfiguration-TelnetOptions-LocalEcho
		INTEGER,
	    termSrvProfile-TerminalModeConfiguration-TelnetOptions-Security
		INTEGER,
	    termSrvProfile-TerminalModeConfiguration-IpAddMsg
		DisplayString,
	    termSrvProfile-TerminalModeConfiguration-PromptFormat
		INTEGER,
	    termSrvProfile-TerminalModeConfiguration-IpNetmaskMsg
		DisplayString,
	    termSrvProfile-TerminalModeConfiguration-IpGwAddMsg
		DisplayString,
	    termSrvProfile-TerminalModeConfiguration-LoginTimeout
		INTEGER,
	    termSrvProfile-TerminalModeConfiguration-PacketizeWaitTime
		INTEGER,
	    termSrvProfile-TerminalModeConfiguration-PacketizeChars
		INTEGER,
	    termSrvProfile-ImmediateModeOptions-Service
		INTEGER,
	    termSrvProfile-ImmediateModeOptions-TelnetHostAuth
		INTEGER,
	    termSrvProfile-ImmediateModeOptions-Host
		DisplayString,
	    termSrvProfile-ImmediateModeOptions-Port
		INTEGER,
	    termSrvProfile-MenuModeOptions-StartWithMenus
		INTEGER,
	    termSrvProfile-MenuModeOptions-ToggleScreen
		INTEGER,
	    termSrvProfile-MenuModeOptions-RemoteConfiguration
		INTEGER,
	    termSrvProfile-MenuModeOptions-Text1
		DisplayString,
	    termSrvProfile-MenuModeOptions-Host1
		DisplayString,
	    termSrvProfile-MenuModeOptions-Service1
		INTEGER,
	    termSrvProfile-MenuModeOptions-Port1
		INTEGER,
	    termSrvProfile-MenuModeOptions-User1
		DisplayString,
	    termSrvProfile-MenuModeOptions-Text2
		DisplayString,
	    termSrvProfile-MenuModeOptions-Host2
		DisplayString,
	    termSrvProfile-MenuModeOptions-Service2
		INTEGER,
	    termSrvProfile-MenuModeOptions-Port2
		INTEGER,
	    termSrvProfile-MenuModeOptions-User2
		DisplayString,
	    termSrvProfile-MenuModeOptions-Text3
		DisplayString,
	    termSrvProfile-MenuModeOptions-Host3
		DisplayString,
	    termSrvProfile-MenuModeOptions-Service3
		INTEGER,
	    termSrvProfile-MenuModeOptions-Port3
		INTEGER,
	    termSrvProfile-MenuModeOptions-User3
		DisplayString,
	    termSrvProfile-MenuModeOptions-Text4
		DisplayString,
	    termSrvProfile-MenuModeOptions-Host4
		DisplayString,
	    termSrvProfile-MenuModeOptions-Service4
		INTEGER,
	    termSrvProfile-MenuModeOptions-Port4
		INTEGER,
	    termSrvProfile-MenuModeOptions-User4
		DisplayString,
	    termSrvProfile-MenuModeOptions-MenuSelectionString
		DisplayString,
	    termSrvProfile-PppModeConfiguration-Ppp
		INTEGER,
	    termSrvProfile-PppModeConfiguration-Delay
		INTEGER,
	    termSrvProfile-PppModeConfiguration-Direct
		INTEGER,
	    termSrvProfile-PppModeConfiguration-Info
		INTEGER,
	    termSrvProfile-SlipModeConfiguration-Slip
		INTEGER,
	    termSrvProfile-SlipModeConfiguration-SlipBootp
		INTEGER,
	    termSrvProfile-SlipModeConfiguration-Info
		INTEGER,
	    termSrvProfile-SlipModeConfiguration-CslipAutoDetect
		INTEGER,
	    termSrvProfile-DialoutConfiguration-Enabled
		INTEGER,
	    termSrvProfile-DialoutConfiguration-DirectAccess
		INTEGER,
	    termSrvProfile-DialoutConfiguration-PortForDirectAccess
		INTEGER,
	    termSrvProfile-DialoutConfiguration-PasswordForDirectAccess
		DisplayString,
	    termSrvProfile-DialoutConfiguration-SecurityForDirectAccess
		INTEGER,
	    termSrvProfile-Action-o
		INTEGER
	}

    termSrvProfile-Index-o	OBJECT-TYPE
	SYNTAX	INTEGER
	ACCESS	read-only
	STATUS	mandatory
	DESCRIPTION	""
	::= { mibtermSrvProfileEntry 1 }

    termSrvProfile-Enabled	OBJECT-TYPE
	SYNTAX	INTEGER {
		    no (1),
		    yes (2)
		}
	ACCESS	read-write
	STATUS	mandatory
	DESCRIPTION	"Terminal server availability flag. When set to no all terminal server functions are disabled."
	::= { mibtermSrvProfileEntry 2 }

    termSrvProfile-SecurityMode	OBJECT-TYPE
	SYNTAX	INTEGER {
		    none (1),
		    partial (2),
		    full (3)
		}
	ACCESS	read-write
	STATUS	mandatory
	DESCRIPTION	"Indicates the type of terminal server security (if any)."
	::= { mibtermSrvProfileEntry 3 }

    termSrvProfile-ModemConfiguration-V42-mnp	OBJECT-TYPE
	SYNTAX	INTEGER {
		    wontV42 (1),
		    willV42 (2),
		    mustV42 (3)
		}
	ACCESS	read-write
	STATUS	mandatory
	DESCRIPTION	"Describes the modem error correction mode. Error correction can be required, not used, or optional."
	::= { mibtermSrvProfileEntry 4 }

    termSrvProfile-ModemConfiguration-MaxBaudRate	OBJECT-TYPE
	SYNTAX	INTEGER {
		    n-33600MaxBaud (1),
		    n-31200MaxBaud (2),
		    n-28800MaxBaud (3),
		    n-26400MaxBaud (4),
		    n-24000MaxBaud (5),
		    n-21600MaxBaud (6),
		    n-19200MaxBaud (7),
		    n-16800MaxBaud (8),
		    n-14400MaxBaud (9),
		    n-12000MaxBaud (10),
		    n-9600MaxBaud (11),
		    n-7200MaxBaud (12),
		    n-4800MaxBaud (13),
		    n-2400MaxBaud (14)
		}
	ACCESS	read-write
	STATUS	mandatory
	DESCRIPTION	"Describes the maximum connection baud rate the modems should try."
	::= { mibtermSrvProfileEntry 5 }

    termSrvProfile-ModemConfiguration-ModemTransmitLevel	OBJECT-TYPE
	SYNTAX	INTEGER {
		    level-13DbMdmTrnLevel (11),
		    level-14DbMdmTrnLevel (12),
		    level-15DbMdmTrnLevel (13),
		    level-16DbMdmTrnLevel (14),
		    level-17DbMdmTrnLevel (15),
		    level-18DbMdmTrnLevel (16)
		}
	ACCESS	read-write
	STATUS	mandatory
	DESCRIPTION	"The transmit attenuate level the modems should try."
	::= { mibtermSrvProfileEntry 6 }

    termSrvProfile-ModemConfiguration-CellModeFirst	OBJECT-TYPE
	SYNTAX	INTEGER {
		    no (1),
		    yes (2)
		}
	ACCESS	read-write
	STATUS	mandatory
	DESCRIPTION	"If yes, the modem attempts cellular connection first - then land connection. If no, land based is attempted first, then cellular."
	::= { mibtermSrvProfileEntry 7 }

    termSrvProfile-ModemConfiguration-CellLevel	OBJECT-TYPE
	SYNTAX	INTEGER {
		    level-18DbCellLevel (1),
		    level-17DbCellLevel (2),
		    level-16DbCellLevel (3),
		    level-15DbCellLevel (4),
		    level-14DbCellLevel (5),
		    level-13DbCellLevel (6),
		    level-12DbCellLevel (7),
		    level-11DbCellLevel (8),
		    level-10DbCellLevel (9)
		}
	ACCESS	read-write
	STATUS	mandatory
	DESCRIPTION	"The modem cellular communications transmit and receive level. Valid values are -10 db .. -18 db."
	::= { mibtermSrvProfileEntry 8 }

    termSrvProfile-ModemConfiguration-o7Even	OBJECT-TYPE
	SYNTAX	INTEGER {
		    no (1),
		    yes (2)
		}
	ACCESS	read-write
	STATUS	mandatory
	DESCRIPTION	"If set to yes, all incoming data has its parity bit cleared and all outgoing data is forced to 7 bits with even parity."
	::= { mibtermSrvProfileEntry 9 }

    termSrvProfile-ModemConfiguration-ModemMod	OBJECT-TYPE
	SYNTAX	INTEGER {
		    k56Modulation (1),
		    v34Modulation (2),
		    v90Modulation (3),
		    v92Modulation (4)
		}
	ACCESS	read-write
	STATUS	mandatory
	DESCRIPTION	"The modulation protocol to be attempted by the modems."
	::= { mibtermSrvProfileEntry 10 }

    termSrvProfile-ModemConfiguration-oATAnswerString	OBJECT-TYPE
	SYNTAX	DisplayString
	ACCESS	read-write
	STATUS	mandatory
	DESCRIPTION	"Allows the user to enter any additional AT commands in the modem answer string."
	::= { mibtermSrvProfileEntry 11 }

    termSrvProfile-ModemConfiguration-ModemOnHoldTimeout	OBJECT-TYPE
	SYNTAX	INTEGER {
		    mohDisabled (1),
		    n-10SecMohTimeout (2),
		    n-20SecMohTimeout (3),
		    n-30SecMohTimeout (4),
		    n-40SecMohTimeout (5),
		    n-1MinMohTimeout (6),
		    n-2MinMohTimeout (7),
		    n-3MinMohTimeout (8),
		    n-4MinMohTimeout (9),
		    n-6MinMohTimeout (10),
		    n-8MinMohTimeout (11),
		    n-12MinMohTimeout (12),
		    n-16MinMohTimeout (13),
		    noLimitMohTimeout (14),
		    connProfileUseGlobal (15)
		}
	ACCESS	read-write
	STATUS	mandatory
	DESCRIPTION	"The allowable Modem-on-Hold timeout values."
	::= { mibtermSrvProfileEntry 85 }

    termSrvProfile-ModemConfiguration-QuickConnectEnabled	OBJECT-TYPE
	SYNTAX	INTEGER {
		    no (1),
		    yes (2)
		}
	ACCESS	read-write
	STATUS	mandatory
	DESCRIPTION	"If set to yes, Quick-Connect will be enabled."
	::= { mibtermSrvProfileEntry 86 }

    termSrvProfile-ModemConfiguration-MaxV92ReceiveBaudRate	OBJECT-TYPE
	SYNTAX	INTEGER {
		    n-48000MaxV92Baud (1),
		    n-46667MaxV92Baud (2),
		    n-45333MaxV92Baud (3),
		    n-44000MaxV92Baud (4),
		    n-42667MaxV92Baud (5),
		    n-41333MaxV92Baud (6),
		    n-40000MaxV92Baud (7),
		    n-38667MaxV92Baud (8),
		    n-37333MaxV92Baud (9),
		    n-36000MaxV92Baud (10),
		    n-34667MaxV92Baud (11),
		    n-33333MaxV92Baud (12),
		    n-32000MaxV92Baud (13),
		    n-30667MaxV92Baud (14),
		    n-29333MaxV92Baud (15),
		    n-28000MaxV92Baud (16),
		    n-26667MaxV92Baud (17),
		    n-25333MaxV92Baud (18),
		    n-24000MaxV92Baud (19)
		}
	ACCESS	read-write
	STATUS	mandatory
	DESCRIPTION	"The maximum V.92 receive baud rate to be attempted by the modems."
	::= { mibtermSrvProfileEntry 87 }

    termSrvProfile-ModemConfiguration-V44Enabled	OBJECT-TYPE
	SYNTAX	INTEGER {
		    no (1),
		    yes (2)
		}
	ACCESS	read-write
	STATUS	mandatory
	DESCRIPTION	"If set to yes, allow V.44 compression to be negotiated"
	::= { mibtermSrvProfileEntry 88 }

    termSrvProfile-TerminalModeConfiguration-SilentMode	OBJECT-TYPE
	SYNTAX	INTEGER {
		    no (1),
		    yes (2)
		}
	ACCESS	read-write
	STATUS	mandatory
	DESCRIPTION	"Don't generate any status messages upon connection."
	::= { mibtermSrvProfileEntry 12 }

    termSrvProfile-TerminalModeConfiguration-ClearScreen	OBJECT-TYPE
	SYNTAX	INTEGER {
		    no (1),
		    yes (2)
		}
	ACCESS	read-write
	STATUS	mandatory
	DESCRIPTION	"Clear the screen at terminal server startup."
	::= { mibtermSrvProfileEntry 13 }

    termSrvProfile-TerminalModeConfiguration-SystemPassword	OBJECT-TYPE
	SYNTAX	DisplayString
	ACCESS	read-write
	STATUS	mandatory
	DESCRIPTION	"Global terminal server system access password."
	::= { mibtermSrvProfileEntry 14 }

    termSrvProfile-TerminalModeConfiguration-Banner	OBJECT-TYPE
	SYNTAX	DisplayString
	ACCESS	read-write
	STATUS	mandatory
	DESCRIPTION	"The terminal server login banner."
	::= { mibtermSrvProfileEntry 15 }

    termSrvProfile-TerminalModeConfiguration-LoginPrompt	OBJECT-TYPE
	SYNTAX	DisplayString
	ACCESS	read-write
	STATUS	mandatory
	DESCRIPTION	"The string used to prompt for user name when authentication is in use."
	::= { mibtermSrvProfileEntry 16 }

    termSrvProfile-TerminalModeConfiguration-PasswordPrompt	OBJECT-TYPE
	SYNTAX	DisplayString
	ACCESS	read-write
	STATUS	mandatory
	DESCRIPTION	"The string used to prompt for password when authentication is in use."
	::= { mibtermSrvProfileEntry 17 }

    termSrvProfile-TerminalModeConfiguration-ThirdLoginPrompt	OBJECT-TYPE
	SYNTAX	DisplayString
	ACCESS	read-write
	STATUS	mandatory
	DESCRIPTION	"An optional third prompt for a terminal server login. If this value is null no third prompt is used."
	::= { mibtermSrvProfileEntry 18 }

    termSrvProfile-TerminalModeConfiguration-ThirdPromptSequence	OBJECT-TYPE
	SYNTAX	INTEGER {
		    last (1),
		    first (2)
		}
	ACCESS	read-write
	STATUS	mandatory
	DESCRIPTION	"Select where the third prompt should appear in the login sequence: either before or after user name & password."
	::= { mibtermSrvProfileEntry 19 }

    termSrvProfile-TerminalModeConfiguration-Prompt	OBJECT-TYPE
	SYNTAX	DisplayString
	ACCESS	read-write
	STATUS	mandatory
	DESCRIPTION	"The current terminal server prompt."
	::= { mibtermSrvProfileEntry 20 }

    termSrvProfile-TerminalModeConfiguration-TerminalType	OBJECT-TYPE
	SYNTAX	DisplayString
	ACCESS	read-write
	STATUS	mandatory
	DESCRIPTION	"The default terminal type for telnet and rlogin sessions."
	::= { mibtermSrvProfileEntry 21 }

    termSrvProfile-TerminalModeConfiguration-ClearCall	OBJECT-TYPE
	SYNTAX	INTEGER {
		    no (1),
		    yes (2)
		}
	ACCESS	read-write
	STATUS	mandatory
	DESCRIPTION	"Select operation when a telnet/rlogin/tcp session terminates. When set to yes, the dial-in session will also terminate."
	::= { mibtermSrvProfileEntry 22 }

    termSrvProfile-TerminalModeConfiguration-BufferChars	OBJECT-TYPE
	SYNTAX	INTEGER {
		    no (1),
		    yes (2)
		}
	ACCESS	read-write
	STATUS	mandatory
	DESCRIPTION	"Whether to buffer termserv characters or to forward them without buffering. Buffering provides better throughput at a slight increase in latency."
	::= { mibtermSrvProfileEntry 23 }

    termSrvProfile-TerminalModeConfiguration-Ping	OBJECT-TYPE
	SYNTAX	INTEGER {
		    no (1),
		    yes (2)
		}
	ACCESS	read-write
	STATUS	mandatory
	DESCRIPTION	"Enable/disable the ping command from the terminal server."
	::= { mibtermSrvProfileEntry 24 }

    termSrvProfile-TerminalModeConfiguration-Traceroute	OBJECT-TYPE
	SYNTAX	INTEGER {
		    no (1),
		    yes (2)
		}
	ACCESS	read-write
	STATUS	mandatory
	DESCRIPTION	"Enable/disable the traceroute command from the terminal server."
	::= { mibtermSrvProfileEntry 25 }

    termSrvProfile-TerminalModeConfiguration-Tcp	OBJECT-TYPE
	SYNTAX	INTEGER {
		    no (1),
		    yes (2)
		}
	ACCESS	read-write
	STATUS	mandatory
	DESCRIPTION	"Enable/disable the tcp command from the terminal server."
	::= { mibtermSrvProfileEntry 26 }

    termSrvProfile-TerminalModeConfiguration-TsAraEnabled	OBJECT-TYPE
	SYNTAX	INTEGER {
		    no (1),
		    yes (2)
		}
	ACCESS	read-write
	STATUS	mandatory
	DESCRIPTION	"TRUE if terminal server users are allowed to intiate async ARA sessions."
	::= { mibtermSrvProfileEntry 27 }

    termSrvProfile-TerminalModeConfiguration-RloginOptions-Rlogin	OBJECT-TYPE
	SYNTAX	INTEGER {
		    no (1),
		    yes (2)
		}
	ACCESS	read-write
	STATUS	mandatory
	DESCRIPTION	"Enable/disable the rlogin command from the terminal server."
	::= { mibtermSrvProfileEntry 28 }

    termSrvProfile-TerminalModeConfiguration-RloginOptions-MaxSourcePort	OBJECT-TYPE
	SYNTAX	INTEGER
	ACCESS	read-write
	STATUS	mandatory
	DESCRIPTION	"A highest limit of the port number used by rlogin. For BSD's rlogin, the client source port range is 512 to 1023."
	::= { mibtermSrvProfileEntry 29 }

    termSrvProfile-TerminalModeConfiguration-RloginOptions-MinSourcePort	OBJECT-TYPE
	SYNTAX	INTEGER
	ACCESS	read-write
	STATUS	mandatory
	DESCRIPTION	"A lowest limit of the port number used by rlogin. For BSD's rlogin, the client source port range is 512 to 1023."
	::= { mibtermSrvProfileEntry 30 }

    termSrvProfile-TerminalModeConfiguration-TelnetOptions-Telnet	OBJECT-TYPE
	SYNTAX	INTEGER {
		    no (1),
		    yes (2)
		}
	ACCESS	read-write
	STATUS	mandatory
	DESCRIPTION	"Enable/disable the use of the telnet terminal server command."
	::= { mibtermSrvProfileEntry 31 }

    termSrvProfile-TerminalModeConfiguration-TelnetOptions-TelnetMode	OBJECT-TYPE
	SYNTAX	INTEGER {
		    ascii (1),
		    binary (2),
		    transparent (3)
		}
	ACCESS	read-write
	STATUS	mandatory
	DESCRIPTION	"Selects default Telnet mode: ASCII, Binary, or Transparent."
	::= { mibtermSrvProfileEntry 32 }

    termSrvProfile-TerminalModeConfiguration-TelnetOptions-AutoTelnet	OBJECT-TYPE
	SYNTAX	INTEGER {
		    no (1),
		    yes (2)
		}
	ACCESS	read-write
	STATUS	mandatory
	DESCRIPTION	"If set to 'yes' unknown terminal server commands will be treated as the name of a host to telnet to."
	::= { mibtermSrvProfileEntry 33 }

    termSrvProfile-TerminalModeConfiguration-TelnetOptions-LocalEcho	OBJECT-TYPE
	SYNTAX	INTEGER {
		    no (1),
		    yes (2)
		}
	ACCESS	read-write
	STATUS	mandatory
	DESCRIPTION	"Defines the default echo mode for telnet sessions. The default mode can be overridded on the command line."
	::= { mibtermSrvProfileEntry 34 }

    termSrvProfile-TerminalModeConfiguration-TelnetOptions-Security	OBJECT-TYPE
	SYNTAX	INTEGER {
		    telnetSecurityNone (1),
		    telnetSecurityGlobal (2),
		    telnetSecurityProfile (3),
		    telnetSecurityAuthSetting (4)
		}
	ACCESS	read-write
	STATUS	mandatory
	DESCRIPTION	"Level of security used to authenticate telnet sessions."
	::= { mibtermSrvProfileEntry 35 }

    termSrvProfile-TerminalModeConfiguration-IpAddMsg	OBJECT-TYPE
	SYNTAX	DisplayString
	ACCESS	read-write
	STATUS	mandatory
	DESCRIPTION	"This is a text field that will be printed in front of the IP address in the terminal server when going into PPP."
	::= { mibtermSrvProfileEntry 36 }

    termSrvProfile-TerminalModeConfiguration-PromptFormat	OBJECT-TYPE
	SYNTAX	INTEGER {
		    no (1),
		    yes (2)
		}
	ACCESS	read-write
	STATUS	mandatory
	DESCRIPTION	"TRUE if the terminal server prompt should interpret \\n."
	::= { mibtermSrvProfileEntry 37 }

    termSrvProfile-TerminalModeConfiguration-IpNetmaskMsg	OBJECT-TYPE
	SYNTAX	DisplayString
	ACCESS	read-write
	STATUS	mandatory
	DESCRIPTION	"This is a text field that will be printed in front of the IP Netmask in the terminal server when going into SLIP."
	::= { mibtermSrvProfileEntry 38 }

    termSrvProfile-TerminalModeConfiguration-IpGwAddMsg	OBJECT-TYPE
	SYNTAX	DisplayString
	ACCESS	read-write
	STATUS	mandatory
	DESCRIPTION	"This is a text field that will be printed in front of the IP Gateway address in the terminal server when going into SLIP."
	::= { mibtermSrvProfileEntry 39 }

    termSrvProfile-TerminalModeConfiguration-LoginTimeout	OBJECT-TYPE
	SYNTAX	INTEGER
	ACCESS	read-write
	STATUS	mandatory
	DESCRIPTION	"The number of seconds to wait at the login prompt for the user to login. A value of 0 disables the timeout."
	::= { mibtermSrvProfileEntry 40 }

    termSrvProfile-TerminalModeConfiguration-PacketizeWaitTime	OBJECT-TYPE
	SYNTAX	INTEGER
	ACCESS	read-write
	STATUS	mandatory
	DESCRIPTION	"The number of milliseconds to accumulate modem data in a packet."
	::= { mibtermSrvProfileEntry 41 }

    termSrvProfile-TerminalModeConfiguration-PacketizeChars	OBJECT-TYPE
	SYNTAX	INTEGER
	ACCESS	read-write
	STATUS	mandatory
	DESCRIPTION	"The number of characters to accumulate modem data in a packet."
	::= { mibtermSrvProfileEntry 42 }

    termSrvProfile-ImmediateModeOptions-Service	OBJECT-TYPE
	SYNTAX	INTEGER {
		    none (1),
		    telnet (2),
		    rawTcp (3),
		    rlogin (4),
		    x25Pad (5),
		    x25T3pos (6)
		}
	ACCESS	read-write
	STATUS	mandatory
	DESCRIPTION	"enable/disable immediate mode and specify the service type. Immediate mode is where a user is automatically connected to a remote host using the specified service."
	::= { mibtermSrvProfileEntry 43 }

    termSrvProfile-ImmediateModeOptions-TelnetHostAuth	OBJECT-TYPE
	SYNTAX	INTEGER {
		    no (1),
		    yes (2)
		}
	ACCESS	read-write
	STATUS	mandatory
	DESCRIPTION	"Option defines if telnet is started directly bypassing the local authentication process. When enabled, authentication is the responsibility of the telnet host."
	::= { mibtermSrvProfileEntry 44 }

    termSrvProfile-ImmediateModeOptions-Host	OBJECT-TYPE
	SYNTAX	DisplayString
	ACCESS	read-write
	STATUS	mandatory
	DESCRIPTION	"Name or IP address or X.121 address of the immediate TELNET, TCP, or X.25/Pad host to connect to."
	::= { mibtermSrvProfileEntry 45 }

    termSrvProfile-ImmediateModeOptions-Port	OBJECT-TYPE
	SYNTAX	INTEGER
	ACCESS	read-write
	STATUS	mandatory
	DESCRIPTION	"TCP port to which the TELNET or TCP stream is to be redirected to."
	::= { mibtermSrvProfileEntry 46 }

    termSrvProfile-MenuModeOptions-StartWithMenus	OBJECT-TYPE
	SYNTAX	INTEGER {
		    no (1),
		    yes (2)
		}
	ACCESS	read-write
	STATUS	mandatory
	DESCRIPTION	"Terminal server interface will start in menu mode when this field is 'yes'."
	::= { mibtermSrvProfileEntry 47 }

    termSrvProfile-MenuModeOptions-ToggleScreen	OBJECT-TYPE
	SYNTAX	INTEGER {
		    no (1),
		    yes (2)
		}
	ACCESS	read-write
	STATUS	mandatory
	DESCRIPTION	"When enabled, users are able to toggle between menu mode and the normal terminal server command line."
	::= { mibtermSrvProfileEntry 48 }

    termSrvProfile-MenuModeOptions-RemoteConfiguration	OBJECT-TYPE
	SYNTAX	INTEGER {
		    no (1),
		    yes (2)
		}
	ACCESS	read-write
	STATUS	mandatory
	DESCRIPTION	"When enabled, the text and host addresses that make up the menu will be retrieved from RADIUS (if RADIUS is enabled)."
	::= { mibtermSrvProfileEntry 49 }

    termSrvProfile-MenuModeOptions-Text1	OBJECT-TYPE
	SYNTAX	DisplayString
	ACCESS	read-write
	STATUS	mandatory
	DESCRIPTION	"The text to put in the terminal server menu for the first login host when remote configuration isn't available."
	::= { mibtermSrvProfileEntry 50 }

    termSrvProfile-MenuModeOptions-Host1	OBJECT-TYPE
	SYNTAX	DisplayString
	ACCESS	read-write
	STATUS	mandatory
	DESCRIPTION	"The address of the first host to access when terminal server menu mode is being used without remote configuration."
	::= { mibtermSrvProfileEntry 51 }

    termSrvProfile-MenuModeOptions-Service1	OBJECT-TYPE
	SYNTAX	INTEGER {
		    telnet (1),
		    rlogin (2),
		    ppp (3),
		    rawtcp (4)
		}
	ACCESS	read-write
	STATUS	mandatory
	DESCRIPTION	"Type of service required for this selection."
	::= { mibtermSrvProfileEntry 52 }

    termSrvProfile-MenuModeOptions-Port1	OBJECT-TYPE
	SYNTAX	INTEGER
	ACCESS	read-write
	STATUS	mandatory
	DESCRIPTION	"The port for contacting host. Used only for telnet service."
	::= { mibtermSrvProfileEntry 53 }

    termSrvProfile-MenuModeOptions-User1	OBJECT-TYPE
	SYNTAX	DisplayString
	ACCESS	read-write
	STATUS	mandatory
	DESCRIPTION	"The user name for this selection. Used only for rlogin service."
	::= { mibtermSrvProfileEntry 54 }

    termSrvProfile-MenuModeOptions-Text2	OBJECT-TYPE
	SYNTAX	DisplayString
	ACCESS	read-write
	STATUS	mandatory
	DESCRIPTION	"The text to put in the terminal server menu for the second login host when remote configuration isn't available."
	::= { mibtermSrvProfileEntry 55 }

    termSrvProfile-MenuModeOptions-Host2	OBJECT-TYPE
	SYNTAX	DisplayString
	ACCESS	read-write
	STATUS	mandatory
	DESCRIPTION	"The address of the second host to access when terminal server menu mode is being used without remote configuration."
	::= { mibtermSrvProfileEntry 56 }

    termSrvProfile-MenuModeOptions-Service2	OBJECT-TYPE
	SYNTAX	INTEGER {
		    telnet (1),
		    rlogin (2),
		    ppp (3),
		    rawtcp (4)
		}
	ACCESS	read-write
	STATUS	mandatory
	DESCRIPTION	"Type of service required for this selection."
	::= { mibtermSrvProfileEntry 57 }

    termSrvProfile-MenuModeOptions-Port2	OBJECT-TYPE
	SYNTAX	INTEGER
	ACCESS	read-write
	STATUS	mandatory
	DESCRIPTION	"The port for contacting host. Used only for telnet service."
	::= { mibtermSrvProfileEntry 58 }

    termSrvProfile-MenuModeOptions-User2	OBJECT-TYPE
	SYNTAX	DisplayString
	ACCESS	read-write
	STATUS	mandatory
	DESCRIPTION	"The user name for this selection. Used only for rlogin service."
	::= { mibtermSrvProfileEntry 59 }

    termSrvProfile-MenuModeOptions-Text3	OBJECT-TYPE
	SYNTAX	DisplayString
	ACCESS	read-write
	STATUS	mandatory
	DESCRIPTION	"The text to put in the terminal server menu for the third login host when remote configuration isn't available."
	::= { mibtermSrvProfileEntry 60 }

    termSrvProfile-MenuModeOptions-Host3	OBJECT-TYPE
	SYNTAX	DisplayString
	ACCESS	read-write
	STATUS	mandatory
	DESCRIPTION	"The address of the third host to access when terminal server menu mode is being used without remote configuration."
	::= { mibtermSrvProfileEntry 61 }

    termSrvProfile-MenuModeOptions-Service3	OBJECT-TYPE
	SYNTAX	INTEGER {
		    telnet (1),
		    rlogin (2),
		    ppp (3),
		    rawtcp (4)
		}
	ACCESS	read-write
	STATUS	mandatory
	DESCRIPTION	"Type of service required for this selection."
	::= { mibtermSrvProfileEntry 62 }

    termSrvProfile-MenuModeOptions-Port3	OBJECT-TYPE
	SYNTAX	INTEGER
	ACCESS	read-write
	STATUS	mandatory
	DESCRIPTION	"The port for contacting host. Used only for telnet service."
	::= { mibtermSrvProfileEntry 63 }

    termSrvProfile-MenuModeOptions-User3	OBJECT-TYPE
	SYNTAX	DisplayString
	ACCESS	read-write
	STATUS	mandatory
	DESCRIPTION	"The user name for this selection. Used only for rlogin service."
	::= { mibtermSrvProfileEntry 64 }

    termSrvProfile-MenuModeOptions-Text4	OBJECT-TYPE
	SYNTAX	DisplayString
	ACCESS	read-write
	STATUS	mandatory
	DESCRIPTION	"The text to put in the terminal server menu for the forth login host when remote configuration isn't available."
	::= { mibtermSrvProfileEntry 65 }

    termSrvProfile-MenuModeOptions-Host4	OBJECT-TYPE
	SYNTAX	DisplayString
	ACCESS	read-write
	STATUS	mandatory
	DESCRIPTION	"The address of the forth host to access when terminal server menu mode is being used without remote configuration."
	::= { mibtermSrvProfileEntry 66 }

    termSrvProfile-MenuModeOptions-Service4	OBJECT-TYPE
	SYNTAX	INTEGER {
		    telnet (1),
		    rlogin (2),
		    ppp (3),
		    rawtcp (4)
		}
	ACCESS	read-write
	STATUS	mandatory
	DESCRIPTION	"Type of service required for this selection."
	::= { mibtermSrvProfileEntry 67 }

    termSrvProfile-MenuModeOptions-Port4	OBJECT-TYPE
	SYNTAX	INTEGER
	ACCESS	read-write
	STATUS	mandatory
	DESCRIPTION	"The port for contacting host. Used only for telnet service."
	::= { mibtermSrvProfileEntry 68 }

    termSrvProfile-MenuModeOptions-User4	OBJECT-TYPE
	SYNTAX	DisplayString
	ACCESS	read-write
	STATUS	mandatory
	DESCRIPTION	"The user name for this selection. Used only for rlogin service."
	::= { mibtermSrvProfileEntry 69 }

    termSrvProfile-MenuModeOptions-MenuSelectionString	OBJECT-TYPE
	SYNTAX	DisplayString
	ACCESS	read-write
	STATUS	mandatory
	DESCRIPTION	"The selection string for the menu mode."
	::= { mibtermSrvProfileEntry 70 }

    termSrvProfile-PppModeConfiguration-Ppp	OBJECT-TYPE
	SYNTAX	INTEGER {
		    no (1),
		    yes (2)
		}
	ACCESS	read-write
	STATUS	mandatory
	DESCRIPTION	"Enable/disable the PPP terminal server command."
	::= { mibtermSrvProfileEntry 71 }

    termSrvProfile-PppModeConfiguration-Delay	OBJECT-TYPE
	SYNTAX	INTEGER
	ACCESS	read-write
	STATUS	mandatory
	DESCRIPTION	"The number of seconds to wait for PPP before putting up the login banner and converting to telnet mode."
	::= { mibtermSrvProfileEntry 72 }

    termSrvProfile-PppModeConfiguration-Direct	OBJECT-TYPE
	SYNTAX	INTEGER {
		    no (1),
		    yes (2)
		}
	ACCESS	read-write
	STATUS	mandatory
	DESCRIPTION	"Option defines if PPP negotiation is started directly after 'PPP' Term Server command is received or, not. When disabled, we wait to receive a PPP packet before sending."
	::= { mibtermSrvProfileEntry 73 }

    termSrvProfile-PppModeConfiguration-Info	OBJECT-TYPE
	SYNTAX	INTEGER {
		    none (1),
		    modePpp (2),
		    sessionPpp (3)
		}
	ACCESS	read-write
	STATUS	mandatory
	DESCRIPTION	"Enable/Disable the PPP/SLIP start up message."
	::= { mibtermSrvProfileEntry 74 }

    termSrvProfile-SlipModeConfiguration-Slip	OBJECT-TYPE
	SYNTAX	INTEGER {
		    no (1),
		    yes (2)
		}
	ACCESS	read-write
	STATUS	mandatory
	DESCRIPTION	"Enable/disable the SLIP command from the terminal server."
	::= { mibtermSrvProfileEntry 75 }

    termSrvProfile-SlipModeConfiguration-SlipBootp	OBJECT-TYPE
	SYNTAX	INTEGER {
		    no (1),
		    yes (2)
		}
	ACCESS	read-write
	STATUS	mandatory
	DESCRIPTION	"Enable/disable the SLIP command from the terminal server."
	::= { mibtermSrvProfileEntry 76 }

    termSrvProfile-SlipModeConfiguration-Info	OBJECT-TYPE
	SYNTAX	INTEGER {
		    basicSlip (1),
		    advancedSlip (2)
		}
	ACCESS	read-write
	STATUS	mandatory
	DESCRIPTION	"Level of information displayed in SLIP start up message."
	::= { mibtermSrvProfileEntry 77 }

    termSrvProfile-SlipModeConfiguration-CslipAutoDetect	OBJECT-TYPE
	SYNTAX	INTEGER {
		    no (1),
		    yes (2)
		}
	ACCESS	read-write
	STATUS	mandatory
	DESCRIPTION	"Enable/disbale auto detecting of SLIP header compression. This feature will try to auto-detect if the caller is using Van Jacobson header compression, and if so, the box will automatically switch to CSLIP mode."
	::= { mibtermSrvProfileEntry 78 }

    termSrvProfile-DialoutConfiguration-Enabled	OBJECT-TYPE
	SYNTAX	INTEGER {
		    no (1),
		    yes (2)
		}
	ACCESS	read-write
	STATUS	mandatory
	DESCRIPTION	"Allow/disallow modem outdial from the terminal server."
	::= { mibtermSrvProfileEntry 79 }

    termSrvProfile-DialoutConfiguration-DirectAccess	OBJECT-TYPE
	SYNTAX	INTEGER {
		    no (1),
		    yes (2)
		}
	ACCESS	read-write
	STATUS	mandatory
	DESCRIPTION	"Allows direct connection to a modem by TELNETing to a configurable modem port."
	::= { mibtermSrvProfileEntry 80 }

    termSrvProfile-DialoutConfiguration-PortForDirectAccess	OBJECT-TYPE
	SYNTAX	INTEGER
	ACCESS	read-write
	STATUS	mandatory
	DESCRIPTION	"The telnet port number for direct access to a modem."
	::= { mibtermSrvProfileEntry 81 }

    termSrvProfile-DialoutConfiguration-PasswordForDirectAccess	OBJECT-TYPE
	SYNTAX	DisplayString
	ACCESS	read-write
	STATUS	mandatory
	DESCRIPTION	"The password that must be used to gain direct access to a modem"
	::= { mibtermSrvProfileEntry 82 }

    termSrvProfile-DialoutConfiguration-SecurityForDirectAccess	OBJECT-TYPE
	SYNTAX	INTEGER {
		    none (1),
		    global (2),
		    user (3)
		}
	ACCESS	read-write
	STATUS	mandatory
	DESCRIPTION	"The security method used to control direct modem access."
	::= { mibtermSrvProfileEntry 83 }

    termSrvProfile-Action-o	OBJECT-TYPE
	SYNTAX	INTEGER {
		    noAction (1),
		    createProfile (2),
		    deleteProfile (3)
		}
	ACCESS	read-write
	STATUS	mandatory
	DESCRIPTION	""
	::= { mibtermSrvProfileEntry 84 }

END
