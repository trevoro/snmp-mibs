Nortel-Magellan-Passport-AtmTrunksMIB
DEFINITIONS ::= BEGIN



IMPORTS

      OBJECT-TYPE
   FROM RFC-1212

      passportMIBs
   FROM Nortel-Magellan-Passport-UsefulDefinitionsMIB

      DisplayString,
      StorageType,
      RowStatus,
      Gauge32,
      Unsigned32
   FROM Nortel-Magellan-Passport-StandardTextualConventionsMIB

      NonReplicated,
      FixedPoint1,
      Link
   FROM Nortel-Magellan-Passport-TextualConventionsMIB

      trkIndex,
      trk
   FROM Nortel-Magellan-Passport-TrunksMIB;




-- LAST-UPDATED   "9902010000Z"
-- ORGANIZATION   "Nortel"
-- CONTACT-INFO   "
--         Nortel Magellan Network Management
--         
--         Postal: P.O. Box 5080, Station F 
--                 Ottawa, Ontario 
--                 Canada  K2C 3T1
--         
--         Email:  nm_plm@nt.com"
-- DESCRIPTION
--    "The module describing the Nortel Magellan Passport
--     AtmTrunks Enterprise MIB."

atmTrunksMIB OBJECT IDENTIFIER ::= { passportMIBs 59 }










-- Trunk/n AtmAccess
-- The AtmAccess component provides a Layer 2 protocol that adds no 
-- overhead to data on the ATM link that it accesses.

trkAtm OBJECT IDENTIFIER ::= { trk 3 }



trkAtmRowStatusTable OBJECT-TYPE
   SYNTAX     SEQUENCE OF TrkAtmRowStatusEntry
   ACCESS     not-accessible
   STATUS     mandatory
   DESCRIPTION
     "This entry controls the addition and deletion of 
      trkAtm components."
::= { trkAtm 1 }

trkAtmRowStatusEntry OBJECT-TYPE
   SYNTAX     TrkAtmRowStatusEntry
   ACCESS     not-accessible
   STATUS     mandatory
   DESCRIPTION
     "A single entry in the table represents a single 
      trkAtm component."
   INDEX {
      trkIndex,
      trkAtmIndex }
::= { trkAtmRowStatusTable 1 }

TrkAtmRowStatusEntry ::= SEQUENCE {
   trkAtmRowStatus
      RowStatus,
   trkAtmComponentName
      DisplayString,
   trkAtmStorageType
      StorageType,
   trkAtmIndex
      NonReplicated }

trkAtmRowStatus OBJECT-TYPE
   SYNTAX     RowStatus 
   ACCESS     read-write
   STATUS     mandatory
   DESCRIPTION
     "This variable is used as the basis for SNMP naming of
      trkAtm components.
      These components can be added and deleted."
::= { trkAtmRowStatusEntry 1 }

trkAtmComponentName OBJECT-TYPE
   SYNTAX     DisplayString 
   ACCESS     read-only
   STATUS     mandatory
   DESCRIPTION
     "This variable provides the component's string name for
      use with the ASCII Console Interface"
::= { trkAtmRowStatusEntry 2 }

trkAtmStorageType OBJECT-TYPE
   SYNTAX     StorageType 
   ACCESS     read-only
   STATUS     mandatory
   DESCRIPTION
     "This variable represents the storage type value for the
      trkAtm tables."
::= { trkAtmRowStatusEntry 4 }

trkAtmIndex OBJECT-TYPE
   SYNTAX     NonReplicated 
   ACCESS     not-accessible
   STATUS     mandatory
   DESCRIPTION
     "This variable represents the index for the trkAtm tables."
::= { trkAtmRowStatusEntry 10 }

trkAtmProvTable OBJECT-TYPE
   SYNTAX     SEQUENCE OF TrkAtmProvEntry
   ACCESS     not-accessible
   STATUS     mandatory
   DESCRIPTION
     "This group of provisionable attributes contains the parameters used 
      by AtmAccess for monitoring link quality."
::= { trkAtm 10 }

trkAtmProvEntry OBJECT-TYPE
   SYNTAX     TrkAtmProvEntry
   ACCESS     not-accessible
   STATUS     mandatory
   DESCRIPTION
     "An entry in the trkAtmProvTable."
   INDEX {
      trkIndex,
      trkAtmIndex }
::= { trkAtmProvTable 1 }

TrkAtmProvEntry ::= SEQUENCE {
   trkAtmMaximumErroredInterval
      Unsigned32,
   trkAtmReceiveErrorSensitivity
      Unsigned32,
   trkAtmAtmAccMaximumErroredInterval
      FixedPoint1 }

trkAtmMaximumErroredInterval OBJECT-TYPE
   SYNTAX     Unsigned32 (0 | 1..15)
   ACCESS     read-write
   STATUS     obsolete
   DESCRIPTION
     "This attribute specifies the interval time over which the error 
      threshold (as specified by receiveErrorSensitivity) must be 
      continuously exceeded before the Unacknowledged, Utp, 
      AtmAccess or FrAccess component can be degraded. Once the error 
      interval count exceeds the provisioned value, the Unacknowledged, 
      Utp, AtmAccess or FrAccess component will issue an alarm 
      indicating that link quality has degraded, and it will also disable its 
      parent component. The exception to this is a value of zero, the 
      default, which indicates that the mechanism is completely disabled."
   DEFVAL     { 0 }
::= { trkAtmProvEntry 1 }

trkAtmReceiveErrorSensitivity OBJECT-TYPE
   SYNTAX     Unsigned32 (0 | 1..10)
   ACCESS     read-write
   STATUS     mandatory
   DESCRIPTION
     "This attribute specifies the allowable error rate beyond which the 
      AtmAccess component can be degraded if the error rate persists for 
      a duration longer than the maximumErrorInterval. The threshold is 
      expressed as a percentage. It is the ratio of the number of errored 
      cells in the last interval over the number of cells received in the last 
      interval. For AAL5, the number of errored cells is converted from 
      rxFrameDiscard of AtmIf Vcc using the assumption that three ATM 
      cells are used to carry a 128 byte AAL5 frame. The number of 
      received cells is specified by rxCell of AtmIf Vcc. 
      
      The configurable values are:
      0 = the mechanism is completely disabled
      1 = 1/(2**1)
      2 = 1/(2**2)
      3 = 1/(2**3)
      :
      10 = 1/(2**10)"
   DEFVAL     { 3 }
::= { trkAtmProvEntry 2 }

trkAtmAtmAccMaximumErroredInterval OBJECT-TYPE
   SYNTAX     FixedPoint1 (0 | 5 | 10 | 15 | 20 | 25 | 30 | 35 | 40 | 45 | 50 | 60 | 70 | 80 | 90 | 100 | 110 | 120 | 130 | 140 | 150)
   ACCESS     read-write
   STATUS     mandatory
   DESCRIPTION
     "This attribute specifies the interval time over which the error 
      threshold (as specified by receiveErrorSensitivity) must be 
      continuously exceeded before the AtmAccess component can be 
      degraded. Once the error interval count exceeds the provisioned 
      value, the AtmAccess component issues an alarm indicating that link 
      quality has degraded, and it disables its parent component. The 
      exception to this is a value of zero, the default, which indicates that 
      the mechanism is completely disabled."
   DEFVAL     { 0 }
::= { trkAtmProvEntry 3 }

trkAtmInterfaceTable OBJECT-TYPE
   SYNTAX     SEQUENCE OF TrkAtmInterfaceEntry
   ACCESS     not-accessible
   STATUS     mandatory
   DESCRIPTION
     "This group of attributes provides the parameters used by the 
      AtmAccess component for specifying access to an ATM interface."
::= { trkAtm 11 }

trkAtmInterfaceEntry OBJECT-TYPE
   SYNTAX     TrkAtmInterfaceEntry
   ACCESS     not-accessible
   STATUS     mandatory
   DESCRIPTION
     "An entry in the trkAtmInterfaceTable."
   INDEX {
      trkIndex,
      trkAtmIndex }
::= { trkAtmInterfaceTable 1 }

TrkAtmInterfaceEntry ::= SEQUENCE {
   trkAtmAtmConnection
      Link,
   trkAtmBwElastic
      INTEGER,
   trkAtmVccReportingBw
      INTEGER }

trkAtmAtmConnection OBJECT-TYPE
   SYNTAX     Link 
   ACCESS     read-write
   STATUS     mandatory
   DESCRIPTION
     "This attribute specifies the component name of the ATM Layer 2 
      AAL5 interface that the AtmAccess component will use."
::= { trkAtmInterfaceEntry 1 }

trkAtmBwElastic OBJECT-TYPE
   SYNTAX     INTEGER  {
                 no(0),
                 yes(1) }
   ACCESS     read-write
   STATUS     mandatory
   DESCRIPTION
     "This attribute specifies how changes in the bandwidth of the 
      atmConnection are handled by the ATM software. If its value is no, 
      the atmConnection will be released by the ATM software if it is 
      incapable of providing the bandwidth specified by the peak cell rate 
      (PCR) defined in txTrafficDescParm of AtmIf Vcc Vcd. If the value 
      is yes, the atmConnection is not released in this situation, but its 
      bandwidth may be reduced. Also, if this value is yes, the Dynamic 
      Speed Reporting mechanism must be enabled, by provisioning at 
      least one value in the speedReportingThresholds attribute of the 
      parent Trunk component."
   DEFVAL     { no }
::= { trkAtmInterfaceEntry 2 }

trkAtmVccReportingBw OBJECT-TYPE
   SYNTAX     INTEGER  {
                 pcr(0),
                 acr(1) }
   ACCESS     read-write
   STATUS     mandatory
   DESCRIPTION
     "This attribute specifies how the bandwidth of the VCC is reported to 
      the parent Trunk component. If its value is pcr and attribute 
      bwElastic of AtmAccess has a value of no, the peak cell rate (PCR) 
      of the VCC, defined in txTrafficDescParm of AtmIf Vcc Vcd, is 
      reported. If its value is pcr and attribute bwElastic of AtmAccess has 
      a value of yes, the minimum of the PCR, defined in 
      txTrafficDescParm of AtmIf Vcc Vcd, and the current cell rate 
      (CCR) of the VCC is reported. If its value is acr, the best 
      measurement of the actual cell rate (ACR) of the VCC is reported, 
      which is the minimum of the PCR, the CCR and the actual shaping 
      rate (ASR). The value of the reported bandwidth of the VCC is 
      indicated by the measuredSpeedToIf attribute of the parent Trunk 
      component."
   DEFVAL     { pcr }
::= { trkAtmInterfaceEntry 3 }

trkAtmStateTable OBJECT-TYPE
   SYNTAX     SEQUENCE OF TrkAtmStateEntry
   ACCESS     not-accessible
   STATUS     mandatory
   DESCRIPTION
     "This group contains the three OSI State attributes and the six OSI 
      Status attributes. The descriptions generically indicate what each 
      attribute implies about the component. Note that not all the values 
      and state combinations described here are supported by every 
      component which uses this group. For component-specific 
      information and the valid state combinations, refer to NTP 241-
      7001-150, Passport Operations and Maintenance Guide."
::= { trkAtm 12 }

trkAtmStateEntry OBJECT-TYPE
   SYNTAX     TrkAtmStateEntry
   ACCESS     not-accessible
   STATUS     mandatory
   DESCRIPTION
     "An entry in the trkAtmStateTable."
   INDEX {
      trkIndex,
      trkAtmIndex }
::= { trkAtmStateTable 1 }

TrkAtmStateEntry ::= SEQUENCE {
   trkAtmAdminState
      INTEGER,
   trkAtmOperationalState
      INTEGER,
   trkAtmUsageState
      INTEGER,
   trkAtmAvailabilityStatus
      OCTET STRING,
   trkAtmProceduralStatus
      OCTET STRING,
   trkAtmControlStatus
      OCTET STRING,
   trkAtmAlarmStatus
      OCTET STRING,
   trkAtmStandbyStatus
      INTEGER,
   trkAtmUnknownStatus
      INTEGER }

trkAtmAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component.
      
      The OSI Status attributes, if supported by the component, may 
      provide more details, qualifying the state of the component."
   DEFVAL     { unlocked }
::= { trkAtmStateEntry 1 }

trkAtmOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle.
      
      The OSI Status attributes, if supported by the component, may 
      provide more details, qualifying the state of the component."
   DEFVAL     { disabled }
::= { trkAtmStateEntry 2 }

trkAtmUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time.
      
      The OSI Status attributes, if supported by the component, may 
      provide more details, qualifying the state of the component."
   DEFVAL     { idle }
::= { trkAtmStateEntry 3 }

trkAtmAvailabilityStatus OBJECT-TYPE
   SYNTAX     OCTET STRING (SIZE (2))
   ACCESS     read-only
   STATUS     mandatory
   DESCRIPTION
     "If supported by the component, this attribute indicates the OSI 
      Availability status of the component. Note that, even though it is 
      defined as a multi-valued set, at most one value is shown to the user.
      
      When no values are in the set, this indicates that either the attribute 
      is not supported or that none of the status conditions described 
      below are present.
      
      The value inTest indicates that the resource is undergoing a test 
      procedure. If adminState is locked or shuttingDown, the normal 
      users are precluded from using the resource and controlStatus is 
      reservedForTest. Tests that do not exclude additional users can be 
      present in any operational or administrative state but the 
      reservedForTest condition should not be present.
      
      The value failed indicates that the component has an internal fault 
      that prevents it from operating. The operationalState is disabled.
      
      The value dependency indicates that the component cannot operate 
      because some other resource on which it depends is unavailable. 
      The operationalState is disabled.
      
      The value powerOff indicates the resource requires power to be 
      applied and it is not powered on. The operationalState is disabled.
      
      The value offLine indicates the resource requires a routine 
      operation (either manual, automatic, or both) to be performed to 
      place it on-line and make it available for use. The operationalState 
      is disabled.
      
      The value offDuty indicates the resource is inactive in accordance 
      with a predetermined time schedule. In the absence of other 
      disabling conditions, the operationalState is enabled or disabled.
      
      The value degraded indicates the service provided by the 
      component is degraded in some way, such as in speed or operating 
      capacity. However, the resource remains available for service. The 
      operationalState is enabled.
      
      The value notInstalled indicates the resource is not present. The 
      operationalState is disabled.
      
      The value logFull is not used.

      Description of bits:
      inTest(0)
      failed(1)
      powerOff(2)
      offLine(3)
      offDuty(4)
      dependency(5)
      degraded(6)
      notInstalled(7)
      logFull(8)"
::= { trkAtmStateEntry 4 }

trkAtmProceduralStatus OBJECT-TYPE
   SYNTAX     OCTET STRING (SIZE (1))
   ACCESS     read-only
   STATUS     mandatory
   DESCRIPTION
     "If supported by the component, this attribute indicates the OSI 
      Procedural status of the component. Note that, even though it is 
      defined as a multi-valued set, at most one value is shown to the user.
      
      When no values are in the set, this indicates that either the attribute 
      is not supported or that none of the status conditions described 
      below are present.
      
      The value initializationRequired indicates (for a resource which 
      doesn't initialize autonomously) that initialization is required before 
      it can perform its normal functions, and this procedure has not been 
      initiated. The operationalState is disabled.
      
      The value notInitialized indicates (for a resource which does 
      initialize autonomously) that initialization is required before it can 
      perform its normal functions, and this procedure has not been 
      initiated. The operationalState may be enabled or disabled.
      
      The value initializing indicates that initialization has been initiated 
      but is not yet complete. The operationalState may be enabled or 
      disabled.
      
      The value reporting indicates the resource has completed some 
      processing operation and is notifying the results. The 
      operationalState is enabled.
      
      The value terminating indicates the component is in a termination 
      phase. If the resource doesn't reinitialize autonomously, 
      operationalState is disabled; otherwise it is enabled or disabled.

      Description of bits:
      initializationRequired(0)
      notInitialized(1)
      initializing(2)
      reporting(3)
      terminating(4)"
::= { trkAtmStateEntry 5 }

trkAtmControlStatus OBJECT-TYPE
   SYNTAX     OCTET STRING (SIZE (1))
   ACCESS     read-only
   STATUS     mandatory
   DESCRIPTION
     "If supported by the component, this attribute indicates the OSI 
      Control status of the component. Note that, even though it is defined 
      as a multi-valued set, at most one value is shown to the user.
      
      When no values are in the set, this indicates that either the attribute 
      is not supported or that none of the status conditions described 
      below are present.
      
      The value subjectToTest indicates the resource is available but tests 
      may be conducted simultaneously at unpredictable times, which 
      may cause it to exhibit unusual characteristics.
      
      The value partOfServicesLocked indicates that part of the service is 
      restricted from users of a resource. The adminState is unlocked.
      
      The value reservedForTest indicates that the component is 
      administratively unavailable because it is undergoing a test 
      procedure. The adminState is locked.
      
      The value suspended indicates that the service has been 
      administratively suspended.

      Description of bits:
      subjectToTest(0)
      partOfServicesLocked(1)
      reservedForTest(2)
      suspended(3)"
::= { trkAtmStateEntry 6 }

trkAtmAlarmStatus OBJECT-TYPE
   SYNTAX     OCTET STRING (SIZE (1))
   ACCESS     read-only
   STATUS     mandatory
   DESCRIPTION
     "If supported by the component, this attribute indicates the OSI 
      Alarm status of the component. Note that, even though it is defined 
      as a multi-valued set, at most one value is shown to the user.
      
      When no values are in the set, this indicates that either the attribute 
      is not supported or that none of the status conditions described 
      below are present.
      
      The value underRepair indicates the component is currently being 
      repaired. The operationalState is enabled or disabled.
      
      The value critical indicates one or more critical alarms are 
      outstanding against the component. Other, less severe, alarms may 
      also be outstanding. The operationalState is enabled or disabled.
      
      The value major indicates one or more major alarms are 
      outstanding against the component. Other, less severe, alarms may 
      also be outstanding. The operationalState is enabled or disabled.
      
      The value minor indicates one or more minor alarms are 
      outstanding against the component. Other, less severe, alarms may 
      also be outstanding. The operationalState is enabled or disabled.
      
      The value alarmOutstanding generically indicates that an alarm of 
      some severity is outstanding against the component.

      Description of bits:
      underRepair(0)
      critical(1)
      major(2)
      minor(3)
      alarmOutstanding(4)"
::= { trkAtmStateEntry 7 }

trkAtmStandbyStatus OBJECT-TYPE
   SYNTAX     INTEGER  {
                 hotStandby(0),
                 coldStandby(1),
                 providingService(2),
                 notSet(15) }
   ACCESS     read-only
   STATUS     mandatory
   DESCRIPTION
     "If supported by the component, this attribute indicates the OSI 
      Standby status of the component.
      
      The value notSet indicates that either the attribute is not supported 
      or that none of the status conditions described below are present. 
      Note that this is a non-standard value, used because the original 
      specification indicated this attribute was set-valued and thus, did not 
      provide a value to indicate that none of the other three are 
      applicable.
      
      The value hotStandby indicates that the resource is not providing 
      service but will be immediately able to take over the role of the 
      resource to be backed up, without initialization activity, and 
      containing the same information as the resource to be backed up.
      
      The value coldStandby indicates the resource is a backup for 
      another resource but will not be immediately able to take over the 
      role of the backed up resource and will require some initialization 
      activity.
      
      The value providingService indicates that this component, as a 
      backup resource, is currently backing up another resource."
   DEFVAL     { notSet }
::= { trkAtmStateEntry 8 }

trkAtmUnknownStatus OBJECT-TYPE
   SYNTAX     INTEGER  {
                 false(0),
                 true(1) }
   ACCESS     read-only
   STATUS     mandatory
   DESCRIPTION
     "This attribute indicates the OSI Unknown status of the component.
      
      The value false indicates that all of the other OSI State and Status 
      attribute values can be considered accurate.
      
      The value true indicates that the actual state of the component is not 
      known for sure."
   DEFVAL     { false }
::= { trkAtmStateEntry 9 }

trkAtmUtilTable OBJECT-TYPE
   SYNTAX     SEQUENCE OF TrkAtmUtilEntry
   ACCESS     not-accessible
   STATUS     mandatory
   DESCRIPTION
     "This group contains all of the provisioning data required to set the 
      ATM VCC utilization alarm thresholds. The ATM VCC utilization 
      is indicated by the lastCalculatedVccUtilization attribute.
      All thresholds are percentages which can take on any value in the 
      range of 0% through 200%. The value 200% is used to disable an 
      individual threshold. For values other than 200%, the minor alarm 
      threshold must be less than the other thresholds and the major alarm 
      threshold must be less than the critical alarm threshold."
::= { trkAtm 14 }

trkAtmUtilEntry OBJECT-TYPE
   SYNTAX     TrkAtmUtilEntry
   ACCESS     not-accessible
   STATUS     mandatory
   DESCRIPTION
     "An entry in the trkAtmUtilTable."
   INDEX {
      trkIndex,
      trkAtmIndex }
::= { trkAtmUtilTable 1 }

TrkAtmUtilEntry ::= SEQUENCE {
   trkAtmMinorVccUtilAlarmThreshold
      Unsigned32,
   trkAtmMajorVccUtilAlarmThreshold
      Unsigned32,
   trkAtmCriticalVccUtilAlarmThreshold
      Unsigned32,
   trkAtmVccUtilAlarmStatus
      INTEGER }

trkAtmMinorVccUtilAlarmThreshold OBJECT-TYPE
   SYNTAX     Unsigned32 (0..200)
   ACCESS     read-write
   STATUS     mandatory
   DESCRIPTION
     "This attribute specifies the threshold value at which a minor alarm 
      will be issued based on a sustained average ATM VCC utilization as 
      indicated by the lastCalculatedVccUtilization attribute. The Set 
      alarm is issued after 3 minutes of utilization greater than the 
      threshold. The corresponding Clear alarm is issued after a 
      subsequent 3 minutes of utilization less than or equal to the 
      threshold.
      The value 200% is used to disable this threshold. For values other 
      than 200%, the minor alarm threshold must be less than the other 
      thresholds."
   DEFVAL     { 75 }
::= { trkAtmUtilEntry 1 }

trkAtmMajorVccUtilAlarmThreshold OBJECT-TYPE
   SYNTAX     Unsigned32 (0..200)
   ACCESS     read-write
   STATUS     mandatory
   DESCRIPTION
     "This attribute specifies the threshold value at which a major alarm 
      will be issued based on a sustained average ATM VCC utilization as 
      indicated by the lastCalculatedVccUtilization attribute. The Set 
      alarm is issued after 3 minutes of utilization greater than the 
      threshold. The corresponding Clear alarm is issued after a 
      subsequent 3 minutes of utilization less than or equal to the 
      threshold.
      The value 200% is used to disable this threshold. For values other 
      than 200%, the major alarm threshold must be greater than the 
      minor threshold and less than the critical threshold."
   DEFVAL     { 85 }
::= { trkAtmUtilEntry 2 }

trkAtmCriticalVccUtilAlarmThreshold OBJECT-TYPE
   SYNTAX     Unsigned32 (0..200)
   ACCESS     read-write
   STATUS     mandatory
   DESCRIPTION
     "This attribute specifies the threshold value at which a critical alarm 
      will be issued based on a sustained average ATM VCC utilization as 
      indicated by the lastCalculatedVccUtilization attribute. The Set 
      alarm is issued after 3 minutes of utilization greater than the 
      threshold. The corresponding Clear alarm is issued after a 
      subsequent 3 minutes of utilization less than or equal to the 
      threshold.
      The value 200% is used to disable this threshold. For values other 
      than 200%, the critical alarm threshold must be greater than the 
      other thresholds."
   DEFVAL     { 95 }
::= { trkAtmUtilEntry 3 }

trkAtmVccUtilAlarmStatus OBJECT-TYPE
   SYNTAX     INTEGER  {
                 disabled(0),
                 enabled(1) }
   ACCESS     read-write
   STATUS     mandatory
   DESCRIPTION
     "This attribute provides control of the generation of ATM VCC 
      utilization alarms. If the value is disabled, none of the alarms is 
      generated (this is equivalent to setting all of the thresholds to 
      200%). If the value is enabled, the individual thresholds are 
      handled."
   DEFVAL     { disabled }
::= { trkAtmUtilEntry 4 }

trkAtmStatsTable OBJECT-TYPE
   SYNTAX     SEQUENCE OF TrkAtmStatsEntry
   ACCESS     not-accessible
   STATUS     mandatory
   DESCRIPTION
     "This group of attributes contains statistics collected by the 
      AtmAccess component."
::= { trkAtm 15 }

trkAtmStatsEntry OBJECT-TYPE
   SYNTAX     TrkAtmStatsEntry
   ACCESS     not-accessible
   STATUS     mandatory
   DESCRIPTION
     "An entry in the trkAtmStatsTable."
   INDEX {
      trkIndex,
      trkAtmIndex }
::= { trkAtmStatsTable 1 }

TrkAtmStatsEntry ::= SEQUENCE {
   trkAtmLastCalculatedVccUtilization
      Gauge32,
   trkAtmLastCalculatedTxVccUtilization
      Gauge32 }

trkAtmLastCalculatedVccUtilization OBJECT-TYPE
   SYNTAX     Gauge32 (0..200)
   ACCESS     read-only
   STATUS     mandatory
   DESCRIPTION
     "This attribute indicates the last calculated receive utilization of the 
      ATM VCC. It is calculated every 30 seconds based on comparing 
      the number of cells received by the AtmIf Vcc with the estimated 
      available bandwidth on the AtmIf Vcc."
   DEFVAL     { 0 }
::= { trkAtmStatsEntry 1 }

trkAtmLastCalculatedTxVccUtilization OBJECT-TYPE
   SYNTAX     Gauge32 (0..200)
   ACCESS     read-only
   STATUS     mandatory
   DESCRIPTION
     "This attribute indicates the last calculated transmit utilization of the 
      ATM VCC. It is calculated every 30 seconds based on comparing 
      the number of cells transmitted by the AtmIf Vcc with the estimated 
      available bandwidth on the AtmIf Vcc."
   DEFVAL     { 0 }
::= { trkAtmStatsEntry 2 }




-- 
-- Version and Compliance statements
-- 



-- Object-Group Statement:
-- A list of all current accessible leaf objects.

-- OBJECTS { trkAtmMajorVccUtilAlarmThreshold,
--           trkAtmAtmConnection,
--           trkAtmStorageType,
--           trkAtmRowStatus,
--           trkAtmVccUtilAlarmStatus,
--           trkAtmMinorVccUtilAlarmThreshold,
--           trkAtmProceduralStatus,
--           trkAtmAtmAccMaximumErroredInterval,
--           trkAtmCriticalVccUtilAlarmThreshold,
--           trkAtmAlarmStatus,
--           trkAtmReceiveErrorSensitivity,
--           trkAtmOperationalState,
--           trkAtmLastCalculatedVccUtilization,
--           trkAtmAvailabilityStatus,
--           trkAtmUsageState,
--           trkAtmControlStatus,
--           trkAtmAdminState,
--           trkAtmVccReportingBw,
--           trkAtmComponentName,
--           trkAtmStandbyStatus,
--           trkAtmBwElastic,
--           trkAtmUnknownStatus,
--           trkAtmLastCalculatedTxVccUtilization }
-- STATUS  mandatory
-- DESCRIPTION
--   "A list of all current accessible leaf objects."

atmTrunksGroup OBJECT IDENTIFIER ::= { atmTrunksMIB 1 }
atmTrunksGroupBE OBJECT IDENTIFIER ::= { atmTrunksGroup 5 }
atmTrunksGroupBE01 OBJECT IDENTIFIER ::= { atmTrunksGroupBE 2 }
atmTrunksGroupBE01A OBJECT IDENTIFIER ::= { atmTrunksGroupBE01 2 }



-- Agent-Capabilities Statement:

-- PRODUCT-RELEASE "Passport Release 7.0 AtmTrunks."
-- STATUS          mandatory
-- DESCRIPTION     "AtmTrunks MIB: MIB Version BE01A,
--                  Software Version BG00S4C."
-- SUPPORTS        Nortel-Magellan-Passport-AtmTrunksMIB
--    INCLUDES     { atmTrunksGroupBE01A }

atmTrunksCapabilities OBJECT IDENTIFIER ::= { atmTrunksMIB 3 }
atmTrunksCapabilitiesBE OBJECT IDENTIFIER ::= { atmTrunksCapabilities 5 }
atmTrunksCapabilitiesBE01 OBJECT IDENTIFIER ::= { atmTrunksCapabilitiesBE 2 }
atmTrunksCapabilitiesBE01A OBJECT IDENTIFIER ::= { atmTrunksCapabilitiesBE01 2 }





END
