XEDIA-DHCP-MIB DEFINITIONS ::= BEGIN

IMPORTS 
        MODULE-IDENTITY, OBJECT-TYPE,
        Integer32, IpAddress, Counter32     FROM SNMPv2-SMI    -- RFC1442
        MODULE-COMPLIANCE, OBJECT-GROUP     FROM SNMPv2-CONF
        TEXTUAL-CONVENTION, DisplayString,
        RowStatus, TruthValue               FROM SNMPv2-TC     -- RFC1443
        ifIndex                             FROM RFC1213-MIB
        xediaMibs                           FROM XEDIA-REG
        ;    

xediaDhcpMIB MODULE-IDENTITY
    LAST-UPDATED "9802232155Z" -- February 23,1998
    ORGANIZATION "Xedia Corp."
    CONTACT-INFO
        "support@xedia.com"
    DESCRIPTION
        "This module defines additional objects for management of DHCP
        support in Xedia devices."
    ::= { xediaMibs 28 }

-- Top-level organization of the MIB

xdhcpObjects         OBJECT IDENTIFIER ::= { xediaDhcpMIB 1 }
xdhcpConformance     OBJECT IDENTIFIER ::= { xediaDhcpMIB 2 }

xdhcpRelay           OBJECT IDENTIFIER ::= { xdhcpObjects 1 }

-- ****************************************************************
-- The DHCP Relay Group
-- ****************************************************************

xdhcpRelayMode OBJECT-TYPE
    SYNTAX      INTEGER { enabled(1), disabled(2) }
    MAX-ACCESS  read-write
    STATUS      current
    DESCRIPTION
        "The Administrative mode to control DHCP relay functions."
    DEFVAL      { disabled }
    ::= { xdhcpRelay 1 }

xdhcpRelayMaxHops OBJECT-TYPE
    SYNTAX      INTEGER (1..16)
    MAX-ACCESS  read-write
    STATUS      current
    DESCRIPTION
        "This value identifies the maximum number of hops allowed for
         requests passing through this relay agent.  Packets received
         with a hop count greater than this value will be discarded."
    DEFVAL      { 4 }
    ::= { xdhcpRelay 2 }

xdhcpRelayIncludeCircuitID OBJECT-TYPE
    SYNTAX      TruthValue
    MAX-ACCESS  read-write
    STATUS      current
    DESCRIPTION
        "Whether the relay agent should add the circuit ID of the ATM or
         frame relay circuit that a DHCP relay request was received to
         the DHCP relay request.  The circuit ID will be added as a 
         agent circuit ID sub-option of a DHCP relay agent information 
         option (option 82) and will be used by the relay agent to 
         forward the reply to the correct circuit."
    DEFVAL      { false }
    ::= { xdhcpRelay 3 }
     
xdhcpRelayDestTable OBJECT-TYPE
    SYNTAX      SEQUENCE OF XdhcpRelayDestEntry
    MAX-ACCESS  not-accessible
    STATUS      current
    DESCRIPTION
        "A table of DHCP server destinations that the DHCP relay agent will
         will relay requests to and responses from."
    ::= { xdhcpRelay 10 }

xdhcpRelayDestEntry OBJECT-TYPE
    SYNTAX      XdhcpRelayDestEntry
    MAX-ACCESS  not-accessible
    STATUS      current
    DESCRIPTION
        "Information about a single DHCP server."
    INDEX       { xdhcpRelayDestIndex }
    ::= { xdhcpRelayDestTable 1 }

XdhcpRelayDestEntry ::= SEQUENCE {
    xdhcpRelayDestIndex        INTEGER,
    xdhcpRelayDestination      DisplayString,
    xdhcpRelayDestOperAddress  IpAddress,
    xdhcpRelayDestRequests     Counter32,
    xdhcpRelayDestReplies      Counter32,
    xdhcpRelayDestProtocol     INTEGER,
    xdhcpRelayDestRowStatus    RowStatus,
    xdhcpRelayDestInterface    DisplayString
}

xdhcpRelayDestIndex OBJECT-TYPE
    SYNTAX      INTEGER (1..16)
    MAX-ACCESS  not-accessible
    STATUS      current
    DESCRIPTION
        "A number uniquely identifying each DHCP
        server that the DHCP relay agent will relay
        requests to and responses from."
    ::= { xdhcpRelayDestEntry 1 }

xdhcpRelayDestination     OBJECT-TYPE
    SYNTAX      DisplayString
    MAX-ACCESS  read-create
    STATUS      current
    DESCRIPTION
        "The destination to which DHCP requests will be sent.  It may
         be a specific server IP address, a local IP subnet on which 
         requests will be broadcast, or an IP server name to be 
         resolved through a DNS lookup."
    DEFVAL { "" }
    ::= { xdhcpRelayDestEntry 2 }

xdhcpRelayDestOperAddress  OBJECT-TYPE
    SYNTAX      IpAddress
    MAX-ACCESS  read-only
    STATUS      current
    DESCRIPTION
        "The operational IP address for this server destination.
         It will either be the configured IP address or the resolved
         address if a server name was specified in xdhcpRelayDestination."
    DEFVAL { '00000000'h }
    ::= { xdhcpRelayDestEntry 3 }

xdhcpRelayDestRequests  OBJECT-TYPE
    SYNTAX      Counter32
    MAX-ACCESS  read-only
    STATUS      current
    DESCRIPTION
        "The number of DHCP requests that were received on
        this interface."
    ::= { xdhcpRelayDestEntry 4 }

xdhcpRelayDestReplies   OBJECT-TYPE
    SYNTAX      Counter32
    MAX-ACCESS  read-only
    STATUS      current
    DESCRIPTION
        "The number of DHCP replies that were received on
        this interface."
    ::= { xdhcpRelayDestEntry 5 }

xdhcpRelayDestProtocol   OBJECT-TYPE
    SYNTAX      INTEGER {
                    dhcp(1),
                    bootp(2),
                    dhcpAndBootp(3)
                }
    MAX-ACCESS  read-create
    STATUS      current
    DESCRIPTION
        "The protocol(s) to be relayed to this destination."
    DEFVAL      { dhcpAndBootp }
    ::= { xdhcpRelayDestEntry 6 }


xdhcpRelayDestRowStatus    OBJECT-TYPE
    SYNTAX      RowStatus
    MAX-ACCESS  read-create
    STATUS      current
    DESCRIPTION
        "This variable displays the status of the entry.  Setting it to
         'destroy' marks the entry as removed.  Eventually, when no other
         applications depend on that particular resource, it will be completely
         removed from the table.  Setting it to  either 'create', or 'active'
         will add a row to the table."
    ::= { xdhcpRelayDestEntry 7 }

xdhcpRelayDestInterface    OBJECT-TYPE
    SYNTAX      DisplayString (SIZE (0..7))
    MAX-ACCESS  read-create
    STATUS      current
    DESCRIPTION
        "The name of the IP interface over which the DHCP relay
         destination will be attempted.  A value of 'all' represents
         all IP interfaces."
    DEFVAL { "all" }
    ::= { xdhcpRelayDestEntry 8 }

-- ****************************************************************
-- Conformance Information
-- ****************************************************************
 
xdhcpCompliances OBJECT IDENTIFIER ::= { xdhcpConformance 1 }
xdhcpGroups      OBJECT IDENTIFIER ::= { xdhcpConformance 2 }
 
--
-- Compliance Statements
--
 
xdhcpCompliance MODULE-COMPLIANCE
    STATUS      current
    DESCRIPTION
        "The compliance statement for all agents that support this
        MIB. A compliant agent implements all objects defined in this
        MIB."
    MODULE  -- this module
    MANDATORY-GROUPS {
        xdhcpAllGroup
    }
    ::= { xdhcpCompliances 1 }
 
--
-- Object Groups
--
 
xdhcpAllGroup OBJECT-GROUP
    OBJECTS {
        xdhcpRelayMode,
        xdhcpRelayMaxHops,
        xdhcpRelayIncludeCircuitID,
        xdhcpRelayDestination,
        xdhcpRelayDestOperAddress,
        xdhcpRelayDestRequests,
        xdhcpRelayDestReplies,
        xdhcpRelayDestProtocol,
        xdhcpRelayDestRowStatus,
        xdhcpRelayDestInterface
    }
    STATUS      current
    DESCRIPTION
        "The set of all accessible objects in this MIB."
    ::= { xdhcpGroups 1 }

END
