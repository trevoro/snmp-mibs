INKTOMI-GLOBAL-REG DEFINITIONS ::= BEGIN

IMPORTS
     OBJECT-IDENTITY, MODULE-IDENTITY, OBJECT-TYPE, NOTIFICATION-TYPE, enterprises
FROM SNMPv2-SMI
     MODULE-COMPLIANCE, OBJECT-GROUP
FROM SNMPv2-CONF;
               
               	vendorInktomi 	   	OBJECT IDENTIFIER ::= { enterprises 1967 }
	inktomiReg 	   	OBJECT IDENTIFIER ::= { vendorInktomi 1 }
	inktomiModules 	   	OBJECT IDENTIFIER ::= { inktomiReg 1 }
	inktomiGlobalRegModule 	   	OBJECT IDENTIFIER ::= { inktomiModules 1 }
	inktomiGeneric    	OBJECT IDENTIFIER ::= { vendorInktomi 2 }
	inktomiProducts 	   	OBJECT IDENTIFIER ::= { vendorInktomi 3 }
    inktomiExpr    	OBJECT IDENTIFIER ::= { vendorInktomi 6 }
    inktomiTSMIBs  	OBJECT IDENTIFIER ::= { inktomiProducts 1 }
    inktomiTSConformance 	OBJECT IDENTIFIER ::= { inktomiTSMIBs 1 }
	inktomiTSObjs      	OBJECT IDENTIFIER ::= { inktomiTSMIBs 2 }
	inktomiTSEvents   OBJECT IDENTIFIER ::= { inktomiTSMIBs 3 }



vendorInktomi OBJECT-IDENTITY
   STATUS current
   DESCRIPTION
        "Inktomi enterprise root assigned by IANA"
   ::= { enterprises 1967 }

inktomiReg OBJECT-IDENTITY
   STATUS current
   DESCRIPTION
        "sub-tree for registrations"
   ::= { vendorInktomi 1 }

inktomiModules OBJECT-IDENTITY
   STATUS current
   DESCRIPTION
        "Sub-tree to register the values assigned to modules with the
         MODULE-IDENTITY construct"
   ::= { inktomiReg 1 }

inktomiGlobalRegModule MODULE-IDENTITY
   LAST-UPDATED   "9804070000Z"
   ORGANIZATION   "Inktomi Corporation"
   CONTACT-INFO   "..."
   DESCRIPTION    "OID registrations for Inktomi"
   REVISION       "9804070000Z"
   DESCRIPTION    "The initial revision"
::= { inktomiModules 1 }

inktomiGeneric OBJECT-IDENTITY
   STATUS current
   DESCRIPTION
        "sub-tree for common object and event definitions"
   ::= { vendorInktomi 2 }

inktomiProducts OBJECT-IDENTITY
   STATUS current
   DESCRIPTION
        "sub-tree for specific object and event definitions"
   ::= { vendorInktomi 3 }

inktomiExpr OBJECT-IDENTITY
   STATUS current
   DESCRIPTION
        "sub-tree for experimental definitions"
   ::= { vendorInktomi 6 }

inktomiTSMIBs OBJECT-IDENTITY
   STATUS current
   DESCRIPTION
        "sub-tree for objects and events in traffic server MIBs"
   ::= { inktomiProducts 1 }

inktomiTSConformance OBJECT-IDENTITY
   STATUS current
   DESCRIPTION
        "sub-tree for groups and conformance for traffic server MIBs"
   ::= { inktomiTSMIBs 1 }

inktomiTSObjs OBJECT-IDENTITY
   STATUS current
   DESCRIPTION
        "sub-tree for objects in traffic server MIBs"
   ::= { inktomiTSMIBs 2 }

inktomiTSEvents OBJECT-IDENTITY
   STATUS current
   DESCRIPTION
        "sub-tree for events in traffic server MIBs"
   ::= { inktomiTSMIBs 3 }

END
