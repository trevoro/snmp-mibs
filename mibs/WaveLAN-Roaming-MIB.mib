-- 
-- SNMP MIB for Roaming for WaveLAN  (Version 1.2, 7-Mar-97)
-- 
-- 
-- Copyright (c) 1997 by Lucent Technologies Inc..
-- All rights reserved.  Distribution of this document is authorized
-- on condition that this copyright notice is included.
-- This Lucent Technologies SNMP Management Information
-- Base Specification (Specification) embodies 
-- Lucent Technologies' proprietary intellectual
-- property. Lucent Technologies retains all title and
-- ownership in the Specification, including any revisions.
-- 
-- It is Lucent Technologies intent to encourage the widespread
-- use of this Specification in connection with the management of
-- WaveLAN products. Lucent Technologies grants 
-- vendors, end-users, and other interested parties a 
-- non-exclusive license to use this Specification in connection 
-- with the management of WaveLAN products.
-- 
-- This Specification is provided "AS IS", and makes no 
-- warranty, either express or implied, as to the use,
-- operation, condition, or performance of the Specification.
-- 
-- WaveLAN and WavePOINT are trademarks of
-- Lucent Technologies.
-- 


WaveLAN-Roaming-MIB
-- { iso org(3) dod(6) internet(1) private(4) enterprises(1) 
--	att-2(74) att-mgmt(2) wavelan(21)}

DEFINITIONS ::= BEGIN

IMPORTS
	enterprises, Counter FROM RFC1155-SMI
	OBJECT-TYPE FROM RFC-1212
	DisplayString FROM RFC1213-MIB
	att-2, att-mgmt, wavelan FROM WaveLAN-MIB;

-- Note: the following 3 statements redefine 'wavelan' to satisfy those
-- MIB compilers that can not handle EXPORTS. Remove the 
-- comment signs to effectuate:
-- att-2		OBJECT IDENTIFIER ::= { enterprises 74 }
-- att-mgmt	OBJECT IDENTIFIER ::= { att-2 2 }
-- wavelan	OBJECT IDENTIFIER ::= { att-mgmt 21 }

wavelanRoaming	OBJECT IDENTIFIER ::= { wavelan 3 }


-- 
-- The WaveLAN-Roaming MIB consist of the following groups:
-- 
-- the Generic Roaming group, mandatory:
-- 	wlrGenTable	OBJECT IDENTIFIER ::= { wavelanRoaming 1 }
-- 
-- the Mobile Station Roaming group, optional; for mobile stations only:
-- 	wlrMsTable	OBJECT IDENTIFIER ::= { wavelanRoaming 2 }
-- 
-- the Access Point Roaming group, optional; for access points only:
-- 	wlrApTable	OBJECT IDENTIFIER ::= { wavelanRoaming 3 }
-- 

-- Some objects in this MIB represent values of timers. 
-- In this MIB, these timers have values in units of hundredth 
-- of a second (i.e. 1/100 s, or 10 ms). 
-- To avoid ambiguity, a data type is defined here as a textual
-- convention and all representation of these timers in this MIB
-- module are defined using this data type:

Timeout  ::=  INTEGER	-- a timer in units of 1/100 seconds.


-- 
-- The Generic Roaming group
-- 
-- Implementation of this group is mandatory
-- 

wlrGenTable OBJECT-TYPE
	SYNTAX  SEQUENCE OF WlrGenEntry
	ACCESS  not-accessible
	STATUS  mandatory
	DESCRIPTION
		"Generic Roaming information for a
		collection of WaveLAN interfaces
		attached to a particular system."
	::= { wavelanRoaming 1 }

wlrGenEntry OBJECT-TYPE
	SYNTAX  WlrGenEntry
	ACCESS  not-accessible
	STATUS  mandatory
	DESCRIPTION
		"Generic Roaming information for a
		particular WaveLAN interface."
	INDEX   { wlrGenIndex }
	::= { wlrGenTable 1 }

WlrGenEntry ::= SEQUENCE {
	wlrGenIndex
		INTEGER,
	wlrDomainId
		OCTET STRING  (SIZE  (2)),
	wlrBeaconKey
		OCTET STRING  (SIZE  (2))
   }

wlrGenIndex OBJECT-TYPE
	SYNTAX  INTEGER
	ACCESS  read-only
	STATUS  mandatory
	DESCRIPTION
		"An index value that uniquely identifies a WaveLAN
		network interface this roaming information applies to.
		The interface associated with a particular
		value of this index is the same interface
		as identified by the same value of ifIndex."
	::= { wlrGenEntry 1 }

wlrDomainId OBJECT-TYPE
	SYNTAX  OCTET STRING  (SIZE  (2))
	ACCESS  read-write
	STATUS  mandatory
	DESCRIPTION
		"The Domain Identifier identifies the
		(multi-cellular) roaming service domain.
		Mobile stations will connect only to those
		access points that have the same DomainId
		as they have been configured with themselves.
		(note: Value '0000'H has a special meaning;
		 it may be used to disable roaming)"
	::= { wlrGenEntry 2 }

wlrBeaconKey OBJECT-TYPE
	SYNTAX  OCTET STRING  (SIZE  (2))
	ACCESS  read-write
	STATUS  mandatory
	DESCRIPTION
		"The key used to encipher the WaveLAN NWID 
		when included as data in the Beacon message."
	::= { wlrGenEntry 3 }


-- 
-- the Mobile Station Roaming group
-- 
-- Implementation of this group is optional
-- 

wlrMsTable OBJECT-TYPE
	SYNTAX  SEQUENCE OF WlrMsEntry
	ACCESS  not-accessible
	STATUS  mandatory
	DESCRIPTION
		"Mobile station roaming information for a
		collection of WaveLAN interfaces
		attached to a particular system."
	::= { wavelanRoaming 2 }

wlrMsEntry OBJECT-TYPE
	SYNTAX  WlrMsEntry
	ACCESS  not-accessible
	STATUS  mandatory
	DESCRIPTION
		"Mobile station roaming information for a
		particular WaveLAN interface."
	INDEX   { wlrMsIndex }
	::= { wlrMsTable 1 }

WlrMsEntry ::= SEQUENCE {
	wlrMsIndex
		INTEGER,
	wlrRetryLimit
		INTEGER,
	wlrNumberOfRecovers
		INTEGER,
	wlrCommsQuality
		INTEGER,
	wlrCurrentApName
		DisplayString,
	wlrMsSignOnFailures
		Counter,
	wlrMsHandovers
		Counter,
	wlrMsHandoverFailures
		Counter,
	wlrMsBeaconsMissedNormal
		Counter,
	wlrMsBeaconsMissedSearch
		Counter,
	wlrMsRegularCellSearchEntered
		Counter,
	wlrMsFastCellSearchEntered
		Counter,
	wlrMsTimeInNormalMode
		Counter,
	wlrMsTimeInRegularSearchMode
		Counter,
	wlrMsTimeInFastSearchMode
		Counter
   }

wlrMsIndex OBJECT-TYPE
	SYNTAX  INTEGER
	ACCESS  read-only
	STATUS  mandatory
	DESCRIPTION
		"An index value that uniquely identifies a WaveLAN
		network interface this roaming information applies to.
		The interface associated with a particular 
		value of this index is the same interface 
		as identified by the same value of ifIndex."
	::= { wlrMsEntry 1 }

wlrRetryLimit OBJECT-TYPE
	SYNTAX  INTEGER  (1..20)
	ACCESS  read-write
	STATUS  mandatory
	DESCRIPTION
		"The protocol retry limit for the handover procedure."
	::= { wlrMsEntry 2 }

wlrNumberOfRecovers OBJECT-TYPE
	SYNTAX  INTEGER
	ACCESS  read-write
	STATUS  mandatory
	DESCRIPTION
		"The number of Recover requests to be sent
		after an unsuccessful handover procedure."
	::= { wlrMsEntry 3 }

wlrCommsQuality OBJECT-TYPE
	SYNTAX  INTEGER  (0..100)
	ACCESS  read-only
	STATUS  mandatory
	DESCRIPTION
		"The Communications Quality to the current 
		access point. This is the running average 
		maintained by the driver software.
		Expressed as percentage of maximum possible."
	::= { wlrMsEntry 4 }

wlrCurrentApName OBJECT-TYPE
	SYNTAX  DisplayString  (SIZE  (1..31))
	ACCESS  read-only
	STATUS  mandatory
	DESCRIPTION
		"The name of the current access point this
		mobile station is connected to."
	::= { wlrMsEntry 5 }

wlrMsSignOnFailures OBJECT-TYPE
	SYNTAX  Counter
	ACCESS  read-only
	STATUS  mandatory
	DESCRIPTION
		"The number of times no timely response 
		was received to the Sign-on request
		protocol message during the sign-on
		and handover procedures."
	::= { wlrMsEntry 6 }

wlrMsHandovers OBJECT-TYPE
	SYNTAX  Counter
	ACCESS  read-only
	STATUS  mandatory
	DESCRIPTION
		"The number of times a handover has been
		initiated. (i.e. Sign-on request sent, 
		not re-sent)."
	::= { wlrMsEntry 7 }

wlrMsHandoverFailures OBJECT-TYPE
	SYNTAX  Counter
	ACCESS  read-only
	STATUS  mandatory
	DESCRIPTION
		"The number of times a handover procedure 
		failed due to not receiving a 
		response to the Sign-on requests 
		and retries got exhausted."
	::= { wlrMsEntry 8 }

wlrMsBeaconsMissedNormal OBJECT-TYPE
	SYNTAX  Counter
	ACCESS  read-only
	STATUS  mandatory
	DESCRIPTION
		"The number of Beacons missed from 
		current access point(s), during
		normal mode."
	::= { wlrMsEntry 9 }

wlrMsBeaconsMissedSearch OBJECT-TYPE
	SYNTAX  Counter
	ACCESS  read-only
	STATUS  mandatory
	DESCRIPTION
		"The number of Beacons missed from 
		current access point(s), during
		regular search mode."
	::= { wlrMsEntry 10 }

wlrMsRegularCellSearchEntered OBJECT-TYPE
	SYNTAX  Counter
	ACCESS  read-only
	STATUS  mandatory
	DESCRIPTION
		"The number of times the regular cell search 
		mode was entered from the normal mode."
	::= { wlrMsEntry 11 }

wlrMsFastCellSearchEntered OBJECT-TYPE
	SYNTAX  Counter
	ACCESS  read-only
	STATUS  mandatory
	DESCRIPTION
		"The number of times the fast cell search 
		mode was entered."
	::= { wlrMsEntry 12 }

wlrMsTimeInNormalMode OBJECT-TYPE
	SYNTAX  Counter
	ACCESS  read-only
	STATUS  mandatory
	DESCRIPTION
		"The total time in normal (i.e. non-cell-search) mode 
		since the roaming functionality got initialized.
		(in seconds)"
	::= { wlrMsEntry 13 }

wlrMsTimeInRegularSearchMode OBJECT-TYPE
	SYNTAX  Counter
	ACCESS  read-only
	STATUS  mandatory
	DESCRIPTION
		"The total time in Regular Cell Search Mode 
		since the roaming functionality got initialized. 
		(in seconds)"
	::= { wlrMsEntry 14 }

wlrMsTimeInFastSearchMode OBJECT-TYPE
	SYNTAX  Counter
	ACCESS  read-only
	STATUS  mandatory
	DESCRIPTION
		"The total time in Fast Cell Search Mode 
		since the roaming functionality got initialized.
		(in seconds)"
	::= { wlrMsEntry 15 }

-- 
-- the Access Point Roaming group:
-- 
-- Implementation of this group is optional
-- 

wlrApTable OBJECT-TYPE
	SYNTAX  SEQUENCE OF WlrApEntry
	ACCESS  not-accessible
	STATUS  mandatory
	DESCRIPTION
		"Access point roaming information for a
		collection of WaveLAN interfaces
		attached to a particular system."
	::= { wavelanRoaming 3 }

wlrApEntry OBJECT-TYPE
	SYNTAX  WlrApEntry
	ACCESS  not-accessible
	STATUS  mandatory
	DESCRIPTION
		"Access point roaming information for a
		particular WaveLAN interface."
	INDEX   { wlrApIndex }
	::= { wlrApTable 1 }

WlrApEntry ::= SEQUENCE {
	wlrApIndex
		INTEGER,
	wlrStopCellSearchThreshold
		INTEGER,
	wlrRegularCellSearchThreshold 
		INTEGER,
	wlrFastCellSearchThreshold
		INTEGER,
	wlrBeaconInterval 
		Timeout,
	wlrBeaconTimeout 
		Timeout,
	wlrApSignOnRequests
		Counter,
	wlrApHandoversSent
		Counter,
	wlrApHandoversReceived
		Counter
   }

wlrApIndex OBJECT-TYPE
	SYNTAX  INTEGER
	ACCESS  read-only
	STATUS  mandatory
	DESCRIPTION
		"An index value that uniquely identifies a WaveLAN
		network interface this roaming information applies to.
		The interface associated with a particular 
		value of this index is the same interface 
		as identified by the same value of ifIndex."
	::= { wlrApEntry 1 }

wlrStopCellSearchThreshold OBJECT-TYPE
	SYNTAX  INTEGER  (0..100)
	ACCESS  read-write
	STATUS  mandatory
	DESCRIPTION
		"The level of communications quality on which 
		the mobile station stops looking for other access point(s).
		Expressed on percentage-scale.
		Should be greater than wlrRegularCellSearchThreshold + 3."
	::= { wlrApEntry 2 }

wlrRegularCellSearchThreshold OBJECT-TYPE
	SYNTAX  INTEGER  (0..100)
	ACCESS  read-write
	STATUS  mandatory
	DESCRIPTION
		"The level of communications quality on which 
		the mobile station starts looking for an access 
		point with a level of communications quality 
		higher than the Stop Cell Search Threshold.
		Expressed on percentage-scale.
		Should be smaller than wlrStopCellSearchThreshold - 3,
		and greater than wlrFastCellSearchThreshold + 3"
	::= { wlrApEntry 3 }

wlrFastCellSearchThreshold OBJECT-TYPE
	SYNTAX  INTEGER  (0..100)
	ACCESS  read-write
	STATUS  mandatory
	DESCRIPTION
		"The level of communications quality on which 
		the mobile station starts looking for an access 
		point with a level of communications quality 
		higher than this threshold.
		Expressed on percentage-scale.
		Should be smaller than wlrRegularCellSearchThreshold - 3"
	::= { wlrApEntry 4 }

wlrBeaconInterval OBJECT-TYPE
	SYNTAX  Timeout
	ACCESS  read-write
	STATUS  mandatory
	DESCRIPTION
		"The Beacon interval time.
		In units of a hundredth of a second (1/100 s, or 10 ms)."
	::= { wlrApEntry 5 }

wlrBeaconTimeout OBJECT-TYPE
	SYNTAX  Timeout
	ACCESS  read-write
	STATUS  mandatory
	DESCRIPTION
		"The Beacon time-out value.
		In units of a hundredth of a second (1/100 s, or 10 ms).
		Should be at least 2 * wlrBeaconInterval."
	::= { wlrApEntry 6 }

wlrApSignOnRequests OBJECT-TYPE
	SYNTAX  Counter
	ACCESS  read-only
	STATUS  mandatory
	DESCRIPTION
		"The number of  Sign-on Requests received."
	::= { wlrApEntry 7 }

wlrApHandoversSent OBJECT-TYPE
	SYNTAX  Counter
	ACCESS  read-only
	STATUS  mandatory
	DESCRIPTION
		"The number of times a handover 
		has been requested from an 
		other Access point."
	::= { wlrApEntry 8 }

wlrApHandoversReceived OBJECT-TYPE
	SYNTAX  Counter
	ACCESS  read-only
	STATUS  mandatory
	DESCRIPTION
		"The number of times a mobile station has 
		been handed over to an other access point."
	::= { wlrApEntry 9 }



END
