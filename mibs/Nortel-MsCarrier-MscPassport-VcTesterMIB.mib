Nortel-MsCarrier-MscPassport-VcTesterMIB
DEFINITIONS ::= BEGIN



IMPORTS

      OBJECT-TYPE
   FROM RFC-1212

      mscPassportMIBs,
      mscComponents
   FROM Nortel-MsCarrier-MscPassport-UsefulDefinitionsMIB

      RowPointer,
      DisplayString,
      StorageType,
      RowStatus,
      Integer32,
      Unsigned32
   FROM Nortel-MsCarrier-MscPassport-StandardTextualConventionsMIB

      AsciiString,
      Hex,
      NonReplicated,
      HexString,
      EnterpriseDateAndTime,
      Link,
      DigitString
   FROM Nortel-MsCarrier-MscPassport-TextualConventionsMIB;




-- LAST-UPDATED   "9909010000Z"
-- ORGANIZATION   "Nortel Networks"
-- CONTACT-INFO   "
--         Nortel Carrier Data Network Management
--         
--         Postal:       P.O. Box 3511, Station C 
--                       Ottawa, Ontario 
--                       Canada  K1Y 4H7
--         
--         via the WEB:  http://www.nortelnetworks.com  
--                       select 'Contact Us' from the menu
--          
--         via phone:    1-800-4NORTEL"
-- DESCRIPTION
--    "The module describing the Nortel MsCarrier MscPassport
--     VcTester Enterprise MIB."

vcTesterMIB OBJECT IDENTIFIER ::= { mscPassportMIBs 34 }










-- 
-- This is the VcTester: a tool designed to test the Passport Virtual 
-- Circuit System (vcs)..

mscVct OBJECT IDENTIFIER ::= { mscComponents 5130 }



mscVctRowStatusTable OBJECT-TYPE
   SYNTAX     SEQUENCE OF MscVctRowStatusEntry
   ACCESS     not-accessible
   STATUS     mandatory
   DESCRIPTION
     "This entry controls the addition and deletion of 
      mscVct components."
::= { mscVct 1 }

mscVctRowStatusEntry OBJECT-TYPE
   SYNTAX     MscVctRowStatusEntry
   ACCESS     not-accessible
   STATUS     mandatory
   DESCRIPTION
     "A single entry in the table represents a single 
      mscVct component."
   INDEX {
      mscVctIndex }
::= { mscVctRowStatusTable 1 }

MscVctRowStatusEntry ::= SEQUENCE {
   mscVctRowStatus
      RowStatus,
   mscVctComponentName
      DisplayString,
   mscVctStorageType
      StorageType,
   mscVctIndex
      Integer32 }

mscVctRowStatus OBJECT-TYPE
   SYNTAX     RowStatus 
   ACCESS     read-write
   STATUS     mandatory
   DESCRIPTION
     "This variable is used as the basis for SNMP naming of
      mscVct components.
      These components can be added and deleted."
::= { mscVctRowStatusEntry 1 }

mscVctComponentName OBJECT-TYPE
   SYNTAX     DisplayString 
   ACCESS     read-only
   STATUS     mandatory
   DESCRIPTION
     "This variable provides the component's string name for
      use with the ASCII Console Interface"
::= { mscVctRowStatusEntry 2 }

mscVctStorageType OBJECT-TYPE
   SYNTAX     StorageType 
   ACCESS     read-only
   STATUS     mandatory
   DESCRIPTION
     "This variable represents the storage type value for the
      mscVct tables."
::= { mscVctRowStatusEntry 4 }

mscVctIndex OBJECT-TYPE
   SYNTAX     Integer32 (1..16)
   ACCESS     not-accessible
   STATUS     mandatory
   DESCRIPTION
     "This variable represents the index for the mscVct tables."
::= { mscVctRowStatusEntry 10 }

mscVctProvTable OBJECT-TYPE
   SYNTAX     SEQUENCE OF MscVctProvEntry
   ACCESS     not-accessible
   STATUS     mandatory
   DESCRIPTION
     "This group provides the set of parameters for theVcTester 
      component"
::= { mscVct 10 }

mscVctProvEntry OBJECT-TYPE
   SYNTAX     MscVctProvEntry
   ACCESS     not-accessible
   STATUS     mandatory
   DESCRIPTION
     "An entry in the mscVctProvTable."
   INDEX {
      mscVctIndex }
::= { mscVctProvTable 1 }

MscVctProvEntry ::= SEQUENCE {
   mscVctLogicalProcessor
      Link,
   mscVctVcName
      INTEGER }

mscVctLogicalProcessor OBJECT-TYPE
   SYNTAX     Link 
   ACCESS     read-write
   STATUS     mandatory
   DESCRIPTION
     "This attribute specifies the logical processor on which the VcTester 
      will run"
::= { mscVctProvEntry 1 }

mscVctVcName OBJECT-TYPE
   SYNTAX     INTEGER  {
                 gvc(1),
                 fvc(2) }
   ACCESS     read-write
   STATUS     mandatory
   DESCRIPTION
     "This attribute specifies the type of vc (fvc or gvc) which will be 
      used by VcTester."
   DEFVAL     { gvc }
::= { mscVctProvEntry 2 }


-- Fruni/n Dna
-- This is the description of the generic application Dna component. It 
-- includes the superset of all attributes which may apply to a Vc. 
-- Particular applications will typically offer only a subset of these 
-- attributes by providing a definition of their own Dna subcomponent. 

mscVctDna OBJECT IDENTIFIER ::= { mscVct 2 }



mscVctDnaRowStatusTable OBJECT-TYPE
   SYNTAX     SEQUENCE OF MscVctDnaRowStatusEntry
   ACCESS     not-accessible
   STATUS     mandatory
   DESCRIPTION
     "This entry controls the addition and deletion of 
      mscVctDna components."
::= { mscVctDna 1 }

mscVctDnaRowStatusEntry OBJECT-TYPE
   SYNTAX     MscVctDnaRowStatusEntry
   ACCESS     not-accessible
   STATUS     mandatory
   DESCRIPTION
     "A single entry in the table represents a single 
      mscVctDna component."
   INDEX {
      mscVctIndex,
      mscVctDnaIndex }
::= { mscVctDnaRowStatusTable 1 }

MscVctDnaRowStatusEntry ::= SEQUENCE {
   mscVctDnaRowStatus
      RowStatus,
   mscVctDnaComponentName
      DisplayString,
   mscVctDnaStorageType
      StorageType,
   mscVctDnaIndex
      NonReplicated }

mscVctDnaRowStatus OBJECT-TYPE
   SYNTAX     RowStatus 
   ACCESS     read-only
   STATUS     mandatory
   DESCRIPTION
     "This variable is used as the basis for SNMP naming of
      mscVctDna components.
      These components cannot be added nor deleted."
::= { mscVctDnaRowStatusEntry 1 }

mscVctDnaComponentName OBJECT-TYPE
   SYNTAX     DisplayString 
   ACCESS     read-only
   STATUS     mandatory
   DESCRIPTION
     "This variable provides the component's string name for
      use with the ASCII Console Interface"
::= { mscVctDnaRowStatusEntry 2 }

mscVctDnaStorageType OBJECT-TYPE
   SYNTAX     StorageType 
   ACCESS     read-only
   STATUS     mandatory
   DESCRIPTION
     "This variable represents the storage type value for the
      mscVctDna tables."
::= { mscVctDnaRowStatusEntry 4 }

mscVctDnaIndex OBJECT-TYPE
   SYNTAX     NonReplicated 
   ACCESS     not-accessible
   STATUS     mandatory
   DESCRIPTION
     "This variable represents the index for the mscVctDna tables."
::= { mscVctDnaRowStatusEntry 10 }

mscVctDnaAddressTable OBJECT-TYPE
   SYNTAX     SEQUENCE OF MscVctDnaAddressEntry
   ACCESS     not-accessible
   STATUS     mandatory
   DESCRIPTION
     "Address group contains attributes common to all Dna's. Every Dna 
      used in the network is defined with this group of 2 attributes. String 
      of address digits is complemented by type of address and Npi. 
      These attributes are used to interpret format of the address digits."
::= { mscVctDna 10 }

mscVctDnaAddressEntry OBJECT-TYPE
   SYNTAX     MscVctDnaAddressEntry
   ACCESS     not-accessible
   STATUS     mandatory
   DESCRIPTION
     "An entry in the mscVctDnaAddressTable."
   INDEX {
      mscVctIndex,
      mscVctDnaIndex }
::= { mscVctDnaAddressTable 1 }

MscVctDnaAddressEntry ::= SEQUENCE {
   mscVctDnaNumberingPlanIndicator
      INTEGER,
   mscVctDnaDataNetworkAddress
      DigitString }

mscVctDnaNumberingPlanIndicator OBJECT-TYPE
   SYNTAX     INTEGER  {
                 x121(0),
                 e164(1) }
   ACCESS     read-write
   STATUS     mandatory
   DESCRIPTION
     "This attribute indicates the Numbering Plan Indicator (NPI) of the 
      Dna that is entered. Address may belong to X.121 or E.164 plans. 
      X.121 is used in packet svitched data networks."
   DEFVAL     { x121 }
::= { mscVctDnaAddressEntry 1 }

mscVctDnaDataNetworkAddress OBJECT-TYPE
   SYNTAX     DigitString (SIZE (1..15))
   ACCESS     read-write
   STATUS     mandatory
   DESCRIPTION
     "Dna attribute contains digits which form unique identifier of the 
      customer interface. It can be compared (approximation only) to 
      telephone number where phone number identifies unique telephone 
      set. Dna digits are selected and assigned by network operators."
::= { mscVctDnaAddressEntry 2 }

mscVctDnaOutgoingOptionsTable OBJECT-TYPE
   SYNTAX     SEQUENCE OF MscVctDnaOutgoingOptionsEntry
   ACCESS     not-accessible
   STATUS     mandatory
   DESCRIPTION
     "OutgoingOptions group defines call options of a Dna for calls 
      which are made out of the interface represented by Dna. All these 
      options are not used for calls arriving to the interface represented by 
      Dna."
::= { mscVctDna 11 }

mscVctDnaOutgoingOptionsEntry OBJECT-TYPE
   SYNTAX     MscVctDnaOutgoingOptionsEntry
   ACCESS     not-accessible
   STATUS     mandatory
   DESCRIPTION
     "An entry in the mscVctDnaOutgoingOptionsTable."
   INDEX {
      mscVctIndex,
      mscVctDnaIndex }
::= { mscVctDnaOutgoingOptionsTable 1 }

MscVctDnaOutgoingOptionsEntry ::= SEQUENCE {
   mscVctDnaOutCalls
      INTEGER,
   mscVctDnaOutNormalCharge
      INTEGER,
   mscVctDnaOutReverseCharge
      INTEGER,
   mscVctDnaOutForceReverseCharge
      INTEGER,
   mscVctDnaOutNormalPriority
      INTEGER,
   mscVctDnaOutHighPriority
      INTEGER,
   mscVctDnaOutDefaultPriority
      INTEGER,
   mscVctDnaOutIntl
      INTEGER,
   mscVctDnaOutFsRestrictedResponse
      INTEGER,
   mscVctDnaOutFsUnrestrictedResponse
      INTEGER,
   mscVctDnaOutDefaultPathSensitivity
      INTEGER,
   mscVctDnaOutPathSensitivityOverRide
      INTEGER,
   mscVctDnaOutPathSensitivitySignal
      INTEGER,
   mscVctDnaOutDefaultPathReliability
      INTEGER,
   mscVctDnaOutPathReliabilityOverRide
      INTEGER,
   mscVctDnaOutPathReliabilitySignal
      INTEGER,
   mscVctDnaOutAccess
      INTEGER,
   mscVctDnaDefaultTransferPriority
      INTEGER,
   mscVctDnaTransferPriorityOverRide
      INTEGER }

mscVctDnaOutCalls OBJECT-TYPE
   SYNTAX     INTEGER  {
                 disallowed(0),
                 allowed(1) }
   ACCESS     read-write
   STATUS     mandatory
   DESCRIPTION
     "This attribute, if set to a value of allowed indicates that outgoing 
      calls (from the DTE to the network) can be made using this 
      particular Dna. If set to a value of disallowed, then outgoing calls 
      cannot be made using this Dna - such calls will be cleared by the 
      local DCE. This attribute corresponds to the ITU-T 'Outgoing Calls 
      Barred' feature for Dnas in that outgoing calls are barred if this 
      attribute is set to a value of disallowed. Either outCalls, or incCalls 
      (or both) must be set to a value of allowed for this Dna to be 
      useable."
   DEFVAL     { allowed }
::= { mscVctDnaOutgoingOptionsEntry 1 }

mscVctDnaOutNormalCharge OBJECT-TYPE
   SYNTAX     INTEGER  {
                 disallowed(0),
                 allowed(1) }
   ACCESS     read-write
   STATUS     mandatory
   DESCRIPTION
     "This attribute, if set to a value of allowed indicates that outgoing 
      normal charged calls (from the DTE to the network) can be made 
      using this particular Dna. If set to a value of disallowed, then such 
      calls cannot be made using this Dna - such calls will be cleared by 
      the local DCE. This attribute is ignored if the corresponding 
      attribute, outCalls is set to a value of disallowed."
   DEFVAL     { allowed }
::= { mscVctDnaOutgoingOptionsEntry 2 }

mscVctDnaOutReverseCharge OBJECT-TYPE
   SYNTAX     INTEGER  {
                 disallowed(0),
                 allowed(1) }
   ACCESS     read-write
   STATUS     mandatory
   DESCRIPTION
     "This attribute, if set to a value of allowed indicates that outgoing 
      reverse charged calls (from the DTE to the network) can be made 
      using this particular Dna. If set to a value of disallowed, then such 
      calls cannot be made using this Dna - such calls will be cleared by 
      the local DCE. This attribute is ignored if the corresponding 
      attribute, outCalls is set to a value of disallowed."
   DEFVAL     { allowed }
::= { mscVctDnaOutgoingOptionsEntry 3 }

mscVctDnaOutForceReverseCharge OBJECT-TYPE
   SYNTAX     INTEGER  {
                 no(0),
                 yes(1) }
   ACCESS     read-write
   STATUS     mandatory
   DESCRIPTION
     "This attribute specifies whether to force outgoing reverse charged 
      calls. This attribute, if set to a value of yes forces reverse charging 
      on all outgoing calls (from the DTE to the network) using this 
      particular Dna unless the caller specifies a NUI in which case the 
      call is charged to the NUI. If set to a value of no then reverse 
      charging is not forced for outgoing calls.
      This attribute is ignored if the corresponding attribute, outCalls is 
      set to a value of disallowed.This attribute must be semantically 
      consistent with the corresponding attribute, outReverseChargeCalls."
   DEFVAL     { no }
::= { mscVctDnaOutgoingOptionsEntry 4 }

mscVctDnaOutNormalPriority OBJECT-TYPE
   SYNTAX     INTEGER  {
                 disallowed(0),
                 allowed(1) }
   ACCESS     read-write
   STATUS     mandatory
   DESCRIPTION
     "This attribute, if set to a value of allowed indicates that outgoing 
      normal priority calls (from the DTE to the network) can be made 
      using this particular Dna. If set to a value of disallowed, then such 
      calls cannot be made using this Dna - such calls will be cleared by 
      the local DCE. This attribute is ignored if the corresponding 
      attribute, outCalls is set to a value of disallowed.
      
      This option can be also included in X.25 signalling, in such case it 
      will be overruled."
   DEFVAL     { allowed }
::= { mscVctDnaOutgoingOptionsEntry 5 }

mscVctDnaOutHighPriority OBJECT-TYPE
   SYNTAX     INTEGER  {
                 disallowed(0),
                 allowed(1) }
   ACCESS     read-write
   STATUS     mandatory
   DESCRIPTION
     "This attribute, if set to a value of allowed indicates that outgoing 
      high priority calls (from the DTE to the network) can be made using 
      this particular Dna. If set to a value of disallowed, then such calls 
      cannot be made using this Dna - such calls will be cleared by the 
      local DCE. This attribute is ignored if the corresponding attribute, 
      outCalls is set to a value of disallowed.
      
      This option can be also included in X.25 signalling, in such case it 
      will be overruled."
   DEFVAL     { allowed }
::= { mscVctDnaOutgoingOptionsEntry 6 }

mscVctDnaOutDefaultPriority OBJECT-TYPE
   SYNTAX     INTEGER  {
                 normal(0),
                 high(1) }
   ACCESS     read-write
   STATUS     mandatory
   DESCRIPTION
     "This attribute, if set to normal indicates that the default priority for 
      outgoing calls (from the DTE to the network) using this particular 
      Dna is normal priority - if the priority is not specified by the DTE. 
      If this attribute is set to high then the default priority for outgoing 
      calls using this particular Dna is high priority.
      
      It can be overridden by the discardPriority under DLCI Direct Call 
      subcomponent.
      
      This option can be also included in X.25 signalling, in such case it 
      will be overruled."
   DEFVAL     { normal }
::= { mscVctDnaOutgoingOptionsEntry 7 }

mscVctDnaOutIntl OBJECT-TYPE
   SYNTAX     INTEGER  {
                 disallowed(0),
                 allowed(1) }
   ACCESS     read-write
   STATUS     mandatory
   DESCRIPTION
     "This attribute, if set to a value of allowed indicates that outgoing 
      international calls (from the DTE to the network) can be made using 
      this particular Dna. If set to a value of disallowed, then such calls 
      cannot be made using this Dna - such calls will be cleared by the 
      local DCE.
      
      This attribute also currently controls access to the E.164 numbering 
      plan, and if set to a value of allowed, then cross-numbering plan 
      calls are allowed.
      
      This attribute is ignored if the corresponding attribute, outCalls is 
      set to a value of disallowed."
   DEFVAL     { disallowed }
::= { mscVctDnaOutgoingOptionsEntry 8 }

mscVctDnaOutFsRestrictedResponse OBJECT-TYPE
   SYNTAX     INTEGER  {
                 disallowed(0),
                 allowed(1) }
   ACCESS     read-write
   STATUS     mandatory
   DESCRIPTION
     "This attribute, if set to a value of allowed indicates that outgoing 
      fast select calls (from the DTE to the network) with a restricted 
      response can be made using this particular Dna. If set to a value of 
      disallowed, then such calls cannot be made using this Dna - such 
      calls will be cleared by the local DCE. This attribute is ignored if 
      the corresponding attribute, outCalls is set to a value of disallowed."
   DEFVAL     { disallowed }
::= { mscVctDnaOutgoingOptionsEntry 9 }

mscVctDnaOutFsUnrestrictedResponse OBJECT-TYPE
   SYNTAX     INTEGER  {
                 disallowed(0),
                 allowed(1) }
   ACCESS     read-write
   STATUS     mandatory
   DESCRIPTION
     "This attribute, if set to a value of allowed indicates that outgoing 
      fast select calls (from the DTE to the network) with an unrestricted 
      response can be made using this particular Dna. If set to a value of 
      disallowed, then such calls cannot be made using this Dna - such 
      calls will be cleared by the local DCE.
      This attribute is ignored if the corresponding attribute, outCalls is 
      set to a value of disallowed."
   DEFVAL     { disallowed }
::= { mscVctDnaOutgoingOptionsEntry 10 }

mscVctDnaOutDefaultPathSensitivity OBJECT-TYPE
   SYNTAX     INTEGER  {
                 throughput(0),
                 delay(1) }
   ACCESS     read-write
   STATUS     obsolete
   DESCRIPTION
     "This attribute specifies the default class of path sensitivity to 
      network for all outgoing calls using this particular Dna. The chosen 
      default class of path sensitivity applies to all outgoing calls 
      established using this Dna. 
      
      This attribute, if set to a value of throughput, indicates that the 
      default class is throughput sensitive. If set to a value of delay, then 
      the default class is delay sensitive. The default of 
      outDefaultPathSensitivity is throughput.
      
      This attribute is obsoleted. Please refer to defaultTransferPriority 
      for the corresponding new attribute.
      
      The migration function here will provide"
   DEFVAL     { throughput }
::= { mscVctDnaOutgoingOptionsEntry 11 }

mscVctDnaOutPathSensitivityOverRide OBJECT-TYPE
   SYNTAX     INTEGER  {
                 no(0),
                 yes(1) }
   ACCESS     read-write
   STATUS     obsolete
   DESCRIPTION
     "If this attribute is set to in the call request, the called end will use 
      the calling end provisioning data on path sensitivity to override its 
      own provisioning data.
      
      The default of outPathSensitivityOverRide is no."
   DEFVAL     { no }
::= { mscVctDnaOutgoingOptionsEntry 12 }

mscVctDnaOutPathSensitivitySignal OBJECT-TYPE
   SYNTAX     INTEGER  {
                 disallowed(0),
                 allowed(1) }
   ACCESS     read-write
   STATUS     mandatory
   DESCRIPTION
     "This is the sensitivity signaling. If this attribute is set to allowed, the 
      signalled value on sensitivity will be used."
   DEFVAL     { disallowed }
::= { mscVctDnaOutgoingOptionsEntry 13 }

mscVctDnaOutDefaultPathReliability OBJECT-TYPE
   SYNTAX     INTEGER  {
                 high(0),
                 normal(1) }
   ACCESS     read-write
   STATUS     mandatory
   DESCRIPTION
     "This attribute specifies the default class of routing for reliability 
      routing for all outgoing calls (from the DTE to the network) using 
      this particular Dna. The chosen default class of routing applies to 
      all outgoing calls established using this Dna, and applies to the 
      packets travelling in both directions on all outgoing calls (local to 
      remote, and remote to local). For incoming calls, the default class of 
      routing is chosen by the calling party (as opposed to DPN, where 
      either end of the call can choose the default routing class).
      This attribute, if set to a value of normal, indicates that the default 
      class of routing is normal reliability routing. If set to a value of 
      high, then the default class of routing is high reliability routing.
      High reliability is the standard choice for most DPN and Passport 
      services. It usually indicates that packets are overflowed or 
      retransmitted at various routing levels. Typically high reliability 
      results in duplication and disordering of packets in the network 
      when errors are detected or during link congestion. However, the Vc 
      handles the duplication and disordering to ensure that packets are 
      delivered to the DTE properly.
      For the Frame Relay service, duplication of packets is not desired, 
      in which case, normal reliability may be chosen as the preferred 
      class of routing."
   DEFVAL     { high }
::= { mscVctDnaOutgoingOptionsEntry 14 }

mscVctDnaOutPathReliabilityOverRide OBJECT-TYPE
   SYNTAX     INTEGER  {
                 no(0),
                 yes(1) }
   ACCESS     read-write
   STATUS     mandatory
   DESCRIPTION
     "If outReliabilityOverRide set in the call request, the called end will 
      use the calling end provisioning data on reliability to overide his 
      provisioning data."
   DEFVAL     { no }
::= { mscVctDnaOutgoingOptionsEntry 15 }

mscVctDnaOutPathReliabilitySignal OBJECT-TYPE
   SYNTAX     INTEGER  {
                 disallowed(0),
                 allowed(1) }
   ACCESS     read-write
   STATUS     mandatory
   DESCRIPTION
     "outPathReliabilitySignal is reliability routing signaling. If this 
      attribute is set to allowed, the signalled value on reliability will be 
      used."
   DEFVAL     { disallowed }
::= { mscVctDnaOutgoingOptionsEntry 16 }

mscVctDnaOutAccess OBJECT-TYPE
   SYNTAX     INTEGER  {
                 disallowed(0),
                 allowed(1) }
   ACCESS     read-write
   STATUS     mandatory
   DESCRIPTION
     "This attribute is an extension of the Closed User Group (CUG) 
      facility, as follows:
      This attribute, if set to a value of allowed indicates that outgoing 
      calls (from the DTE to the network) to the open (non-CUG) part of 
      the network are permitted. It also permits outgoing calls to DTE's 
      that have Incoming Access capabilities. If set to a value of 
      disallowed, then such calls cannot be made using this Dna - such 
      calls will be cleared by the local DCE.
      This attribute corresponds to the ITU-T 'Closed User Group with 
      Outgoing Access' feature for Dna's in that outgoing access is 
      granted if this attribute is set to a value of allowed."
   DEFVAL     { disallowed }
::= { mscVctDnaOutgoingOptionsEntry 17 }

mscVctDnaDefaultTransferPriority OBJECT-TYPE
   SYNTAX     INTEGER  {
                 normal(0),
                 high(9) }
   ACCESS     read-write
   STATUS     mandatory
   DESCRIPTION
     "This attribute specifies the default transfer priority to network for 
      all outgoing calls using this particular Dna. It is overRidden by 
      the transferPriority provisioned in the DLCI Direct Call sub-
      component.
      
      The transfer priority is a preference specified by an application 
      according to its delay-sensitivity requirement. Frames with high
      transfer priority are served by the network before the frames with 
      normal priority. 
      
      Each transfer priority contains a predetermined setting for trunk 
      queue (interrupting, delay or throughput), and routing metric (delay 
      or throughput). 
      
      When the transfer priority is set at high, the trunk queue is set to 
      high, the routing metric is set to delay.
      
      When the transfer priority is set at normal, the trunk queue is set to 
      normal, the routing metric is set to throughput.
      
      The default of defaultTransferPriority is normal."
   DEFVAL     { normal }
::= { mscVctDnaOutgoingOptionsEntry 18 }

mscVctDnaTransferPriorityOverRide OBJECT-TYPE
   SYNTAX     INTEGER  {
                 no(0),
                 yes(1) }
   ACCESS     read-write
   STATUS     mandatory
   DESCRIPTION
     "When this attribute is set to yes, the called end will use the calling 
      end provisioning data on transfer priority to override its own 
      provisioning data. If it is set no, the called end will use its own 
      provisioning data on transfer priority.
      
      For more information about transfer priority, please refer to the 
      previous attribute defaultTransferPriority.
      
      The default of transferPriorityOverRide is no."
   DEFVAL     { no }
::= { mscVctDnaOutgoingOptionsEntry 19 }

mscVctDnaIncomingOptionsTable OBJECT-TYPE
   SYNTAX     SEQUENCE OF MscVctDnaIncomingOptionsEntry
   ACCESS     not-accessible
   STATUS     mandatory
   DESCRIPTION
     "IncomingOptions defines set of options for incoming calls. These 
      options are used for calls arriving to the interface represented by 
      Dna. For calls originated from the interfasce, IncomingOptions 
      attributes are not used."
::= { mscVctDna 12 }

mscVctDnaIncomingOptionsEntry OBJECT-TYPE
   SYNTAX     MscVctDnaIncomingOptionsEntry
   ACCESS     not-accessible
   STATUS     mandatory
   DESCRIPTION
     "An entry in the mscVctDnaIncomingOptionsTable."
   INDEX {
      mscVctIndex,
      mscVctDnaIndex }
::= { mscVctDnaIncomingOptionsTable 1 }

MscVctDnaIncomingOptionsEntry ::= SEQUENCE {
   mscVctDnaIncCalls
      INTEGER,
   mscVctDnaIncHighPriorityReverseCharge
      INTEGER,
   mscVctDnaIncNormalPriorityReverseCharge
      INTEGER,
   mscVctDnaIncIntlNormalCharge
      INTEGER,
   mscVctDnaIncIntlReverseCharge
      INTEGER,
   mscVctDnaIncFastSelect
      INTEGER,
   mscVctDnaIncSameService
      INTEGER,
   mscVctDnaIncChargeTransfer
      INTEGER,
   mscVctDnaIncAccess
      INTEGER }

mscVctDnaIncCalls OBJECT-TYPE
   SYNTAX     INTEGER  {
                 disallowed(0),
                 allowed(1) }
   ACCESS     read-write
   STATUS     mandatory
   DESCRIPTION
     "This attribute, if set to a value of allowed indicates that incoming 
      calls (from the network to the DTE) can be made to this Dna. If set 
      to a value of disallowed, then incoming calls cannot be made to this 
      Dna - such calls will be cleared by the local DCE. This attribute 
      corresponds to the ITU-T 'Incoming Calls Barred' feature for Dna's 
      in that incoming calls are barred if this attribute is set to a value of 
      disallowed.
      
      Either outCalls, or incCalls (or both) must be set to a value of 
      allowed for this Dna to be useable."
   DEFVAL     { allowed }
::= { mscVctDnaIncomingOptionsEntry 1 }

mscVctDnaIncHighPriorityReverseCharge OBJECT-TYPE
   SYNTAX     INTEGER  {
                 disallowed(0),
                 allowed(1) }
   ACCESS     read-write
   STATUS     mandatory
   DESCRIPTION
     "This attribute, if set to a value of allowed indicates that incoming 
      high priority, reverse charged calls (from the network to the DTE) 
      can be made to this Dna. If set to a value of disallowed,then such 
      calls cannot be made to this Dna - such calls will be cleared by the 
      local DCE.
      This attribute, together with the 
      incNormalPriorityReverseChargeCalls attribute corresponds
      to the ITU-T 'Reverse Charging Acceptance' feature for Dna's in 
      that reverse charged calls are accepted if both attributes are set to a 
      value of allowed.
      This attribute is ignored if the corresponding attribute, incCalls is 
      set to a value of disallowed."
   DEFVAL     { allowed }
::= { mscVctDnaIncomingOptionsEntry 2 }

mscVctDnaIncNormalPriorityReverseCharge OBJECT-TYPE
   SYNTAX     INTEGER  {
                 disallowed(0),
                 allowed(1) }
   ACCESS     read-write
   STATUS     mandatory
   DESCRIPTION
     "This attribute, if set to a value of allowed indicates that incoming 
      normal priority, reverse charged calls (from the network to the 
      DTE) can be made to this Dna. If set to a value of disallowed, then 
      such calls cannot be made to this Dna - such calls will be cleared by 
      the local DCE. 
      This attribute, together with the 
      incHighPriorityReverseChargeCalls attribute corresponds to the 
      ITU-T 'Reverse Charging Acceptance' feature for Dna's in that 
      reverse charged calls are accepted if both attributes are set to a value 
      of allowed.
      This attribute is ignored if the corresponding attribute, incCalls is 
      set to a value of disallowed."
   DEFVAL     { allowed }
::= { mscVctDnaIncomingOptionsEntry 3 }

mscVctDnaIncIntlNormalCharge OBJECT-TYPE
   SYNTAX     INTEGER  {
                 disallowed(0),
                 allowed(1) }
   ACCESS     read-write
   STATUS     mandatory
   DESCRIPTION
     "This attribute, if set to a value of allowed indicates that incoming 
      international normal charged calls (from the network to the DTE) 
      can be made to this Dna. If set to a value of disallowed, then such 
      calls cannot be made to this Dna - such calls will be cleared by the 
      local DCE.
      This attribute also currently controls access to/from the E.164 
      numbering plan, and if set to a value of allowed, then cross-
      numbering plan calls (also normal charged) are allowed. 
      This attribute is ignored if the corresponding attribute, incCalls is 
      set to a value of disallowed."
   DEFVAL     { allowed }
::= { mscVctDnaIncomingOptionsEntry 4 }

mscVctDnaIncIntlReverseCharge OBJECT-TYPE
   SYNTAX     INTEGER  {
                 disallowed(0),
                 allowed(1) }
   ACCESS     read-write
   STATUS     mandatory
   DESCRIPTION
     "This attribute, if set to a value of allowed indicates that incoming 
      international reverse charged calls (from the network to the DTE) 
      can be made to this Dna. If set to a value of disallowed, then such 
      calls cannot be made to this Dna - such calls will be cleared by the 
      local DCE.
      This attribute also currently controls access to/from the E.164 
      numbering plan, and if set to a value of allowed, then cross-
      numbering plan calls (also normal charged) are allowed.
      This attribute is ignored if the corresponding attribute, incCalls is 
      set to a value of disallowed."
   DEFVAL     { allowed }
::= { mscVctDnaIncomingOptionsEntry 5 }

mscVctDnaIncFastSelect OBJECT-TYPE
   SYNTAX     INTEGER  {
                 disallowed(0),
                 allowed(1) }
   ACCESS     read-write
   STATUS     mandatory
   DESCRIPTION
     "This attribute specifies whether fast select calls may be received.
      This attribute, if set to a value of allowed indicates that incoming 
      fast select calls (from the network to the DTE) can be made to this 
      Dna. If set to a value of disallowed, then such calls cannot be made 
      to this Dna - such calls will be cleared by the local DCE.
      This attribute corresponds to the ITU-T 'Fast Select Acceptance' 
      feature for Dnas in that incoming fast select calls are accepted if 
      this attribute is set to a value of allowed.
      This attribute is ignored if the corresponding attribute, incCalls is 
      set to a value of disallowed."
   DEFVAL     { disallowed }
::= { mscVctDnaIncomingOptionsEntry 6 }

mscVctDnaIncSameService OBJECT-TYPE
   SYNTAX     INTEGER  {
                 disallowed(0),
                 allowed(1) }
   ACCESS     read-write
   STATUS     mandatory
   DESCRIPTION
     "This attribute, if set to a value of allowed indicates that incoming 
      calls from the same service type (eg: X.25, ITI, SNA) (from the 
      network to the DTE) can be made to this Dna. If set to a value of 
      disallowed, then such calls cannot be made to this Dna - such calls 
      will be cleared by the local DCE.
      This attribute is ignored if the corresponding attribute, incCalls is 
      set to a value of disallowed."
   DEFVAL     { allowed }
::= { mscVctDnaIncomingOptionsEntry 7 }

mscVctDnaIncChargeTransfer OBJECT-TYPE
   SYNTAX     INTEGER  {
                 no(0),
                 yes(1) }
   ACCESS     read-write
   STATUS     mandatory
   DESCRIPTION
     "This attribute, if set to a value of yes indicates that the charges for 
      incoming normal charged calls from a DTE with the same DNIC 
      (calls from the network to the DTE) will be transferred to the called 
      DTE. If set to a value of no, then charges will not be transferred.
      This attribute is ignored if the corresponding attribute, incCalls is 
      set to a value of disallowed."
   DEFVAL     { no }
::= { mscVctDnaIncomingOptionsEntry 8 }

mscVctDnaIncAccess OBJECT-TYPE
   SYNTAX     INTEGER  {
                 disallowed(0),
                 allowed(1) }
   ACCESS     read-write
   STATUS     mandatory
   DESCRIPTION
     "This attribute is an extension of the Closed User Group (CUG) 
      facility, as follows:
      This attribute, if set to a value of allowed indicates that incoming 
      calls (from the network to the DTE) from the open (non-CUG) part 
      of the network are permitted. It also permits incoming calls from 
      DTE's that have Outgoing Access capabilities. If set to a value of 
      disallowed, then such calls cannot be made to this Dna - such calls 
      will be cleared by the local DCE.
      This attribute corresponds to the ITU-T 'Closed User Group with 
      Incoming Access' feature for Dnas in that incoming access is 
      granted if this attribute is set to a value of allowed."
   DEFVAL     { disallowed }
::= { mscVctDnaIncomingOptionsEntry 9 }

mscVctDnaCallOptionsTable OBJECT-TYPE
   SYNTAX     SEQUENCE OF MscVctDnaCallOptionsEntry
   ACCESS     not-accessible
   STATUS     mandatory
   DESCRIPTION
     "CallOptions group defines additional options for calls not related 
      directly to direction of a call."
::= { mscVctDna 13 }

mscVctDnaCallOptionsEntry OBJECT-TYPE
   SYNTAX     MscVctDnaCallOptionsEntry
   ACCESS     not-accessible
   STATUS     mandatory
   DESCRIPTION
     "An entry in the mscVctDnaCallOptionsTable."
   INDEX {
      mscVctIndex,
      mscVctDnaIndex }
::= { mscVctDnaCallOptionsTable 1 }

MscVctDnaCallOptionsEntry ::= SEQUENCE {
   mscVctDnaServiceCategory
      INTEGER,
   mscVctDnaPacketSizes
      OCTET STRING,
   mscVctDnaDefaultRecvFrmNetworkPacketSize
      INTEGER,
   mscVctDnaDefaultSendToNetworkPacketSize
      INTEGER,
   mscVctDnaDefaultRecvFrmNetworkThruputClass
      Unsigned32,
   mscVctDnaDefaultSendToNetworkThruputClass
      Unsigned32,
   mscVctDnaDefaultRecvFrmNetworkWindowSize
      Unsigned32,
   mscVctDnaDefaultSendToNetworkWindowSize
      Unsigned32,
   mscVctDnaPacketSizeNegotiation
      INTEGER,
   mscVctDnaCugFormat
      INTEGER,
   mscVctDnaCug0AsNonCugCall
      INTEGER,
   mscVctDnaSignalPreferentialCugToLink
      INTEGER,
   mscVctDnaSignalIntlAddressToLink
      INTEGER,
   mscVctDnaFastSelectCallsOnly
      INTEGER,
   mscVctDnaPreselectRpoa
      INTEGER,
   mscVctDnaAccountClass
      Unsigned32,
   mscVctDnaAccountCollection
      OCTET STRING,
   mscVctDnaServiceExchange
      Unsigned32,
   mscVctDnaEgressAccounting
      INTEGER,
   mscVctDnaRpoa
      DigitString,
   mscVctDnaDataPath
      INTEGER }

mscVctDnaServiceCategory OBJECT-TYPE
   SYNTAX     INTEGER  {
                 gsp(0),
                 x25(1),
                 enhancedIti(2),
                 ncs(3),
                 mlti(4),
                 sm(5),
                 ici(6),
                 dsp3270(7),
                 iam(8),
                 mlhi(9),
                 term3270(10),
                 iti(11),
                 bsi(13),
                 hostIti(14),
                 x75(15),
                 hdsp3270(16),
                 api3201(20),
                 sdlc(21),
                 snaMultiHost(22),
                 redirectionServ(23),
                 trSnaTpad(24),
                 offnetNui(25),
                 gasServer(26),
                 vapServer(28),
                 vapAgent(29),
                 frameRelay(30),
                 ipiVc(31),
                 gvcIf(32) }
   ACCESS     read-write
   STATUS     mandatory
   DESCRIPTION
     "This attribute is assigned for each different type of service within 
      which this Dna is configured. It is placed into the Service Category 
      attribute in the accounting record by both ends of the Vc."
   DEFVAL     { frameRelay }
::= { mscVctDnaCallOptionsEntry 1 }

mscVctDnaPacketSizes OBJECT-TYPE
   SYNTAX     OCTET STRING (SIZE (2))
   ACCESS     read-write
   STATUS     mandatory
   DESCRIPTION
     "This attribute indicates the allowable packet sizes supported for call 
      setup using this Dna. ITU-T recommends that packet size 128 
      always be supported. Attributes defaultRecvFrmNetworkPacketSize 
      and defaultSendToNetworkPacketSize are related to this attribute.

      Description of bits:
      n16(0)
      n32(1)
      n64(2)
      n128(3)
      n256(4)
      n512(5)
      n1024(6)
      n2048(7)
      n4096(8)"
   DEFVAL     { '1c00'H }
::= { mscVctDnaCallOptionsEntry 2 }

mscVctDnaDefaultRecvFrmNetworkPacketSize OBJECT-TYPE
   SYNTAX     INTEGER  {
                 n16(4),
                 n32(5),
                 n64(6),
                 n128(7),
                 n256(8),
                 n512(9),
                 n1024(10),
                 n2048(11),
                 n4096(12) }
   ACCESS     read-write
   STATUS     mandatory
   DESCRIPTION
     "This attribute indicates the default local receive packet size from 
      network to DTE for all calls using this particular Dna. Attribute 
      packetSizes has to be set with corresponding value."
   DEFVAL     { n128 }
::= { mscVctDnaCallOptionsEntry 3 }

mscVctDnaDefaultSendToNetworkPacketSize OBJECT-TYPE
   SYNTAX     INTEGER  {
                 n16(4),
                 n32(5),
                 n64(6),
                 n128(7),
                 n256(8),
                 n512(9),
                 n1024(10),
                 n2048(11),
                 n4096(12) }
   ACCESS     read-write
   STATUS     mandatory
   DESCRIPTION
     "This attribute indicates the default local send packet size from DTE 
      to network for all calls using this particular Dna.
      Attribute packetSizes has to be set with corresponding value."
   DEFVAL     { n128 }
::= { mscVctDnaCallOptionsEntry 4 }

mscVctDnaDefaultRecvFrmNetworkThruputClass OBJECT-TYPE
   SYNTAX     Unsigned32 (3..15)
   ACCESS     read-write
   STATUS     mandatory
   DESCRIPTION
     "This attribute indicates the default receive throughput class for all 
      calls using this particular Dna."
   DEFVAL     { 10 }
::= { mscVctDnaCallOptionsEntry 5 }

mscVctDnaDefaultSendToNetworkThruputClass OBJECT-TYPE
   SYNTAX     Unsigned32 (0..15)
   ACCESS     read-write
   STATUS     mandatory
   DESCRIPTION
     "This attribute indicates the default send throughput class for all calls 
      using this particular Dna."
   DEFVAL     { 10 }
::= { mscVctDnaCallOptionsEntry 6 }

mscVctDnaDefaultRecvFrmNetworkWindowSize OBJECT-TYPE
   SYNTAX     Unsigned32 (1..7)
   ACCESS     read-write
   STATUS     mandatory
   DESCRIPTION
     "This attribute indicates the default number of data packets that can 
      be received by the DTE from the DCE before more packets can be 
      received. This view is oriented with respect to the DTE."
   DEFVAL     { 2 }
::= { mscVctDnaCallOptionsEntry 7 }

mscVctDnaDefaultSendToNetworkWindowSize OBJECT-TYPE
   SYNTAX     Unsigned32 (1..7)
   ACCESS     read-write
   STATUS     mandatory
   DESCRIPTION
     "This attribute indicates the number of data packets that can be 
      transmitted from the DTE to the DCE and must be acknowledged 
      before more packets can be transmitted."
   DEFVAL     { 2 }
::= { mscVctDnaCallOptionsEntry 8 }

mscVctDnaPacketSizeNegotiation OBJECT-TYPE
   SYNTAX     INTEGER  {
                 endToEnd(0),
                 local(1) }
   ACCESS     read-write
   STATUS     mandatory
   DESCRIPTION
     "This attribute, if set to local indicates that packet sizes can be 
      negotiated locally at the interface irrespective of the remote 
      interface. If set to endtoEnd, then local negotiation is not permitted 
      and packet sizes are negotiated between 2 ends of Vc."
   DEFVAL     { endToEnd }
::= { mscVctDnaCallOptionsEntry 9 }

mscVctDnaCugFormat OBJECT-TYPE
   SYNTAX     INTEGER  {
                 basic(0),
                 extended(1) }
   ACCESS     read-write
   STATUS     mandatory
   DESCRIPTION
     "This attribute specifies which cug format is used when DTE signals 
      CUG indices, basic or extended.
      This attribute, if set to extended indicates that the DTE signals and 
      receives CUG indices in extended CUG format. If set to a value of 
      basic, then the DTE signals and receives CUG indices in the basic 
      CUG format."
   DEFVAL     { basic }
::= { mscVctDnaCallOptionsEntry 10 }

mscVctDnaCug0AsNonCugCall OBJECT-TYPE
   SYNTAX     INTEGER  {
                 disallowed(0),
                 allowed(1) }
   ACCESS     read-write
   STATUS     mandatory
   DESCRIPTION
     "This attribute, if set to allowed indicates that when a CUG index of 
      0 is signalled in a call request packet, the call is treated as a non-
      CUG call. If this attribute is set to disallowed, then a CUG index of 
      0 is treated as an index, and an attempt is made to find the particular 
      CUG corresponding with the Dna."
   DEFVAL     { disallowed }
::= { mscVctDnaCallOptionsEntry 11 }

mscVctDnaSignalPreferentialCugToLink OBJECT-TYPE
   SYNTAX     INTEGER  {
                 no(0),
                 yes(1) }
   ACCESS     read-write
   STATUS     mandatory
   DESCRIPTION
     "This attribute, if set to no, indicates that, at the destination (called) 
      DTE, when a CUG call is received using the called DTE's 
      preferential CUG, the preferential CUG's index is not signalled to 
      the called DTE in the incoming call request packet. Otherwise, the 
      preferential CUG's index is signalled to the link in the incoming call 
      request packet."
   DEFVAL     { no }
::= { mscVctDnaCallOptionsEntry 12 }

mscVctDnaSignalIntlAddressToLink OBJECT-TYPE
   SYNTAX     INTEGER  {
                 no(0),
                 yes(1) }
   ACCESS     read-write
   STATUS     mandatory
   DESCRIPTION
     "This attribute, if set to yes, indicates that all addresses presented by 
      the network (DCE) to the link (DTE) within incoming call request., 
      call connected and clear packets are presented in international 
      format with no prefix digit. International format includes DNIC in 
      the address."
   DEFVAL     { no }
::= { mscVctDnaCallOptionsEntry 13 }

mscVctDnaFastSelectCallsOnly OBJECT-TYPE
   SYNTAX     INTEGER  {
                 no(0),
                 yes(1) }
   ACCESS     read-write
   STATUS     mandatory
   DESCRIPTION
     "This attribute, if set to yes, indicates that the service is permitted 
      restricted fast select calls in both the incoming and the outgoing 
      directions using this Dna. If set to no, then non fast select calls are 
      permitted as well."
   DEFVAL     { no }
::= { mscVctDnaCallOptionsEntry 14 }

mscVctDnaPreselectRpoa OBJECT-TYPE
   SYNTAX     INTEGER  {
                 no(0),
                 yes(1) }
   ACCESS     read-write
   STATUS     mandatory
   DESCRIPTION
     "This attribute, if set to yes, indicates that this Dna subscribes to a 
      pre-selected RPOA, in which case, the pre-selected RPOA is 
      contained in the rpoa attribute described below. If set to no, then a 
      pre-selected RPOA is not subscribed."
   DEFVAL     { no }
::= { mscVctDnaCallOptionsEntry 15 }

mscVctDnaAccountClass OBJECT-TYPE
   SYNTAX     Unsigned32 (0..255)
   ACCESS     read-write
   STATUS     mandatory
   DESCRIPTION
     "This attribute specifies the accounting class which is reserved for 
      network operations usage. Its value is returned in the accounting 
      record in the local and remote service type attributes. Use of this 
      attribute is decided by network operator and it is an arbitrary 
      number."
   DEFVAL     { 0 }
::= { mscVctDnaCallOptionsEntry 16 }

mscVctDnaAccountCollection OBJECT-TYPE
   SYNTAX     OCTET STRING (SIZE (1))
   ACCESS     read-write
   STATUS     mandatory
   DESCRIPTION
     "This attribute indicates that accounting records are to be collected 
      by the network for the various reasons: billing, test, study, auditing. 
      The last of the parameters, force, indicates that accounting records 
      are to be collected irrespective of other collection reasons. If none 
      of these reasons are set, then accounting will be suppressed.

      Description of bits:
      bill(0)
      test(1)
      study(2)
      audit(3)
      force(4)"
   DEFVAL     { '80'H }
::= { mscVctDnaCallOptionsEntry 17 }

mscVctDnaServiceExchange OBJECT-TYPE
   SYNTAX     Unsigned32 (0..255)
   ACCESS     read-write
   STATUS     mandatory
   DESCRIPTION
     "This attribute is an arbitrary number, entered by the network 
      operator. The value of serviceExchange is included in the 
      accounting record generated by Vc."
   DEFVAL     { 0 }
::= { mscVctDnaCallOptionsEntry 18 }

mscVctDnaEgressAccounting OBJECT-TYPE
   SYNTAX     INTEGER  {
                 no(0),
                 yes(1) }
   ACCESS     read-write
   STATUS     mandatory
   DESCRIPTION
     "egressAccounting	 specifies if Egress accounting is enabled by 
      Frame Relay service. Disabling of Egress accounting means that 
      only segment counts are collected by VC and there are no frame 
      relay counts in accounting records for Frame Relay service. 
      Enabling of Egress accounting means that the accounting records 
      for Frame Relay contain frame relay specific counts."
   DEFVAL     { no }
::= { mscVctDnaCallOptionsEntry 19 }

mscVctDnaRpoa OBJECT-TYPE
   SYNTAX     DigitString (SIZE (4))
   ACCESS     read-write
   STATUS     mandatory
   DESCRIPTION
     "rpoa - Recognized Private Operating Agency is a ITU-T specified 
      facility which allows the user to specify--at call setup time--the next 
      transit network the call should use. The rpoa can override all 
      routing decisions.
      If Dna subscribes to preselectRpoa as indicated by the previously 
      described attribute, (preselectRpoa set to yes) then this attribute 
      contains preselected rpoa. If the preselectRpoa attribute is set to no, 
      then this attribute can be left at its default.
      This preselected rpoa will be used for all outgoing call request 
      packets using this Dna if an rpoa is not explicitly specified in the 
      call request. The rpoa represents the dnic of the directly connected 
      network through which the call will be routed in the presence of the 
      rpoa."
   DEFVAL     { '30303030'H }  -- "0000"
::= { mscVctDnaCallOptionsEntry 20 }

mscVctDnaDataPath OBJECT-TYPE
   SYNTAX     INTEGER  {
                 dprsOnly(0),
                 dprsMcsOnly(1),
                 dprsMcsFirst(2) }
   ACCESS     read-write
   STATUS     mandatory
   DESCRIPTION
     "This attribute specifies the data path to be used by Virtual Circuits 
      on this interface. If the connection has a DirectCall component then 
      the value can be overridden by the dataPath attribute of the 
      DirectCall component.
      
      This value applies to the connection after data transfer state is 
      reached. All the data and control trafic will be sent using this data 
      path. If the provisioned dataPath is not available the connection is 
      not established.
      
      The value of the dataPath is signalled by both ends of the 
      connection. If this value is not the same at both ends dprsOnly is 
      used for the duration of the connection.
      
      A virtual circuit connection is always established using dprsOnly 
      even if this attribute is provisioned as some other value.
      
      dprsOnly - dynamic packet routing system is used
      
      dprsMcsOnly - dprs Multi-Service Cut-Through Switching path is 
      used.
      
      dprsMcsFirst - dprs Multi-Service Cut-Through Switching path is 
      used if it is available. If it is not avaliable dprsOnly is used."
   DEFVAL     { dprsOnly }
::= { mscVctDnaCallOptionsEntry 21 }


-- Fruni/n Dna Cug
-- ClosedUserGroup options defines options associated with national 
-- or international Cug Identifier. Other Dna's in the network can have 
-- Cug's defined which groups these Dna's by Cug interlockCode. If 
-- Dna's are defined with Cugs, calls from Dna's which do not have 
-- the same interlockCode defined are refused. Attributes incAccess 
-- and outAccess can override this rule.

mscVctDnaCug OBJECT IDENTIFIER ::= { mscVctDna 2 }



mscVctDnaCugRowStatusTable OBJECT-TYPE
   SYNTAX     SEQUENCE OF MscVctDnaCugRowStatusEntry
   ACCESS     not-accessible
   STATUS     mandatory
   DESCRIPTION
     "This entry controls the addition and deletion of 
      mscVctDnaCug components."
::= { mscVctDnaCug 1 }

mscVctDnaCugRowStatusEntry OBJECT-TYPE
   SYNTAX     MscVctDnaCugRowStatusEntry
   ACCESS     not-accessible
   STATUS     mandatory
   DESCRIPTION
     "A single entry in the table represents a single 
      mscVctDnaCug component."
   INDEX {
      mscVctIndex,
      mscVctDnaIndex,
      mscVctDnaCugIndex }
::= { mscVctDnaCugRowStatusTable 1 }

MscVctDnaCugRowStatusEntry ::= SEQUENCE {
   mscVctDnaCugRowStatus
      RowStatus,
   mscVctDnaCugComponentName
      DisplayString,
   mscVctDnaCugStorageType
      StorageType,
   mscVctDnaCugIndex
      Integer32 }

mscVctDnaCugRowStatus OBJECT-TYPE
   SYNTAX     RowStatus 
   ACCESS     read-write
   STATUS     mandatory
   DESCRIPTION
     "This variable is used as the basis for SNMP naming of
      mscVctDnaCug components.
      These components can be added and deleted."
::= { mscVctDnaCugRowStatusEntry 1 }

mscVctDnaCugComponentName OBJECT-TYPE
   SYNTAX     DisplayString 
   ACCESS     read-only
   STATUS     mandatory
   DESCRIPTION
     "This variable provides the component's string name for
      use with the ASCII Console Interface"
::= { mscVctDnaCugRowStatusEntry 2 }

mscVctDnaCugStorageType OBJECT-TYPE
   SYNTAX     StorageType 
   ACCESS     read-only
   STATUS     mandatory
   DESCRIPTION
     "This variable represents the storage type value for the
      mscVctDnaCug tables."
::= { mscVctDnaCugRowStatusEntry 4 }

mscVctDnaCugIndex OBJECT-TYPE
   SYNTAX     Integer32 (0..255)
   ACCESS     not-accessible
   STATUS     mandatory
   DESCRIPTION
     "This variable represents the index for the mscVctDnaCug tables."
::= { mscVctDnaCugRowStatusEntry 10 }

mscVctDnaCugCugOptionsTable OBJECT-TYPE
   SYNTAX     SEQUENCE OF MscVctDnaCugCugOptionsEntry
   ACCESS     not-accessible
   STATUS     mandatory
   DESCRIPTION
     "This group defines options for. Attributes in this group defines 
      ClosedUserGroup options associated with interlockCode. Dna's 
      with the same Cug (interlockCode) can make calls within this 
      group. Various combinations which permit or prevent calls in the 
      same Cug group are defined here."
::= { mscVctDnaCug 10 }

mscVctDnaCugCugOptionsEntry OBJECT-TYPE
   SYNTAX     MscVctDnaCugCugOptionsEntry
   ACCESS     not-accessible
   STATUS     mandatory
   DESCRIPTION
     "An entry in the mscVctDnaCugCugOptionsTable."
   INDEX {
      mscVctIndex,
      mscVctDnaIndex,
      mscVctDnaCugIndex }
::= { mscVctDnaCugCugOptionsTable 1 }

MscVctDnaCugCugOptionsEntry ::= SEQUENCE {
   mscVctDnaCugType
      INTEGER,
   mscVctDnaCugDnic
      DigitString,
   mscVctDnaCugInterlockCode
      Unsigned32,
   mscVctDnaCugPreferential
      INTEGER,
   mscVctDnaCugOutCalls
      INTEGER,
   mscVctDnaCugIncCalls
      INTEGER,
   mscVctDnaCugPrivileged
      INTEGER }

mscVctDnaCugType OBJECT-TYPE
   SYNTAX     INTEGER  {
                 national(0),
                 international(1) }
   ACCESS     read-write
   STATUS     mandatory
   DESCRIPTION
     "This attribute specifies the Cug type - the Cug is either a national 
      Cug, or an international Cug. International closed user groups are 
      usually established between DTE's for which there is an X.75 
      Gateway between; whereas national closed user groups are usually 
      established between DTE's for which there is no X.75 Gateway 
      between. (National Cugs cannot normally traverse an X.75 
      Gateway).
      If this attribute is set to national, then the Cug is a national Cug, in 
      which case, the dnic should be left at its default value since it is not 
      part of a national Cug. If this attribute is set to international, then 
      the Cug is an international Cug, in which case, the dnic should be 
      set appropriately as part of the Cug interlockCode."
   DEFVAL     { national }
::= { mscVctDnaCugCugOptionsEntry 1 }

mscVctDnaCugDnic OBJECT-TYPE
   SYNTAX     DigitString (SIZE (4))
   ACCESS     read-write
   STATUS     mandatory
   DESCRIPTION
     "This attribute specifies the dnic (Data Network ID Code) of the Cug 
      by which packet networks are identified. This attribute is not 
      applicable if the Cug is a national Cug, as specified by the Cug type 
      attribute. There are usually 1 or 2 dnics assigned per country, for 
      public networks. The U.S. is an exception where each BOC has a 
      dnic. Also, a group of private networks can have its own dnic.
      
      dnic value is not an arbitrary number. It is assigned by international 
      agreement and controlled by ITU-T."
   DEFVAL     { '30303030'H }  -- "0000"
::= { mscVctDnaCugCugOptionsEntry 2 }

mscVctDnaCugInterlockCode OBJECT-TYPE
   SYNTAX     Unsigned32 (0..65535)
   ACCESS     read-write
   STATUS     mandatory
   DESCRIPTION
     "This attribute specifies the Cug identifier of a national or 
      international Cug call. It is an arbitrary number and it also can be 
      called Cug in some descriptions. Interfaces (Dna's) defined with 
      this number can make calls to Dna's with the same interlockCode."
   DEFVAL     { 0 }
::= { mscVctDnaCugCugOptionsEntry 3 }

mscVctDnaCugPreferential OBJECT-TYPE
   SYNTAX     INTEGER  {
                 no(0),
                 yes(1) }
   ACCESS     read-write
   STATUS     mandatory
   DESCRIPTION
     "This attribute, if set to yes indicates that this Cug is the preferential 
      Cug, in which case it will be used during the call establishment 
      phase if the DTE has not explicitly specified a Cug index in the call 
      request packet. If set to no, then this Cug is not the preferential 
      Cug.
      Only one of the Cugs associated with a particular Dna can be the 
      preferential Cug - only one Cug can have this attribute set to yes."
   DEFVAL     { no }
::= { mscVctDnaCugCugOptionsEntry 4 }

mscVctDnaCugOutCalls OBJECT-TYPE
   SYNTAX     INTEGER  {
                 disallowed(0),
                 allowed(1) }
   ACCESS     read-write
   STATUS     mandatory
   DESCRIPTION
     "This attribute, if set to allowed indicates that outgoing calls (from 
      the DTE into the network) can be made using this particular Cug. If 
      set to a value of disallowed, then outgoing calls cannot be made 
      using this Cug - such calls will be cleared by the local DCE.
      This attribute corresponds to the ITU-T 'Outgoing Calls Barred' 
      feature for cugs in that outgoing calls are barred if this attribute is 
      set to a value of disallowed."
   DEFVAL     { allowed }
::= { mscVctDnaCugCugOptionsEntry 5 }

mscVctDnaCugIncCalls OBJECT-TYPE
   SYNTAX     INTEGER  {
                 disallowed(0),
                 allowed(1) }
   ACCESS     read-write
   STATUS     mandatory
   DESCRIPTION
     "This attribute, if set to allowed indicates that incoming calls (from 
      the network to the DTE) can be made using this particular Cug. If 
      set to disallowed, then incoming calls cannot be made using this 
      Cug - such calls will be cleared by the local DCE.
      This attribute corresponds to the ITU-T 'Incoming Calls Barred' 
      feature for Cugs in that incoming calls are barred if this attribute is 
      set to a value of disallowed."
   DEFVAL     { allowed }
::= { mscVctDnaCugCugOptionsEntry 6 }

mscVctDnaCugPrivileged OBJECT-TYPE
   SYNTAX     INTEGER  {
                 no(0),
                 yes(1) }
   ACCESS     read-write
   STATUS     mandatory
   DESCRIPTION
     "This attribute, if set to yes indicates that this Cug is a privileged 
      Cug. In DPN, at least one side of a call setup within a Cug must 
      have the Cug as a privileged Cug. If set to no, then the Cug is not 
      privileged.
      If both the local DTE and the remote DTE subscribe to the Cug, but 
      it is not privileged, then the call will be cleared. This attribute is 
      typically used for a host DTE which must accept calls from many 
      other DTE's in which case the other DTE's cannot call one another, 
      but can call the host. In this example, the host would have the 
      privileged Cug, and the other DTE's would belong to the same Cug, 
      but it would not be privileged."
   DEFVAL     { yes }
::= { mscVctDnaCugCugOptionsEntry 7 }


-- GvcIf/n Dna/n HgMember
-- This component specifies the Hunt Groups to which this member 
-- belongs. A hunt group member subscribes to at least one hunt 
-- group.

mscVctDnaHgM OBJECT IDENTIFIER ::= { mscVctDna 3 }



mscVctDnaHgMRowStatusTable OBJECT-TYPE
   SYNTAX     SEQUENCE OF MscVctDnaHgMRowStatusEntry
   ACCESS     not-accessible
   STATUS     mandatory
   DESCRIPTION
     "This entry controls the addition and deletion of 
      mscVctDnaHgM components."
::= { mscVctDnaHgM 1 }

mscVctDnaHgMRowStatusEntry OBJECT-TYPE
   SYNTAX     MscVctDnaHgMRowStatusEntry
   ACCESS     not-accessible
   STATUS     mandatory
   DESCRIPTION
     "A single entry in the table represents a single 
      mscVctDnaHgM component."
   INDEX {
      mscVctIndex,
      mscVctDnaIndex,
      mscVctDnaHgMIndex }
::= { mscVctDnaHgMRowStatusTable 1 }

MscVctDnaHgMRowStatusEntry ::= SEQUENCE {
   mscVctDnaHgMRowStatus
      RowStatus,
   mscVctDnaHgMComponentName
      DisplayString,
   mscVctDnaHgMStorageType
      StorageType,
   mscVctDnaHgMIndex
      NonReplicated }

mscVctDnaHgMRowStatus OBJECT-TYPE
   SYNTAX     RowStatus 
   ACCESS     read-write
   STATUS     mandatory
   DESCRIPTION
     "This variable is used as the basis for SNMP naming of
      mscVctDnaHgM components.
      These components can be added and deleted."
::= { mscVctDnaHgMRowStatusEntry 1 }

mscVctDnaHgMComponentName OBJECT-TYPE
   SYNTAX     DisplayString 
   ACCESS     read-only
   STATUS     mandatory
   DESCRIPTION
     "This variable provides the component's string name for
      use with the ASCII Console Interface"
::= { mscVctDnaHgMRowStatusEntry 2 }

mscVctDnaHgMStorageType OBJECT-TYPE
   SYNTAX     StorageType 
   ACCESS     read-only
   STATUS     mandatory
   DESCRIPTION
     "This variable represents the storage type value for the
      mscVctDnaHgM tables."
::= { mscVctDnaHgMRowStatusEntry 4 }

mscVctDnaHgMIndex OBJECT-TYPE
   SYNTAX     NonReplicated 
   ACCESS     not-accessible
   STATUS     mandatory
   DESCRIPTION
     "This variable represents the index for the mscVctDnaHgM tables."
::= { mscVctDnaHgMRowStatusEntry 10 }

mscVctDnaHgMIfTable OBJECT-TYPE
   SYNTAX     SEQUENCE OF MscVctDnaHgMIfEntry
   ACCESS     not-accessible
   STATUS     mandatory
   DESCRIPTION
     "This group contains the interface parameters between the 
      HuntGroupMember and the Hunt Group server."
::= { mscVctDnaHgM 10 }

mscVctDnaHgMIfEntry OBJECT-TYPE
   SYNTAX     MscVctDnaHgMIfEntry
   ACCESS     not-accessible
   STATUS     mandatory
   DESCRIPTION
     "An entry in the mscVctDnaHgMIfTable."
   INDEX {
      mscVctIndex,
      mscVctDnaIndex,
      mscVctDnaHgMIndex }
::= { mscVctDnaHgMIfTable 1 }

MscVctDnaHgMIfEntry ::= SEQUENCE {
   mscVctDnaHgMAvailabilityUpdateThreshold
      Unsigned32 }

mscVctDnaHgMAvailabilityUpdateThreshold OBJECT-TYPE
   SYNTAX     Unsigned32 (0..4096)
   ACCESS     read-write
   STATUS     mandatory
   DESCRIPTION
     "This attribute indicates the number of channels that have to be freed 
      or occupied before the Availability Message Packet (AMP) is sent 
      to the Hunt Group Server informing it of the status of this interface."
   DEFVAL     { 1 }
::= { mscVctDnaHgMIfEntry 1 }

mscVctDnaHgMOpTable OBJECT-TYPE
   SYNTAX     SEQUENCE OF MscVctDnaHgMOpEntry
   ACCESS     not-accessible
   STATUS     mandatory
   DESCRIPTION
     "This group contains the operational attributes of the 
      HuntGroupMember component."
::= { mscVctDnaHgM 11 }

mscVctDnaHgMOpEntry OBJECT-TYPE
   SYNTAX     MscVctDnaHgMOpEntry
   ACCESS     not-accessible
   STATUS     mandatory
   DESCRIPTION
     "An entry in the mscVctDnaHgMOpTable."
   INDEX {
      mscVctIndex,
      mscVctDnaIndex,
      mscVctDnaHgMIndex }
::= { mscVctDnaHgMOpTable 1 }

MscVctDnaHgMOpEntry ::= SEQUENCE {
   mscVctDnaHgMMaxAvailableChannels
      Unsigned32,
   mscVctDnaHgMAvailableChannels
      Unsigned32,
   mscVctDnaHgMAvailabilityDelta
      INTEGER }

mscVctDnaHgMMaxAvailableChannels OBJECT-TYPE
   SYNTAX     Unsigned32 (0..4096)
   ACCESS     read-only
   STATUS     mandatory
   DESCRIPTION
     "This attribute indicates the maximum number of available channels 
      for this HuntGroupMember."
::= { mscVctDnaHgMOpEntry 1 }

mscVctDnaHgMAvailableChannels OBJECT-TYPE
   SYNTAX     Unsigned32 (0..4096)
   ACCESS     read-only
   STATUS     mandatory
   DESCRIPTION
     "This attribute indicates the number of available channels reported to 
      the hunt group in the Availability Message Packet (AMP). It is 
      modified by adding 1 by the application when a channel is freed and 
      subtracting 1 when a channel is occupied."
::= { mscVctDnaHgMOpEntry 2 }

mscVctDnaHgMAvailabilityDelta OBJECT-TYPE
   SYNTAX     INTEGER (-4096..4096)
   ACCESS     read-only
   STATUS     mandatory
   DESCRIPTION
     "This attribute indicates the net change in the available channels 
      since the last Availability Message Packet (AMP) was sent to the 
      Hunt Group. Once the absolute value of this attribute reaches the 
      availabilityUpdateThreshold an AMP is sent to the host and the 
      availabilityDelta is reset to 0.
      If this attribute is positive it means an increase of the number of 
      available channels. If it is negative it means a decrease in the 
      number of available channels."
::= { mscVctDnaHgMOpEntry 3 }


-- GvcIf/n Dna/n HgM HuntGroupAddress/n
-- This component specifies the Hunt Group address to which this 
-- member belongs. A hunt group member belongs to at least one hunt 
-- group.

mscVctDnaHgMHgAddr OBJECT IDENTIFIER ::= { mscVctDnaHgM 2 }



mscVctDnaHgMHgAddrRowStatusTable OBJECT-TYPE
   SYNTAX     SEQUENCE OF MscVctDnaHgMHgAddrRowStatusEntry
   ACCESS     not-accessible
   STATUS     mandatory
   DESCRIPTION
     "This entry controls the addition and deletion of 
      mscVctDnaHgMHgAddr components."
::= { mscVctDnaHgMHgAddr 1 }

mscVctDnaHgMHgAddrRowStatusEntry OBJECT-TYPE
   SYNTAX     MscVctDnaHgMHgAddrRowStatusEntry
   ACCESS     not-accessible
   STATUS     mandatory
   DESCRIPTION
     "A single entry in the table represents a single 
      mscVctDnaHgMHgAddr component."
   INDEX {
      mscVctIndex,
      mscVctDnaIndex,
      mscVctDnaHgMIndex,
      mscVctDnaHgMHgAddrIndex }
::= { mscVctDnaHgMHgAddrRowStatusTable 1 }

MscVctDnaHgMHgAddrRowStatusEntry ::= SEQUENCE {
   mscVctDnaHgMHgAddrRowStatus
      RowStatus,
   mscVctDnaHgMHgAddrComponentName
      DisplayString,
   mscVctDnaHgMHgAddrStorageType
      StorageType,
   mscVctDnaHgMHgAddrIndex
      Integer32 }

mscVctDnaHgMHgAddrRowStatus OBJECT-TYPE
   SYNTAX     RowStatus 
   ACCESS     read-write
   STATUS     mandatory
   DESCRIPTION
     "This variable is used as the basis for SNMP naming of
      mscVctDnaHgMHgAddr components.
      These components can be added and deleted."
::= { mscVctDnaHgMHgAddrRowStatusEntry 1 }

mscVctDnaHgMHgAddrComponentName OBJECT-TYPE
   SYNTAX     DisplayString 
   ACCESS     read-only
   STATUS     mandatory
   DESCRIPTION
     "This variable provides the component's string name for
      use with the ASCII Console Interface"
::= { mscVctDnaHgMHgAddrRowStatusEntry 2 }

mscVctDnaHgMHgAddrStorageType OBJECT-TYPE
   SYNTAX     StorageType 
   ACCESS     read-only
   STATUS     mandatory
   DESCRIPTION
     "This variable represents the storage type value for the
      mscVctDnaHgMHgAddr tables."
::= { mscVctDnaHgMHgAddrRowStatusEntry 4 }

mscVctDnaHgMHgAddrIndex OBJECT-TYPE
   SYNTAX     Integer32 (0..1)
   ACCESS     not-accessible
   STATUS     mandatory
   DESCRIPTION
     "This variable represents the index for the mscVctDnaHgMHgAddr tables."
::= { mscVctDnaHgMHgAddrRowStatusEntry 10 }

mscVctDnaHgMHgAddrAddrTable OBJECT-TYPE
   SYNTAX     SEQUENCE OF MscVctDnaHgMHgAddrAddrEntry
   ACCESS     not-accessible
   STATUS     mandatory
   DESCRIPTION
     "This group contains attributes common to all DNAs. Every DNA 
      used in the network is defined with this group of 2 attributes. String 
      of address digits complemented by the NPI."
::= { mscVctDnaHgMHgAddr 10 }

mscVctDnaHgMHgAddrAddrEntry OBJECT-TYPE
   SYNTAX     MscVctDnaHgMHgAddrAddrEntry
   ACCESS     not-accessible
   STATUS     mandatory
   DESCRIPTION
     "An entry in the mscVctDnaHgMHgAddrAddrTable."
   INDEX {
      mscVctIndex,
      mscVctDnaIndex,
      mscVctDnaHgMIndex,
      mscVctDnaHgMHgAddrIndex }
::= { mscVctDnaHgMHgAddrAddrTable 1 }

MscVctDnaHgMHgAddrAddrEntry ::= SEQUENCE {
   mscVctDnaHgMHgAddrNumberingPlanIndicator
      INTEGER,
   mscVctDnaHgMHgAddrDataNetworkAddress
      DigitString }

mscVctDnaHgMHgAddrNumberingPlanIndicator OBJECT-TYPE
   SYNTAX     INTEGER  {
                 x121(0),
                 e164(1) }
   ACCESS     read-write
   STATUS     mandatory
   DESCRIPTION
     "This attribute indicates the Numbering Plan Indicator (NPI) the Dna 
      that is entered. Address may belong to X.121 or E.164 plans."
   DEFVAL     { x121 }
::= { mscVctDnaHgMHgAddrAddrEntry 1 }

mscVctDnaHgMHgAddrDataNetworkAddress OBJECT-TYPE
   SYNTAX     DigitString (SIZE (1..15))
   ACCESS     read-write
   STATUS     mandatory
   DESCRIPTION
     "This attribute contains digits which form unique identifier of the 
      customer interface. It can be compared (approximation only) 
      telephone number where phone number identifies unique telephone 
      set. Dna digits are selected and assigned by network operators."
::= { mscVctDnaHgMHgAddrAddrEntry 2 }


-- Fruni/n Dlci/n dc
-- This component defines direct call options for calls issued without 
-- operator intervention. Connection is complete and can be initiated 
-- automatically. Frequency of connection tries is controlled by retry 
-- timer.

mscVctDc OBJECT IDENTIFIER ::= { mscVct 3 }



mscVctDcRowStatusTable OBJECT-TYPE
   SYNTAX     SEQUENCE OF MscVctDcRowStatusEntry
   ACCESS     not-accessible
   STATUS     mandatory
   DESCRIPTION
     "This entry controls the addition and deletion of 
      mscVctDc components."
::= { mscVctDc 1 }

mscVctDcRowStatusEntry OBJECT-TYPE
   SYNTAX     MscVctDcRowStatusEntry
   ACCESS     not-accessible
   STATUS     mandatory
   DESCRIPTION
     "A single entry in the table represents a single 
      mscVctDc component."
   INDEX {
      mscVctIndex,
      mscVctDcIndex }
::= { mscVctDcRowStatusTable 1 }

MscVctDcRowStatusEntry ::= SEQUENCE {
   mscVctDcRowStatus
      RowStatus,
   mscVctDcComponentName
      DisplayString,
   mscVctDcStorageType
      StorageType,
   mscVctDcIndex
      Integer32 }

mscVctDcRowStatus OBJECT-TYPE
   SYNTAX     RowStatus 
   ACCESS     read-write
   STATUS     mandatory
   DESCRIPTION
     "This variable is used as the basis for SNMP naming of
      mscVctDc components.
      These components can be added and deleted."
::= { mscVctDcRowStatusEntry 1 }

mscVctDcComponentName OBJECT-TYPE
   SYNTAX     DisplayString 
   ACCESS     read-only
   STATUS     mandatory
   DESCRIPTION
     "This variable provides the component's string name for
      use with the ASCII Console Interface"
::= { mscVctDcRowStatusEntry 2 }

mscVctDcStorageType OBJECT-TYPE
   SYNTAX     StorageType 
   ACCESS     read-only
   STATUS     mandatory
   DESCRIPTION
     "This variable represents the storage type value for the
      mscVctDc tables."
::= { mscVctDcRowStatusEntry 4 }

mscVctDcIndex OBJECT-TYPE
   SYNTAX     Integer32 (1..10)
   ACCESS     not-accessible
   STATUS     mandatory
   DESCRIPTION
     "This variable represents the index for the mscVctDc tables."
::= { mscVctDcRowStatusEntry 10 }

mscVctDcOptionsTable OBJECT-TYPE
   SYNTAX     SEQUENCE OF MscVctDcOptionsEntry
   ACCESS     not-accessible
   STATUS     mandatory
   DESCRIPTION
     "Options group defines attributes associated with direct call. It 
      defines complete connection in terms of path and call options. This 
      connection can be permanent (pvc) or switched (svc). It can have 
      facilities. The total number of bytes of facilities including the 
      facility codes, and all of the facility data from all of the four classes 
      of facilities:
      ITU-T_Facilities
      DTE_Facilities
      National_Facilities
      International_Facilities
      must not exceed maximum subnet packet size defined for the whole 
      network in ModuleData Vcs component."
::= { mscVctDc 10 }

mscVctDcOptionsEntry OBJECT-TYPE
   SYNTAX     MscVctDcOptionsEntry
   ACCESS     not-accessible
   STATUS     mandatory
   DESCRIPTION
     "An entry in the mscVctDcOptionsTable."
   INDEX {
      mscVctIndex,
      mscVctDcIndex }
::= { mscVctDcOptionsTable 1 }

MscVctDcOptionsEntry ::= SEQUENCE {
   mscVctDcLocalNpi
      INTEGER,
   mscVctDcLocalDna
      DigitString,
   mscVctDcRemoteNpi
      INTEGER,
   mscVctDcRemoteDna
      DigitString,
   mscVctDcRemoteLcn
      Unsigned32,
   mscVctDcType
      INTEGER,
   mscVctDcSvcAutoCallRetry
      INTEGER,
   mscVctDcUserData
      HexString,
   mscVctDcDiscardPriority
      INTEGER,
   mscVctDcDataPath
      INTEGER,
   mscVctDcCugIndex
      Unsigned32,
   mscVctDcCugType
      INTEGER }

mscVctDcLocalNpi OBJECT-TYPE
   SYNTAX     INTEGER  {
                 x121(0),
                 e164(1) }
   ACCESS     read-write
   STATUS     mandatory
   DESCRIPTION
     "This attribute specifies the Numbering Plan Indicator (NPI) of the 
      localDna."
   DEFVAL     { x121 }
::= { mscVctDcOptionsEntry 1 }

mscVctDcLocalDna OBJECT-TYPE
   SYNTAX     DigitString (SIZE (0..15))
   ACCESS     read-write
   STATUS     mandatory
   DESCRIPTION
     "This attribute specifies the Data Network Address (Dna) of the local 
      DTE. This address is used in formatting of call request to 
      remoteDna."
::= { mscVctDcOptionsEntry 2 }

mscVctDcRemoteNpi OBJECT-TYPE
   SYNTAX     INTEGER  {
                 x121(0),
                 e164(1) }
   ACCESS     read-write
   STATUS     mandatory
   DESCRIPTION
     "Remote numbering Plan Indicator (Npi) indicates the numbering 
      plan used in the remoteDna."
   DEFVAL     { x121 }
::= { mscVctDcOptionsEntry 3 }

mscVctDcRemoteDna OBJECT-TYPE
   SYNTAX     DigitString (SIZE (1..15))
   ACCESS     read-write
   STATUS     mandatory
   DESCRIPTION
     "This attribute specifies the Data Network Address (Dna) of the 
      remote. This is the called (destination) DTE address (Dna) to which 
      this direct call will be sent. Initially, the called DTE address 
      attribute must be present, that is, there must be a valid destination 
      address. However, it may be possible in the future to configure the 
      direct call with a mnemonic address, in which case, this attribute 
      will contain a zero-length Dna, and the mnemonic address will be 
      carried as one of the facilities."
::= { mscVctDcOptionsEntry 4 }

mscVctDcRemoteLcn OBJECT-TYPE
   SYNTAX     Unsigned32 (0..4095)
   ACCESS     read-write
   STATUS     mandatory
   DESCRIPTION
     "This attribute provides the remote LCN (Logical Channel Number) 
      - it is used only for PVCs, where attribute type is set to 
      permanentMaster or permanentSlave or permanentBackupSlave.
      In switched case, value of remoteLcn is not known when call 
      request is made."
   DEFVAL     { 0 }
::= { mscVctDcOptionsEntry 5 }

mscVctDcType OBJECT-TYPE
   SYNTAX     INTEGER  {
                 switched(0),
                 permanentMaster(1),
                 permanentSlave(2),
                 permanentBackupSlave(3),
                 permanentSlaveWithBackup(4),
                 spvcMaster(5),
                 spvcSlave(6),
                 spvcBackupSlave(7),
                 spvcSlaveWithBackup(8) }
   ACCESS     read-write
   STATUS     mandatory
   DESCRIPTION
     "This attribute specifies the type of Vc call:
      switched,
      permanentMaster, 
      permanentSlave, 
      permanentSlaveWithBackup,
      permanentBackupSlave,
      spvcMaster,
      spvcSlave,
      spvcSlaveWithBackup,
      spvcBackupSlave.
      
      If the value of this attribute is set to switched then the remote end
      must also be provisioned as switched. No information at the remote
      end is defined about this switched interface.
      
      If the value is set to permanentMaster, then a permanent 
      connection will be established between 2 ends. The remote end 
      must be defined as a permanentSlave, permanentBackupSlave or 
      permanentSlaveWithBackup. The connection cannot be established 
      if the remote end is defined as anything else. The end defined as 
      permanentMaster always initiates the calls. It will attempt to call 
      once per minute.
      
      If the value is set to permanentSlave then a permanent connection 
      will be established between 2 ends. The remote end must be defined 
      as a permanentMaster. The connection cannot be established if the 
      remote end is defined as anything else. The permanentSlave end 
      will attempt to call once per minute.
      
      If the value is set to permanentSlaveWithBackup then a permanent 
      connection will be established between the two ends. The remote 
      end must be defined as a permanentMaster. The connection cannot 
      be established if the remote interface end is defined as anything 
      else. The permanentSlaveWithBackup end will attempt to call once 
      per minute. When type is set to permanentSlaveWithBackup 
      connection will be cleared if interface becomes unavailable. This 
      enables a retry of the connection which can be redirected to 
      permanentBackupSlave.
      
      If the value is set to permanentBackupSlave then a permanent 
      connection will be established between the 2 ends only if the 
      permanentMaster end is disconnected from the 
      permanentSlaveWithBackup end and a backup call is established 
      by the redirection system. If the permanentSlaveWithBackup 
      interface becomes visible again, the permanentBackupSlave end is 
      disconnected and the permanentSlaveWithBackup end is 
      reconnected to the permanentMaster end. The 
      permanentBackupSlave end does not try to establish pvc call.
      
      If the value is set to spvcMaster, then a permanent connection will 
      be established between two ends, with resiliency at the NNI(s), if 
      the connection transits across two or more networks. The remote 
      end, which may be in the same network, or an external network that 
      is reachable via Frame Relay NNIs, must be defined as either a 
      spvcSlave, spvcBackupSlave or spvcSlaveWithBackup. The 
      connection cannot be established if the remote end is defined as 
      anything else. The end defined as spvcMaster always initiates the 
      calls. It will attempt to call once per minute. The call is attempted 
      by the spvcMaster, and accepted by the remote end, only if all three 
      of the following conditions are satisfied at both ends:
      1. The datalink layer must be operational
      2. The LMI procedures must be in normal condition (i.e. no service 
      affecting condition)
      3. If the LMI side attribute is provisioned to both, the A-bit received 
      from the interface must be Active. If the LMI side attribute is not 
      provisioned to both, this condition does not apply.
      After a call is cleared, the end defined as spvcMaster attempts to 
      retry the call according to the rule for the clear cause. If the call is 
      cleared or rejected due to the failure of one of the three conditions 
      indicated above, or due to unavailability of resources along any 
      point in the connection path, the call will be retried after 60 
      seconds. For all other causes, such as loss of service at an NNI, the 
      call will be retried immediately.
      
      If the value is set to spvcSlave then a SPVC connection will be 
      established between two ends. The remote end must be defined as a 
      spvcMaster. The connection cannot be established if the remote end 
      is defined as anything else. The spvcSlave end never attempts to 
      call.
      
      If the value is set to spvcSlaveWithBackup then a SPVC connection 
      will be established between the two ends. The remote end must be 
      defined as a spvcMaster. The connection cannot be established if 
      the remote interface end is defined as anything else. Unlike a 
      permanentSlaveWithBackup end, the spvcSlaveWithBackup end 
      never attempts to call. If the value is set to spvcSlaveWithBackup, 
      the connection will be cleared if the interface becomes unavailable. 
      This enables a retry of the connection by the spvcMaster end, which 
      may be redirected to an end that is set to spvcBackupSlave.
      
      If the value is set to spvcBackupSlave then a SPVC connection will 
      be established between the two ends only if the spvcMaster end is 
      disconnected from the spvcSlaveWithBackup, end and a backup 
      call is redirected by the call redirection system. Unlike the 
      permanent connection, if the spvcSlaveWithBackup interface 
      becomes available again, the spvcBackupSlave end is not 
      disconnected and the spvcSlaveWithBackup end is not reconnected 
      to the spvcMaster end. Neither the spvcBackupSlave nor the 
      spvcSlaveWithBackup end try to establish a SPVC call."
   DEFVAL     { switched }
::= { mscVctDcOptionsEntry 6 }

mscVctDcSvcAutoCallRetry OBJECT-TYPE
   SYNTAX     INTEGER  {
                 no(0),
                 yes(1) }
   ACCESS     read-write
   STATUS     mandatory
   DESCRIPTION
     "svcAutoCallRetry is used only for switched calls, in which case the 
      attribute type is set to switched. Otherwise, this attribute is ignored 
      by the Vcs.
      This attribute, if set to yes for Svc, indicates that the Vc will 
      continually try to establish the SVC rather than clearing the Vc after 
      the first unsuccessful call attempt. Further, if the call fails while in 
      data transfer phase, then the Vc will automatically attempt to 
      reconnect. The call attempts are made by the Vc once per time 
      provisioned in InterfaceOptions as callRetryTimer, repeatedly. If set 
      to no for SVCs, then the Vc behaves in the standard mode, making a 
      single call attempt."
   DEFVAL     { no }
::= { mscVctDcOptionsEntry 7 }

mscVctDcUserData OBJECT-TYPE
   SYNTAX     HexString (SIZE (0..128))
   ACCESS     read-write
   STATUS     mandatory
   DESCRIPTION
     "This attribute contains the user data, if present. userData is a 0 to 16 
      length string which is appended to the call request packet that is 
      presented to the called (destination) DTE.
      
      User data can be a 0 to 128 byte string for fast select calls; 
      otherwise it is 0 to 16 byte string. 
      
      Fast select calls are indicated as such using the X.25 ITU-T facility 
      for 'Reverse Charging'.
      
      The length of the user data attribute is not verified during service 
      provisioning. If more than 16 bytes of user data is specified on a 
      call without the fast select option, then the call is cleared with a 
      clear cause of 'local procedure error', and a diagnostic code of 39 
      (as defined in the ITU-T X.25 Recommendation)."
::= { mscVctDcOptionsEntry 8 }

mscVctDcDiscardPriority OBJECT-TYPE
   SYNTAX     INTEGER  {
                 normal(0),
                 high(1),
                 useDnaDefPriority(3) }
   ACCESS     read-write
   STATUS     mandatory
   DESCRIPTION
     "This attribute specifies the discard priority for outgoing call using 
      this DLCI. 
      
      The discard priority has three provisioning values: normal, high, 
      and useDnaDefPriority. Traffic with normal priority are discarded 
      first than the traffic with high priority. The Dna default value 
      (provisioned by outDefaultPriority) is taken if this attribute is set to 
      the value useDnaDefPriority.
      
      The default of discardPriority is useDnaDefPriority."
   DEFVAL     { useDnaDefPriority }
::= { mscVctDcOptionsEntry 10 }

mscVctDcDataPath OBJECT-TYPE
   SYNTAX     INTEGER  {
                 dprsOnly(0),
                 dprsMcsOnly(1),
                 dprsMcsFirst(2),
                 useDnaValue(3) }
   ACCESS     read-write
   STATUS     mandatory
   DESCRIPTION
     "This attribute specifies the data path to be used by Virtual Circuits 
      on this interface. The value of the dataPath attribute in the Dna 
      component is overridden by this attribute if the value is not 
      useDnaValue.
      
      This value applies to the connection after data transfer state is 
      reached. All the data and control trafic will be sent using this data 
      path. If the provisioned dataPath is not available the connection is 
      not established.
      
      The value of the dataPath is signalled by both ends of the 
      connection. If this value is not the same at both ends dprsOnly is 
      used for the duration of the connection.
      
      A virtual circuit connection is always established using dprsOnly 
      even if this attribute is provisioned as some other value.
      
      dprsOnly - dynamic packet routing system is used
      
      dprsMcsOnly - dprs Multi-Service Cut-Through Switching path is 
      used.
      
      dprsMcsFirst - dprs Multi-Service Cut-Through Switching path is 
      used if it is available. If it is not avaliable dprsOnly is used.
      
      useDnaValue - use the value provisioned in Dna component."
   DEFVAL     { dprsOnly }
::= { mscVctDcOptionsEntry 11 }

mscVctDcCugIndex OBJECT-TYPE
   SYNTAX     Unsigned32 (0..255)
   ACCESS     read-write
   STATUS     mandatory
   DESCRIPTION
     "This attribute specifies the CUG index which is to be signalled in 
      PVC call requests to the remote end.
      
      The type of CUG signalling is defined in attribute cugType in this 
      component."
   DEFVAL     { 0 }
::= { mscVctDcOptionsEntry 13 }

mscVctDcCugType OBJECT-TYPE
   SYNTAX     INTEGER  {
                 doNotSignal(0),
                 cug(3),
                 cugOa(9) }
   ACCESS     read-write
   STATUS     mandatory
   DESCRIPTION
     "This attribute specifies the type of CUG signalling to be used in 
      PVC call request. Index of CUG to be used is defined in attribute 
      cugIndex in this component.
      
      Possible values are:
      cug - signal cug
      cugOa - signal cug with outgoing access
      doNotSignal - no CUG in call request"
   DEFVAL     { doNotSignal }
::= { mscVctDcOptionsEntry 14 }

mscVctDcCfaTable OBJECT-TYPE
   SYNTAX     SEQUENCE OF MscVctDcCfaEntry
   ACCESS     not-accessible
   STATUS     mandatory
   DESCRIPTION
     "This is the i'th ITU-T facility required for this direct call. Within 
      the provisioning system, the user specifies the facility code along 
      with the facility parameters. The facility is represented internally as 
      a hexadecimal string following the X.25 ITU-T representation for 
      facility data.
      The user specifies the facility code when adding, changing or 
      deleting a facility. The upper two bits of the facility code indicate 
      the class of facility. From the class of the facility, one can derive the 
      number of bytes of facility data, as follows:
      Class A - 1 byte of fax data
      Class B - 2 bytes of fax data
      Class C - 3 bytes of fax data
      Class D - variable length of fax data."
::= { mscVctDc 267 }

mscVctDcCfaEntry OBJECT-TYPE
   SYNTAX     MscVctDcCfaEntry
   ACCESS     not-accessible
   STATUS     mandatory
   DESCRIPTION
     "An entry in the mscVctDcCfaTable."
   INDEX {
      mscVctIndex,
      mscVctDcIndex,
      mscVctDcCfaIndex }
::= { mscVctDcCfaTable 1 }

MscVctDcCfaEntry ::= SEQUENCE {
   mscVctDcCfaIndex
      Integer32,
   mscVctDcCfaValue
      HexString,
   mscVctDcCfaRowStatus
      RowStatus }

mscVctDcCfaIndex OBJECT-TYPE
   SYNTAX     Integer32 (1 | 2 | 3 | 4 | 9 | 66 | 67 | 68 | 71 | 72 | 73 | 196 | 198)
   ACCESS     not-accessible
   STATUS     mandatory
   DESCRIPTION
     "This variable represents the index for the mscVctDcCfaTable."
::= { mscVctDcCfaEntry 1 }

mscVctDcCfaValue OBJECT-TYPE
   SYNTAX     HexString (SIZE (0..128))
   ACCESS     read-write
   STATUS     mandatory
   DESCRIPTION
     "This variable represents an individual value for the
      mscVctDcCfaTable."
::= { mscVctDcCfaEntry 2 }

mscVctDcCfaRowStatus OBJECT-TYPE
   SYNTAX     RowStatus 
   ACCESS     write-only
   STATUS     mandatory
   DESCRIPTION
     "This variable is used to control the addition and deletion 
      of individual values of the mscVctDcCfaTable."
::= { mscVctDcCfaEntry 3 }

mscVctDcDfaTable OBJECT-TYPE
   SYNTAX     SEQUENCE OF MscVctDcDfaEntry
   ACCESS     not-accessible
   STATUS     mandatory
   DESCRIPTION
     "This is the i'th DTE facility required for this direct call. Within the 
      provisioning system, the user specifies the facility code along with 
      the facility parameters. The facility is represented internally as a 
      hexadecimal string following the X.25 ITU-T representation for 
      facility data."
::= { mscVctDc 268 }

mscVctDcDfaEntry OBJECT-TYPE
   SYNTAX     MscVctDcDfaEntry
   ACCESS     not-accessible
   STATUS     mandatory
   DESCRIPTION
     "An entry in the mscVctDcDfaTable."
   INDEX {
      mscVctIndex,
      mscVctDcIndex,
      mscVctDcDfaIndex }
::= { mscVctDcDfaTable 1 }

MscVctDcDfaEntry ::= SEQUENCE {
   mscVctDcDfaIndex
      Integer32,
   mscVctDcDfaValue
      HexString,
   mscVctDcDfaRowStatus
      RowStatus }

mscVctDcDfaIndex OBJECT-TYPE
   SYNTAX     Integer32 (10 | 11 | 201 | 202 | 203 | 210 | 211)
   ACCESS     not-accessible
   STATUS     mandatory
   DESCRIPTION
     "This variable represents the index for the mscVctDcDfaTable."
::= { mscVctDcDfaEntry 1 }

mscVctDcDfaValue OBJECT-TYPE
   SYNTAX     HexString (SIZE (0..128))
   ACCESS     read-write
   STATUS     mandatory
   DESCRIPTION
     "This variable represents an individual value for the
      mscVctDcDfaTable."
::= { mscVctDcDfaEntry 2 }

mscVctDcDfaRowStatus OBJECT-TYPE
   SYNTAX     RowStatus 
   ACCESS     write-only
   STATUS     mandatory
   DESCRIPTION
     "This variable is used to control the addition and deletion 
      of individual values of the mscVctDcDfaTable."
::= { mscVctDcDfaEntry 3 }

mscVctDcNfaTable OBJECT-TYPE
   SYNTAX     SEQUENCE OF MscVctDcNfaEntry
   ACCESS     not-accessible
   STATUS     obsolete
   DESCRIPTION
     "This is the i'th National facility required for this direct call. Within 
      the provisioning system, the user specifies the facility code along 
      with the facility parameters. The facility is represented internally as 
      a hexadecimal string following the X.25 ITU-T representation for 
      facility data.
      
      Two explicit attributes discardPriority and transferPriority are 
      created to replace H.01 and H.30 in the group 
      VcsDirectCallOptionsProv of this file. The migrate escape here 
      propagates the old provisioning data under H.01 and H.30 into 
      discardPriority and transferPriority. 
      
      The rule of the above propagation are: 0 in H.01 is equivalent to 
      discardPriority 0; 1 in H.01 is equivalent to discardPriority 1. And 
      0 in H.30 is equivalent to transferPriority normal; 1 in H.30 is 
      equivalent to transferPriority high.
      
      Please refer to discardPriority and transferPriority for more 
      information on how to use them."
::= { mscVctDc 269 }

mscVctDcNfaEntry OBJECT-TYPE
   SYNTAX     MscVctDcNfaEntry
   ACCESS     not-accessible
   STATUS     obsolete
   DESCRIPTION
     "An entry in the mscVctDcNfaTable."
   INDEX {
      mscVctIndex,
      mscVctDcIndex,
      mscVctDcNfaIndex }
::= { mscVctDcNfaTable 1 }

MscVctDcNfaEntry ::= SEQUENCE {
   mscVctDcNfaIndex
      Integer32,
   mscVctDcNfaValue
      HexString,
   mscVctDcNfaRowStatus
      RowStatus }

mscVctDcNfaIndex OBJECT-TYPE
   SYNTAX     Integer32 (1 | 48 | 127 | 212)
   ACCESS     not-accessible
   STATUS     obsolete
   DESCRIPTION
     "This variable represents the index for the mscVctDcNfaTable."
::= { mscVctDcNfaEntry 1 }

mscVctDcNfaValue OBJECT-TYPE
   SYNTAX     HexString (SIZE (0..128))
   ACCESS     read-write
   STATUS     obsolete
   DESCRIPTION
     "This variable represents an individual value for the
      mscVctDcNfaTable."
::= { mscVctDcNfaEntry 2 }

mscVctDcNfaRowStatus OBJECT-TYPE
   SYNTAX     RowStatus 
   ACCESS     write-only
   STATUS     obsolete
   DESCRIPTION
     "This variable is used to control the addition and deletion 
      of individual values of the mscVctDcNfaTable."
::= { mscVctDcNfaEntry 3 }

mscVctDcIfaTable OBJECT-TYPE
   SYNTAX     SEQUENCE OF MscVctDcIfaEntry
   ACCESS     not-accessible
   STATUS     mandatory
   DESCRIPTION
     "This is the i'th International facility required for this direct call. 
      Within the provisioning system, the user specifies the facility code 
      along with the facility parameters. The facility is represented 
      internally as a hexadecimal string following the X.25 ITU-T 
      representation for facility data."
::= { mscVctDc 270 }

mscVctDcIfaEntry OBJECT-TYPE
   SYNTAX     MscVctDcIfaEntry
   ACCESS     not-accessible
   STATUS     mandatory
   DESCRIPTION
     "An entry in the mscVctDcIfaTable."
   INDEX {
      mscVctIndex,
      mscVctDcIndex,
      mscVctDcIfaIndex }
::= { mscVctDcIfaTable 1 }

MscVctDcIfaEntry ::= SEQUENCE {
   mscVctDcIfaIndex
      Integer32,
   mscVctDcIfaValue
      HexString,
   mscVctDcIfaRowStatus
      RowStatus }

mscVctDcIfaIndex OBJECT-TYPE
   SYNTAX     Integer32 (1..255)
   ACCESS     not-accessible
   STATUS     mandatory
   DESCRIPTION
     "This variable represents the index for the mscVctDcIfaTable."
::= { mscVctDcIfaEntry 1 }

mscVctDcIfaValue OBJECT-TYPE
   SYNTAX     HexString (SIZE (0..128))
   ACCESS     read-write
   STATUS     mandatory
   DESCRIPTION
     "This variable represents an individual value for the
      mscVctDcIfaTable."
::= { mscVctDcIfaEntry 2 }

mscVctDcIfaRowStatus OBJECT-TYPE
   SYNTAX     RowStatus 
   ACCESS     write-only
   STATUS     mandatory
   DESCRIPTION
     "This variable is used to control the addition and deletion 
      of individual values of the mscVctDcIfaTable."
::= { mscVctDcIfaEntry 3 }


-- ... Vc()
-- This component defines display of general Vc dynamic attributes

mscVctVc OBJECT IDENTIFIER ::= { mscVct 4 }



mscVctVcRowStatusTable OBJECT-TYPE
   SYNTAX     SEQUENCE OF MscVctVcRowStatusEntry
   ACCESS     not-accessible
   STATUS     mandatory
   DESCRIPTION
     "This entry controls the addition and deletion of 
      mscVctVc components."
::= { mscVctVc 1 }

mscVctVcRowStatusEntry OBJECT-TYPE
   SYNTAX     MscVctVcRowStatusEntry
   ACCESS     not-accessible
   STATUS     mandatory
   DESCRIPTION
     "A single entry in the table represents a single 
      mscVctVc component."
   INDEX {
      mscVctIndex,
      mscVctVcIndex }
::= { mscVctVcRowStatusTable 1 }

MscVctVcRowStatusEntry ::= SEQUENCE {
   mscVctVcRowStatus
      RowStatus,
   mscVctVcComponentName
      DisplayString,
   mscVctVcStorageType
      StorageType,
   mscVctVcIndex
      NonReplicated }

mscVctVcRowStatus OBJECT-TYPE
   SYNTAX     RowStatus 
   ACCESS     read-only
   STATUS     mandatory
   DESCRIPTION
     "This variable is used as the basis for SNMP naming of
      mscVctVc components.
      These components cannot be added nor deleted."
::= { mscVctVcRowStatusEntry 1 }

mscVctVcComponentName OBJECT-TYPE
   SYNTAX     DisplayString 
   ACCESS     read-only
   STATUS     mandatory
   DESCRIPTION
     "This variable provides the component's string name for
      use with the ASCII Console Interface"
::= { mscVctVcRowStatusEntry 2 }

mscVctVcStorageType OBJECT-TYPE
   SYNTAX     StorageType 
   ACCESS     read-only
   STATUS     mandatory
   DESCRIPTION
     "This variable represents the storage type value for the
      mscVctVc tables."
::= { mscVctVcRowStatusEntry 4 }

mscVctVcIndex OBJECT-TYPE
   SYNTAX     NonReplicated 
   ACCESS     not-accessible
   STATUS     mandatory
   DESCRIPTION
     "This variable represents the index for the mscVctVc tables."
::= { mscVctVcRowStatusEntry 10 }

mscVctVcCadTable OBJECT-TYPE
   SYNTAX     SEQUENCE OF MscVctVcCadEntry
   ACCESS     not-accessible
   STATUS     mandatory
   DESCRIPTION
     "This group represents operational call data related to General Vc. It 
      can be displayed only for General Vc which is created by 
      application."
::= { mscVctVc 10 }

mscVctVcCadEntry OBJECT-TYPE
   SYNTAX     MscVctVcCadEntry
   ACCESS     not-accessible
   STATUS     mandatory
   DESCRIPTION
     "An entry in the mscVctVcCadTable."
   INDEX {
      mscVctIndex,
      mscVctVcIndex }
::= { mscVctVcCadTable 1 }

MscVctVcCadEntry ::= SEQUENCE {
   mscVctVcType
      INTEGER,
   mscVctVcState
      INTEGER,
   mscVctVcPreviousState
      INTEGER,
   mscVctVcDiagnosticCode
      Unsigned32,
   mscVctVcPreviousDiagnosticCode
      Unsigned32,
   mscVctVcCalledNpi
      INTEGER,
   mscVctVcCalledDna
      DigitString,
   mscVctVcCalledLcn
      Unsigned32,
   mscVctVcCallingNpi
      INTEGER,
   mscVctVcCallingDna
      DigitString,
   mscVctVcCallingLcn
      Unsigned32,
   mscVctVcAccountingEnabled
      INTEGER,
   mscVctVcFastSelectCall
      INTEGER,
   mscVctVcLocalRxPktSize
      INTEGER,
   mscVctVcLocalTxPktSize
      INTEGER,
   mscVctVcLocalTxWindowSize
      Unsigned32,
   mscVctVcLocalRxWindowSize
      Unsigned32,
   mscVctVcPathReliability
      INTEGER,
   mscVctVcAccountingEnd
      INTEGER,
   mscVctVcPriority
      INTEGER,
   mscVctVcSegmentSize
      Unsigned32,
   mscVctVcSubnetTxPktSize
      INTEGER,
   mscVctVcSubnetTxWindowSize
      Unsigned32,
   mscVctVcSubnetRxPktSize
      INTEGER,
   mscVctVcSubnetRxWindowSize
      Unsigned32,
   mscVctVcMaxSubnetPktSize
      Unsigned32,
   mscVctVcTransferPriorityToNetwork
      INTEGER,
   mscVctVcTransferPriorityFromNetwork
      INTEGER }

mscVctVcType OBJECT-TYPE
   SYNTAX     INTEGER  {
                 svc(0),
                 pvc(1) }
   ACCESS     read-only
   STATUS     mandatory
   DESCRIPTION
     "This attribute displays the type of call, pvc or svc. type is provided 
      at provisioning time."
::= { mscVctVcCadEntry 1 }

mscVctVcState OBJECT-TYPE
   SYNTAX     INTEGER  {
                 creating(0),
                 readyP1(1),
                 dteWaitingP2(2),
                 dceWaitingP3(3),
                 dataTransferP4(4),
                 unsupportedP5(5),
                 dteClearRequestP6(6),
                 dceClearIndicationP7(7),
                 termination(8) }
   ACCESS     read-only
   STATUS     mandatory
   DESCRIPTION
     "This attribute displays the state of call control. P5 state is not 
      supported but is listed for completness. Transitions from one state to 
      another take very short time. state most often displayed is 
      dataTransferP4."
::= { mscVctVcCadEntry 2 }

mscVctVcPreviousState OBJECT-TYPE
   SYNTAX     INTEGER  {
                 creating(0),
                 readyP1(1),
                 dteWaitingP2(2),
                 dceWaitingP3(3),
                 dataTransferP4(4),
                 unsupportedP5(5),
                 dteClearRequestP6(6),
                 dceClearIndicationP7(7),
                 termination(8) }
   ACCESS     read-only
   STATUS     mandatory
   DESCRIPTION
     "This attribute displays the previous state of call control. This is a 
      valuable field to determine how the processing is progressing."
::= { mscVctVcCadEntry 3 }

mscVctVcDiagnosticCode OBJECT-TYPE
   SYNTAX     Unsigned32 (0..255)
   ACCESS     read-only
   STATUS     mandatory
   DESCRIPTION
     "This attribute displays the internal substate of call control. It is used 
      to further refine state of call processing."
::= { mscVctVcCadEntry 4 }

mscVctVcPreviousDiagnosticCode OBJECT-TYPE
   SYNTAX     Unsigned32 (0..255)
   ACCESS     read-only
   STATUS     mandatory
   DESCRIPTION
     "This attribute displays the internal substate of call control. It is used 
      to further refine state of call processing."
::= { mscVctVcCadEntry 5 }

mscVctVcCalledNpi OBJECT-TYPE
   SYNTAX     INTEGER  {
                 x121(0),
                 e164(1) }
   ACCESS     read-only
   STATUS     mandatory
   DESCRIPTION
     "This attribute displays the Numbering Plan Indicator (NPI) of the 
      called end."
::= { mscVctVcCadEntry 6 }

mscVctVcCalledDna OBJECT-TYPE
   SYNTAX     DigitString (SIZE (1..15))
   ACCESS     read-only
   STATUS     mandatory
   DESCRIPTION
     "This attribute displays the Data Network Address (Dna) of the 
      called (destination) DTE to which this call is sent. This address if 
      defined at recieving end will complete Vc connection."
::= { mscVctVcCadEntry 7 }

mscVctVcCalledLcn OBJECT-TYPE
   SYNTAX     Unsigned32 (1..65535)
   ACCESS     read-only
   STATUS     mandatory
   DESCRIPTION
     "This attribute displays the Logical Channel Number of the called 
      end. It is valid only after both ends of Vc exchanged relevant 
      information."
::= { mscVctVcCadEntry 8 }

mscVctVcCallingNpi OBJECT-TYPE
   SYNTAX     INTEGER  {
                 x121(0),
                 e164(1) }
   ACCESS     read-only
   STATUS     mandatory
   DESCRIPTION
     "This attribute displays the Numbering Plan Indicator (NPI) of the 
      calling end."
::= { mscVctVcCadEntry 9 }

mscVctVcCallingDna OBJECT-TYPE
   SYNTAX     DigitString (SIZE (1..15))
   ACCESS     read-only
   STATUS     mandatory
   DESCRIPTION
     "This attribute displays the Data Network Address (Dna) of the 
      calling end."
::= { mscVctVcCadEntry 10 }

mscVctVcCallingLcn OBJECT-TYPE
   SYNTAX     Unsigned32 (1..65535)
   ACCESS     read-only
   STATUS     mandatory
   DESCRIPTION
     "This attribute displays the Logical Channel Number of the calling 
      end."
::= { mscVctVcCadEntry 11 }

mscVctVcAccountingEnabled OBJECT-TYPE
   SYNTAX     INTEGER  {
                 yes(0),
                 no(1) }
   ACCESS     read-only
   STATUS     mandatory
   DESCRIPTION
     "This attribute indicates that this optional section of accounting 
      record is suppressed or permitted. If accountingEnabled is yes, 
      conditions for generation of accounting record were met. These 
      conditions include billing options, vc recovery conditions and 
      Module wide accounting data options."
::= { mscVctVcCadEntry 12 }

mscVctVcFastSelectCall OBJECT-TYPE
   SYNTAX     INTEGER  {
                 no(0),
                 yes(1) }
   ACCESS     read-only
   STATUS     mandatory
   DESCRIPTION
     "This attribute displays that this is a fast select call."
::= { mscVctVcCadEntry 13 }

mscVctVcLocalRxPktSize OBJECT-TYPE
   SYNTAX     INTEGER  {
                 unknown(0),
                 n16(4),
                 n32(5),
                 n64(6),
                 n128(7),
                 n256(8),
                 n512(9),
                 n1024(10),
                 n2048(11),
                 n4096(12) }
   ACCESS     read-only
   STATUS     mandatory
   DESCRIPTION
     "This attribute displays the locally negotiated size of send packets."
::= { mscVctVcCadEntry 14 }

mscVctVcLocalTxPktSize OBJECT-TYPE
   SYNTAX     INTEGER  {
                 unknown(0),
                 n16(4),
                 n32(5),
                 n64(6),
                 n128(7),
                 n256(8),
                 n512(9),
                 n1024(10),
                 n2048(11),
                 n4096(12) }
   ACCESS     read-only
   STATUS     mandatory
   DESCRIPTION
     "This attribute displays the locally negotiated size of send packets."
::= { mscVctVcCadEntry 15 }

mscVctVcLocalTxWindowSize OBJECT-TYPE
   SYNTAX     Unsigned32 (0..127)
   ACCESS     read-only
   STATUS     mandatory
   DESCRIPTION
     "This attribute displays the send window size provided on incoming 
      call packets or the default when a call request packet does not 
      explicitly provide the window size."
::= { mscVctVcCadEntry 16 }

mscVctVcLocalRxWindowSize OBJECT-TYPE
   SYNTAX     Unsigned32 (0..127)
   ACCESS     read-only
   STATUS     mandatory
   DESCRIPTION
     "This attribute displays the receive window size provided on 
      incoming call packets or the default when a call request does not 
      explicitly provide the window sizes."
::= { mscVctVcCadEntry 17 }

mscVctVcPathReliability OBJECT-TYPE
   SYNTAX     INTEGER  {
                 high(0),
                 normal(1) }
   ACCESS     read-only
   STATUS     mandatory
   DESCRIPTION
     "This attribute displays the path reliability."
::= { mscVctVcCadEntry 19 }

mscVctVcAccountingEnd OBJECT-TYPE
   SYNTAX     INTEGER  {
                 callingEnd(0),
                 calledEnd(1) }
   ACCESS     read-only
   STATUS     mandatory
   DESCRIPTION
     "This attribute indicates if this end should generate an accounting 
      record. Normally, callingEnd is the end to generate an accounting 
      record."
::= { mscVctVcCadEntry 20 }

mscVctVcPriority OBJECT-TYPE
   SYNTAX     INTEGER  {
                 normal(0),
                 high(1) }
   ACCESS     read-only
   STATUS     mandatory
   DESCRIPTION
     "This attribute displays whether the call is a normal or a high 
      priority call."
::= { mscVctVcCadEntry 21 }

mscVctVcSegmentSize OBJECT-TYPE
   SYNTAX     Unsigned32 (0..4096)
   ACCESS     read-only
   STATUS     mandatory
   DESCRIPTION
     "This attribute displays the segment size (in bytes) used on the call. 
      It is used to calculate the number of segments transmitted and 
      received."
::= { mscVctVcCadEntry 22 }

mscVctVcSubnetTxPktSize OBJECT-TYPE
   SYNTAX     INTEGER  {
                 unknown(0),
                 n16(4),
                 n32(5),
                 n64(6),
                 n128(7),
                 n256(8),
                 n512(9),
                 n1024(10),
                 n2048(11),
                 n4096(12) }
   ACCESS     read-only
   STATUS     mandatory
   DESCRIPTION
     "This attribute displays the locally negotiated size of the data packets 
      on this Vc."
::= { mscVctVcCadEntry 23 }

mscVctVcSubnetTxWindowSize OBJECT-TYPE
   SYNTAX     Unsigned32 (0..4096)
   ACCESS     read-only
   STATUS     mandatory
   DESCRIPTION
     "This attribute displays the current send window size of Vc."
::= { mscVctVcCadEntry 24 }

mscVctVcSubnetRxPktSize OBJECT-TYPE
   SYNTAX     INTEGER  {
                 unknown(0),
                 n16(4),
                 n32(5),
                 n64(6),
                 n128(7),
                 n256(8),
                 n512(9),
                 n1024(10),
                 n2048(11),
                 n4096(12) }
   ACCESS     read-only
   STATUS     mandatory
   DESCRIPTION
     "This attribute displays the locally negotiated size of receive packets."
::= { mscVctVcCadEntry 25 }

mscVctVcSubnetRxWindowSize OBJECT-TYPE
   SYNTAX     Unsigned32 (0..4096)
   ACCESS     read-only
   STATUS     mandatory
   DESCRIPTION
     "This attribute displays the receive window size provided on 
      incoming call packets and to the default when a call request does 
      not explicitly provide the window sizes."
::= { mscVctVcCadEntry 26 }

mscVctVcMaxSubnetPktSize OBJECT-TYPE
   SYNTAX     Unsigned32 (0..4096)
   ACCESS     read-only
   STATUS     mandatory
   DESCRIPTION
     "This attribute displays the maximum packet size allowed on Vc."
::= { mscVctVcCadEntry 27 }

mscVctVcTransferPriorityToNetwork OBJECT-TYPE
   SYNTAX     INTEGER  {
                 normal(0),
                 high(9) }
   ACCESS     read-only
   STATUS     mandatory
   DESCRIPTION
     "This attribute displays the priority in which data is transferred to the 
      network.
      
      The transfer priority is a preference specified by an application 
      according to its delay-sensitivity requirement. Frames with high
      transfer priority are served by the network before the frames with 
      normal priority. 
      
      Each transfer priority contains a predetermined setting for trunk 
      queue (interrupting, delay or throughput), and routing metric (delay 
      or throughput).
      
      When the transfer priority is set at high, the trunk queue is set to 
      high, the routing metric is set to delay.
      
      When the transfer priority is set at normal, the trunk queue is set to 
      normal, the routing metric is set to throughput."
::= { mscVctVcCadEntry 28 }

mscVctVcTransferPriorityFromNetwork OBJECT-TYPE
   SYNTAX     INTEGER  {
                 normal(0),
                 high(9) }
   ACCESS     read-only
   STATUS     mandatory
   DESCRIPTION
     "This attribute displays the priority in which data is transferred from 
      the network.
      
      The transfer priority is a preference specified by an application 
      according to its delay-sensitivity requirement. Frames with high
      transfer priority are served by the network before the frames with 
      normal priority. 
      
      Each transfer priority contains a predetermined setting for trunk 
      queue (interrupting, delay or throughput), and routing metric (delay 
      or throughput). 
      
      When the transfer priority is set at high, and the trunk queue is set 
      to high, the routing metric is set to delay.
      
      When the transfer priority is set at normal, the trunk queue is set to 
      normal, and the routing metric is set to throughput."
::= { mscVctVcCadEntry 29 }

mscVctVcIntdTable OBJECT-TYPE
   SYNTAX     SEQUENCE OF MscVctVcIntdEntry
   ACCESS     not-accessible
   STATUS     mandatory
   DESCRIPTION
     "This group defines display of interval data collected by Vc. Data in 
      this group is variable and may depend on time when this display 
      command is issued."
::= { mscVctVc 11 }

mscVctVcIntdEntry OBJECT-TYPE
   SYNTAX     MscVctVcIntdEntry
   ACCESS     not-accessible
   STATUS     mandatory
   DESCRIPTION
     "An entry in the mscVctVcIntdTable."
   INDEX {
      mscVctIndex,
      mscVctVcIndex }
::= { mscVctVcIntdTable 1 }

MscVctVcIntdEntry ::= SEQUENCE {
   mscVctVcCallReferenceNumber
      Hex,
   mscVctVcElapsedTimeTillNow
      Unsigned32,
   mscVctVcSegmentsRx
      Unsigned32,
   mscVctVcSegmentsSent
      Unsigned32,
   mscVctVcStartTime
      EnterpriseDateAndTime,
   mscVctVcCallReferenceNumberDecimal
      Unsigned32 }

mscVctVcCallReferenceNumber OBJECT-TYPE
   SYNTAX     Hex (0..16777215)
   ACCESS     read-only
   STATUS     obsolete
   DESCRIPTION
     "This attribute is obsolete. It is replaced by the callReferenceNumber 
      attribute to display the call reference number in decimal. The 
      SNMP reference for the callReferenceNumber attribute is 
      callReferenceNumberDecimal."
::= { mscVctVcIntdEntry 1 }

mscVctVcElapsedTimeTillNow OBJECT-TYPE
   SYNTAX     Unsigned32 (0..16777215)
   ACCESS     read-only
   STATUS     mandatory
   DESCRIPTION
     "This attribute displays the elapsed time representing the period of 
      this interval data. It is elapsed time in 0.1 second increments since 
      Vc started."
::= { mscVctVcIntdEntry 2 }

mscVctVcSegmentsRx OBJECT-TYPE
   SYNTAX     Unsigned32 (0..16777215)
   ACCESS     read-only
   STATUS     mandatory
   DESCRIPTION
     "This attribute displays the number of segments received at the time 
      command was issued. This is the segment received count 
      maintained by accounting at each end of the Vc. This counter is 
      updated only when the packet cannot be successfully delivered out 
      of the sink Vc and to the sink AP Conditions in which packets may 
      be discarded by the sink Vc include: missing packets due to subnet 
      discards, segmentation protocol violations due to subnet discard, 
      duplicated and out-of-ranged packets and packets that arrive while 
      Vc is in path recovery state."
::= { mscVctVcIntdEntry 3 }

mscVctVcSegmentsSent OBJECT-TYPE
   SYNTAX     Unsigned32 (0..16777215)
   ACCESS     read-only
   STATUS     mandatory
   DESCRIPTION
     "This attribute displays the number of segments sent at the time 
      command was issued. This is the segment sent count maintained by 
      accounting at the source Vc. Vc only counts packets that Vc thinks 
      can be delivered successfully into the subnet. In reality, these 
      packets may be dropped by trunking, for instance. This counter is 
      not updated when splitting fails, when Vc is in a path recovery state, 
      when packet forwarding fails to forward this packet and when 
      subsequent packets have to be discarded as we want to minimize the 
      chance of out-of-sequence and do not intentionally send out-of-
      sequenced packets into the subnet."
::= { mscVctVcIntdEntry 4 }

mscVctVcStartTime OBJECT-TYPE
   SYNTAX     EnterpriseDateAndTime (SIZE (0 | 19))
   ACCESS     read-only
   STATUS     mandatory
   DESCRIPTION
     "This attribute displays the start time of this interval period. If Vc 
      spans 12 hour time or time of day change startTime reflects new 
      time as recorded at 12 hour periods or time of day changes."
::= { mscVctVcIntdEntry 5 }

mscVctVcCallReferenceNumberDecimal OBJECT-TYPE
   SYNTAX     Unsigned32 (0..4294967295)
   ACCESS     read-only
   STATUS     mandatory
   DESCRIPTION
     "This attribute displays the call reference number which is a unique 
      number generated by the switch.The same Call Reference Number 
      is stored in the interval data (accounting record) at both ends of the 
      call. It can be used as one of the attributes in matching duplicate 
      records generated at each end of the call."
::= { mscVctVcIntdEntry 7 }

mscVctVcStatsTable OBJECT-TYPE
   SYNTAX     SEQUENCE OF MscVctVcStatsEntry
   ACCESS     not-accessible
   STATUS     mandatory
   DESCRIPTION
     "... Statistics(Stats)
      This group defines general attributes collected by general Vc.
      The purpose of Vc attributes is to aid end users and verification 
      people to understand the Vc internal behavior. This is particularly 
      useful when the network has experienced abnormality and we want 
      to isolate problems and pinpoint trouble spots. 
      Attributes are collected on a per Vc basis. Until a need is identified, 
      statistics are not collected at a processor level. Each attribute is 
      stored in a 32 bit field and is initialized to zero when a Vc enters 
      into the data transfer state. When a PVC is disconnected and then 
      connected again, the attributes will be reset. Attributes cannot be 
      reset through other methods."
::= { mscVctVc 12 }

mscVctVcStatsEntry OBJECT-TYPE
   SYNTAX     MscVctVcStatsEntry
   ACCESS     not-accessible
   STATUS     mandatory
   DESCRIPTION
     "An entry in the mscVctVcStatsTable."
   INDEX {
      mscVctIndex,
      mscVctVcIndex }
::= { mscVctVcStatsTable 1 }

MscVctVcStatsEntry ::= SEQUENCE {
   mscVctVcAckStackingTimeouts
      Unsigned32,
   mscVctVcOutOfRangeFrmFromSubnet
      Unsigned32,
   mscVctVcDuplicatesFromSubnet
      Unsigned32,
   mscVctVcFrmRetryTimeouts
      Unsigned32,
   mscVctVcPeakRetryQueueSize
      Unsigned32,
   mscVctVcPeakOoSeqQueueSize
      Unsigned32,
   mscVctVcPeakOoSeqFrmForwarded
      Unsigned32,
   mscVctVcPeakStackedAcksRx
      Unsigned32,
   mscVctVcSubnetRecoveries
      Unsigned32,
   mscVctVcWindowClosuresToSubnet
      Unsigned32,
   mscVctVcWindowClosuresFromSubnet
      Unsigned32,
   mscVctVcWrTriggers
      Unsigned32 }

mscVctVcAckStackingTimeouts OBJECT-TYPE
   SYNTAX     Unsigned32 (0..5000)
   ACCESS     read-only
   STATUS     mandatory
   DESCRIPTION
     "This attribute counts the number of ack stacking timer expiries.
      It is used as an indicator of the acknowledgment behavior across the 
      subnet when ack stacking is in effect. If it expires often, usually this 
      means end users will experience longer delay.
      The ack stacking timer specifies how long the Vc will wait before 
      finally sending the subnet acknowledgment. if this attribute is set to 
      a value of 0, then the Vc will automatically return acknowledgment 
      packets without delay. If this attribute is set to a value other than 
      zero, then the Vc will wait for this amount of time in an attempt to 
      piggyback the acknowledgment packet on another credit or data 
      packet. If the Vc cannot piggyback the acknowledgment packet 
      within this time, then the packet is returned without piggybacking."
::= { mscVctVcStatsEntry 1 }

mscVctVcOutOfRangeFrmFromSubnet OBJECT-TYPE
   SYNTAX     Unsigned32 (0..5000)
   ACCESS     read-only
   STATUS     mandatory
   DESCRIPTION
     "This attribute counts the number of subnet frames discarded due to 
      the sequence number being out of range.
      Two Categories apply for the General Vc
      1) lost Acks (previous Range)
      2) unexpected Packets (next Range)
      Vc internally maintains its own sequence number of packet order 
      and sequencing. Due to packet retransmission, Vc may receive 
      duplicate packets that have the same Vc internal sequence number. 
      Only 1 copy is accepted by the Vc and other copies of the same 
      packets are detected through this count. This attribute can be used to 
      record the frequency of packet retransmission due to Vc and other 
      part of the subnet."
::= { mscVctVcStatsEntry 2 }

mscVctVcDuplicatesFromSubnet OBJECT-TYPE
   SYNTAX     Unsigned32 (0..5000)
   ACCESS     read-only
   STATUS     mandatory
   DESCRIPTION
     "This attribute counts the number of subnet packets discarded due to 
      duplication. It is used to detect software error fault or duplication 
      caused by retransmitting."
::= { mscVctVcStatsEntry 3 }

mscVctVcFrmRetryTimeouts OBJECT-TYPE
   SYNTAX     Unsigned32 (0..5000)
   ACCESS     read-only
   STATUS     mandatory
   DESCRIPTION
     "This attribute counts the number of frames which have 
      retransmission time-out.
      If packets from Vc into the subnet are discarded by the subnet, the 
      source Vc will not receive any acknowledgment. The retransmission 
      timer then expires and packets will be retransmitted again. Note that 
      the Vc idle probe may be retransmitted and is included in this count. 
      This statistics does not show the distribution of how many times 
      packets are retransmitted (e.g. first retransmission results in 
      successful packet forwarding)."
::= { mscVctVcStatsEntry 4 }

mscVctVcPeakRetryQueueSize OBJECT-TYPE
   SYNTAX     Unsigned32 (0..5000)
   ACCESS     read-only
   STATUS     mandatory
   DESCRIPTION
     "This attribute indicates the peak size of the retransmission queue.
      This attribute is used as an indicator of the acknowledgment 
      behavior across the subnet. It records the largest body of 
      unacknowledged packets."
::= { mscVctVcStatsEntry 5 }

mscVctVcPeakOoSeqQueueSize OBJECT-TYPE
   SYNTAX     Unsigned32 (0..5000)
   ACCESS     read-only
   STATUS     mandatory
   DESCRIPTION
     "This attribute indicates the peak size of the out of sequence queue.
      This attribute is used as an indicator of the sequencing behavior 
      across the subnet. It records the largest body of out of sequence 
      packets."
::= { mscVctVcStatsEntry 6 }

mscVctVcPeakOoSeqFrmForwarded OBJECT-TYPE
   SYNTAX     Unsigned32 (0..5000)
   ACCESS     read-only
   STATUS     mandatory
   DESCRIPTION
     "This attribute indicates the peak size of the sequence packet queue.
      This attribute is used as an indicator of the sequencing behavior 
      across the subnet. It records the largest body of out of sequence 
      packets, which by the receipt of an expected packet have been 
      transformed to expected packets. The number of times this peak is 
      reached is not recorded as it is traffic dependent."
::= { mscVctVcStatsEntry 7 }

mscVctVcPeakStackedAcksRx OBJECT-TYPE
   SYNTAX     Unsigned32 (0..5000)
   ACCESS     read-only
   STATUS     mandatory
   DESCRIPTION
     "This attribute indicates the peak size of wait acks.
      This attribute is used as an indicator of the acknowledgment 
      behavior across the subnet. It records the largest collective 
      acknowledgment."
::= { mscVctVcStatsEntry 8 }

mscVctVcSubnetRecoveries OBJECT-TYPE
   SYNTAX     Unsigned32 (0..5000)
   ACCESS     read-only
   STATUS     mandatory
   DESCRIPTION
     "This attribute counts the number of successful Vc recovery attempts.
      This attribute is used as an indicator of how many times the Vc path 
      is broken but can be recovered. This attribute is useful to record the 
      number of network path failures."
::= { mscVctVcStatsEntry 9 }

mscVctVcWindowClosuresToSubnet OBJECT-TYPE
   SYNTAX     Unsigned32 (0..5000)
   ACCESS     read-only
   STATUS     mandatory
   DESCRIPTION
     "This attribute counts the number of window closures to subnet.
      A packet may have been sent into the subnet but its 
      acknowledgment from the remote Vc has not yet been received. 
      This is a 8 bit sequence number.This number is useful in detecting 
      whether the Vc is sending any packet into the subnet."
::= { mscVctVcStatsEntry 10 }

mscVctVcWindowClosuresFromSubnet OBJECT-TYPE
   SYNTAX     Unsigned32 (0..5000)
   ACCESS     read-only
   STATUS     mandatory
   DESCRIPTION
     "This attribute counts the number of window closures from subnet.
      This attribute is useful in detecting whether the Vc is receiving any 
      packet from the subnet."
::= { mscVctVcStatsEntry 11 }

mscVctVcWrTriggers OBJECT-TYPE
   SYNTAX     Unsigned32 (0..5000)
   ACCESS     read-only
   STATUS     mandatory
   DESCRIPTION
     "This attribute displays the number of times the Vc stays within the 
      W-R region. The W-R region is a value used to determined the 
      timing of credit transmission. Should the current window size be 
      beneath this value, the credits will be transmitted immediately. 
      Otherwise, they will be transmitted later with actual data. The 
      wrTriggers statistic is therefore used to analyze the flow control and 
      credit mechanism."
::= { mscVctVcStatsEntry 12 }


-- 
-- This component defines the statistics collected by Frame Relay Vc. 
-- It is needed for ligthweight vc.

mscVctVcfr OBJECT IDENTIFIER ::= { mscVct 5 }



mscVctVcfrRowStatusTable OBJECT-TYPE
   SYNTAX     SEQUENCE OF MscVctVcfrRowStatusEntry
   ACCESS     not-accessible
   STATUS     mandatory
   DESCRIPTION
     "This entry controls the addition and deletion of 
      mscVctVcfr components."
::= { mscVctVcfr 1 }

mscVctVcfrRowStatusEntry OBJECT-TYPE
   SYNTAX     MscVctVcfrRowStatusEntry
   ACCESS     not-accessible
   STATUS     mandatory
   DESCRIPTION
     "A single entry in the table represents a single 
      mscVctVcfr component."
   INDEX {
      mscVctIndex,
      mscVctVcfrIndex }
::= { mscVctVcfrRowStatusTable 1 }

MscVctVcfrRowStatusEntry ::= SEQUENCE {
   mscVctVcfrRowStatus
      RowStatus,
   mscVctVcfrComponentName
      DisplayString,
   mscVctVcfrStorageType
      StorageType,
   mscVctVcfrIndex
      NonReplicated }

mscVctVcfrRowStatus OBJECT-TYPE
   SYNTAX     RowStatus 
   ACCESS     read-only
   STATUS     mandatory
   DESCRIPTION
     "This variable is used as the basis for SNMP naming of
      mscVctVcfr components.
      These components cannot be added nor deleted."
::= { mscVctVcfrRowStatusEntry 1 }

mscVctVcfrComponentName OBJECT-TYPE
   SYNTAX     DisplayString 
   ACCESS     read-only
   STATUS     mandatory
   DESCRIPTION
     "This variable provides the component's string name for
      use with the ASCII Console Interface"
::= { mscVctVcfrRowStatusEntry 2 }

mscVctVcfrStorageType OBJECT-TYPE
   SYNTAX     StorageType 
   ACCESS     read-only
   STATUS     mandatory
   DESCRIPTION
     "This variable represents the storage type value for the
      mscVctVcfr tables."
::= { mscVctVcfrRowStatusEntry 4 }

mscVctVcfrIndex OBJECT-TYPE
   SYNTAX     NonReplicated 
   ACCESS     not-accessible
   STATUS     mandatory
   DESCRIPTION
     "This variable represents the index for the mscVctVcfr tables."
::= { mscVctVcfrRowStatusEntry 10 }

mscVctVcfrCadTable OBJECT-TYPE
   SYNTAX     SEQUENCE OF MscVctVcfrCadEntry
   ACCESS     not-accessible
   STATUS     mandatory
   DESCRIPTION
     "This group represents operational call data related to Frame Relay 
      Vc. It can be displayed only for Frame Relay Vc which is created by 
      application."
::= { mscVctVcfr 10 }

mscVctVcfrCadEntry OBJECT-TYPE
   SYNTAX     MscVctVcfrCadEntry
   ACCESS     not-accessible
   STATUS     mandatory
   DESCRIPTION
     "An entry in the mscVctVcfrCadTable."
   INDEX {
      mscVctIndex,
      mscVctVcfrIndex }
::= { mscVctVcfrCadTable 1 }

MscVctVcfrCadEntry ::= SEQUENCE {
   mscVctVcfrType
      INTEGER,
   mscVctVcfrState
      INTEGER,
   mscVctVcfrPreviousState
      INTEGER,
   mscVctVcfrDiagnosticCode
      Unsigned32,
   mscVctVcfrPreviousDiagnosticCode
      Unsigned32,
   mscVctVcfrCalledNpi
      INTEGER,
   mscVctVcfrCalledDna
      DigitString,
   mscVctVcfrCalledLcn
      Unsigned32,
   mscVctVcfrCallingNpi
      INTEGER,
   mscVctVcfrCallingDna
      DigitString,
   mscVctVcfrCallingLcn
      Unsigned32,
   mscVctVcfrAccountingEnabled
      INTEGER,
   mscVctVcfrFastSelectCall
      INTEGER,
   mscVctVcfrPathReliability
      INTEGER,
   mscVctVcfrAccountingEnd
      INTEGER,
   mscVctVcfrPriority
      INTEGER,
   mscVctVcfrSegmentSize
      Unsigned32,
   mscVctVcfrMaxSubnetPktSize
      Unsigned32,
   mscVctVcfrRcosToNetwork
      INTEGER,
   mscVctVcfrRcosFromNetwork
      INTEGER,
   mscVctVcfrEmissionPriorityToNetwork
      INTEGER,
   mscVctVcfrEmissionPriorityFromNetwork
      INTEGER,
   mscVctVcfrDataPath
      AsciiString }

mscVctVcfrType OBJECT-TYPE
   SYNTAX     INTEGER  {
                 svc(0),
                 pvc(1),
                 spvc(2),
                 frf10spvc(3) }
   ACCESS     read-only
   STATUS     mandatory
   DESCRIPTION
     "This attribute displays the type of call, pvc,svc,spvc or frf10spvc."
::= { mscVctVcfrCadEntry 1 }

mscVctVcfrState OBJECT-TYPE
   SYNTAX     INTEGER  {
                 creating(0),
                 readyP1(1),
                 dteWaitingP2(2),
                 dceWaitingP3(3),
                 dataTransferP4(4),
                 unsupportedP5(5),
                 dteClearRequestP6(6),
                 dceClearIndicationP7(7),
                 termination(8) }
   ACCESS     read-only
   STATUS     mandatory
   DESCRIPTION
     "This attribute displays the state of call control. P5 state is not 
      supported but is listed for completness. Transitions from one state to 
      another take very short time. state most often displayed is 
      dataTransferP4."
::= { mscVctVcfrCadEntry 2 }

mscVctVcfrPreviousState OBJECT-TYPE
   SYNTAX     INTEGER  {
                 creating(0),
                 readyP1(1),
                 dteWaitingP2(2),
                 dceWaitingP3(3),
                 dataTransferP4(4),
                 unsupportedP5(5),
                 dteClearRequestP6(6),
                 dceClearIndicationP7(7),
                 termination(8) }
   ACCESS     read-only
   STATUS     mandatory
   DESCRIPTION
     "This attribute displays the previous state of call control. This is a 
      valuable field to determine how the processing is progressing."
::= { mscVctVcfrCadEntry 3 }

mscVctVcfrDiagnosticCode OBJECT-TYPE
   SYNTAX     Unsigned32 (0..255)
   ACCESS     read-only
   STATUS     mandatory
   DESCRIPTION
     "This attribute displays the internal substate of call control. It is used 
      to further refine state of call processing."
::= { mscVctVcfrCadEntry 4 }

mscVctVcfrPreviousDiagnosticCode OBJECT-TYPE
   SYNTAX     Unsigned32 (0..255)
   ACCESS     read-only
   STATUS     mandatory
   DESCRIPTION
     "This attribute displays the internal substate of call control. It is used 
      to further refine state of call processing."
::= { mscVctVcfrCadEntry 5 }

mscVctVcfrCalledNpi OBJECT-TYPE
   SYNTAX     INTEGER  {
                 x121(0),
                 e164(1) }
   ACCESS     read-only
   STATUS     mandatory
   DESCRIPTION
     "This attribute displays the Numbering Plan Indicator (NPI) of the 
      called end."
::= { mscVctVcfrCadEntry 6 }

mscVctVcfrCalledDna OBJECT-TYPE
   SYNTAX     DigitString (SIZE (1..15))
   ACCESS     read-only
   STATUS     mandatory
   DESCRIPTION
     "This attribute displays the Data Network Address (Dna) of the 
      called (destination) DTE to which this call is sent. This address if 
      defined at recieving end will complete Vc connection."
::= { mscVctVcfrCadEntry 7 }

mscVctVcfrCalledLcn OBJECT-TYPE
   SYNTAX     Unsigned32 (1..65535)
   ACCESS     read-only
   STATUS     mandatory
   DESCRIPTION
     "This attribute displays the Logical Channel Number of the called 
      end. It is valid only after both ends of Vc exchanged relevant 
      information."
::= { mscVctVcfrCadEntry 8 }

mscVctVcfrCallingNpi OBJECT-TYPE
   SYNTAX     INTEGER  {
                 x121(0),
                 e164(1) }
   ACCESS     read-only
   STATUS     mandatory
   DESCRIPTION
     "This attribute displays the Numbering Plan Indicator (NPI) of the 
      calling end."
::= { mscVctVcfrCadEntry 9 }

mscVctVcfrCallingDna OBJECT-TYPE
   SYNTAX     DigitString (SIZE (1..15))
   ACCESS     read-only
   STATUS     mandatory
   DESCRIPTION
     "This attribute displays the Data Network Address (Dna) of the 
      calling end."
::= { mscVctVcfrCadEntry 10 }

mscVctVcfrCallingLcn OBJECT-TYPE
   SYNTAX     Unsigned32 (1..65535)
   ACCESS     read-only
   STATUS     mandatory
   DESCRIPTION
     "This attribute displays the Logical Channel Number of the calling 
      end."
::= { mscVctVcfrCadEntry 11 }

mscVctVcfrAccountingEnabled OBJECT-TYPE
   SYNTAX     INTEGER  {
                 yes(0),
                 no(1) }
   ACCESS     read-only
   STATUS     mandatory
   DESCRIPTION
     "This attribute indicates that this optional section of accounting 
      record is suppressed or permitted. If accountingEnabled is yes, 
      conditions for generation of accounting record were met. These 
      conditions include billing options, vc recovery conditions and 
      Module wide accounting data options."
::= { mscVctVcfrCadEntry 12 }

mscVctVcfrFastSelectCall OBJECT-TYPE
   SYNTAX     INTEGER  {
                 no(0),
                 yes(1) }
   ACCESS     read-only
   STATUS     mandatory
   DESCRIPTION
     "This attribute displays that this is a fast select call."
::= { mscVctVcfrCadEntry 13 }

mscVctVcfrPathReliability OBJECT-TYPE
   SYNTAX     INTEGER  {
                 high(0),
                 normal(1) }
   ACCESS     read-only
   STATUS     mandatory
   DESCRIPTION
     "This attribute displays the path reliability."
::= { mscVctVcfrCadEntry 19 }

mscVctVcfrAccountingEnd OBJECT-TYPE
   SYNTAX     INTEGER  {
                 callingEnd(0),
                 calledEnd(1) }
   ACCESS     read-only
   STATUS     mandatory
   DESCRIPTION
     "This attribute indicates if this end should generate an accounting 
      record. Normally, callingEnd is the end to generate an accounting 
      record."
::= { mscVctVcfrCadEntry 20 }

mscVctVcfrPriority OBJECT-TYPE
   SYNTAX     INTEGER  {
                 normal(0),
                 high(1) }
   ACCESS     read-only
   STATUS     mandatory
   DESCRIPTION
     "This attribute displays whether the call is a normal or a high 
      priority call."
::= { mscVctVcfrCadEntry 21 }

mscVctVcfrSegmentSize OBJECT-TYPE
   SYNTAX     Unsigned32 (0..4096)
   ACCESS     read-only
   STATUS     mandatory
   DESCRIPTION
     "This attribute displays the segment size (in bytes) used on the call. 
      It is used to calculate the number of segments transmitted and 
      received."
::= { mscVctVcfrCadEntry 22 }

mscVctVcfrMaxSubnetPktSize OBJECT-TYPE
   SYNTAX     Unsigned32 (0..4096)
   ACCESS     read-only
   STATUS     mandatory
   DESCRIPTION
     "This attribute indicates the maximum packet size allowed on the Vc."
::= { mscVctVcfrCadEntry 27 }

mscVctVcfrRcosToNetwork OBJECT-TYPE
   SYNTAX     INTEGER  {
                 throughput(0),
                 delay(1),
                 multimedia(2) }
   ACCESS     read-only
   STATUS     mandatory
   DESCRIPTION
     "This attribute indicates the routing metric routing class of service to
      the network."
::= { mscVctVcfrCadEntry 28 }

mscVctVcfrRcosFromNetwork OBJECT-TYPE
   SYNTAX     INTEGER  {
                 throughput(0),
                 delay(1),
                 multimedia(2) }
   ACCESS     read-only
   STATUS     mandatory
   DESCRIPTION
     "This attribute displays the routing metric Routing Class of Service 
      from the Network."
::= { mscVctVcfrCadEntry 29 }

mscVctVcfrEmissionPriorityToNetwork OBJECT-TYPE
   SYNTAX     INTEGER  {
                 normal(0),
                 high(1),
                 interrupting(2) }
   ACCESS     read-only
   STATUS     mandatory
   DESCRIPTION
     "This attribute displays the network internal emission priotity to the 
      network."
::= { mscVctVcfrCadEntry 30 }

mscVctVcfrEmissionPriorityFromNetwork OBJECT-TYPE
   SYNTAX     INTEGER  {
                 normal(0),
                 high(1),
                 interrupting(2) }
   ACCESS     read-only
   STATUS     mandatory
   DESCRIPTION
     "This attribute displays the network internal emission priotity from 
      the network."
::= { mscVctVcfrCadEntry 31 }

mscVctVcfrDataPath OBJECT-TYPE
   SYNTAX     AsciiString (SIZE (0..32))
   ACCESS     read-only
   STATUS     mandatory
   DESCRIPTION
     "This attribute indicates the data path used by the connection. The 
      data path is provisioned in Dna and DirectCall components. The 
      displayed value of this attribute can be different from the 
      provisioned value.
      
      If the connection is using dprsOnly data path, the string 
      dprsOnly is displayed. (dynamic packet routing system)
      
      If the connection is using dprsMcsOnly data path, the string 
      dprsMcsOnly is displayed.
      
      If the connection is using dprsMcsFirst data path, the string 
      dprsMcsFirst is displayed."
::= { mscVctVcfrCadEntry 32 }

mscVctVcfrIntdTable OBJECT-TYPE
   SYNTAX     SEQUENCE OF MscVctVcfrIntdEntry
   ACCESS     not-accessible
   STATUS     mandatory
   DESCRIPTION
     "This group defines display of interval data collected by Vc. Data in 
      this group is variable and may depend on time when this display 
      command is issued."
::= { mscVctVcfr 11 }

mscVctVcfrIntdEntry OBJECT-TYPE
   SYNTAX     MscVctVcfrIntdEntry
   ACCESS     not-accessible
   STATUS     mandatory
   DESCRIPTION
     "An entry in the mscVctVcfrIntdTable."
   INDEX {
      mscVctIndex,
      mscVctVcfrIndex }
::= { mscVctVcfrIntdTable 1 }

MscVctVcfrIntdEntry ::= SEQUENCE {
   mscVctVcfrCallReferenceNumber
      Hex,
   mscVctVcfrElapsedTimeTillNow
      Unsigned32,
   mscVctVcfrSegmentsRx
      Unsigned32,
   mscVctVcfrSegmentsSent
      Unsigned32,
   mscVctVcfrStartTime
      EnterpriseDateAndTime,
   mscVctVcfrCallReferenceNumberDecimal
      Unsigned32 }

mscVctVcfrCallReferenceNumber OBJECT-TYPE
   SYNTAX     Hex (0..16777215)
   ACCESS     read-only
   STATUS     obsolete
   DESCRIPTION
     "This attribute is obsolete. It is replaced by the callReferenceNumber 
      attribute to display the call reference number in decimal. The 
      SNMP reference for the callReferenceNumber attribute is 
      callReferenceNumberDecimal."
::= { mscVctVcfrIntdEntry 1 }

mscVctVcfrElapsedTimeTillNow OBJECT-TYPE
   SYNTAX     Unsigned32 (0..16777215)
   ACCESS     read-only
   STATUS     mandatory
   DESCRIPTION
     "This attribute displays the elapsed time representing the period of 
      this interval data. It is elapsed time in 0.1 second increments since 
      Vc started."
::= { mscVctVcfrIntdEntry 2 }

mscVctVcfrSegmentsRx OBJECT-TYPE
   SYNTAX     Unsigned32 (0..16777215)
   ACCESS     read-only
   STATUS     mandatory
   DESCRIPTION
     "This attribute displays the number of segments received at the time 
      command was issued. This is the segment received count 
      maintained by accounting at each end of the Vc. This counter is 
      updated only when the packet cannot be successfully delivered out 
      of the sink Vc and to the sink AP Conditions in which packets may 
      be discarded by the sink Vc include: missing packets due to subnet 
      discards, segmentation protocol violations due to subnet discard, 
      duplicated and out-of-ranged packets and packets that arrive while 
      Vc is in path recovery state."
::= { mscVctVcfrIntdEntry 3 }

mscVctVcfrSegmentsSent OBJECT-TYPE
   SYNTAX     Unsigned32 (0..16777215)
   ACCESS     read-only
   STATUS     mandatory
   DESCRIPTION
     "This attribute displays the number of segments sent at the time 
      command was issued. This is the segment sent count maintained by 
      accounting at the source Vc. Vc only counts packets that Vc thinks 
      can be delivered successfully into the subnet. In reality, these 
      packets may be dropped by trunking, for instance. This counter is 
      not updated when splitting fails, when Vc is in a path recovery state, 
      when packet forwarding fails to forward this packet and when 
      subsequent packets have to be discarded as we want to minimize the 
      chance of out-of-sequence and do not intentionally send out-of-
      sequenced packets into the subnet."
::= { mscVctVcfrIntdEntry 4 }

mscVctVcfrStartTime OBJECT-TYPE
   SYNTAX     EnterpriseDateAndTime (SIZE (0 | 19))
   ACCESS     read-only
   STATUS     mandatory
   DESCRIPTION
     "This attribute displays the start time of this interval period. If Vc 
      spans 12 hour time or time of day change startTime reflects new 
      time as recorded at 12 hour periods or time of day changes."
::= { mscVctVcfrIntdEntry 5 }

mscVctVcfrCallReferenceNumberDecimal OBJECT-TYPE
   SYNTAX     Unsigned32 (0..4294967295)
   ACCESS     read-only
   STATUS     mandatory
   DESCRIPTION
     "This attribute displays the call reference number which is a unique 
      number generated by the switch.The same Call Reference Number 
      is stored in the interval data (accounting record) at both ends of the 
      call. It can be used as one of the attributes in matching duplicate 
      records generated at each end of the call."
::= { mscVctVcfrIntdEntry 7 }

mscVctVcfrFrdTable OBJECT-TYPE
   SYNTAX     SEQUENCE OF MscVctVcfrFrdEntry
   ACCESS     not-accessible
   STATUS     mandatory
   DESCRIPTION
     "This group defines Frame Relay attributes collected by Frame Relay 
      Vc.
      The purpose of Vc attributes is to aid end users and verification 
      people to understand the Vc internal behavior. This is particularly 
      useful when the network has experienced abnormality and we want 
      to isolate problems and pinpoint trouble spots. 
      Attributes are collected on a per Vc basis. Until a need is identified, 
      statistics are not collected at a processor level. Each attribute is 
      stored in a 32 bit field and is initialized to zero when a Vc enters 
      into the data transfer state. When a PVC is disconnected and then 
      connected again, the attributes will be reset. Attributes cannot be 
      reset through other methods. 
      Frame Relay Vc uses a best effort data packet delivery protocol and 
      a different packet segmentation and combination methods from the 
      General Vc. The Frame Relay Vc uses the same call setup and 
      control mechanism (e.g. the support of non-flow control data 
      packets) as in a General Vc. Most General Vc statistics and internal 
      variables are used in a Frame Relay Vc and are displayed by 
      software developers"
::= { mscVctVcfr 12 }

mscVctVcfrFrdEntry OBJECT-TYPE
   SYNTAX     MscVctVcfrFrdEntry
   ACCESS     not-accessible
   STATUS     mandatory
   DESCRIPTION
     "An entry in the mscVctVcfrFrdTable."
   INDEX {
      mscVctIndex,
      mscVctVcfrIndex }
::= { mscVctVcfrFrdTable 1 }

MscVctVcfrFrdEntry ::= SEQUENCE {
   mscVctVcfrFrmCongestedToSubnet
      Unsigned32,
   mscVctVcfrCannotForwardToSubnet
      Unsigned32,
   mscVctVcfrNotDataXferToSubnet
      Unsigned32,
   mscVctVcfrOutOfRangeFrmFromSubnet
      Unsigned32,
   mscVctVcfrCombErrorsFromSubnet
      Unsigned32,
   mscVctVcfrDuplicatesFromSubnet
      Unsigned32,
   mscVctVcfrNotDataXferFromSubnet
      Unsigned32,
   mscVctVcfrFrmLossTimeouts
      Unsigned32,
   mscVctVcfrOoSeqByteCntExceeded
      Unsigned32,
   mscVctVcfrPeakOoSeqPktCount
      Unsigned32,
   mscVctVcfrPeakOoSeqFrmForwarded
      Unsigned32,
   mscVctVcfrSendSequenceNumber
      Unsigned32,
   mscVctVcfrPktRetryTimeouts
      Unsigned32,
   mscVctVcfrPeakRetryQueueSize
      Unsigned32,
   mscVctVcfrSubnetRecoveries
      Unsigned32,
   mscVctVcfrOoSeqPktCntExceeded
      Unsigned32,
   mscVctVcfrPeakOoSeqByteCount
      Unsigned32 }

mscVctVcfrFrmCongestedToSubnet OBJECT-TYPE
   SYNTAX     Unsigned32 (0..5000)
   ACCESS     read-only
   STATUS     mandatory
   DESCRIPTION
     "This attribute displays the number of frames from link discarded 
      due to lack of resources. It keeps track of the number of frames 
      from link that have to be discarded. The discard reasons include 
      insufficient memory for splitting the frame into smaller subnet 
      packet size."
::= { mscVctVcfrFrdEntry 2 }

mscVctVcfrCannotForwardToSubnet OBJECT-TYPE
   SYNTAX     Unsigned32 (0..5000)
   ACCESS     read-only
   STATUS     mandatory
   DESCRIPTION
     "This attribute displays the number of discarded packets that can not 
      be forwarded into the subnet because of subnet congestion.
      Number of frames from link discarded due to failure in forwarding 
      a packet from Vc into the subnet.- This attribute is increased when 
      packet forwarding fails to forward a packet into the subnet. If a 
      frame is split into multiple subnet packets and a partial packet has 
      to be discarded, all subsequent partial packets that have not yet been 
      delivered to the subnet will be discarded as well."
::= { mscVctVcfrFrdEntry 3 }

mscVctVcfrNotDataXferToSubnet OBJECT-TYPE
   SYNTAX     Unsigned32 (0..5000)
   ACCESS     read-only
   STATUS     mandatory
   DESCRIPTION
     "This attribute records the number of frames from link discarded 
      when the Vc tries to recover from internal path failure."
::= { mscVctVcfrFrdEntry 4 }

mscVctVcfrOutOfRangeFrmFromSubnet OBJECT-TYPE
   SYNTAX     Unsigned32 (0..5000)
   ACCESS     read-only
   STATUS     mandatory
   DESCRIPTION
     "This attribute displays the number of frames from subnet discarded 
      due to out of sequence range for arriving too late."
::= { mscVctVcfrFrdEntry 5 }

mscVctVcfrCombErrorsFromSubnet OBJECT-TYPE
   SYNTAX     Unsigned32 (0..5000)
   ACCESS     read-only
   STATUS     mandatory
   DESCRIPTION
     "This attribute records the number of subnet packets discarded at the 
      sink Vc due to the Vc segmentation and combination protocol error. 
      Usually, this occurs when the subnet discards packets and thus this 
      statistics can be used to guest the number of subnet packets that are 
      not delivered to the Vc. It cannot be used as an actual measure 
      because some subnet packets may have been delivered to Vc but 
      have to be discarded because these are partial packets to a frame in 
      which some other partial packets have not been properly delivered 
      to Vc"
::= { mscVctVcfrFrdEntry 6 }

mscVctVcfrDuplicatesFromSubnet OBJECT-TYPE
   SYNTAX     Unsigned32 (0..5000)
   ACCESS     read-only
   STATUS     mandatory
   DESCRIPTION
     "This attribute displays the number of subnet packets discarded due 
      to duplication. Although packets are not retransmitted by the Frame 
      Relay Vc, it is possible for the subnet to retransmit packets. When 
      packets are out-of-sequenced and copies of the same packets arrive, 
      then this attribute is increased."
::= { mscVctVcfrFrdEntry 7 }

mscVctVcfrNotDataXferFromSubnet OBJECT-TYPE
   SYNTAX     Unsigned32 (0..5000)
   ACCESS     read-only
   STATUS     mandatory
   DESCRIPTION
     "This attribute displays the number of subnet packets discarded when 
      data transfer is suspended in Vc recovery."
::= { mscVctVcfrFrdEntry 8 }

mscVctVcfrFrmLossTimeouts OBJECT-TYPE
   SYNTAX     Unsigned32 (0..5000)
   ACCESS     read-only
   STATUS     mandatory
   DESCRIPTION
     "This attribute displays the number of lost frame timer expiries.
      When this count is excessive, the network is very congested and 
      packets have been discarded in the subnet."
::= { mscVctVcfrFrdEntry 9 }

mscVctVcfrOoSeqByteCntExceeded OBJECT-TYPE
   SYNTAX     Unsigned32 (0..5000)
   ACCESS     read-only
   STATUS     mandatory
   DESCRIPTION
     "This attribute displays the number times that the out of sequence 
      byte threshold is exceeded. When the threshold is exceeded, this 
      condition is treated as if the loss frame timer has expired and all 
      frames queued at the sink Vc are delivered to the AP. We need to 
      keep this count to examine if the threshold is engineered properly. 
      This should be used in conjunction with the peak value of out-of-
      sequenced queue and the number of times the loss frame timer has 
      expired. This count should be relatively small when compared with 
      loss frame timer expiry count."
::= { mscVctVcfrFrdEntry 10 }

mscVctVcfrPeakOoSeqPktCount OBJECT-TYPE
   SYNTAX     Unsigned32 (0..5000)
   ACCESS     read-only
   STATUS     mandatory
   DESCRIPTION
     "This attribute displays the frame relay peak packet count of the out 
      of sequence queue. This attribute records the maximum queue 
      length of the out-of-sequenced queue. The counter can be used to 
      deduce the message buffer requirement on a Vc."
::= { mscVctVcfrFrdEntry 11 }

mscVctVcfrPeakOoSeqFrmForwarded OBJECT-TYPE
   SYNTAX     Unsigned32 (0..5000)
   ACCESS     read-only
   STATUS     mandatory
   DESCRIPTION
     "This attribute displays the frame relay peak size of the 
      sequence packet queue. The subnet may deliver packets out-of-
      sequenced. These packets are then queued in an out-of-sequenced 
      queue, waiting for a packet with the expected sequence number to 
      come. When that packet arrives, this attribute records the maximum 
      number of packets that were out-of-sequenced, but now have 
      become in-sequenced. The statistics is used to measure expected 
      queue size due to normal subnet packet disorder (not due to subnet 
      packet discard). Current implementation also uses this statistics to 
      set a maximum size for the out-of-sequenced queue."
::= { mscVctVcfrFrdEntry 12 }

mscVctVcfrSendSequenceNumber OBJECT-TYPE
   SYNTAX     Unsigned32 (0..5000)
   ACCESS     read-only
   STATUS     mandatory
   DESCRIPTION
     "This attribute displays the Vc internal packet's send sequence 
      number. Note that a 'packet' in this context, may be either a user 
      data packet, or an OAM frame."
::= { mscVctVcfrFrdEntry 13 }

mscVctVcfrPktRetryTimeouts OBJECT-TYPE
   SYNTAX     Unsigned32 (0..5000)
   ACCESS     read-only
   STATUS     mandatory
   DESCRIPTION
     "This attribute displays the number of packets which have 
      retransmission time-outs. When this count is excessive, the network 
      is very congested and packets have been discarded in the subnet."
::= { mscVctVcfrFrdEntry 15 }

mscVctVcfrPeakRetryQueueSize OBJECT-TYPE
   SYNTAX     Unsigned32 (0..5000)
   ACCESS     read-only
   STATUS     mandatory
   DESCRIPTION
     "This attribute displays the peak size of retransmission queue.
      This attribute is used as an indicator of the acknowledgment 
      behavior across the subnet. Records the largest body of 
      unacknowledged packets."
::= { mscVctVcfrFrdEntry 16 }

mscVctVcfrSubnetRecoveries OBJECT-TYPE
   SYNTAX     Unsigned32 (0..5000)
   ACCESS     read-only
   STATUS     mandatory
   DESCRIPTION
     "This attribute displays the number of successful Vc recovery 
      attempts."
::= { mscVctVcfrFrdEntry 17 }

mscVctVcfrOoSeqPktCntExceeded OBJECT-TYPE
   SYNTAX     Unsigned32 (0..255)
   ACCESS     read-only
   STATUS     mandatory
   DESCRIPTION
     "This attribute displays the number times that the out of sequence 
      packet threshold is exceeded. When the threshold is exceeded, this 
      condition is treated as if the loss frame timer has expired and all 
      frames queued at the sink Vc are delivered to the AP. We need to 
      keep this count to examine if the threshold is engineered properly. 
      This should be used in conjunction with the peak value of out-of-
      sequenced queue and the number of times the loss frame timer has 
      expired. This count should be relatively small when compared with 
      loss frame timer expiry count."
::= { mscVctVcfrFrdEntry 19 }

mscVctVcfrPeakOoSeqByteCount OBJECT-TYPE
   SYNTAX     Unsigned32 (0..50000)
   ACCESS     read-only
   STATUS     mandatory
   DESCRIPTION
     "This attribute displays the frame relay peak byte count of the out of 
      sequence queue. This attribute records the maximum queue length 
      of the out-of-sequenced queue. The counter can be used to deduce 
      the message buffer requirement on a Vc."
::= { mscVctVcfrFrdEntry 20 }

mscVctVcfrDmepTable OBJECT-TYPE
   SYNTAX     SEQUENCE OF MscVctVcfrDmepEntry
   ACCESS     not-accessible
   STATUS     mandatory
   DESCRIPTION
     "This attribute displays the data path used by the connection. Data 
      path is provisioned in Dna and DirectCall components.
      
      If the connection is using dprsOnly data path, this attribute is 
      empty.
      
      If the connection is using dprsMcsOnly or dprsMcsFirst data path, 
      this attribute displays component name of the dprsMcsEndPoint."
::= { mscVctVcfr 417 }

mscVctVcfrDmepEntry OBJECT-TYPE
   SYNTAX     MscVctVcfrDmepEntry
   ACCESS     not-accessible
   STATUS     mandatory
   DESCRIPTION
     "An entry in the mscVctVcfrDmepTable."
   INDEX {
      mscVctIndex,
      mscVctVcfrIndex,
      mscVctVcfrDmepValue }
::= { mscVctVcfrDmepTable 1 }

MscVctVcfrDmepEntry ::= SEQUENCE {
   mscVctVcfrDmepValue
      RowPointer }

mscVctVcfrDmepValue OBJECT-TYPE
   SYNTAX     RowPointer 
   ACCESS     read-only
   STATUS     mandatory
   DESCRIPTION
     "This variable represents both the value and the index for the
      mscVctVcfrDmepTable."
::= { mscVctVcfrDmepEntry 1 }




-- 
-- Version and Compliance statements
-- 



-- Object-Group Statement:
-- A list of all current accessible leaf objects.

-- OBJECTS { mscVctDcRemoteLcn,
--           mscVctDnaIncHighPriorityReverseCharge,
--           mscVctVcPriority,
--           mscVctVcPeakOoSeqFrmForwarded,
--           mscVctVcSegmentsRx,
--           mscVctDnaCugRowStatus,
--           mscVctVcfrType,
--           mscVctVcfrSegmentSize,
--           mscVctVcfrSegmentsSent,
--           mscVctDnaPacketSizeNegotiation,
--           mscVctDcCfaRowStatus,
--           mscVctVcMaxSubnetPktSize,
--           mscVctDnaIncFastSelect,
--           mscVctVcfrPreviousDiagnosticCode,
--           mscVctVcPathReliability,
--           mscVctVcfrPreviousState,
--           mscVctVcfrFrmCongestedToSubnet,
--           mscVctComponentName,
--           mscVctDcCugIndex,
--           mscVctVcLocalTxWindowSize,
--           mscVctDcCugType,
--           mscVctVcfrPriority,
--           mscVctDnaFastSelectCallsOnly,
--           mscVctDnaIncIntlNormalCharge,
--           mscVctDnaCug0AsNonCugCall,
--           mscVctDnaOutPathSensitivitySignal,
--           mscVctDnaHgMStorageType,
--           mscVctDnaCugDnic,
--           mscVctDnaHgMAvailabilityUpdateThreshold,
--           mscVctDnaOutFsRestrictedResponse,
--           mscVctDcDfaRowStatus,
--           mscVctVcfrSubnetRecoveries,
--           mscVctDnaDefaultSendToNetworkPacketSize,
--           mscVctDnaComponentName,
--           mscVctVcDuplicatesFromSubnet,
--           mscVctVcStorageType,
--           mscVctDnaAccountClass,
--           mscVctVcfrFastSelectCall,
--           mscVctVcfrCalledLcn,
--           mscVctDnaRpoa,
--           mscVctVcfrComponentName,
--           mscVctDcDfaValue,
--           mscVctVcDiagnosticCode,
--           mscVctDcRowStatus,
--           mscVctDnaHgMHgAddrComponentName,
--           mscVctVcfrCallingNpi,
--           mscVctRowStatus,
--           mscVctVcLocalRxWindowSize,
--           mscVctVcOutOfRangeFrmFromSubnet,
--           mscVctDnaHgMRowStatus,
--           mscVctVcCallingLcn,
--           mscVctVcWindowClosuresToSubnet,
--           mscVctDnaOutCalls,
--           mscVctVcfrOoSeqByteCntExceeded,
--           mscVctDcCfaValue,
--           mscVctDnaPreselectRpoa,
--           mscVctVcSegmentsSent,
--           mscVctDnaOutAccess,
--           mscVctDnaHgMMaxAvailableChannels,
--           mscVctVcfrEmissionPriorityToNetwork,
--           mscVctVcCalledDna,
--           mscVctVcType,
--           mscVctVcStartTime,
--           mscVctDnaOutFsUnrestrictedResponse,
--           mscVctDnaDefaultRecvFrmNetworkWindowSize,
--           mscVctVcfrCalledDna,
--           mscVctDnaNumberingPlanIndicator,
--           mscVctDcDiscardPriority,
--           mscVctVcfrCallReferenceNumberDecimal,
--           mscVctVcfrState,
--           mscVctVcPreviousState,
--           mscVctDnaHgMAvailableChannels,
--           mscVctVcSubnetRecoveries,
--           mscVctDcRemoteNpi,
--           mscVctVcPeakRetryQueueSize,
--           mscVctVcLocalTxPktSize,
--           mscVctDnaDefaultTransferPriority,
--           mscVctVcfrMaxSubnetPktSize,
--           mscVctVcAccountingEnabled,
--           mscVctVcfrSendSequenceNumber,
--           mscVctDnaDataNetworkAddress,
--           mscVctDcType,
--           mscVctVcSegmentSize,
--           mscVctDnaAccountCollection,
--           mscVctVcFastSelectCall,
--           mscVctVcfrPeakOoSeqByteCount,
--           mscVctDnaCugFormat,
--           mscVctDnaStorageType,
--           mscVctVcfrFrmLossTimeouts,
--           mscVctDnaCugType,
--           mscVctDcLocalNpi,
--           mscVctDnaIncNormalPriorityReverseCharge,
--           mscVctDnaHgMHgAddrDataNetworkAddress,
--           mscVctVcfrStorageType,
--           mscVctVcComponentName,
--           mscVctDnaOutDefaultPriority,
--           mscVctDnaOutDefaultPathReliability,
--           mscVctDnaIncCalls,
--           mscVctVcSubnetRxPktSize,
--           mscVctVcWindowClosuresFromSubnet,
--           mscVctVcfrEmissionPriorityFromNetwork,
--           mscVctDnaHgMHgAddrStorageType,
--           mscVctDcStorageType,
--           mscVctDnaOutHighPriority,
--           mscVctDnaIncAccess,
--           mscVctVcSubnetTxWindowSize,
--           mscVctVcfrAccountingEnd,
--           mscVctVcLocalRxPktSize,
--           mscVctVcfrCalledNpi,
--           mscVctVcfrPktRetryTimeouts,
--           mscVctDnaEgressAccounting,
--           mscVctVcfrPeakOoSeqPktCount,
--           mscVctVcAckStackingTimeouts,
--           mscVctVcCalledLcn,
--           mscVctDnaOutForceReverseCharge,
--           mscVctVcFrmRetryTimeouts,
--           mscVctVcPeakOoSeqQueueSize,
--           mscVctDnaRowStatus,
--           mscVctDnaHgMAvailabilityDelta,
--           mscVctDcSvcAutoCallRetry,
--           mscVctVcPreviousDiagnosticCode,
--           mscVctVcfrRowStatus,
--           mscVctVcfrDataPath,
--           mscVctDnaIncChargeTransfer,
--           mscVctDcDataPath,
--           mscVctDnaCugComponentName,
--           mscVctVcfrCannotForwardToSubnet,
--           mscVctDnaHgMHgAddrRowStatus,
--           mscVctDnaTransferPriorityOverRide,
--           mscVctVcfrOoSeqPktCntExceeded,
--           mscVctDnaIncSameService,
--           mscVctDnaDefaultRecvFrmNetworkThruputClass,
--           mscVctDnaCugOutCalls,
--           mscVctDnaCugInterlockCode,
--           mscVctDnaServiceCategory,
--           mscVctDnaServiceExchange,
--           mscVctVcTransferPriorityFromNetwork,
--           mscVctLogicalProcessor,
--           mscVctVcfrRcosToNetwork,
--           mscVctVcPeakStackedAcksRx,
--           mscVctVcfrOutOfRangeFrmFromSubnet,
--           mscVctVcfrAccountingEnabled,
--           mscVctVcfrCombErrorsFromSubnet,
--           mscVctDnaPacketSizes,
--           mscVctVcfrCallingDna,
--           mscVctDnaHgMHgAddrNumberingPlanIndicator,
--           mscVctVcfrPeakRetryQueueSize,
--           mscVctDnaOutPathReliabilityOverRide,
--           mscVctVcfrPeakOoSeqFrmForwarded,
--           mscVctVcfrSegmentsRx,
--           mscVctDcRemoteDna,
--           mscVctDnaOutPathReliabilitySignal,
--           mscVctVcName,
--           mscVctDnaSignalIntlAddressToLink,
--           mscVctVcAccountingEnd,
--           mscVctDnaOutIntl,
--           mscVctDcIfaRowStatus,
--           mscVctVcfrElapsedTimeTillNow,
--           mscVctDnaDefaultSendToNetworkWindowSize,
--           mscVctDnaCugPreferential,
--           mscVctDnaOutReverseCharge,
--           mscVctVcfrNotDataXferFromSubnet,
--           mscVctDcComponentName,
--           mscVctVcSubnetTxPktSize,
--           mscVctVcCalledNpi,
--           mscVctDnaDefaultRecvFrmNetworkPacketSize,
--           mscVctVcElapsedTimeTillNow,
--           mscVctDcIfaValue,
--           mscVctVcfrPathReliability,
--           mscVctDnaHgMComponentName,
--           mscVctVcSubnetRxWindowSize,
--           mscVctVcfrNotDataXferToSubnet,
--           mscVctVcCallReferenceNumberDecimal,
--           mscVctVcTransferPriorityToNetwork,
--           mscVctVcfrRcosFromNetwork,
--           mscVctVcRowStatus,
--           mscVctVcfrDuplicatesFromSubnet,
--           mscVctDnaCugStorageType,
--           mscVctVcfrStartTime,
--           mscVctVcCallingNpi,
--           mscVctDnaCugPrivileged,
--           mscVctVcfrDmepValue,
--           mscVctVcWrTriggers,
--           mscVctVcState,
--           mscVctDnaOutNormalPriority,
--           mscVctDnaCugIncCalls,
--           mscVctDcUserData,
--           mscVctDcLocalDna,
--           mscVctDnaIncIntlReverseCharge,
--           mscVctDnaSignalPreferentialCugToLink,
--           mscVctDnaOutNormalCharge,
--           mscVctVcfrDiagnosticCode,
--           mscVctVcfrCallingLcn,
--           mscVctStorageType,
--           mscVctDnaDefaultSendToNetworkThruputClass,
--           mscVctVcCallingDna,
--           mscVctDnaDataPath }
-- STATUS  mandatory
-- DESCRIPTION
--   "A list of all current accessible leaf objects."

vcTesterGroup OBJECT IDENTIFIER ::= { vcTesterMIB 1 }
vcTesterGroupCA OBJECT IDENTIFIER ::= { vcTesterGroup 1 }
vcTesterGroupCA02 OBJECT IDENTIFIER ::= { vcTesterGroupCA 3 }
vcTesterGroupCA02A OBJECT IDENTIFIER ::= { vcTesterGroupCA02 2 }



-- Agent-Capabilities Statement:

-- PRODUCT-RELEASE "MscPassport Release 1.2 VcTester."
-- STATUS          mandatory
-- DESCRIPTION     "Carrier Passport VcTester MIB: MIB Version CA02A,
--                  Software Version CA02S9C."
-- SUPPORTS        Nortel-MsCarrier-MscPassport-VcTesterMIB
--    INCLUDES     { vcTesterGroupCA02A }

vcTesterCapabilities OBJECT IDENTIFIER ::= { vcTesterMIB 3 }
vcTesterCapabilitiesCA OBJECT IDENTIFIER ::= { vcTesterCapabilities 1 }
vcTesterCapabilitiesCA02 OBJECT IDENTIFIER ::= { vcTesterCapabilitiesCA 3 }
vcTesterCapabilitiesCA02A OBJECT IDENTIFIER ::= { vcTesterCapabilitiesCA02 2 }





END
