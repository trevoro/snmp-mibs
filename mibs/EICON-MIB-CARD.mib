-- Documents: 285-517-1.

EICON-MIB-CARD DEFINITIONS  ::=  BEGIN


IMPORTS
	TimeTicks, enterprises
		FROM RFC1155-SMI
	OBJECT-TYPE
		FROM RFC-1212
	TRAP-TYPE
		FROM RFC-1215
	DisplayString, sysName
		FROM RFC1213-MIB;

eicon           OBJECT IDENTIFIER  ::= { enterprises 434 }
management      OBJECT IDENTIFIER  ::= { eicon 2 }
mibv2           OBJECT IDENTIFIER  ::= { management 2 }
module          OBJECT IDENTIFIER  ::= { mibv2 4 }

--      Title

card    OBJECT IDENTIFIER  ::= { mibv2 2 }

--      The card group contains information about all EiconCards in the server.  The information is 
--      organized in following tables:
--              cardTable,
--              cardHardwareTable,
--              cardSoftwareTable,
--              cardBiosSessionTable.

OperState ::= INTEGER {
	other (1),              -- none of what follows
	disabled (2),           -- not in ready state
	ready (3),              -- in ready state
	active (4),             -- ready and operating
	busy (5)                        -- operating but cannot accept more traffic
	}

CardAdminState ::= INTEGER {
	start (1),
	stop (2),
	dump (3),
	test (4),
	invalid (5),
	reset (6)
	}

ActionState ::= INTEGER {
	done (1),
	failed (2),
	in-progress (3)
	}


EiconCardType ::= INTEGER {
	ect-NONE (1),
	ect-PC-NA (2),
	ect-PC-DNA (3),
	ect-PC-SPNA (4),
	ect-MC-SPCC (5),
	ect-PC-DPNA (6),
	ect-PC-EC (7),
	ect-PC-ECHSI (8),
	ect-PC-QPNA (9),
	ect-PC-MPNA (10),
	ect-MC-EC (11),
	ect-MC-HSI (12),
	ect-XX-DIGI (13),
	ect-MC-IMC (14),
	ect-PC-IMC (15),
	ect-MC-MPNA (16),       
	ect-PC-HSI1M (17),
	ect-MC-HSI1M (18),
	ect-NB-HSI1M (19),
	ect-PC-EC1M (20),
	ect-MC-EC1M (21),
	ect-NB-EC1M (22),
	ect-NB-IMC (23),
	ect-NB-SPCC (24),
	ect-NB-EC (25),
	ect-PC-ACC8 (26),
	ect-PC-ISDN (27),
	ect-PC-DPNA2M (28),
	ect-PC-MPNA2M (29),
	ect-MC-MPNA2M (30),
	ect-MC-SPCC2 (31),
	ect-PP-IMC (32),
	ect-MC-ISDN (33),
	ect-PP-EC (34),
	ect-PC-HSI2 (35),
	ect-PC-S51 (36),
	ect-PC-S52 (37)
	}

CardRef ::= INTEGER (1..6)      -- EiconCard reference on the server.

PortRef ::= INTEGER (1..48)     -- Port reference on the server.

PositiveInteger ::= INTEGER (0..2147483647)


cardNumberOfCards       OBJECT-TYPE
	SYNTAX  PositiveInteger
	ACCESS  read-only 
	STATUS  mandatory
	DESCRIPTION
		"The number of EiconCards seen by the Agent."
	::= { card 1 }

cardTable               OBJECT-TYPE
	SYNTAX  SEQUENCE OF  CardEntry
	ACCESS  not-accessible
	STATUS  mandatory
	DESCRIPTION     
		"The table of EiconCards as seen by the agent."
	::= { card 2 }

cardEntry               OBJECT-TYPE
	SYNTAX  CardEntry
	ACCESS  not-accessible
	STATUS  mandatory
	DESCRIPTION     
		"The set of attributes for one EiconCard."
	INDEX           { cardIndex }
	::= { cardTable 1 }
   
CardEntry ::= SEQUENCE {
	cardIndex
		CardRef,
	cardName
		DisplayString,
	cardType
		EiconCardType,
	cardOperState
		OperState,
	cardAdminStateCtr
		CardAdminState,
	cardDomainConfigDirName
		DisplayString,
	cardLoadTime
		TimeTicks,
	cardActionState
		ActionState,
	cardActionError
		INTEGER,
	cardActionOutputFile
		DisplayString,
	cardProtocols
		INTEGER
	}

cardIndex               OBJECT-TYPE
	SYNTAX  CardRef
	ACCESS  read-only 
	STATUS  mandatory
	DESCRIPTION     
		"The ID of the EiconCard provided by  the local administrator"
	::= { cardEntry 1 }

cardName                OBJECT-TYPE
	SYNTAX  DisplayString (SIZE(0..16))
	ACCESS  read-only 
	STATUS  mandatory
	DESCRIPTION     
		"The name of the EiconCard given by the local administration."
	::= { cardEntry 2 }

cardType                OBJECT-TYPE
	SYNTAX  EiconCardType   
	ACCESS  read-only 
	STATUS  mandatory
	DESCRIPTION     
		"The type of the EiconCard.  The value '0' indicates that the row is invalid."
	::= { cardEntry 3 }
 
cardOperState           OBJECT-TYPE
	SYNTAX  OperState
	ACCESS  read-only 
	STATUS  mandatory
	DESCRIPTION     
		"The EiconCard operational state."
	::= { cardEntry 4 }

cardAdminStateCtr       OBJECT-TYPE
	SYNTAX  CardAdminState
	ACCESS  read-write 
	STATUS  mandatory
	DESCRIPTION     
		"The administrative state of the EiconCard.  Management station can 
		modify the value of that parameter in order to perform a 
		specific action on the EiconCard. Value 'start' is used to 
		start the EiconCard, value 'stop' is used to stop the EiconCard. Value
		'dump' is used to dump the EiconCard and value 'test'  is used to
		test the EiconCard hardware.  Before the EiconCard is started, the Agent
		will read the name of the configuration file directory to be 
		used from the srvDomainConfigDir.  Agent will respond to that 
		request immediately and start the action.  The Management 
		station will poll the cardActionState variable to find out the 
		results of the action and the cardActionError variable to find 
		the error code in the case of the action failure. If the action
		produces an output file, then the mib variable 
		cardActionOutputFile has to be initialized by the Management 
		station."
	::= { cardEntry 5 }

cardDomainConfigDirName OBJECT-TYPE
	SYNTAX  DisplayString (SIZE(0..256))
	ACCESS  read-only 
	STATUS  mandatory
	DESCRIPTION     
		"The name of the directory in the ESS from which the current 
		configuration file of the card has been taken.  The Agent will
		intialize this value (equal to srvDomainConfigDir) after the 
		card has been successfully started."
	::= { cardEntry 6 }

cardLoadTime            OBJECT-TYPE
	SYNTAX  TimeTicks
	ACCESS  read-only 
	STATUS  mandatory
	DESCRIPTION     
		"The time elapsed in seconds since the card was loaded."
	::= { cardEntry 7 }

cardActionState         OBJECT-TYPE
	SYNTAX  ActionState
	ACCESS  read-only 
	STATUS  mandatory
	DESCRIPTION     
		"The state of the operation performed on the card by the Agent 
		as a result of setting the values to the cardAdminStateCtr. 
		The Management station will poll that variable after initiating
		an action on the card.  The value done(1) indicates that the 
		action terminated successfully. The value failed(2) indicates 
		that the action terminated with an error. In this case the 
		variable cardActionError indicates the error code."
	::= { cardEntry 8 }

cardActionError         OBJECT-TYPE
	SYNTAX  INTEGER
	ACCESS  read-only 
	STATUS  mandatory
	DESCRIPTION     
		"The error code displayed by an unsuccessful operation."
	::= { cardEntry 9 }

cardActionOutputFile    OBJECT-TYPE
	SYNTAX  DisplayString (SIZE(0..256))
	ACCESS  read-write 
	STATUS  mandatory
	DESCRIPTION     
		"The name of file which contains the output of the requested
		action, ex. 'dump' or 'test'. The default filename
		is dump<x> or test<x>; where <x> is the card number"
	::= { cardEntry 10 }

cardProtocols           OBJECT-TYPE
	SYNTAX  INTEGER
	ACCESS  read-only 
	STATUS  mandatory
	DESCRIPTION     
		"The mask indicating which protocols are installed on the card.
		snapc=0x10, snafm=0x20, appc=0x40, llc=0x80,
		xport_iso=0x200, xport_tgx=0x400, netview=0x800"
	::= { cardEntry 11 }


cardHardwareTable       OBJECT-TYPE
	SYNTAX  SEQUENCE OF  CardHardwareEntry
	ACCESS  not-accessible
	STATUS  mandatory
	DESCRIPTION     
		"The table of the EiconCards as seen by the Agent."
	::= { card 3 }

cardHardwareEntry       OBJECT-TYPE
	SYNTAX  CardHardwareEntry
	ACCESS  not-accessible
	STATUS  mandatory
	DESCRIPTION     
		"The set of hardware attributes for each card."
	INDEX   { cardHardCardRef }
	::= { cardHardwareTable 1 }
   
--      The following is the list of all cardHarwareEntry attributes.

CardHardwareEntry ::= SEQUENCE {
	cardHardCardRef
		CardRef,
	cardHardMemAddr
		INTEGER,
	cardHardIoAddr
		INTEGER,
	cardHardIntrLevel
		INTEGER,
	cardHardNbOfPorts
		PortRef,
	cardHardSlotNumber
		INTEGER,
	cardHardVersion                 -- Not supported by Eicon Agent
		DisplayString,
	cardHardSerialNb                -- Not supported by Eicon Agent
		PositiveInteger,
	cardHardComponents              -- Not supported by Eicon Agent
		DisplayString
	}

cardHardCardRef         OBJECT-TYPE
	SYNTAX  CardRef
	ACCESS  read-only 
	STATUS  mandatory
	DESCRIPTION     
		"The ID of the EiconCard that should match the cardIndex from the cardTable."
	::= { cardHardwareEntry 1 }

cardHardMemAddr OBJECT-TYPE
	SYNTAX  INTEGER
	ACCESS  read-only 
	STATUS  mandatory
	DESCRIPTION     
		"The EiconCard memory segment address."
	::= { cardHardwareEntry 2 }

cardHardIoAddr          OBJECT-TYPE
	SYNTAX  INTEGER (1..9999)
	ACCESS  read-only 
	STATUS  mandatory
	DESCRIPTION     
		"The EiconCard IO address."
	::= { cardHardwareEntry 3 }

cardHardIntrLevel       OBJECT-TYPE
	SYNTAX  INTEGER (1..99)
	ACCESS  read-only 
	STATUS  mandatory
	DESCRIPTION     
		"The EiconCard interrupt level."
	::= { cardHardwareEntry 4 }

cardHardNbOfPorts       OBJECT-TYPE
	SYNTAX  PortRef
	ACCESS  read-only 
	STATUS  mandatory
	DESCRIPTION     
		"The number of ports on the EiconCard."
	::= { cardHardwareEntry 5 }

cardHardSlotNumber      OBJECT-TYPE
	SYNTAX  INTEGER (1..8)
	ACCESS  read-only 
	STATUS  mandatory
	DESCRIPTION     
		"The slot number for MicroChannel."
	::= { cardHardwareEntry 6 }

cardHardVersion         OBJECT-TYPE
	SYNTAX  DisplayString (SIZE(0..16))
	ACCESS  read-only 
	STATUS  mandatory
	DESCRIPTION     
		"The hardware version of the EiconCard."
	::= { cardHardwareEntry 7 }

cardHardSerialNb        OBJECT-TYPE
	SYNTAX  PositiveInteger
	ACCESS  read-only 
	STATUS  mandatory
	DESCRIPTION     
		"The EiconCard serial number."
	::= { cardHardwareEntry 8 }

cardHardComponents      OBJECT-TYPE
	SYNTAX  DisplayString (SIZE(0..16))
	ACCESS  read-only 
	STATUS  mandatory
	DESCRIPTION     
		"The names of special hardware components."
	::= { cardHardwareEntry 9 }
 
cardSoftwareTable       OBJECT-TYPE
	SYNTAX  SEQUENCE OF  CardSoftwareEntry
	ACCESS  not-accessible
	STATUS  mandatory
	DESCRIPTION     
		"The table of all software modules (.elm) that are configured 
		for all EiconCards seen by the Agent.
		The configuration file from the directory srvProductLocalDirName 
		will be used by the Agent to provide that information"
	::= { card 4 }

cardSoftwareEntry       OBJECT-TYPE
	SYNTAX  CardSoftwareEntry
	ACCESS  not-accessible
	STATUS  mandatory
	DESCRIPTION     
		"The set of attributes for one software module and one card."
	INDEX   { cardSoftCardRef,  cardSoftModuleIndex }
	::= { cardSoftwareTable 1 }

CardSoftwareEntry ::= SEQUENCE {
	cardSoftCardRef
		CardRef,
	cardSoftModuleIndex
		PositiveInteger,
	cardSoftModuleName
		DisplayString,
	cardSoftVersion 
		DisplayString,
	cardSoftDateProd 
		DisplayString, --TimeTicks,
	cardSoftRealSize 
		PositiveInteger
	}

cardSoftCardRef         OBJECT-TYPE
	SYNTAX  CardRef
	ACCESS  read-only 
	STATUS  mandatory
	DESCRIPTION     
		"The ID of the EiconCard; should match the cardIndex from the cardTable."
	::= { cardSoftwareEntry 1 }

cardSoftModuleIndex     OBJECT-TYPE
	SYNTAX  PositiveInteger
	ACCESS  read-only 
	STATUS  mandatory
	DESCRIPTION     
		"The module index number given by the Agent."
	::= { cardSoftwareEntry 2 }

cardSoftModuleName      OBJECT-TYPE
	SYNTAX  DisplayString (SIZE(0..16))
	ACCESS  read-only 
	STATUS  mandatory
	DESCRIPTION     
		"The module name."
	::= { cardSoftwareEntry 3 }

cardSoftVersion         OBJECT-TYPE
	SYNTAX  DisplayString (SIZE(0..16))
	ACCESS  read-only 
	STATUS  mandatory
	DESCRIPTION     
		"The module version string found inside the module."
	::= { cardSoftwareEntry 4 }

cardSoftDateProd        OBJECT-TYPE
	SYNTAX  DisplayString (SIZE(0..16))
	ACCESS  read-only 
	STATUS  mandatory
	DESCRIPTION     
		"The module production date found inside the module."
	::= { cardSoftwareEntry 5 }

cardSoftRealSize                OBJECT-TYPE
	SYNTAX  PositiveInteger
	ACCESS  read-only 
	STATUS  mandatory
	DESCRIPTION     
		"The module size (in bytes).  If the value is '0' then this entry is invalid."
	::= { cardSoftwareEntry 6 }

cardBiosSessionTable    OBJECT-TYPE
	SYNTAX  SEQUENCE OF  CardBiosSessionEntry
	ACCESS  not-accessible
	STATUS  mandatory
	DESCRIPTION     
		"The table of all sessions handled by the BIOS task for all cards."
	::= { card 5 }

cardBiosSessionEntry    OBJECT-TYPE
	SYNTAX  CardBiosSessionEntry
	ACCESS  not-accessible
	STATUS  mandatory
	DESCRIPTION     
		"The set of attributes for one session and one card."
	INDEX   { cardBiosSsnCardRef,  cardBiosSsnIndex }
	::= { cardBiosSessionTable 1 }

CardBiosSessionEntry ::= SEQUENCE {
	cardBiosSsnCardRef
		CardRef,
	cardBiosSsnIndex
		PositiveInteger,
	cardBiosSsnLsn
		PositiveInteger,
	cardBiosSsnPortRef
		PortRef,
	cardBiosSsnOperState
		INTEGER,
	cardBiosSsnProtocol
		INTEGER,
	cardBiosSsnApplName
		DisplayString,
	cardBiosSsnStartTime
		TimeTicks
	}

cardBiosSsnCardRef      OBJECT-TYPE
	SYNTAX  CardRef
	ACCESS  read-only 
	STATUS  mandatory
	DESCRIPTION     
		"The ID of the EiconCard; should match the cardIndex from the cardTable."
	::= { cardBiosSessionEntry 1 }

cardBiosSsnIndex        OBJECT-TYPE
	SYNTAX  PositiveInteger
	ACCESS  read-only 
	STATUS  mandatory
	DESCRIPTION     
		"The session index given by the Agent."
	::= { cardBiosSessionEntry 2 }

cardBiosSsnLsn          OBJECT-TYPE
	SYNTAX  PositiveInteger
	ACCESS  read-only 
	STATUS  mandatory
	DESCRIPTION     
		"The logical (BIOS) session number."
	::= { cardBiosSessionEntry 3 }

cardBiosSsnPortRef      OBJECT-TYPE
	SYNTAX  PortRef
	ACCESS  read-only 
	STATUS  mandatory
	DESCRIPTION     
		"The reference of the port where the session is established; should match the portIndex 	
		from the portTable."
	::= { cardBiosSessionEntry 4 }

cardBiosSsnOperState    OBJECT-TYPE
	SYNTAX  INTEGER {
		other (1),
		listening (2),
		calling (3),
		connected (4),
		hangingup (5),
		hungup (6),
		aborted (7),
		wait-for-user (8)
		}
	ACCESS  read-only 
	STATUS  mandatory
	DESCRIPTION     
		"The state of the session."
	::= { cardBiosSessionEntry 5 }

cardBiosSsnProtocol     OBJECT-TYPE
	SYNTAX  INTEGER {
		other (1),
		sdlc (2),
		snapc (3),
		snafm (4),
		appc (5),
		dlc (6),
		dialer (7),
		xportiso (8),
		xporttgx (9),
		sndcf (10),
		x25 (11),
		hdlc (12),
		frbs (13),
		conmgr (14),
		remoteec (15)
		}
	ACCESS  read-only 
	STATUS  mandatory
	DESCRIPTION     
		"The protocol used by the session."
	::= { cardBiosSessionEntry 6 }

cardBiosSsnApplName     OBJECT-TYPE
	SYNTAX  DisplayString (SIZE(0..16))
	ACCESS  read-only 
	STATUS  mandatory
	DESCRIPTION     
		"The session Application Name"
	::= { cardBiosSessionEntry 7 }

cardBiosSsnStartTime    OBJECT-TYPE
	SYNTAX  TimeTicks
	ACCESS  read-only 
	STATUS  mandatory
	DESCRIPTION     
		"The time elapsed in seconds since session esablishment time."
	::= { cardBiosSessionEntry 8 }


--      This section contains the definition of card specific traps. 
--      Will not be implemented in the current release (ICSV3R2) of the Agent.

cardTrapHeartbeatLost   TRAP-TYPE       -- Not supported by Eicon Agent
	ENTERPRISE      eicon
	VARIABLES       { sysName,  cardIndex  }
	DESCRIPTION
		"The 'cardTrapHeartbeatLost'  trap indicates that a EiconCard stopped sending statics to 	
		the Agent."
	::=  21

cardTrapStateChange     TRAP-TYPE
	ENTERPRISE      eicon
	VARIABLES       { sysName,  cardIndex, cardOperState  }
	DESCRIPTION
		"The generic Internal trap indicates that the EiconCard has changed state."
  ::=  22


END
