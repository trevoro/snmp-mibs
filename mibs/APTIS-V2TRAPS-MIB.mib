--
--      Aptis Enterprise MIB
--      V2 Notifications Module (V2 SMI)
-- 
--	Nortel Networks
--	11 Elizabeth Drive
--	Chelmsford, MA 01824
--
--	Copyright (c) 1997-2000 Nortel Networks
--	All Rights Reserved.
--

--  Guidelines for modifying this file:
--  1) Do not use tabs, only spaces.
--  2) For trap pairs (e.g., down/up), use an odd number for the 1st
--     trap and an even number for the 2nd trap.  Generally, the 1st
--     trap would be the alarm causing trap and the 2nd one would be
--     the alarm clearing trap.
--  3) Alarm creating traps and alarm clearing traps should have the
--     same severity.  The most important reason for this is that if
--     a trap severity filter is on, if the user sees an alarm creating
--     trap, he/she should also be able to see the corresponding alarm
--     clearing trap.

APTIS-V2TRAPS-MIB DEFINITIONS ::= BEGIN

    IMPORTS
        snmp, ifIndex, egpNeighAddr
            FROM RFC1213-MIB
        TRAP-TYPE
            FROM RFC-1215
        OBJECT-IDENTITY, MODULE-IDENTITY, OBJECT-TYPE, NOTIFICATION-TYPE, IpAddress
            FROM SNMPv2-SMI
        DisplayString, RowStatus
            FROM SNMPv2-TC
        aptis-traps, Boolean
            FROM APTIS-MIB
        aptis-modules
            FROM APTIS-REG-MIB
        policyConfigSlotModemThresholdWarning,
        policyConfigChassisModemThresholdWarning      
            FROM APTIS-CONFIG-MIB;

    aptisTrapsModule MODULE-IDENTITY
        LAST-UPDATED "0004250000Z"
        ORGANIZATION "Nortel Networks"
        CONTACT-INFO
            "         Customer Service Department
                      Nortel Networks

               Email: support@aptis.com"

        DESCRIPTION
            "The following variables describe the Aptis Notifications."

        REVISION     "0004250000Z"
        DESCRIPTION  "04/25/00, rss
                     1) Made the following changes to the CVX traps:
                     
                            OBSOLETED TRAPS       |      SUPERCEDED BY
                     -----------------------------+-------------------------
                     aptis-l2f-tunnel-start  (31) | cvx-tunnel-start  (53)
                     aptis-l2f-tunnel-stop   (32) | cvx-tunnel-stop   (54)
                     aptis-l2f-tunnel-reject (33) | cvx-tunnel-reject (55)

                     2) Changed the notation of CVX-1800 to the generic CVX."


        REVISION     "0003200000Z"
        DESCRIPTION  "03/20/00, ssm
                     1) Changed t1 references to ds1 and
                        t3 to ds3.
                     2) Added VPOP id to trap
                        cvxSessionAuthenticationFailure."

        REVISION     "0003170000Z"
        DESCRIPTION  "03/17/00, ssm
                     1) Added traps:
                        cvxSlaveSccFileSyncFailed,
                        cvxSlaveSccFileSyncCompleted, and
                        cvxSlaveSccFailed.
                     2) Changed severities of many traps.
                     3) Reformatted previously added traps:
                        encryptionNotAllowed,
                        cvxRadiusdSessionDisc,
                        cvxRadiusdUnknownClient, and
                        cvxRadiusdClientAuthFailed."

        REVISION     "0003070000Z"
        DESCRIPTION  "03/07/00, ssm
                     Fix syntax errors."

        REVISION     "0002090000Z"
        DESCRIPTION  "02/09/00, ssm
                     authenticationFailure trap was erroneously being
                     referred to as generic trap # 4 (should be 5 in v2)."

        REVISION     "0001271200Z"
        DESCRIPTION  "01/27/00, ssm
                     Changed subid of aptisProtrapsV2 from 2 to 0.
                     This was done so that traps can be converted from
                     v1 to v2 and vice-versa without changing the oid
                     of the trap.
                     See also the v1 version of this MIB
                     (aptis_traps.mib)."

        REVISION     "0001270000Z"
        DESCRIPTION  "01/27/00, ssm
                     Obsoleted trap 15 (authenticationFailure).
                     Added traps 81 (cvxLocalAuthenticationFailure)
                     and 82 (cvxSessionAuthenticationFailure)."

        REVISION     "0001200000Z"
        DESCRIPTION  "01/20/00, ssm
                     Added 5 traps:
                     cvxSlaveSccRemoved,
                     cvxSlaveSccInserted,
                     cvxFailedSlaveSccRemoved,
                     cvxCardCrashed, and
                     cvxCardNotResponding."

        REVISION     "0001140000Z"
        DESCRIPTION  "01/14/00, ssm
                     Added 1 trap:
                     cvxSlaveSccFlashDetected."

        REVISION     "0001100000Z"
        DESCRIPTION  "01/10/00, ssm
                     1) Added 2 traps:
                        cvxSlotTempWarning and
                        cvxSlotTempNormal.
                     2) Replaced all tabs with spaces.
                     3) Minor restructuring of text.
                     4) Replaced MAX-ACCESS of trap variables from
                        'read-only' to 'accessible-for-notify'."

        REVISION     "9912270000Z"
        DESCRIPTION  "12/27/99, ssm
                     Added 4 traps:
                     cvxAuthServerRevived,
                     cvxPrimaryDhcpServerContactFailed,
                     cvxPrimaryDhcpServerContactRevived, and
                     cvxSecondaryDhcpServerContactFailed."

        ::= { aptis-modules 7 }

    aptisProtraps           OBJECT-IDENTITY
        STATUS              current
        DESCRIPTION
            "This subtree contains the aptis proprietary traps."
        ::= { aptis-traps 1 }

    aptisProtrapsV2         OBJECT-IDENTITY
        STATUS              current
        DESCRIPTION 
            "V2 subtree for aptis proprietary traps."
        ::= {aptisProtraps 0}

    aptis-fandown NOTIFICATION-TYPE
        OBJECTS   { trapGenNum, trapPath, trapSeverity }
        STATUS    current
        DESCRIPTION
            "The fans on the chassis have stopped functioning.
             This trap is only supported on systems with the
             smart fan tray.

             This trap carries a severity of 6 (emergency)."
        ::= {aptisProtrapsV2 1}

    aptis-dc1down NOTIFICATION-TYPE
        OBJECTS   { trapGenNum, trapPath, trapSeverity }
        STATUS    current
        DESCRIPTION
            "The DC1 power supply has stopped functioning.

             This trap carries a severity of 6 (emergency)."
        ::= {aptisProtrapsV2 2}

    aptis-dc2down NOTIFICATION-TYPE
        OBJECTS   { trapGenNum, trapPath, trapSeverity }
        STATUS    current
        DESCRIPTION
            "The DC2 power supply has stopped functioning.

             This trap carries a severity of 6 (emergency)."
         ::= {aptisProtrapsV2 3}

    aptis-ac1down NOTIFICATION-TYPE
        OBJECTS   { trapGenNum, trapPath, trapSeverity }
        STATUS    obsolete
        DESCRIPTION
            "The AC1 power supply has stopped functioning.

             This trap is no longer supported."
        ::= {aptisProtrapsV2 4}

    aptis-ac2down NOTIFICATION-TYPE
        OBJECTS   { trapGenNum, trapPath, trapSeverity }
        STATUS    obsolete
        DESCRIPTION
            "The AC2 power supply has stopped functioning.

             This trap is no longer supported."
        ::= {aptisProtrapsV2 5}

    aptis-acdc1down NOTIFICATION-TYPE
        OBJECTS   { trapGenNum, trapPath, trapSeverity }
        STATUS    current
        DESCRIPTION
            "The ACDC1 power converter has stopped functioning.

             This trap carries a severity of 6 (emergency)."
        ::= {aptisProtrapsV2 6}

    aptis-acdc2down NOTIFICATION-TYPE
        OBJECTS   { trapGenNum, trapPath, trapSeverity }
        STATUS    current
        DESCRIPTION
            "The ACDC2 power converter has stopped functioning.

             This trap carries a severity of 6 (emergency)."
        ::= {aptisProtrapsV2 7}

    aptis-acdc3down NOTIFICATION-TYPE
        OBJECTS   { trapGenNum, trapPath, trapSeverity }
        STATUS    current
        DESCRIPTION
            "The ACDC3 power converter has stopped functioning.

             This trap carries a severity of 6 (emergency)."
        ::= {aptisProtrapsV2 8}

    aptis-flashmount NOTIFICATION-TYPE
        OBJECTS   { trapGenNum, trapPath, trapSeverity }
        STATUS    current
        DESCRIPTION
            "The flash card has been mounted.

             See also trap aptis-flashdismount.

             This trap carries a severity of 2 (warning)."
        ::= {aptisProtrapsV2 9}

    aptis-flashdismount NOTIFICATION-TYPE
        OBJECTS   { trapGenNum, trapPath, trapSeverity }
        STATUS    current
        DESCRIPTION
            "The flash card has been dismounted.

             See also trap aptis-flashmount.

             This trap carries a severity of 2 (warning)."
        ::= {aptisProtrapsV2 10}

    aptis-coldStart NOTIFICATION-TYPE
        OBJECTS   { trapGenNum, trapPath, trapSeverity }
        STATUS    current
        DESCRIPTION
            "A coldStart trap signifies that the sending
            protocol entity is reinitializing itself such
            that the agent's configuration or the protocol
            entity implementation may be altered.

            This trap carries a severity of 2 (warning)."
        ::= {aptisProtrapsV2 11}
  

    warmStart NOTIFICATION-TYPE
        OBJECTS   { trapGenNum, trapPath, trapSeverity }
        STATUS    current
        DESCRIPTION
            "A warmStart trap signifies that the sending
             protocol entity is reinitializing itself such
             that neither the agent configuration nor the
             protocol entity implementation is altered.

             This trap carries a severity of 2 (warning)."
        ::= {aptisProtrapsV2 12}

    linkDown NOTIFICATION-TYPE
        OBJECTS   { ifIndex, trapGenNum, trapPath,
                    trapSeverity }
        STATUS    obsolete
        DESCRIPTION
            "A linkDown trap signifies that the sending
             protocol entity recognizes a failure in one of
             the communications links represented in the
             agent's configuration.

             This trap carries a severity of 6 (emergency)."
        ::= {aptisProtrapsV2 13}

    linkUp NOTIFICATION-TYPE
        OBJECTS   { ifIndex, trapGenNum, trapPath,
                    trapSeverity }
        STATUS    obsolete
        DESCRIPTION
            "A linkUp trap signifies that the sending
             protocol entity recognizes that one of the
             communications links represented in the agent's
             configuration has come up.

             This trap carries a severity of 6 (emergency)."
        ::= {aptisProtrapsV2 14} 

    authenticationFailure NOTIFICATION-TYPE
        OBJECTS   { trapGenNum, trapPath, trapSeverity }
        STATUS    obsolete
        DESCRIPTION
            "An authenticationFailure trap signifies that
             the sending protocol entity is the addressee
             of a protocol message that is not properly
             authenticated. While implementations of the
             SNMP must be capable of generating this trap,
             they must also be capable of suppressing the
             emission of such traps via an
             implementation-specific mechanism.

             NOTE: This trap has been obsoleted and replaced by
             specific trap #s 81 (cvxLocalAuthenticationFailure)
             and 82 (cvxSessionAuthenticationFailure) and generic
             trap # 5 (authenticationFailure).

             This trap carries a severity of 3 (error)."
        ::= {aptisProtrapsV2 15}

    aptis-radius-fail NOTIFICATION-TYPE
        OBJECTS   { trapGenNum, trapPath, trapSeverity }
        STATUS    current
        DESCRIPTION
            "No Radius Server is available.

             This trap carries a severity of 5 (alert)."
        ::= {aptisProtrapsV2 16}

    aptis-slot-up NOTIFICATION-TYPE
        OBJECTS   { trapGenNum, trapPath, trapSeverity }
        STATUS    current
        DESCRIPTION
            "Slot is up.

             See also trap aptis-slot-down.

             This trap carries a severity of 5 (alert)."
        ::= {aptisProtrapsV2 17}

    aptis-slot-down NOTIFICATION-TYPE
        OBJECTS   { trapGenNum, trapPath, trapSeverity }
        STATUS    current
        DESCRIPTION
            "Slot is down.

             See also trap aptis-slot-up.

             This trap carries a severity of 5 (alert)."
        ::= {aptisProtrapsV2 18}

    aptis-slot-cfg-chng NOTIFICATION-TYPE
        OBJECTS   { trapGenNum, trapPath, trapSeverity }
        STATUS    current
        DESCRIPTION
            "Slot configuration has changed.

             This trap carries a severity of 1 (notice)."
        ::= {aptisProtrapsV2 19}

    aptis-ds1-red-alarm NOTIFICATION-TYPE
        OBJECTS   { trapGenNum, trapPath, trapSeverity }
        STATUS    current
        DESCRIPTION
            "The specified DS1 is in red alarm.

             See also trap aptis-ds1-alarm-clear.

             This trap carries a severity of 5 (alert)."
        ::= {aptisProtrapsV2 20}

    aptis-ds1-yellow-alarm NOTIFICATION-TYPE
        OBJECTS   { trapGenNum, trapPath, trapSeverity }
        STATUS    current
        DESCRIPTION
            "The specified DS1 is in yellow alarm.

             See also trap aptis-ds1-alarm-clear.

             This trap carries a severity of 5 (alert)."
        ::= {aptisProtrapsV2 21}

    aptis-ds1-alarm-clear NOTIFICATION-TYPE
        OBJECTS   { trapGenNum, trapPath, trapSeverity }
        STATUS    current
        DESCRIPTION
            "The specified DS1 is no longer in alarm.

             See also traps aptis-ds1-red-alarm and
             aptis-ds1-yellow-alarm.

             This trap carries a severity of 5 (alert)."
        ::= {aptisProtrapsV2 22}

    aptis-ds3-red-alarm NOTIFICATION-TYPE
        OBJECTS   { trapGenNum, trapPath, trapSeverity }
        STATUS    current
        DESCRIPTION
            "The specified DS3 is in red alarm.

             See also trap aptis-ds3-alarm-clear.

             This trap carries a severity of 5 (alert)."
        ::= {aptisProtrapsV2 23}

    aptis-ds3-yellow-alarm NOTIFICATION-TYPE
        OBJECTS   { trapGenNum, trapPath, trapSeverity }
        STATUS    current
        DESCRIPTION
            "The specified DS3 is in yellow alarm.

             See also trap aptis-ds3-alarm-clear.

             This trap carries a severity of 5 (alert)."
        ::= {aptisProtrapsV2 24}

    aptis-ds3-alarm-clear NOTIFICATION-TYPE
        OBJECTS   { trapGenNum, trapPath, trapSeverity }
        STATUS    current
        DESCRIPTION
            "The specified DS3 is no longer in alarm.

             See also traps aptis-ds3-red-alarm and
             aptis-ds3-yellow-alarm.

             This trap carries a severity of 5 (alert)."
        ::= {aptisProtrapsV2 25}

    aptis-isdn-link-up NOTIFICATION-TYPE
        OBJECTS   { trapGenNum, trapPath, trapSeverity }
        STATUS    current
        DESCRIPTION
            "The specified ISDN data link is up.

             See also trap aptis-isdn-link-down.

             This trap carries a severity of 3 (error)."
        ::= {aptisProtrapsV2 26}

    aptis-isdn-link-down NOTIFICATION-TYPE
        OBJECTS   { trapGenNum, trapPath, trapSeverity }
        STATUS    current
        DESCRIPTION
            "The specified ISDN data link is down.

             See also trap aptis-isdn-link-up.

             This trap carries a severity of 3 (error)."
        ::= {aptisProtrapsV2 27}

    aptis-isdn-link-reset NOTIFICATION-TYPE
        OBJECTS   { trapGenNum, trapPath, trapSeverity }
        STATUS    current
        DESCRIPTION
            "The specified ISDN data link has been reset
             by the switch.

             This trap carries a severity of 3 (error)."
        ::= {aptisProtrapsV2 28}

    aptis-temp-exceeded NOTIFICATION-TYPE
        OBJECTS   { trapGenNum, trapPath, trapSeverity }
        STATUS    current
        DESCRIPTION
            "The card in the specified slot has exceeded its
             safe operational temperature and is being shut down.

             See also traps cvxSlotTempWarning and
             cvxSlotTempNormal.

             This trap carries a severity of 7 (fatal)."
        ::= {aptisProtrapsV2 29}

    aptis-cvx-ss7-gateway-failover NOTIFICATION-TYPE 
        OBJECTS   { trapGenNum, trapPath, trapSeverity }
        STATUS    current
        DESCRIPTION
            "The CVX has failed over to the next CVX-SS7
             Gateway.

             This trap carries a severity of 2 (warning)."
        ::= {aptisProtrapsV2 30}

    aptis-l2f-tunnel-start NOTIFICATION-TYPE 
        OBJECTS   { trapGenNum, trapPath, trapSeverity,
                    trapString }
        STATUS    obsolete
        DESCRIPTION
            "The CVX has successfully opened an L2F tunnel.

             See also trap aptis-l2f-tunnel-stop.

             This trap carries a severity of 1 (notice).

             This trap has been replaced by cvx-tunnel-start, {aptisProtrapsV2 53}."
        ::= {aptisProtrapsV2 31}

    aptis-l2f-tunnel-stop NOTIFICATION-TYPE 
        OBJECTS   { trapGenNum, trapPath, trapSeverity,
                    trapString }
        STATUS    obsolete
        DESCRIPTION
            "The CVX has closed an L2F tunnel that had been
             opened successfully.

             See also trap aptis-l2f-tunnel-start.

             This trap carries a severity of 1 (notice).

             This trap has been replaced by cvx-tunnel-stop, {aptisProtrapsV2 54}."
        ::= {aptisProtrapsV2 32}

    aptis-l2f-tunnel-reject NOTIFICATION-TYPE 
        OBJECTS   { trapGenNum, trapPath, trapSeverity,
                    trapString }
        STATUS    obsolete
        DESCRIPTION
            "The CVX has failed to open an L2F tunnel.

             This trap carries a severity of 5 (alert). 

             This trap has been replaced by cvx-tunnel-reject, {aptisProtrapsV2 55}."
        ::= {aptisProtrapsV2 33}

    cvx-MAC-modems-below-threshold NOTIFICATION-TYPE 
        OBJECTS   { trapGenNum, trapPath, trapSeverity,
                    trapSlotNum, policyConfigSlotModemThresholdWarning,
					trapModemCount }
        STATUS    current
        DESCRIPTION
            "The percent of functioning modems on the specified
             MAC board has gone below the defined threshold.

             See also trap cvx-MAC-modems-above-threshold.

             This trap carries a severity of 4 (critical)."
        ::= {aptisProtrapsV2 34}

    cvx-MAC-modems-above-threshold NOTIFICATION-TYPE 
        OBJECTS   { trapGenNum, trapPath, trapSeverity,
                    trapSlotNum, policyConfigSlotModemThresholdWarning,
					trapModemCount }
        STATUS    current
        DESCRIPTION
            "The percent of functioning modems on the specified
             MAC board has gone above or equal to the defined
             threshold.

             See also trap cvx-MAC-modems-below-threshold.

             This trap carries a severity of 4 (critical)."
        ::= {aptisProtrapsV2 35}

    cvx-total-modems-below-threshold NOTIFICATION-TYPE 
        OBJECTS   { trapGenNum, trapPath, trapSeverity,
                    policyConfigChassisModemThresholdWarning,
					trapModemCount }
        STATUS    current
        DESCRIPTION
            "The percent of functioning modems on the CVX
             has fallen below the defined threshold.

             See also trap cvx-total-modems-above-threshold.

             This trap carries a severity of 4 (critical)."
        ::= {aptisProtrapsV2 36}

    cvx-total-modems-above-threshold NOTIFICATION-TYPE 
        OBJECTS   { trapGenNum, trapPath, trapSeverity,
                    policyConfigChassisModemThresholdWarning,
					trapModemCount }
        STATUS    current
        DESCRIPTION
            "The percent of functioning modems on the CVX
             is now equal to or above the defined threshold.

             See also trap cvx-total-modems-below-threshold.

             This trap carries a severity of 4 (critical)."
        ::= {aptisProtrapsV2 37}

    cvx-local-pswd-change NOTIFICATION-TYPE 
        OBJECTS   { trapGenNum, trapPath, trapSeverity,
                    trapUserName }
        STATUS    current
        DESCRIPTION
            "The local password on the CVX has been modified.

             This trap carries a severity of 1 (notice)."
        ::= {aptisProtrapsV2 38}

    cvx-auth-server-failover NOTIFICATION-TYPE 
        OBJECTS   { trapGenNum, trapPath, trapSeverity,
                    trapIpAddr }
        STATUS    current
        DESCRIPTION
            "The most recently used authentication server cannot be
             contacted.  The primary contact has been switched to the
             server indicated.

             See also trap cvxAuthServerRevived.

             This trap carries a severity of 2 (warning)."
        ::= {aptisProtrapsV2 39}

    cvx-acct-server-failure NOTIFICATION-TYPE 
        OBJECTS   { trapGenNum, trapPath, trapSeverity,
                    trapIpAddr }
        STATUS    current
        DESCRIPTION
            "Communication has been lost with all configured accounting
             servers.  The address indicated in the trap is the last
             address tried.

             This trap carries a severity of 5 (alert)."
        ::= {aptisProtrapsV2 40}

    cvx-acct-server-failover NOTIFICATION-TYPE 
        OBJECTS   { trapGenNum, trapPath, trapSeverity,
                    trapIpAddr }
        STATUS    current
        DESCRIPTION
            "The most recently used accounting server cannot be
             contacted.  The primary contact has been switched to the
             server indicated.

             This trap carries a severity of 2 (warning)."
        ::= {aptisProtrapsV2 41}

    cvx-ss7-gateway-down NOTIFICATION-TYPE 
        OBJECTS   { trapGenNum, trapPath, trapSeverity,
                    trapIpAddr }
        STATUS    current
        DESCRIPTION
            "Communication has been lost with the ss7 gateway
             indicated.

             See also trap cvx-ss7-gateway-up.

             This trap carries a severity of 6 (emergency)."
        ::= {aptisProtrapsV2 42}

    cvx-ss7-gateway-up NOTIFICATION-TYPE 
        OBJECTS   { trapGenNum, trapPath, trapSeverity,
                    trapIpAddr }
        STATUS    current
        DESCRIPTION
            "Communication has been established with the ss7 gateway
             indicated.

             See also trap cvx-ss7-gateway-down.

             This trap carries a severity of 6 (emergency)."
        ::= {aptisProtrapsV2 43}

    cvx-Ds3-failover NOTIFICATION-TYPE 
        OBJECTS   { trapGenNum, trapPath, trapSeverity,
                    trapSlotNum }
        STATUS    current
        DESCRIPTION
            "The primary DS3 in the indicated slot has failed and the
             secondary has resumed responsibility.

             This trap carries a severity of 6 (emergency)."
        ::= {aptisProtrapsV2 44}

    cvx-Scc-failover NOTIFICATION-TYPE 
        OBJECTS   { trapGenNum, trapPath, trapSeverity,
                    trapSlotNum }
        STATUS    current
        DESCRIPTION
            "The primary SCC in the indicated slot has failed and the
             secondary has resumed operation.

             This trap carries a severity of 6 (emergency)."
        ::= {aptisProtrapsV2 45}

    cvx-ethernet-port-up NOTIFICATION-TYPE 
        OBJECTS   { trapGenNum, trapPath, trapSeverity,
                    trapPortNum }
        STATUS    current
        DESCRIPTION
            "The specified Ethernet Port is initialized.  This trap
             will occur at boot time and when an ethernet port is
             reinitialized after a cvx-ethernet-port-down trap.

             This trap carries a severity of 5 (alert)."
        ::= {aptisProtrapsV2 46}

    cvx-ethernet-port-down NOTIFICATION-TYPE 
        OBJECTS   { trapGenNum, trapPath, trapSeverity,
                    trapPortNum }
        STATUS    current
        DESCRIPTION
            "The specified Ethernet port has failed.

             This trap carries a severity of 5 (alert)."
        ::= {aptisProtrapsV2 47}

    cvx-Hssi-port-up NOTIFICATION-TYPE 
        OBJECTS   { trapGenNum, trapPath, trapSeverity,
                    trapPortNum }
        STATUS    current
        DESCRIPTION
            "The specified HSSI Port is initialized.  This trap will
             occur at boot time and when an HSSI port is reinitialized
             after a cvx-hssi-port-down trap.

             This trap carries a severity of 7 (fatal)."
        ::= {aptisProtrapsV2 48}

    cvx-Hssi-port-down NOTIFICATION-TYPE 
        OBJECTS   { trapGenNum, trapPath, trapSeverity, trapPortNum }
        STATUS    current
        DESCRIPTION
            "The specified HSSI port has failed.

             This trap carries a severity of 7 (fatal)."
        ::= {aptisProtrapsV2 49}

    cvx-local-auth-failure-threshold-exceeded NOTIFICATION-TYPE 
        OBJECTS   { trapGenNum, trapPath, trapSeverity,
                    trapAuthThreshold, trapString }
        STATUS    current
        DESCRIPTION
            "A consecutive number of local authorization failures has
             exceeded the noted threshold.  The trap contains the
             number of consecutive failed attempts and additional
             information on the client host (an IP Address for FTP, or
             session number for telnet connections).

             This trap carries a severity of 2 (warning)."
        ::= {aptisProtrapsV2 50}

    cvx-preAuth-fail NOTIFICATION-TYPE 
        OBJECTS   { trapGenNum, trapPath, trapSeverity,
                    trapIpAddr }
        STATUS    current
        DESCRIPTION
            "No pre-authorization server is available.  The IP
             address shows the last server tried.

             This trap carries a severity of 5 (alert)."
        ::= {aptisProtrapsV2 51}

    cvx-auth-fail NOTIFICATION-TYPE 
        OBJECTS   { trapGenNum, trapPath, trapSeverity,
                    trapIpAddr }
        STATUS    current
        DESCRIPTION
            "No authorization server is available.  The IP address
             shows the last server tried.

             This trap carries a severity of 5 (alert)."
        ::= {aptisProtrapsV2 52}

    cvx-tunnel-start NOTIFICATION-TYPE 
        OBJECTS   { trapGenNum, trapPath, trapSeverity,
                    trapTunnelType, trapIpAddr }
        STATUS    current
        DESCRIPTION
            "The CVX has successfully opened a tunnel.

             This trap carries a severity of 1 (notice)."
        ::= {aptisProtrapsV2 53}

    cvx-tunnel-stop NOTIFICATION-TYPE 
        OBJECTS   { trapGenNum, trapPath, trapSeverity,
                    trapTunnelType, trapIpAddr }
        STATUS    current
        DESCRIPTION
            "The CVX has closed a tunnel that had been opened
             successfully.

             This trap carries a severity of 1 (notice)."
        ::= {aptisProtrapsV2 54}

    cvx-tunnel-reject NOTIFICATION-TYPE 
        OBJECTS   { trapGenNum, trapPath, trapSeverity,
                    trapTunnelType, trapIpAddr }
        STATUS    current
        DESCRIPTION
            "The CVX has failed to open a tunnel.

             This trap carries a severity of 5 (alert)."
        ::= {aptisProtrapsV2 55}

    cvx-radius-packet-discard NOTIFICATION-TYPE
        OBJECTS   { trapGenNum, trapPath, trapSeverity, trapString }
        STATUS    current
        DESCRIPTION
            "A radius response packet was discarded.

             This trap carries a severity of 3 (error)."
        ::= {aptisProtrapsV2 56}

    cvx-fanup NOTIFICATION-TYPE
        OBJECTS   { trapGenNum, trapPath, trapSeverity }
        STATUS    current
        DESCRIPTION
            "The fans on the chassis have resumed functioning.
             This trap is only supported on systems with the
             smart fan tray.

             This trap carries a severity of 6 (emergency)."
        ::= {aptisProtrapsV2 57}

    cvx-dc1up NOTIFICATION-TYPE
        OBJECTS   { trapGenNum, trapPath, trapSeverity }
        STATUS    current
        DESCRIPTION
            "The DC1 power supply has resumed functioning.

             This trap carries a severity of 6 (emergency)."
        ::= {aptisProtrapsV2 58}

    cvx-dc2up NOTIFICATION-TYPE
        OBJECTS   { trapGenNum, trapPath, trapSeverity }
        STATUS    current
        DESCRIPTION
            "The DC2 power supply has resumed functioning.

             This trap carries a severity of 6 (emergency)."
        ::= {aptisProtrapsV2 59}

    cvx-acdc1up NOTIFICATION-TYPE
        OBJECTS   { trapGenNum, trapPath, trapSeverity }
        STATUS    current
        DESCRIPTION
            "The ACDC1 power converter has resumed functioning.

             This trap carries a severity of 6 (emergency)."
        ::= {aptisProtrapsV2 62}

    cvx-acdc2up NOTIFICATION-TYPE
        OBJECTS   { trapGenNum, trapPath, trapSeverity }
        STATUS    current
        DESCRIPTION
            "The ACDC2 power converter has resumed functioning.

             This trap carries a severity of 6 (emergency)."
        ::= {aptisProtrapsV2 63}

    cvx-acdc3up NOTIFICATION-TYPE
        OBJECTS   { trapGenNum, trapPath, trapSeverity }
        STATUS    current
        DESCRIPTION
            "The ACDC3 power converter has resumed functioning.

             This trap carries a severity of 6 (emergency)."
        ::= {aptisProtrapsV2 64}

    cvx-filter-error  NOTIFICATION-TYPE 
        OBJECTS   { trapGenNum, trapPath, trapSeverity,
                    trapFilterName, trapIpAddr }
        STATUS    current
        DESCRIPTION   
            "A Filter-Id attribute containing an unknown
             filter name was received from a radius server.

             This trap carries a severity of 5 (alert)."
        ::= {aptisProtrapsV2 65}

    cvx-slave-flash-missing NOTIFICATION-TYPE
        OBJECTS   { trapGenNum, trapPath, trapSeverity }
        STATUS    current
        DESCRIPTION
            "No flash card has been detected on the slave SCC
             (System Control Card) unit.

             See also trap cvxSlaveSccFlashDetected.

             This trap carries a severity of 3 (error)."
        ::= {aptisProtrapsV2 66}

    cvxSlaveSccFlashDetected NOTIFICATION-TYPE
        OBJECTS   { trapGenNum, trapPath, trapSeverity }
        STATUS    current 
        DESCRIPTION
            "The flash card has been detected on the slave SCC
             (System Control Card) unit.

             NOTE: This trap is only sent if the complementary
             trap cvx-slave-flash-missing was sent previously.

             This trap carries a severity of 3 (error)."
        ::= {aptisProtrapsV2 67}

    cvxAuthServerRevived NOTIFICATION-TYPE 
        OBJECTS   { trapGenNum, trapPath, trapSeverity,
                    trapIpAddr }
        STATUS    current
        DESCRIPTION
            "The authentication server identified by trapIpAddr
             that had previously failed has been revived.  The
             server is identified by trapIpAddr.

             See also notification cvx-auth-server-failover.

             This trap carries a severity of 1 (notice)."
        ::= {aptisProtrapsV2 68}

    cvxPrimaryDhcpServerContactFailed NOTIFICATION-TYPE 
        OBJECTS   { trapGenNum, trapPath, trapSeverity,
                    trapIpAddr }
        STATUS    current
        DESCRIPTION
            "Failed to establish contact with the primary DHCP
             server identified by trapIpAddr.  If a secondary DHCP
             server has been configured, it will be tried next.

             NOTE: Every time a new request is received to obtain
             an IP address via DHCP, the primary DHCP server is
             always tried first (even though previous attempts to
             contact it may have failed).

             See also trap cvxPrimaryDhcpServerContactRevived.

             This trap carries a severity of 5 (alert)."
        ::= {aptisProtrapsV2 69}

    cvxPrimaryDhcpServerContactRevived NOTIFICATION-TYPE 
        OBJECTS   { trapGenNum, trapPath, trapSeverity,
                    trapIpAddr }
        STATUS    current
        DESCRIPTION
            "Contact has been reestablished with the primary DHCP
             server identified by trapIpAddr.

             NOTE: Every time a new request is received to obtain
             an IP address via DHCP, the primary DHCP server is
             always tried first (even though previous attempts to
             contact it may have failed).

             See also trap cvxPrimaryDhcpServerContactFail.

             This trap carries a severity of 5 (alert)."
        ::= {aptisProtrapsV2 70}

    cvxSecondaryDhcpServerContactFailed NOTIFICATION-TYPE 
        OBJECTS   { trapGenNum, trapPath, trapSeverity,
                    trapIpAddr }
        STATUS    current
        DESCRIPTION
            "Failed to establish contact with the secondary (backup)
             DHCP server identified by trapIpAddr.

             Note that no trap is issued when contact is reestablished
             with the secondary DHCP server.

             This trap carries a severity of 5 (alert)."
        ::= {aptisProtrapsV2 71}

    -- 72 skipped

    cvxSlotTempWarning NOTIFICATION-TYPE 
        OBJECTS   { trapGenNum, trapPath, trapSeverity, 
                    trapSlotNum, trapTempCurrent,
                    trapTempConfigWarningLevel }
        STATUS    current
        DESCRIPTION
            "Slot temperature has exceeded the configured warning
             level.  If the slot temperature exceeds the configured
             threshold limit, the card in the slot will be shut down. 

             trapSlotNum identifies the affected slot. 
             trapTempCurrent specifies the current temperature and
             trapTempConfigWarningLevel specifies the configured
             warning level (both in degrees Celsius).

             See also traps cvxSlotTempNormal and
             aptis-temp-exceeded.

            This trap carries a severity of 4 (critical)."
        ::= {aptisProtrapsV2 73}

    cvxSlotTempNormal NOTIFICATION-TYPE 
        OBJECTS   { trapGenNum, trapPath, trapSeverity, 
                    trapSlotNum, trapTempCurrent,
                    trapTempConfigWarningLevel }
        STATUS    current
        DESCRIPTION
            "Slot temperature is back to normal (below the configured
             warning level).

             trapSlotNum identifies the affected slot. 
             trapTempCurrent specifies the current temperature and
             trapTempConfigWarningLevel specifies the configured
             warning level (both in degrees Celsius).

             See also traps cvxSlotTempWarning and
             aptis-temp-exceeded.

             This trap carries a severity of 4 (critical)."
        ::= {aptisProtrapsV2 74}

    cvxSlaveSccRemoved NOTIFICATION-TYPE
        OBJECTS   { trapGenNum, trapPath, trapSeverity } 
        STATUS    current
        DESCRIPTION
            "The master SCC (System Control Card) has detected
             that the slave SCC has been removed from the system.
             File synchronization will cease.

             See also traps cvxSlaveSccInserted and
             cvxFailedSlaveSccRemoved.

             This trap carries a severity of 3 (error)."
        ::= {aptisProtrapsV2 75}

    cvxSlaveSccInserted NOTIFICATION-TYPE
        OBJECTS   { trapGenNum, trapPath, trapSeverity } 
        STATUS    current
        DESCRIPTION
            "The master SCC (System Control Card) has detected
             that the slave SCC has been inserted into the system.
             File synchronization will start or resume.

             See also traps cvxSlaveSccRemoved and
             cvxFailedSlaveSccRemoved.

            This trap carries a severity of 3 (error)."
        ::= {aptisProtrapsV2 76}

    cvxFailedSlaveSccRemoved NOTIFICATION-TYPE
        OBJECTS   { trapGenNum, trapPath, trapSeverity } 
        STATUS    current
        DESCRIPTION
            "The master SCC (System Control Card) has detected
             that the slave SCC that had previously failed has
             been removed from the system.

             See also traps cvxSlaveSccRemoved and
             cvxSlaveSccInserted.

             This trap carries a severity of 3 (error)."
        ::= {aptisProtrapsV2 77}

    -- 78 skipped

    cvxCardCrashed NOTIFICATION-TYPE
        OBJECTS   { trapGenNum, trapPath, trapSeverity,
                    trapSlotNum } 
        STATUS    current
        DESCRIPTION
            "The card in slot trapSlotNum has crashed.  The
             crash block has been written to the flash card.
             A restart of the card will be attempted.

             This trap carries a severity of 6 (emergency)."
        ::= {aptisProtrapsV2 79}

    cvxCardNotResponding NOTIFICATION-TYPE
        OBJECTS   { trapGenNum, trapPath, trapSeverity,
                    trapSlotNum } 
        STATUS    current
        DESCRIPTION
            "The card in slot trapSlotNum is not responding
             to the system watchdog.  A restart of the card
             will be attempted.

             This trap carries a severity of 6 (emergency)."
        ::= {aptisProtrapsV2 80}

    cvxLocalAuthenticationFailure NOTIFICATION-TYPE
        OBJECTS   { trapGenNum, trapPath, trapSeverity,
                    trapUserName }
        STATUS    current
        DESCRIPTION
            "This trap is generated when a user fails the local
             authentication process while trying to log into the
             CVX shell service.  Local authentication is performed
             via a unix-like username/password sequence.  The
             username associated with the login is contained in the
             variable trapUserName.

             A sufficient number of local authentication failures
             can trigger the trap
             cvx-local-auth-failure-threshold-exceeded.

             For an authentication failure related to the
             authentication of received SNMP packets, the generic
             trap authenticationFailure (generic trap # 5) is
             used.

             NOTE: The previously defined enterprise-specific trap
             called authenticationFailure (specific trap # 15)
             that used to cover all kinds of authentication failures
             has been obsoleted and replaced by this trap, trap
             cvxSessionAuthenticationFailure, and generic trap
             authenticationFailure (generic trap # 5).

             This trap carries a severity of 1 (notice)."
        ::= {aptisProtrapsV2 81}

    cvxSessionAuthenticationFailure NOTIFICATION-TYPE
        OBJECTS   { trapGenNum, trapPath, trapSeverity,
                    trapSessionId, trapVpopId }
        STATUS    current
        DESCRIPTION
            "This trap is generated when an authentication
             failure occurs during session setup.  The session id
             number associated with the session is contained in the
             variable trapSessionId.  If there is an associated
             VPOP id, it is returned in the variable trapVpopId.

             The types of sessions for which this trap can be
             issued are: atmp, tcp, dvs, fax, ppp, rlogin, telnet,
             and voip.

             For an authentication failure related to the
             authentication of received SNMP packets, the generic
             trap authenticationFailure (generic trap # 5) is
             used.

             NOTE: The previously defined enterprise-specific trap
             called authenticationFailure (specific trap # 15)
             that used to cover all kinds of authentication failures
             has been obsoleted and replaced by this trap, trap
             cvxLocalAuthenticationFailure, and generic trap
             authenticationFailure (generic trap # 5).

             This trap carries a severity of 1 (notice)."
        ::= {aptisProtrapsV2 82}
 
    encryptionNotAllowed NOTIFICATION-TYPE
        OBJECTS   { trapGenNum, trapPath, trapSeverity }
        STATUS    current
        DESCRIPTION
            "Encryption operations cannot be performed if the SCC I
             board is present.

             Encryption is only supported on a SCC II board that has
             a VMS120 chip for encryption acceleration.  Also, even
             if the VMS120 chip is present, it may not have encrypting
             functionality turned on in the hardware.  The encryption
             may also have been disabled via configuration.
           
             This trap has a high severity because none of the packets 
             protected by the IPSec encryption may now be received or
             sent by the CVX.
           
             This trap carries a severity of 6 (emergency)."
        ::= {aptisProtrapsV2 83}

    cvxRadiusdSessionDisc NOTIFICATION-TYPE
        OBJECTS   { trapGenNum, trapPath, trapSeverity,
                    trapIpAddr }
        STATUS    current
        DESCRIPTION
            "A Disconnect-Request received from the RADIUS
             client with IP address trapIpAddr resulted
             in termination of one or more sessions.

             This trap carries a severity of 0 (info)."
        ::= {aptisProtrapsV2 84}

    cvxRadiusdUnknownClient NOTIFICATION-TYPE 
        OBJECTS   { trapGenNum, trapPath, trapSeverity,
                    trapIpAddr }
        STATUS    current
        DESCRIPTION
            "A Disconnect-Request was received from an unknown
             RADIUS client with IP address trapIpAddr.

             This trap carries a severity of 0 (info)."
        ::= {aptisProtrapsV2 85}

    cvxRadiusdClientAuthFailed NOTIFICATION-TYPE 
        OBJECTS   { trapGenNum, trapPath, trapSeverity,
                    trapIpAddr }
        STATUS    current
        DESCRIPTION
            "A Disconnect-Request received from the RADIUS
             client with IP address trapIpAddr failed
             authentication.

             This trap carries a severity of 0 (info)."
        ::= {aptisProtrapsV2 86}

    cvxSlaveSccFileSyncFailed NOTIFICATION-TYPE 
        OBJECTS   { trapGenNum, trapPath, trapSeverity } 
        STATUS    current
        DESCRIPTION
            "The master SCC (System Control Card) detected error(s)
             while performing file synchronization with the slave
             SCC.

             This trap carries a severity of 4 (critical)."
        ::= {aptisProtrapsV2 87}

    cvxSlaveSccFileSyncCompleted NOTIFICATION-TYPE 
        OBJECTS   { trapGenNum, trapPath, trapSeverity } 
        STATUS    current
        DESCRIPTION
            "The master SCC (System Control Card) successfully
             completed file synchronization with the slave SCC.

             This trap carries a severity of 1 (notice)."
        ::= {aptisProtrapsV2 88}

    cvxSlaveSccFailed NOTIFICATION-TYPE 
        OBJECTS   { trapGenNum, trapPath, trapSeverity } 
        STATUS    current
        DESCRIPTION
            "The master SCC (System Control Card) has detected
             that the slave SCC has failed.  File synchronization
             will cease.

             See also related trap cvxFailedSlaveSccRemoved.

             This trap carries a severity of 7 (fatal)."
        ::= {aptisProtrapsV2 89}

-- The following variables are for use in the varbinds of traps only.
-- They cannot be retrieved by the NMS.
          
      trapGenNum              OBJECT-TYPE
            SYNTAX            INTEGER (0..2147483647)
            MAX-ACCESS        accessible-for-notify
            STATUS            current
            DESCRIPTION      
                "A unigue incrementing integer assigned for each trap."

      ::= { aptis-traps 2 }

      trapPath                OBJECT-TYPE
            SYNTAX            OCTET STRING
            MAX-ACCESS        accessible-for-notify
            STATUS            current
            DESCRIPTION      
                "A path string to the object associated with the trap."

      ::= { aptis-traps 3 }

      trapSeverity            OBJECT-TYPE
            SYNTAX            INTEGER (0..7)
            MAX-ACCESS        accessible-for-notify
            STATUS            current
            DESCRIPTION      
                "The severity of this trap, 7 being most severe."

      ::= { aptis-traps 4 }

      trapString              OBJECT-TYPE
            SYNTAX            OCTET STRING
            MAX-ACCESS        accessible-for-notify
            STATUS            current
            DESCRIPTION      
                "Extra text associated with the trap."

      ::= { aptis-traps 5 }

      trapIpAddr              OBJECT-TYPE
            SYNTAX            IpAddress
            MAX-ACCESS        accessible-for-notify
            STATUS            current
            DESCRIPTION      
                "An IP address associated with the trap."

      ::= { aptis-traps 6 }

      trapSlotNum             OBJECT-TYPE
            SYNTAX            INTEGER
            MAX-ACCESS        accessible-for-notify
            STATUS            current
            DESCRIPTION      
                "A slot number associated with the trap."

      ::= { aptis-traps 7 }

      trapPortNum             OBJECT-TYPE
            SYNTAX            INTEGER
            MAX-ACCESS        accessible-for-notify
            STATUS            current
            DESCRIPTION      
                "A port number associated with the trap."

      ::= { aptis-traps 8 }

      trapTunnelType          OBJECT-TYPE
            SYNTAX            INTEGER
                              {
                              unknown(0),
                              none(1),
                              other(2),
                              l2f(3),
                              l2tp(4)
                              }
            MAX-ACCESS        accessible-for-notify
            STATUS            current
            DESCRIPTION      
                "A tunnel type associated with the trap."

      ::= { aptis-traps 9 }

      trapUserName            OBJECT-TYPE
            SYNTAX            OCTET STRING
            MAX-ACCESS        accessible-for-notify
            STATUS            current
            DESCRIPTION      
                "The user name assiciated with this trap."

      ::= { aptis-traps 10 }

      trapAuthThreshold       OBJECT-TYPE
            SYNTAX            INTEGER
            MAX-ACCESS        accessible-for-notify
            STATUS            current
            DESCRIPTION      
                "The number of consecutive authorization failures."

      ::= { aptis-traps 11 }

      trapFilterName          OBJECT-TYPE
            SYNTAX            OCTET STRING
            MAX-ACCESS        accessible-for-notify
            STATUS            current
            DESCRIPTION      
                "The filter name assiciated with this trap."

      ::= { aptis-traps 12 }

      trapTempCurrent         OBJECT-TYPE
            SYNTAX            INTEGER
            UNITS             "Degrees Celsius"
            MAX-ACCESS        accessible-for-notify
            STATUS            current
            DESCRIPTION      
                  "Current temperature in degrees Celsius."

      ::= { aptis-traps 13 }

      trapTempConfigWarningLevel OBJECT-TYPE
            SYNTAX            INTEGER
            UNITS             "Degrees Celsius"
            MAX-ACCESS        accessible-for-notify
            STATUS            current
            DESCRIPTION      
                  "Configured warning level temperature in degrees
                   Celsius."

      ::= { aptis-traps 14 }

      trapSessionId OBJECT-TYPE
            SYNTAX            INTEGER
            MAX-ACCESS        accessible-for-notify
            STATUS            current
            DESCRIPTION      
                  "A session id number associated with the trap."

      ::= { aptis-traps 15 }

      trapVpopId OBJECT-TYPE
            SYNTAX            INTEGER
            MAX-ACCESS        accessible-for-notify
            STATUS            current
            DESCRIPTION      
                  "A VPOP (Virtual Point of Presence) id associated
                   with the trap."

      ::= { aptis-traps 16 }

      trapModemCount OBJECT-TYPE
            SYNTAX            INTEGER
            MAX-ACCESS        accessible-for-notify
            STATUS            current
            DESCRIPTION      
                  "The number of available modems."

      ::= { aptis-traps 17 }
END
