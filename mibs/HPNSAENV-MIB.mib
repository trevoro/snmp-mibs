--*****************************************************************************
--                      HP NetServer Environment Information 
--              Management Information Base for SNMP Network Management
--
--      Copyright 1997 Hewlett-Packard Company
--      All Rights Reserved.
--
--      The information in this document is subject to change without
--        notice. 
--
--      The HP enterprise number is 11.
--      The ASN.1 prefix to, and including the HP Enterprise is:
--      1.3.6.1.4.1.11
--
-- ****************************************************************************
-- Summary of HP NSA Environment Information MIB
-- ****************************************************************************
--    hp  (1.3.6.1.4.1.11)
--       nm  (hp.2)
--          hpnsa  (nm.23)
--             hpnsaEnvironment Group      (hpnsa.26)  
--                hpnsaEnvMibRev Group      (hpnsa.26.1)
--                   hpnsaEnvMibRevMajor        (hpnsa.26.1.1)
--                   hpnsaEnvMibRevMinor        (hpnsa.26.1.2)
--                hpnsaEnvVoltageData Group       (hpnsa.26.2)
--                   hpnsaEnvVoltageSensorTable          (hpnsa.26.2.1) 
--                      hpnsaEnvVoltageSensorEntry           (hpnsa.26.2.1.1) 
--                         hpnsaEnvVoltageSensorIndex        (hpnsa.26.2.1.1.1)
--                         hpnsaEnvVoltageSensorType         (hpnsa.26.2.1.1.2)  
--                         hpnsaEnvVoltageSensorLocation     (hpnsa.26.2.1.1.3)
--                         hpnsaEnvVoltageSensorDescription  (hpnsa.26.2.1.1.4) 
--                         hpnsaEnvVoltageSensorStatus       (hpnsa.26.2.1.1.5)
--                         hpnsaEnvVoltageSensorLevel        (hpnsa.26.2.1.1.6)
--                         hpnsaEnvVoltageSensorNominalLevel (hpnsa.26.2.1.1.7)
--                         hpnsaEnvVoltageSensorNormalMaximum
--                            (hpnsa.26.2.1.1.8)
--                         hpnsaEnvVoltageSensorNormalMinimum
--                            (hpnsa.26.2.1.1.9)
--                         hpnsaEnvVoltageSensorMaximum
--                            (hpnsa.26.2.1.1.10)
--                         hpnsaEnvVoltageSensorMinimum
--                            (hpnsa.26.2.1.1.11)
--                         hpnsaEnvVoltageSensorLowerNonCriticalThreshold
--                            (hpnsa.26.2.1.1.12)
--                         hpnsaEnvVoltageSensorUpperNonCriticalThreshold
--                            (hpnsa.26.2.1.1.13)
--                         hpnsaEnvVoltageSensorLowerCriticalThreshold
--                            (hpnsa.26.2.1.1.14)
--                         hpnsaEnvVoltageSensorUpperCriticalThreshold
--                            (hpnsa.26.2.1.1.15)
--                         hpnsaEnvVoltageSensorLowerNonRecoverableThreshold
--                            (hpnsa.26.2.1.1.16)
--                         hpnsaEnvVoltageSensorUpperNonRecoverableThreshold
--                            (hpnsa.26.2.1.1.17)
--                         hpnsaEnvVoltageSensorResolution  
--                            (hpnsa.26.2.1.1.18)
--                         hpnsaEnvVoltageSensorTolerance   
--                            (hpnsa.26.2.1.1.19)
--                         hpnsaEnvVoltageSensorAccuracy    
--                            (hpnsa.26.2.1.1.20)
--                         hpnsaEnvVoltagePositiveHysterisis
--                            (hpnsa.26.2.1.1.21)
--                         hpnsaEnvVoltageNegativeHysterisis
--                            (hpnsa.26.2.1.1.22
--                hpnsaEnvTemperatureData Group       (hpnsa.26.3)
--                   hpnsaEnvTemperatureSensorTable      (hpnsa.26.3.1) 
--                      hpnsaEnvTemperatureSensorEntry      (hpnsa.26.3.1.1) 
--                         hpnsaEnvTemperatureSensorIndex      (hpnsa.26.3.1.1.1)
--                         hpnsaEnvTemperatureSensorType       (hpnsa.26.3.1.1.2)
--                         hpnsaEnvTemperatureSensorLocation 
--                            (hpnsa.26.3.1.1.3)
--                         hpnsaEnvTemperatureSensorDescription
--                            (hpnsa.26.3.1.1.4)
--                         hpnsaEnvTemperatureSensorStatus  
--                            (hpnsa.26.3.1.1.5)
--                         hpnsaEnvTemperatureSensorReading 
--                            (hpnsa.26.3.1.1.6)
--                         hpnsaEnvTemperatureSensorNominalReading 
--                            (hpnsa.26.3.1.1.7)
--                         hpnsaEnvTemperatureSensorNormalMaximum
--                            (hpnsa.26.3.1.1.8)
--                         hpnsaEnvTemperatureSensorNormalMinimum
--                            (hpnsa.26.3.1.1.9)
--                         hpnsaEnvTemperatureSensorMaximum
--                            (hpnsa.26.3.1.1.10)
--                         hpnsaEnvTemperatureSensorMinimum
--                            (hpnsa.26.3.1.1.11)
--                         hpnsaEnvTemperatureSensorLowerNonCriticalThreshold
--                            (hpnsa.26.3.1.1.12)
--                         hpnsaEnvTemperatureSensorUpperNonCriticalThreshold
--                            (hpnsa.26.3.1.1.13)
--                         hpnsaEnvTemperatureSensorLowerCriticalThreshold
--                            (hpnsa.26.3.1.1.14)
--                         hpnsaEnvTemperatureSensorUpperCriticalThreshold
--                            (hpnsa.26.3.1.1.15)
--                         hpnsaEnvTemperatureSensorLowerNonRecoverableThreshold
--                            (hpnsa.26.3.1.1.16)
--                         hpnsaEnvTemperatureSensorUpperNonRecoverableThreshold
--                            (hpnsa.26.3.1.1.17)
--                         hpnsaEnvTemperatureSensorResolution
--                            (hpnsa.26.3.1.1.18)
--                         hpnsaEnvTemperatureSensorTolerance
--                            (hpnsa.26.3.1.1.19)
--                         hpnsaEnvTemperatureSensorAccuracy
--                            (hpnsa.26.3.1.1.20)
--                         hpnsaEnvTemperaturePositiveHysterisis
--                            (hpnsa.26.3.1.1.21)
--                         hpnsaEnvTemperatureNegativeHysterisis
--                            (hpnsa.26.3.1.1.22)
--                hpnsaEnvFanSensorData Group         (hpnsa.26.4)
--                   hpnsaEnvFanSensorTable              (hpnsa.26.4.1) 
--                      hpnsaEnvFanSensorEntry              (hpnsa.26.4.1.1) 
--                         hpnsaEnvFanSensorIndex              (hpnsa.26.4.1.1.1)
--                         hpnsaEnvFanSensorType               (hpnsa.26.4.1.1.2)
--                         hpnsaEnvFanSensorLocation           (hpnsa.26.4.1.1.3)
--                         hpnsaEnvFanSensorDescription        (hpnsa.26.4.1.1.4) 
--                         hpnsaEnvFanSensorStatus             (hpnsa.26.4.1.1.5)
--                         hpnsaEnvFanSensorReading            (hpnsa.26.4.1.1.6)
--                         hpnsaEnvFanSensorNominalReading     (hpnsa.26.4.1.1.7)
--                         hpnsaEnvFanSensorNormalMaximum      (hpnsa.26.4.1.1.8)
--                         hpnsaEnvFanSensorNormalMinimum      (hpnsa.26.4.1.1.9)
--                         hpnsaEnvFanSensorMaximum            (hpnsa.26.4.1.1.10)
--                         hpnsaEnvFanSensorMinimum            (hpnsa.26.4.1.1.11)
--                         hpnsaEnvFanSensorLowerNonCriticalThreshold
--                           (hpnsa.26.4.1.1.12)
--                         hpnsaEnvFanSensorUpperNonCriticalThreshold
--                           (hpnsa.26.4.1.1.13)
--                         hpnsaEnvFanSensorLowerCriticalThreshold
--                           (hpnsa.26.4.1.1.14)
--                         hpnsaEnvFanSensorUpperCriticalThreshold
--                           (hpnsa.26.4.1.1.15)
--                         hpnsaEnvFanSensorLowerNonRecoverableThreshold
--                           (hpnsa.26.4.1.1.16)
--                         hpnsaEnvFanSensorUpperNonRecoverableThreshold
--                           (hpnsa.26.4.1.1.17)
--                         hpnsaEnvFanSensorResolution         (hpnsa.26.4.1.1.18)
--                         hpnsaEnvFanSensorTolerance          (hpnsa.26.4.1.1.19)
--                         hpnsaEnvFanSensorAccuracy           (hpnsa.26.4.1.1.20)
--                         hpnsaEnvFanSensorPositiveHysterisis (hpnsa.26.4.1.1.21)
--                         hpnsaEnvFanSensorNegativeHysterisis (hpnsa.26.4.1.1.22)
--                hpnsaEnvChassisData Group     (hpnsa.26.5)
--                   hpnsaEnvChassisStatus         (hpnsa.26.5.1)
-- ****************************************************************************


HPNSAENV-MIB DEFINITIONS ::= BEGIN
   IMPORTS
   enterprises    FROM RFC1155-SMI
   DisplayString  FROM RFC1213-MIB
   OBJECT-TYPE    FROM RFC-1212;

   hp                      OBJECT IDENTIFIER ::= { enterprises 11 }
   nm                      OBJECT IDENTIFIER ::= { hp 2 }
   hpnsa                   OBJECT IDENTIFIER ::= { nm 23 }  
   hpnsaEnvironment            OBJECT IDENTIFIER ::= { hpnsa 26 }
   hpnsaEnvMibRev          OBJECT IDENTIFIER ::= { hpnsaEnvironment 1 }
   hpnsaEnvVoltageData     OBJECT IDENTIFIER ::= { hpnsaEnvironment 2 }
   hpnsaEnvTemperatureData OBJECT IDENTIFIER ::= { hpnsaEnvironment 3 }
   hpnsaEnvFanSensorData         OBJECT IDENTIFIER ::= { hpnsaEnvironment 4 }
   hpnsaEnvChassisData     OBJECT IDENTIFIER ::= { hpnsaEnvironment 5 }

    
-- *************************************************************************
-- hpnsaEnvMibRev (1.3.6.1.4.1.11.2.23.26.1)
-- *************************************************************************
--    hp  (1.3.6.1.4.1.11)
--       nm  (hp.2)
--          hpnsa  (nm.23)
--             hpnsaEnvironment Group      (hpnsa.26)  
--                hpnsaEnvMibRev Group      (hpnsa.26.1)
--                   hpnsaEnvMibRevMajor        (hpnsa.26.1.1)
--                   hpnsaEnvMibRevMinor        (hpnsa.26.1.2)
-- *************************************************************************

hpnsaEnvMibRevMajor OBJECT-TYPE
   SYNTAX INTEGER (0..65535)
   ACCESS read-only
   STATUS mandatory
   DESCRIPTION
   "The major revision level of the Agent (left of the decimal).
    Used for presence checking."
::= { hpnsaEnvMibRev 1 }

hpnsaEnvMibRevMinor OBJECT-TYPE
   SYNTAX INTEGER (0..65535)
   ACCESS read-only
   STATUS mandatory
   DESCRIPTION
   "The minor revision level of the Agent (right of the decimal)."
::= { hpnsaEnvMibRev 2 }




-- *************************************************************************
-- hpnsaEnvVoltageData (1.3.6.1.4.1.11.2.23.26.2)
-- *************************************************************************
--    hp  (1.3.6.1.4.1.11)
--       nm  (hp.2)
--          hpnsa  (nm.23)
--             hpnsaEnvironment Group      (hpnsa.26)  
--                hpnsaEnvVoltageData Group       (hpnsa.26.2)
--                   hpnsaEnvVoltageSensorTable          (hpnsa.26.2.1) 
--                      hpnsaEnvVoltageSensorEntry           (hpnsa.26.2.1.1) 
--                         hpnsaEnvVoltageSensorIndex        (hpnsa.26.2.1.1.1)
--                         hpnsaEnvVoltageSensorType         (hpnsa.26.2.1.1.2)  
--                         hpnsaEnvVoltageSensorLocation     (hpnsa.26.2.1.1.3)
--                         hpnsaEnvVoltageSensorDescription  (hpnsa.26.2.1.1.4) 
--                         hpnsaEnvVoltageSensorStatus       (hpnsa.26.2.1.1.5)
--                         hpnsaEnvVoltageSensorLevel        (hpnsa.26.2.1.1.6)
--                         hpnsaEnvVoltageSensorNominalLevel (hpnsa.26.2.1.1.7)
--                         hpnsaEnvVoltageSensorNormalMaximum
--                            (hpnsa.26.2.1.1.8)
--                         hpnsaEnvVoltageSensorNormalMinimum
--                            (hpnsa.26.2.1.1.9)
--                         hpnsaEnvVoltageSensorMaximum
--                            (hpnsa.26.2.1.1.10)
--                         hpnsaEnvVoltageSensorMinimum
--                            (hpnsa.26.2.1.1.11)
--                         hpnsaEnvVoltageSensorLowerNonCriticalThreshold
--                            (hpnsa.26.2.1.1.12)
--                         hpnsaEnvVoltageSensorUpperNonCriticalThreshold
--                            (hpnsa.26.2.1.1.13)
--                         hpnsaEnvVoltageSensorLowerCriticalThreshold
--                            (hpnsa.26.2.1.1.14)
--                         hpnsaEnvVoltageSensorUpperCriticalThreshold
--                            (hpnsa.26.2.1.1.15)
--                         hpnsaEnvVoltageSensorLowerNonRecoverableThreshold
--                            (hpnsa.26.2.1.1.16)
--                         hpnsaEnvVoltageSensorUpperNonRecoverableThreshold
--                            (hpnsa.26.2.1.1.17)
--                         hpnsaEnvVoltageSensorResolution  
--                            (hpnsa.26.2.1.1.18)
--                         hpnsaEnvVoltageSensorTolerance   
--                            (hpnsa.26.2.1.1.19)
--                         hpnsaEnvVoltageSensorAccuracy    
--                            (hpnsa.26.2.1.1.20)
--                         hpnsaEnvVoltagePositiveHysterisis
--                            (hpnsa.26.2.1.1.21)
--                         hpnsaEnvVoltageNegativeHysterisis
--                            (hpnsa.26.2.1.1.22
-- *************************************************************************

hpnsaEnvVoltageSensorTable OBJECT-TYPE
   SYNTAX  SEQUENCE OF HPnsaEnvVoltageSensorEntry
   ACCESS  not-accessible
   STATUS  mandatory
   DESCRIPTION
   "A table consisting of status, thresholds, and readings of the voltage
    sensors."
::= { hpnsaEnvVoltageData 1 }

hpnsaEnvVoltageSensorEntry OBJECT-TYPE
   SYNTAX  HPnsaEnvVoltageSensorEntry
   ACCESS  not-accessible
   STATUS  mandatory
   DESCRIPTION
   "Reading, status, and a set of system thresholds for a particular system
   environmet voltage sensor."
   INDEX   { hpnsaEnvVoltageSensorIndex }
::= { hpnsaEnvVoltageSensorTable 1 }
       
HPnsaEnvVoltageSensorEntry ::= SEQUENCE 
{
   hpnsaEnvVoltageSensorIndex                          INTEGER,
   hpnsaEnvVoltageSensorType                           INTEGER,
   hpnsaEnvVoltageSensorLocation                       INTEGER,
   hpnsaEnvVoltageSensorDescription                    INTEGER,
   hpnsaEnvVoltageSensorStatus                         INTEGER,
   hpnsaEnvVoltageSensorLevel                          INTEGER,
   hpnsaEnvVoltageSensorNominalLevel                   INTEGER,
   hpnsaEnvVoltageSensorNormalMaximum                  INTEGER,
   hpnsaEnvVoltageSensorNormalMinimum                  INTEGER,
   hpnsaEnvVoltageSensorMaximum                        INTEGER,
   hpnsaEnvVoltageSensorMinimum                        INTEGER,
   hpnsaEnvVoltageSensorLowerNonCriticalThreshold      INTEGER,
   hpnsaEnvVoltageSensorUpperNonCriticalThreshold      INTEGER,
   hpnsaEnvVoltageSensorLowerCriticalThreshold         INTEGER,
   hpnsaEnvVoltageSensorUpperCriticalThreshold         INTEGER,
   hpnsaEnvVoltageSensorLowerNonRecoverableThreshold   INTEGER,
   hpnsaEnvVoltageSensorUpperNonRecoverableThreshold   INTEGER,
   hpnsaEnvVoltageSensorResolution                     INTEGER,
   hpnsaEnvVoltageSensorTolerance                      INTEGER,
   hpnsaEnvVoltageSensorAccuracy                       INTEGER,
   hpnsaEnvVoltageSensorPositiveHysterisis             INTEGER,
   hpnsaEnvVoltageSensorNegativeHysterisis             INTEGER
}

hpnsaEnvVoltageSensorIndex OBJECT-TYPE
   SYNTAX  INTEGER (0..255)
   ACCESS  read-only
   STATUS  mandatory
   DESCRIPTION
   "A unique index for this sensor."
::= { hpnsaEnvVoltageSensorEntry 1 }

hpnsaEnvVoltageSensorType OBJECT-TYPE
   SYNTAX   INTEGER 
   {
      other(1),
      unknown(2),
      analog(3),
      digital(4),
      three-state-discrete(5),
      four-state-discrete(6)
   }
   ACCESS  read-only
   STATUS  mandatory
   DESCRIPTION
   "The sensor type (analog, digital, etc.)."
::= { hpnsaEnvVoltageSensorEntry 2 }

hpnsaEnvVoltageSensorLocation OBJECT-TYPE
   SYNTAX   INTEGER 
   {
      other(1),
      unknown(2),
      processor(3),
      disk(4),
      peripheral-bay(5),
      system-management-module(6),
      motherboard(7),
      memory-module(8),
      processor-module(9),
      power-unit(10),
      add-in-card(11)
   }
   ACCESS  read-only
   STATUS  mandatory
   DESCRIPTION
   "The location for this sensor."
::= { hpnsaEnvVoltageSensorEntry 3 }

hpnsaEnvVoltageSensorDescription OBJECT-TYPE
   SYNTAX INTEGER 
   {
      voltsensor-other(1),
      voltsensor-unknown(2),
      voltsensor-plus-5-volt(3),
      voltsensor-minus-5-volt(4),
      voltsensor-plus-12-volt(5),
      voltsensor-minus-12-volt(6),
      voltsensor-plus-3-3-volt(7),
      voltsensor-plus-2-5-volt(8),
      voltsensor-scsi-terminator(9),
      voltsensor-processor-1(10),
      voltsensor-processor-2(11),
      voltsensor-processor-3(12),
      voltsensor-processor-4(13)
   }
   ACCESS  read-only
   STATUS  mandatory
   DESCRIPTION
   "The description of the voltage sensor."
::= { hpnsaEnvVoltageSensorEntry 4 }

hpnsaEnvVoltageSensorStatus OBJECT-TYPE
   SYNTAX INTEGER
   {
      other(1),
      unknown(2),
      ok(3),
      non-critical(4),
      critical(5),
      non-recoverable(6)
   }
   ACCESS  read-only
   STATUS  mandatory
   DESCRIPTION
   "The status for this sensor."
::= { hpnsaEnvVoltageSensorEntry 5 }

hpnsaEnvVoltageSensorLevel OBJECT-TYPE
   SYNTAX  INTEGER
   ACCESS  read-only
   STATUS  mandatory
   DESCRIPTION
   "The current voltage reading for the sensor (in millivolts)."
::= { hpnsaEnvVoltageSensorEntry 6 }

hpnsaEnvVoltageSensorNominalLevel OBJECT-TYPE
   SYNTAX  INTEGER
   ACCESS  read-only
   STATUS  mandatory
   DESCRIPTION
   "The nominal (expected) voltage reading of the voltage sensor (in
   millivolts)."
::= { hpnsaEnvVoltageSensorEntry 7 }

hpnsaEnvVoltageSensorNormalMaximum OBJECT-TYPE
   SYNTAX  INTEGER
   ACCESS  read-only
   STATUS  mandatory
   DESCRIPTION
   "The normal maximum voltage reading of the voltage sensor (in
   millivolts)."
::= { hpnsaEnvVoltageSensorEntry 8 }

hpnsaEnvVoltageSensorNormalMinimum OBJECT-TYPE
   SYNTAX  INTEGER
   ACCESS  read-only
   STATUS  mandatory
   DESCRIPTION
   "The normal minimum voltage reading of the voltage sensor (in
   millivolts)."
::= { hpnsaEnvVoltageSensorEntry 9 }

hpnsaEnvVoltageSensorMaximum OBJECT-TYPE
   SYNTAX  INTEGER
   ACCESS  read-only
   STATUS  mandatory
   DESCRIPTION
   "The maximum possible voltage reading of the voltage sensor (in
   millivolts)."
::= { hpnsaEnvVoltageSensorEntry 10 }

hpnsaEnvVoltageSensorMinimum OBJECT-TYPE
   SYNTAX  INTEGER
   ACCESS  read-only
   STATUS  mandatory
   DESCRIPTION
   "The minimum possible voltage reading of the voltage sensor (in
   millivolts)."
::= { hpnsaEnvVoltageSensorEntry 11 }

hpnsaEnvVoltageSensorLowerNonCriticalThreshold OBJECT-TYPE
   SYNTAX  INTEGER
   ACCESS  read-write
   STATUS  mandatory
   DESCRIPTION
   "The lower non-critical voltage threshold for the sensor (in millivolts)."
::= { hpnsaEnvVoltageSensorEntry 12 }

hpnsaEnvVoltageSensorUpperNonCriticalThreshold OBJECT-TYPE
   SYNTAX  INTEGER
   ACCESS  read-write
   STATUS  mandatory
   DESCRIPTION
   "The upper non-critical voltage threshold for the sensor (in millivolts)."
::= { hpnsaEnvVoltageSensorEntry 13 }

hpnsaEnvVoltageSensorLowerCriticalThreshold OBJECT-TYPE
   SYNTAX  INTEGER
   ACCESS  read-write
   STATUS  mandatory
   DESCRIPTION
   "The lower critical voltage threshold for the sensor (in millivolts)."
::= { hpnsaEnvVoltageSensorEntry 14 }

hpnsaEnvVoltageSensorUpperCriticalThreshold OBJECT-TYPE
   SYNTAX  INTEGER
   ACCESS  read-write
   STATUS  mandatory
   DESCRIPTION
   "The upper critical voltage threshold for the sensor (in millivolts)."
::= { hpnsaEnvVoltageSensorEntry 15 }

hpnsaEnvVoltageSensorLowerNonRecoverableThreshold OBJECT-TYPE
   SYNTAX  INTEGER
   ACCESS  read-write
   STATUS  mandatory
   DESCRIPTION
   "The lower non-recoverable voltage threshold for the sensor (in millivolts)."
::= { hpnsaEnvVoltageSensorEntry 16 }

hpnsaEnvVoltageSensorUpperNonRecoverableThreshold OBJECT-TYPE
   SYNTAX  INTEGER
   ACCESS  read-write
   STATUS  mandatory
   DESCRIPTION
   "The upper non-recoverable voltage threshold for the sensor (in millivolts)."
::= { hpnsaEnvVoltageSensorEntry 17 }

hpnsaEnvVoltageSensorResolution OBJECT-TYPE
   SYNTAX  INTEGER
   ACCESS  read-only
   STATUS  mandatory
   DESCRIPTION
   "The resolution of the voltage sensor reading (in tenths of millivolts)."
::= { hpnsaEnvVoltageSensorEntry 18 }

hpnsaEnvVoltageSensorTolerance OBJECT-TYPE
   SYNTAX  INTEGER
   ACCESS  read-only
   STATUS  mandatory
   DESCRIPTION
   "The tolerance of the voltage sensor reading (in plus/minus millivolts)."
::= { hpnsaEnvVoltageSensorEntry 19 }

hpnsaEnvVoltageSensorAccuracy OBJECT-TYPE
   SYNTAX  INTEGER
   ACCESS  read-only
   STATUS  mandatory
   DESCRIPTION
   "The accuracy of the voltage sensor reading (in plus/minus hundredths of a
   percent)."
::= { hpnsaEnvVoltageSensorEntry 20 }

hpnsaEnvVoltageSensorPositiveHysterisis OBJECT-TYPE
   SYNTAX  INTEGER
   ACCESS  read-write
   STATUS  mandatory
   DESCRIPTION
   "The positive hysterisis value for the voltage sensor (in millivolts)."
::= { hpnsaEnvVoltageSensorEntry 21 }

hpnsaEnvVoltageSensorNegativeHysterisis OBJECT-TYPE
   SYNTAX  INTEGER
   ACCESS  read-write
   STATUS  mandatory
   DESCRIPTION
   "The negative hysterisis value for the voltage sensor (in millivolts)."
::= { hpnsaEnvVoltageSensorEntry 22 }


-- *************************************************************************
-- hpnsaEnvTemperatureData (1.3.6.1.4.1.11.2.23.26.3)
-- *************************************************************************
--    hp  (1.3.6.1.4.1.11)
--       nm  (hp.2)
--          hpnsa  (nm.23)
--             hpnsaEnvironment Group      (hpnsa.26)  
--                hpnsaEnvTemperatureData Group       (hpnsa.26.3)
--                   hpnsaEnvTemperatureSensorTable      (hpnsa.26.3.1) 
--                      hpnsaEnvTemperatureSensorEntry      (hpnsa.26.3.1.1) 
--                         hpnsaEnvTemperatureSensorIndex      (hpnsa.26.3.1.1.1)
--                         hpnsaEnvTemperatureSensorType       (hpnsa.26.3.1.1.2)
--                         hpnsaEnvTemperatureSensorLocation 
--                            (hpnsa.26.3.1.1.3)
--                         hpnsaEnvTemperatureSensorDescription
--                            (hpnsa.26.3.1.1.4)
--                         hpnsaEnvTemperatureSensorStatus  
--                            (hpnsa.26.3.1.1.5)
--                         hpnsaEnvTemperatureSensorReading 
--                            (hpnsa.26.3.1.1.6)
--                         hpnsaEnvTemperatureSensorNominalReading 
--                            (hpnsa.26.3.1.1.7)
--                         hpnsaEnvTemperatureSensorNormalMaximum
--                            (hpnsa.26.3.1.1.8)
--                         hpnsaEnvTemperatureSensorNormalMinimum
--                            (hpnsa.26.3.1.1.9)
--                         hpnsaEnvTemperatureSensorMaximum
--                            (hpnsa.26.3.1.1.10)
--                         hpnsaEnvTemperatureSensorMinimum
--                            (hpnsa.26.3.1.1.11)
--                         hpnsaEnvTemperatureSensorLowerNonCriticalThreshold
--                            (hpnsa.26.3.1.1.12)
--                         hpnsaEnvTemperatureSensorUpperNonCriticalThreshold
--                            (hpnsa.26.3.1.1.13)
--                         hpnsaEnvTemperatureSensorLowerCriticalThreshold
--                            (hpnsa.26.3.1.1.14)
--                         hpnsaEnvTemperatureSensorUpperCriticalThreshold
--                            (hpnsa.26.3.1.1.15)
--                         hpnsaEnvTemperatureSensorLowerNonRecoverableThreshold
--                            (hpnsa.26.3.1.1.16)
--                         hpnsaEnvTemperatureSensorUpperNonRecoverableThreshold
--                            (hpnsa.26.3.1.1.17)
--                         hpnsaEnvTemperatureSensorResolution
--                            (hpnsa.26.3.1.1.18)
--                         hpnsaEnvTemperatureSensorTolerance
--                            (hpnsa.26.3.1.1.19)
--                         hpnsaEnvTemperatureSensorAccuracy
--                            (hpnsa.26.3.1.1.20)
--                         hpnsaEnvTemperaturePositiveHysterisis
--                            (hpnsa.26.3.1.1.21)
--                         hpnsaEnvTemperatureNegativeHysterisis
--                            (hpnsa.26.3.1.1.22)
-- *************************************************************************

hpnsaEnvTemperatureSensorTable OBJECT-TYPE
   SYNTAX  SEQUENCE OF HPnsaEnvTemperatureSensorEntry
   ACCESS  not-accessible
   STATUS  mandatory
   DESCRIPTION
   "A table consisting of status, thresholds, and readings of the temperature
    sensors."
::= { hpnsaEnvTemperatureData 1 }

hpnsaEnvTemperatureSensorEntry OBJECT-TYPE
   SYNTAX  HPnsaEnvTemperatureSensorEntry
   ACCESS  not-accessible
   STATUS  mandatory
   DESCRIPTION
   "Reading, status, and a set of system thresholds for a particular system
   environmet temperature sensor."
   INDEX   { hpnsaEnvTemperatureSensorIndex }
::= { hpnsaEnvTemperatureSensorTable 1 }
       
HPnsaEnvTemperatureSensorEntry ::= SEQUENCE 
{
   hpnsaEnvTemperatureSensorIndex                           INTEGER,
   hpnsaEnvTemperatureSensorType                            INTEGER,
   hpnsaEnvTemperatureSensorLocation                        INTEGER,
   hpnsaEnvTemperatureSensorDescription                     INTEGER,
   hpnsaEnvTemperatureSensorStatus                          INTEGER,
   hpnsaEnvTemperatureSensorReading                         INTEGER,
   hpnsaEnvTemperatureSensorNominalReading                  INTEGER,
   hpnsaEnvTemperatureSensorNormalMaximum                   INTEGER,
   hpnsaEnvTemperatureSensorNormalMinimum                   INTEGER,
   hpnsaEnvTemperatureSensorMaximum                         INTEGER,
   hpnsaEnvTemperatureSensorMinimum                         INTEGER,
   hpnsaEnvTemperatureSensorLowerNonCriticalThreshold       INTEGER,
   hpnsaEnvTemperatureSensorUpperNonCriticalThreshold       INTEGER,
   hpnsaEnvTemperatureSensorLowerCriticalThreshold          INTEGER,
   hpnsaEnvTemperatureSensorUpperCriticalThreshold          INTEGER,
   hpnsaEnvTemperatureSensorLowerNonRecoverableThreshold    INTEGER,
   hpnsaEnvTemperatureSensorUpperNonRecoverableThreshold    INTEGER,
   hpnsaEnvTemperatureSensorResolution                      INTEGER,
   hpnsaEnvTemperatureSensorTolerance                       INTEGER,
   hpnsaEnvTemperatureSensorAccuracy                        INTEGER,
   hpnsaEnvTemperatureSensorPositiveHysterisis              INTEGER,
   hpnsaEnvTemperatureSensorNegativeHysterisis              INTEGER
}

hpnsaEnvTemperatureSensorIndex OBJECT-TYPE
   SYNTAX  INTEGER (0..255)
   ACCESS  read-only
   STATUS  mandatory
   DESCRIPTION
   "A unique index for this sensor."
::= { hpnsaEnvTemperatureSensorEntry 1 }

hpnsaEnvTemperatureSensorType OBJECT-TYPE
   SYNTAX   INTEGER 
   {
      other(1),
      unknown(2),
      analog(3),
      digital(4),
      three-state-discrete(5),
      four-state-discrete(6)
   }
   ACCESS  read-only
   STATUS  mandatory
   DESCRIPTION
   "The sensor type (analog, digital, etc.)."
::= { hpnsaEnvTemperatureSensorEntry 2 }

hpnsaEnvTemperatureSensorLocation OBJECT-TYPE
   SYNTAX   INTEGER 
   {
      other(1),
      unknown(2),
      processor(3),
      disk(4),
      peripheral-bay(5),
      system-management-module(6),
      motherboard(7),
      memory-module(8),
      processor-module(9),
      power-unit(10),
      add-in-card(11)
   }
   ACCESS  read-only
   STATUS  mandatory
   DESCRIPTION
   "The location for this sensor."
::= { hpnsaEnvTemperatureSensorEntry 3 }

hpnsaEnvTemperatureSensorDescription OBJECT-TYPE
   SYNTAX INTEGER 
   {
      temperature-sensor-other(1),
      temperature-sensor-unknown(2),
      temperature-sensor-processor-1(3),
      temperature-sensor-processor-2(4),
      temperature-sensor-processor-3(5),
      temperature-sensor-processor-4(6),
      temperature-sensor-processor-5(7),
      temperature-sensor-processor-6(8),
      temperature-sensor-processor-7(9),
      temperature-sensor-processor-8(10),
      temperature-sensor-system-board(11),
      temperature-sensor-disk-backplane(12)
   }
   ACCESS  read-only
   STATUS  mandatory
   DESCRIPTION
   "The description of the temperature sensor."
::= { hpnsaEnvTemperatureSensorEntry 4 }

hpnsaEnvTemperatureSensorStatus OBJECT-TYPE
   SYNTAX INTEGER
   {
      other(1),
      unknown(2),
      ok(3),
      non-critical(4),
      critical(5),
      non-recoverable(6)
   }
   ACCESS  read-only
   STATUS  mandatory
   DESCRIPTION
   "The status for this sensor."
::= { hpnsaEnvTemperatureSensorEntry 5 }

hpnsaEnvTemperatureSensorReading OBJECT-TYPE
   SYNTAX  INTEGER
   ACCESS  read-only
   STATUS  mandatory
   DESCRIPTION
   "The current temperature reading for the sensor (in degrees Celsius)."
::= { hpnsaEnvTemperatureSensorEntry 6 }

hpnsaEnvTemperatureSensorNominalReading OBJECT-TYPE
   SYNTAX  INTEGER
   ACCESS  read-only
   STATUS  mandatory
   DESCRIPTION
   "The nominal (expected) temperature reading of the temperature sensor (in
   degrees Celsius)."
::= { hpnsaEnvTemperatureSensorEntry 7 }

hpnsaEnvTemperatureSensorNormalMaximum OBJECT-TYPE
   SYNTAX  INTEGER
   ACCESS  read-only
   STATUS  mandatory
   DESCRIPTION
   "The normal maximum temperature reading of the temperature sensor (in
   degrees Celsius)."
::= { hpnsaEnvTemperatureSensorEntry 8 }

hpnsaEnvTemperatureSensorNormalMinimum OBJECT-TYPE
   SYNTAX  INTEGER
   ACCESS  read-only
   STATUS  mandatory
   DESCRIPTION
   "The normal minimum temperature reading of the temperature sensor (in
   degrees Celsius)."
::= { hpnsaEnvTemperatureSensorEntry 9 }

hpnsaEnvTemperatureSensorMaximum OBJECT-TYPE
   SYNTAX  INTEGER
   ACCESS  read-only
   STATUS  mandatory
   DESCRIPTION
   "The maximum possible temperature reading of the temperature sensor (in
   degrees Celsius)."
::= { hpnsaEnvTemperatureSensorEntry 10 }

hpnsaEnvTemperatureSensorMinimum OBJECT-TYPE
   --SYNTAX  INTEGER
   SYNTAX  INTEGER
   ACCESS  read-only
   STATUS  mandatory
   DESCRIPTION
   "The minimum possible temperature reading of the temperature sensor (in
   degrees Celsius)."
::= { hpnsaEnvTemperatureSensorEntry 11 }

hpnsaEnvTemperatureSensorLowerNonCriticalThreshold OBJECT-TYPE
   SYNTAX  INTEGER
   ACCESS  read-write
   STATUS  mandatory
   DESCRIPTION
   "The lower non-critical temperature threshold for the sensor (in degrees
   Celsius)."
::= { hpnsaEnvTemperatureSensorEntry 12 }

hpnsaEnvTemperatureSensorUpperNonCriticalThreshold OBJECT-TYPE
   SYNTAX  INTEGER
   ACCESS  read-write
   STATUS  mandatory
   DESCRIPTION
   "The upper non-critical temperature threshold for the sensor (in degrees
   Celsius)."
::= { hpnsaEnvTemperatureSensorEntry 13 }

hpnsaEnvTemperatureSensorLowerCriticalThreshold OBJECT-TYPE
   SYNTAX  INTEGER
   ACCESS  read-write
   STATUS  mandatory
   DESCRIPTION
   "The lower critical temperature threshold for the sensor (in degrees Celsius)."
::= { hpnsaEnvTemperatureSensorEntry 14 }

hpnsaEnvTemperatureSensorUpperCriticalThreshold OBJECT-TYPE
   SYNTAX  INTEGER
   ACCESS  read-write
   STATUS  mandatory
   DESCRIPTION
   "The upper critical temperature threshold for the sensor (in degrees Celsius)."
::= { hpnsaEnvTemperatureSensorEntry 15 }

hpnsaEnvTemperatureSensorLowerNonRecoverableThreshold OBJECT-TYPE
   SYNTAX  INTEGER
   ACCESS  read-write
   STATUS  mandatory
   DESCRIPTION
   "The lower non-recoverable temperature threshold for the sensor (in degrees
   Celsius)."
::= { hpnsaEnvTemperatureSensorEntry 16 }

hpnsaEnvTemperatureSensorUpperNonRecoverableThreshold OBJECT-TYPE
   SYNTAX  INTEGER
   ACCESS  read-write
   STATUS  mandatory
   DESCRIPTION
   "The upper non-recoverable temperature threshold for the sensor (in degrees
   Celsius)."
::= { hpnsaEnvTemperatureSensorEntry 17 }

hpnsaEnvTemperatureSensorResolution OBJECT-TYPE
   SYNTAX  INTEGER
   ACCESS  read-only
   STATUS  mandatory
   DESCRIPTION
   "The resolution of the temperature sensor reading (in tenths of degrees
   Celsius)."
::= { hpnsaEnvTemperatureSensorEntry 18 }

hpnsaEnvTemperatureSensorTolerance OBJECT-TYPE
   SYNTAX  INTEGER
   ACCESS  read-only
   STATUS  mandatory
   DESCRIPTION
   "The tolerance of the temperature sensor reading (in plus/minus tenths of
   a degree Celsius)."
::= { hpnsaEnvTemperatureSensorEntry 19 }

hpnsaEnvTemperatureSensorAccuracy OBJECT-TYPE
   SYNTAX  INTEGER
   ACCESS  read-only
   STATUS  mandatory
   DESCRIPTION
   "The accuracy of the temperature sensor reading (in plus/minus hundredths of a
   percent)."
::= { hpnsaEnvTemperatureSensorEntry 20 }

hpnsaEnvTemperatureSensorPositiveHysterisis OBJECT-TYPE
   SYNTAX  INTEGER
   ACCESS  read-write
   STATUS  mandatory
   DESCRIPTION
   "The positive hysterisis value for the temperature sensor (in degrees
   Celsius)."
::= { hpnsaEnvTemperatureSensorEntry 21 }

hpnsaEnvTemperatureSensorNegativeHysterisis OBJECT-TYPE
   SYNTAX  INTEGER
   ACCESS  read-write
   STATUS  mandatory
   DESCRIPTION
   "The negative hysterisis value for the temperature sensor (in degrees
   Celsius)."
::= { hpnsaEnvTemperatureSensorEntry 22 }

-- ****************************************************************************
-- hpnsaEnvFanSensorData (1.3.6.1.4.1.11.2.23.26.4)
-- ****************************************************************************
--    hp  (1.3.6.1.4.1.11)
--       nm  (hp.2)
--          hpnsa  (nm.23)
--             hpnsaEnvironment Group      (hpnsa.26)  
--                hpnsaEnvFanSensorData Group         (hpnsa.26.4)
--                   hpnsaEnvFanSensorTable              (hpnsa.26.4.1) 
--                      hpnsaEnvFanSensorEntry              (hpnsa.26.4.1.1) 
--                         hpnsaEnvFanSensorIndex              (hpnsa.26.4.1.1.1)
--                         hpnsaEnvFanSensorType               (hpnsa.26.4.1.1.2)
--                         hpnsaEnvFanSensorLocation           (hpnsa.26.4.1.1.3)
--                         hpnsaEnvFanSensorDescription        (hpnsa.26.4.1.1.4) 
--                         hpnsaEnvFanSensorStatus             (hpnsa.26.4.1.1.5)
--                         hpnsaEnvFanSensorReading            (hpnsa.26.4.1.1.6)
--                         hpnsaEnvFanSensorNominalReading     (hpnsa.26.4.1.1.7)
--                         hpnsaEnvFanSensorNormalMaximum      (hpnsa.26.4.1.1.8)
--                         hpnsaEnvFanSensorNormalMinimum      (hpnsa.26.4.1.1.9)
--                         hpnsaEnvFanSensorMaximum            (hpnsa.26.4.1.1.10)
--                         hpnsaEnvFanSensorMinimum            (hpnsa.26.4.1.1.11)
--                         hpnsaEnvFanSensorLowerNonCriticalThreshold
--                           (hpnsa.26.4.1.1.12)
--                         hpnsaEnvFanSensorUpperNonCriticalThreshold
--                           (hpnsa.26.4.1.1.13)
--                         hpnsaEnvFanSensorLowerCriticalThreshold
--                           (hpnsa.26.4.1.1.14)
--                         hpnsaEnvFanSensorUpperCriticalThreshold
--                           (hpnsa.26.4.1.1.15)
--                         hpnsaEnvFanSensorLowerNonRecoverableThreshold
--                           (hpnsa.26.4.1.1.16)
--                         hpnsaEnvFanSensorUpperNonRecoverableThreshold
--                           (hpnsa.26.4.1.1.17)
--                         hpnsaEnvFanSensorResolution         (hpnsa.26.4.1.1.18)
--                         hpnsaEnvFanSensorTolerance          (hpnsa.26.4.1.1.19)
--                         hpnsaEnvFanSensorAccuracy           (hpnsa.26.4.1.1.20)
--                         hpnsaEnvFanSensorPositiveHysterisis (hpnsa.26.4.1.1.21)
--                         hpnsaEnvFanSensorNegativeHysterisis (hpnsa.26.4.1.1.22)
-- ****************************************************************************

hpnsaEnvFanSensorTable OBJECT-TYPE
   SYNTAX  SEQUENCE OF HPnsaEnvFanSensorEntry
   ACCESS  not-accessible
   STATUS  mandatory
   DESCRIPTION
   "A table consisting of status, thresholds, and readings of the fan
    sensors."
::= { hpnsaEnvFanSensorData 1 }

hpnsaEnvFanSensorEntry OBJECT-TYPE
   SYNTAX  HPnsaEnvFanSensorEntry
   ACCESS  not-accessible
   STATUS  mandatory
   DESCRIPTION
   "Reading, status, and a set of system thresholds for a particular system
   environmet fan sensor."
   INDEX   { hpnsaEnvFanSensorIndex }
::= { hpnsaEnvFanSensorTable 1 }
       
HPnsaEnvFanSensorEntry ::= SEQUENCE 
{
   hpnsaEnvFanSensorIndex                          INTEGER,
   hpnsaEnvFanSensorType                           INTEGER,
   hpnsaEnvFanSensorLocation                       INTEGER,
   hpnsaEnvFanSensorDescription                    INTEGER,
   hpnsaEnvFanSensorStatus                         INTEGER,
   hpnsaEnvFanSensorReading                        INTEGER,
   hpnsaEnvFanSensorNominalReading                 INTEGER,
   hpnsaEnvFanSensorNormalMaximum                  INTEGER,
   hpnsaEnvFanSensorNormalMinimum                  INTEGER,
   hpnsaEnvFanSensorMaximum                        INTEGER,
   hpnsaEnvFanSensorMinimum                        INTEGER,
   hpnsaEnvFanSensorLowerNonCriticalThreshold      INTEGER,
   hpnsaEnvFanSensorUpperNonCriticalThreshold      INTEGER,
   hpnsaEnvFanSensorLowerCriticalThreshold         INTEGER,
   hpnsaEnvFanSensorUpperCriticalThreshold         INTEGER,
   hpnsaEnvFanSensorLowerNonRecoverableThreshold   INTEGER,
   hpnsaEnvFanSensorUpperNonRecoverableThreshold   INTEGER,
   hpnsaEnvFanSensorResolution                     INTEGER,
   hpnsaEnvFanSensorTolerance                      INTEGER,
   hpnsaEnvFanSensorAccuracy                       INTEGER,
   hpnsaEnvFanSensorPositiveHysterisis             INTEGER,
   hpnsaEnvFanSensorNegativeHysterisis             INTEGER
}

hpnsaEnvFanSensorIndex OBJECT-TYPE
   SYNTAX  INTEGER (0..255)
   ACCESS  read-only
   STATUS  mandatory
   DESCRIPTION
   "A unique index for this sensor."
::= { hpnsaEnvFanSensorEntry 1 }

hpnsaEnvFanSensorType OBJECT-TYPE
   SYNTAX   INTEGER 
   {
      other(1),
      unknown(2),
      analog(3),
      digital(4),
      three-state-discrete(5),
      four-state-discrete(6)
   }
   ACCESS  read-only
   STATUS  mandatory
   DESCRIPTION
   "The sensor type (analog, digital, etc.)."
::= { hpnsaEnvFanSensorEntry 2 }

hpnsaEnvFanSensorLocation OBJECT-TYPE
   SYNTAX   INTEGER 
   {
      other(1),
      unknown(2),
      processor(3),
      disk(4),
      peripheral-bay(5),
      system-management-module(6),
      motherboard(7),
      memory-module(8),
      processor-module(9),
      power-unit(10),
      add-in-card(11)
   }
   ACCESS  read-only
   STATUS  mandatory
   DESCRIPTION
   "The location for this sensor."
::= { hpnsaEnvFanSensorEntry 3 }

hpnsaEnvFanSensorDescription OBJECT-TYPE
   SYNTAX INTEGER 
   {
      fan-sensor-other(1),
      fan-sensor-unknown(2),
      fan-sensor-cpu-board(3),
      fan-sensor-chassis(4)
   }
   ACCESS  read-only
   STATUS  mandatory
   DESCRIPTION
   "The description of the fan sensor."
::= { hpnsaEnvFanSensorEntry 4 }

hpnsaEnvFanSensorStatus OBJECT-TYPE
   SYNTAX INTEGER
   {
      other(1),
      unknown(2),
      ok(3),
      non-critical(4),
      critical(5),
      non-recoverable(6) 
   }
   ACCESS  read-only
   STATUS  mandatory
   DESCRIPTION
   "The status for this sensor."
::= { hpnsaEnvFanSensorEntry 5 }

hpnsaEnvFanSensorReading OBJECT-TYPE
   SYNTAX  INTEGER (0..65535)
   ACCESS  read-only
   STATUS  mandatory
   DESCRIPTION
   "The current fan reading for the sensor (in RPMs)."
::= { hpnsaEnvFanSensorEntry 6 }

hpnsaEnvFanSensorNominalReading OBJECT-TYPE
   SYNTAX  INTEGER (0..65535)
   ACCESS  read-only
   STATUS  mandatory
   DESCRIPTION
   "The nominal (expected) fan reading of the fan sensor (in
   RPMs)."
::= { hpnsaEnvFanSensorEntry 7 }

hpnsaEnvFanSensorNormalMaximum OBJECT-TYPE
   SYNTAX  INTEGER (0..65535)
   ACCESS  read-only
   STATUS  mandatory
   DESCRIPTION
   "The normal maximum fan reading of the fan sensor (in
   RPMs)."
::= { hpnsaEnvFanSensorEntry 8 }

hpnsaEnvFanSensorNormalMinimum OBJECT-TYPE
   SYNTAX  INTEGER (0..65535)
   ACCESS  read-only
   STATUS  mandatory
   DESCRIPTION
   "The normal minimum fan reading of the fan sensor (in
   RPMs)."
::= { hpnsaEnvFanSensorEntry 9 }

hpnsaEnvFanSensorMaximum OBJECT-TYPE
   SYNTAX  INTEGER (0..65535)
   ACCESS  read-only
   STATUS  mandatory
   DESCRIPTION
   "The maximum possible fan reading of the fan sensor (in
   RPMs)."
::= { hpnsaEnvFanSensorEntry 10 }

hpnsaEnvFanSensorMinimum OBJECT-TYPE
   SYNTAX  INTEGER (0..65535)
   ACCESS  read-only
   STATUS  mandatory
   DESCRIPTION
   "The minimum possible fan reading of the fan sensor (in
   RPMs)."
::= { hpnsaEnvFanSensorEntry 11 }

hpnsaEnvFanSensorLowerNonCriticalThreshold OBJECT-TYPE
   SYNTAX  INTEGER (0..65535)
   ACCESS  read-write
   STATUS  mandatory
   DESCRIPTION
   "The lower non-critical fan threshold for the sensor (in RPMs)."
::= { hpnsaEnvFanSensorEntry 12 }

hpnsaEnvFanSensorUpperNonCriticalThreshold OBJECT-TYPE
   SYNTAX  INTEGER (0..65535)
   ACCESS  read-write
   STATUS  mandatory
   DESCRIPTION
   "The upper non-critical fan threshold for the sensor (in RPMs)."
::= { hpnsaEnvFanSensorEntry 13 }

hpnsaEnvFanSensorLowerCriticalThreshold OBJECT-TYPE
   SYNTAX  INTEGER (0..65535)
   ACCESS  read-write
   STATUS  mandatory
   DESCRIPTION
   "The lower critical fan threshold for the sensor (in RPMs)."
::= { hpnsaEnvFanSensorEntry 14 }

hpnsaEnvFanSensorUpperCriticalThreshold OBJECT-TYPE
   SYNTAX  INTEGER (0..65535)
   ACCESS  read-write
   STATUS  mandatory
   DESCRIPTION
   "The upper critical fan threshold for the sensor (in RPMs)."
::= { hpnsaEnvFanSensorEntry 15 }

hpnsaEnvFanSensorLowerNonRecoverableThreshold OBJECT-TYPE
   SYNTAX  INTEGER (0..65535)
   ACCESS  read-write
   STATUS  mandatory
   DESCRIPTION
   "The lower non-recoverable fan threshold for the sensor (in RPMs)."
::= { hpnsaEnvFanSensorEntry 16 }

hpnsaEnvFanSensorUpperNonRecoverableThreshold OBJECT-TYPE
   SYNTAX  INTEGER (0..65535)
   ACCESS  read-write
   STATUS  mandatory
   DESCRIPTION
   "The upper non-recoverable fan threshold for the sensor (in RPMs)."
::= { hpnsaEnvFanSensorEntry 17 }

hpnsaEnvFanSensorResolution OBJECT-TYPE
   SYNTAX  INTEGER (0..65535)
   ACCESS  read-only
   STATUS  mandatory
   DESCRIPTION
   "The resolution of the fan sensor reading (in tenths of RPMs)."
::= { hpnsaEnvFanSensorEntry 18 }

hpnsaEnvFanSensorTolerance OBJECT-TYPE
   SYNTAX  INTEGER (0..65535)
   ACCESS  read-only
   STATUS  mandatory
   DESCRIPTION
   "The tolerance of the fan sensor reading (in plus/minus RPMs)."
::= { hpnsaEnvFanSensorEntry 19 }

hpnsaEnvFanSensorAccuracy OBJECT-TYPE
   SYNTAX  INTEGER (0..65535)
   ACCESS  read-only
   STATUS  mandatory
   DESCRIPTION
   "The accuracy of the fan sensor reading (in plus/minus hundredths of a
   percent)."
::= { hpnsaEnvFanSensorEntry 20 }

hpnsaEnvFanSensorPositiveHysterisis OBJECT-TYPE
   SYNTAX  INTEGER (0..65535)
   ACCESS  read-write
   STATUS  mandatory
   DESCRIPTION
   "The positive hysterisis value for the fan sensor (in RPMs)."
::= { hpnsaEnvFanSensorEntry 21 }

hpnsaEnvFanSensorNegativeHysterisis OBJECT-TYPE
   SYNTAX  INTEGER (0..65535)
   ACCESS  read-write
   STATUS  mandatory
   DESCRIPTION
   "The negative hysterisis value for the fan sensor (in RPMs)."
::= { hpnsaEnvFanSensorEntry 22 }


-- ****************************************************************************
-- hpnsaEnvChassisData (1.3.6.1.4.1.11.2.23.26.5)
-- ****************************************************************************
--    hp  (1.3.6.1.4.1.11)
--       nm  (hp.2)
--          hpnsa  (nm.23)
--             hpnsaEnvironment Group      (hpnsa.26)  
--                hpnsaEnvChassisData Group     (hpnsa.26.5)
--                   hpnsaEnvChassisStatus         (hpnsa.26.5.1)
-- ****************************************************************************

hpnsaEnvChassisStatus OBJECT-TYPE
   SYNTAX  INTEGER
   {
      chassis-open(1),
      chassis-closed(2)
   }
   ACCESS  read-only
   STATUS  mandatory
   DESCRIPTION
   "The status of the system chassis."
::= { hpnsaEnvChassisData 1 }

END
