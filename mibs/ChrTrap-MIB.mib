ChrTrap-MIB DEFINITIONS ::= BEGIN

IMPORTS
	TRAP-TYPE FROM RFC-1215
	chrComTrap FROM Chromatis-MIB;


          chrComTrapLoggedTrap TRAP-TYPE
              ENTERPRISE  chrComTrap
              DESCRIPTION
                      "This trap informs about a new event that was reported to the
					   TrapLog table."
              ::= 1


END
