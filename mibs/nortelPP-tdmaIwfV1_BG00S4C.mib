Nortel-Magellan-Passport-TdmaIwfMIB
DEFINITIONS ::= BEGIN



IMPORTS

      OBJECT-TYPE
   FROM RFC-1212

      IpAddress
   FROM RFC1155-SMI

      components,
      passportMIBs
   FROM Nortel-Magellan-Passport-UsefulDefinitionsMIB

      Counter32,
      RowPointer,
      DisplayString,
      StorageType,
      RowStatus,
      Gauge32,
      Integer32,
      Unsigned32
   FROM Nortel-Magellan-Passport-StandardTextualConventionsMIB

      AsciiString,
      NonReplicated,
      Link,
      FixedPoint2
   FROM Nortel-Magellan-Passport-TextualConventionsMIB;




-- LAST-UPDATED   "9906090000Z"
-- ORGANIZATION   "Nortel"
-- CONTACT-INFO   "
--         Nortel Magellan Network Management
--         
--         Postal: P.O. Box 5080, Station F 
--                 Ottawa, Ontario 
--                 Canada  K2C 3T1
--         
--         Email:  nm_plm@nt.com"
-- DESCRIPTION
--    "The module describing the Nortel Magellan Passport
--     TdmaIwf Enterprise MIB."

tdmaIwfMIB OBJECT IDENTIFIER ::= { passportMIBs 140 }










-- TdmaCs/<csIndex>
-- The TdmaIwfCallServer component represents an instance of a call 
-- manager for Mobile Telephone eXchange communications (MTX) 
-- InterWorking Function (IWF) calls on this node. The 
-- TdmaIwfCallServer provides a mechanism to segregate call 
-- resources (TdmaIwfBearerChannels) and maintenance activities for 
-- the TdmaIwfBearerChannel(s) associated with that 
-- TdmaIwfCallServer. The csIndex bears no particular significance 
-- and is arbitrary.
-- 
-- This component is specific to the tdmaIwfCallServer feature of the 
-- tdmaIwf application.

tdmaCs OBJECT IDENTIFIER ::= { components 135 }



tdmaCsRowStatusTable OBJECT-TYPE
   SYNTAX     SEQUENCE OF TdmaCsRowStatusEntry
   ACCESS     not-accessible
   STATUS     mandatory
   DESCRIPTION
     "This entry controls the addition and deletion of 
      tdmaCs components."
::= { tdmaCs 1 }

tdmaCsRowStatusEntry OBJECT-TYPE
   SYNTAX     TdmaCsRowStatusEntry
   ACCESS     not-accessible
   STATUS     mandatory
   DESCRIPTION
     "A single entry in the table represents a single 
      tdmaCs component."
   INDEX {
      tdmaCsCsIndex }
::= { tdmaCsRowStatusTable 1 }

TdmaCsRowStatusEntry ::= SEQUENCE {
   tdmaCsRowStatus
      RowStatus,
   tdmaCsComponentName
      DisplayString,
   tdmaCsStorageType
      StorageType,
   tdmaCsCsIndex
      Integer32 }

tdmaCsRowStatus OBJECT-TYPE
   SYNTAX     RowStatus 
   ACCESS     read-write
   STATUS     mandatory
   DESCRIPTION
     "This variable is used as the basis for SNMP naming of
      tdmaCs components.
      These components can be added and deleted."
::= { tdmaCsRowStatusEntry 1 }

tdmaCsComponentName OBJECT-TYPE
   SYNTAX     DisplayString 
   ACCESS     read-only
   STATUS     mandatory
   DESCRIPTION
     "This variable provides the component's string name for
      use with the ASCII Console Interface"
::= { tdmaCsRowStatusEntry 2 }

tdmaCsStorageType OBJECT-TYPE
   SYNTAX     StorageType 
   ACCESS     read-only
   STATUS     mandatory
   DESCRIPTION
     "This variable represents the storage type value for the
      tdmaCs tables."
::= { tdmaCsRowStatusEntry 4 }

tdmaCsCsIndex OBJECT-TYPE
   SYNTAX     Integer32 (1..10)
   ACCESS     not-accessible
   STATUS     mandatory
   DESCRIPTION
     "This variable represents the index for the tdmaCs tables."
::= { tdmaCsRowStatusEntry 10 }

tdmaCsServProvTable OBJECT-TYPE
   SYNTAX     SEQUENCE OF TdmaCsServProvEntry
   ACCESS     not-accessible
   STATUS     mandatory
   DESCRIPTION
     "This group contains all the necessary timers for call setup and call 
      clearing scenarios on the IWF."
::= { tdmaCs 100 }

tdmaCsServProvEntry OBJECT-TYPE
   SYNTAX     TdmaCsServProvEntry
   ACCESS     not-accessible
   STATUS     mandatory
   DESCRIPTION
     "An entry in the tdmaCsServProvTable."
   INDEX {
      tdmaCsCsIndex }
::= { tdmaCsServProvTable 1 }

TdmaCsServProvEntry ::= SEQUENCE {
   tdmaCsTIwf1
      Unsigned32,
   tdmaCsTIwf2
      Unsigned32,
   tdmaCsT303
      Unsigned32,
   tdmaCsT305
      Unsigned32,
   tdmaCsT308
      Unsigned32,
   tdmaCsT313
      Unsigned32,
   tdmaCsT999
      Unsigned32,
   tdmaCsSupportedTechnology
      INTEGER,
   tdmaCsSupportedService
      INTEGER }

tdmaCsTIwf1 OBJECT-TYPE
   SYNTAX     Unsigned32 (0..3600)
   ACCESS     read-write
   STATUS     mandatory
   DESCRIPTION
     "This is an internal timer to the call server of the IWF and is used 
      during call setup for ensuring the MIT protocol stack and the NIT 
      modem for a new call have been allocated and initialized."
   DEFVAL     { 4 }
::= { tdmaCsServProvEntry 1 }

tdmaCsTIwf2 OBJECT-TYPE
   SYNTAX     Unsigned32 (0..3600)
   ACCESS     read-write
   STATUS     mandatory
   DESCRIPTION
     "This is an internal timer to the call server of the IWF and is used 
      during call clearing for ensuring the MIT protocol stack and NIT 
      modem for a call have been deallocated correctly."
   DEFVAL     { 4 }
::= { tdmaCsServProvEntry 2 }

tdmaCsT303 OBJECT-TYPE
   SYNTAX     Unsigned32 (0..3600)
   ACCESS     read-write
   STATUS     mandatory
   DESCRIPTION
     "This timer is a call setup timer and is used for ensuring a 
      CallProceeding message is received for a Setup message that has 
      been sent by the IWF to the MTX."
   DEFVAL     { 4 }
::= { tdmaCsServProvEntry 3 }

tdmaCsT305 OBJECT-TYPE
   SYNTAX     Unsigned32 (0..3600)
   ACCESS     read-write
   STATUS     mandatory
   DESCRIPTION
     "This timer is a call clearing timer and is used for ensuring a Release 
      message is received for a Disconnect message the IWF has sent to 
      the MTX."
   DEFVAL     { 30 }
::= { tdmaCsServProvEntry 4 }

tdmaCsT308 OBJECT-TYPE
   SYNTAX     Unsigned32 (0..3600)
   ACCESS     read-write
   STATUS     mandatory
   DESCRIPTION
     "This timer is a call clearing timer and is used for ensuring a 
      ReleaseComplete message is received for the Release message the 
      IWF has sent to the MTX."
   DEFVAL     { 4 }
::= { tdmaCsServProvEntry 5 }

tdmaCsT313 OBJECT-TYPE
   SYNTAX     Unsigned32 (0..3600)
   ACCESS     read-write
   STATUS     mandatory
   DESCRIPTION
     "This is a call setup timer and is used for ensuring a ConnectAck 
      message is received in response for the Connect message the IWF 
      has sent to the MTX."
   DEFVAL     { 4 }
::= { tdmaCsServProvEntry 6 }

tdmaCsT999 OBJECT-TYPE
   SYNTAX     Unsigned32 (0..3600)
   ACCESS     read-write
   STATUS     mandatory
   DESCRIPTION
     "This timer is used during a mobile termination call setup and is used 
      for ensuring the Setup message is received from the MTX."
   DEFVAL     { 300 }
::= { tdmaCsServProvEntry 7 }

tdmaCsSupportedTechnology OBJECT-TYPE
   SYNTAX     INTEGER  {
                 tdmaOnly(0),
                 cdmaOnly(1),
                 tdmaAndCdma(2) }
   ACCESS     read-write
   STATUS     mandatory
   DESCRIPTION
     "This attribute specifies the wireless technology that is supported for 
      data calls on this IWF."
   DEFVAL     { tdmaOnly }
::= { tdmaCsServProvEntry 8 }

tdmaCsSupportedService OBJECT-TYPE
   SYNTAX     INTEGER  {
                 asyncDataOnly(0),
                 g3FaxOnly(1),
                 analogFaxOnly(2),
                 packetOnly(3),
                 asyncDataAndG3Fax(4),
                 asyncDataAndAnalogFax(5),
                 asyncDataAndPacket(6),
                 asyncDataG3FaxAndPacket(7),
                 asyncDataAFaxAndPacket(8) }
   ACCESS     read-write
   STATUS     mandatory
   DESCRIPTION
     "This attribute specifies the type(s) of data calls this IWF supports."
   DEFVAL     { asyncDataOnly }
::= { tdmaCsServProvEntry 9 }

tdmaCsMiscProvTable OBJECT-TYPE
   SYNTAX     SEQUENCE OF TdmaCsMiscProvEntry
   ACCESS     not-accessible
   STATUS     mandatory
   DESCRIPTION
     "This group contains general provisioning data for the 
      TdmaIwfCallServer that does not fit within other provisioning 
      groups."
::= { tdmaCs 101 }

tdmaCsMiscProvEntry OBJECT-TYPE
   SYNTAX     TdmaCsMiscProvEntry
   ACCESS     not-accessible
   STATUS     mandatory
   DESCRIPTION
     "An entry in the tdmaCsMiscProvTable."
   INDEX {
      tdmaCsCsIndex }
::= { tdmaCsMiscProvTable 1 }

TdmaCsMiscProvEntry ::= SEQUENCE {
   tdmaCsCommentText
      AsciiString,
   tdmaCsMscIpAddress
      IpAddress,
   tdmaCsVirtualRouterName
      RowPointer,
   tdmaCsVoiceLaw
      INTEGER }

tdmaCsCommentText OBJECT-TYPE
   SYNTAX     AsciiString (SIZE (0..40))
   ACCESS     read-write
   STATUS     mandatory
   DESCRIPTION
     "Use of this attribute is at the discretion of the system administrator. 
      Typically, this attribute is used to specify the name of the DMS-
      MTX configured for this TdmaIwfCallServer plus any other 
      commentary information."
   DEFVAL     { ''H }  -- ""
::= { tdmaCsMiscProvEntry 1 }

tdmaCsMscIpAddress OBJECT-TYPE
   SYNTAX     IpAddress 
   ACCESS     read-write
   STATUS     mandatory
   DESCRIPTION
     "This attribute specifies the Internet Protocol (IP) Address of the 
      Mobile Telephone Exchange (MTX) that is permitted to set up 
      MTX InterWorking Function (IWF) data calls using this 
      TdmaIwfCallServer. This address must be specified in order for this 
      TdmaIwfCallServer to provide service.
      If call setups are attempted from an MSC which does not have this 
      address, those calls are rejected. The callsRequested statistic of this 
      TdmaIwfCallServer is incremented and appropriate call failure logs 
      are generated at the MSC."
   DEFVAL     { '00000000'H }  -- "0.0.0.0"
::= { tdmaCsMiscProvEntry 2 }

tdmaCsVirtualRouterName OBJECT-TYPE
   SYNTAX     RowPointer 
   ACCESS     read-write
   STATUS     mandatory
   DESCRIPTION
     "This attribute specifies the virtual router that this 
      TdmaIwfCallServer uses for transmitting and receiving signaling 
      messages to and from the DMS-MTX."
::= { tdmaCsMiscProvEntry 3 }

tdmaCsVoiceLaw OBJECT-TYPE
   SYNTAX     INTEGER  {
                 aLaw(0),
                 muLaw(1) }
   ACCESS     read-write
   STATUS     mandatory
   DESCRIPTION
     "This attribute specifies the voice law to be established for the IWF 
      to PSTN modem link for calls established by this 
      TdmaIwfCallServer. This attribute has one of the following values:
      aLaw: A protocol for encoding voice-band audio, Pulse Code 
      Modulation (PCM).
      muLaw: A protocol for encoding voice-band audio, PCM. 
      Note that this value must match the voice law used at the DMS-
      MTX connected to this TdmaIwfCallServer."
::= { tdmaCsMiscProvEntry 4 }

tdmaCsCidDataTable OBJECT-TYPE
   SYNTAX     SEQUENCE OF TdmaCsCidDataEntry
   ACCESS     not-accessible
   STATUS     mandatory
   DESCRIPTION
     "This group contains the attribute for a component's Customer 
      Identifier (CID). Refer to the attribute description for a detailed 
      explanation of CIDs."
::= { tdmaCs 103 }

tdmaCsCidDataEntry OBJECT-TYPE
   SYNTAX     TdmaCsCidDataEntry
   ACCESS     not-accessible
   STATUS     mandatory
   DESCRIPTION
     "An entry in the tdmaCsCidDataTable."
   INDEX {
      tdmaCsCsIndex }
::= { tdmaCsCidDataTable 1 }

TdmaCsCidDataEntry ::= SEQUENCE {
   tdmaCsCustomerIdentifier
      Unsigned32 }

tdmaCsCustomerIdentifier OBJECT-TYPE
   SYNTAX     Unsigned32 (0 | 1..8191)
   ACCESS     read-write
   STATUS     mandatory
   DESCRIPTION
     "This attribute holds the Customer Identifier (CID).
      
      Every component has a CID. If a component has a cid attribute, the 
      component's CID is the provisioned value of that attribute; 
      otherwise the component inherits the CID of its parent. The top-
      level component has a CID of 0.
      
      Every operator session also has a CID, which is the CID 
      provisioned for the operator's user ID. An operator will see only the 
      stream data for components having a matching CID. Also, the 
      operator will be allowed to issue commands for only those 
      components which have a matching CID.
      
      An operator CID of 0 is used to identify the Network Manager 
      (referred to as 'NetMan' in DPN). This CID matches the CID of 
      any component. Values 1 to 8191 inclusive (equivalent to 'basic 
      CIDs' in DPN) may be assigned to specific customers."
   DEFVAL     { 0 }
::= { tdmaCsCidDataEntry 1 }

tdmaCsStateTable OBJECT-TYPE
   SYNTAX     SEQUENCE OF TdmaCsStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { tdmaCs 104 }

tdmaCsStateEntry OBJECT-TYPE
   SYNTAX     TdmaCsStateEntry
   ACCESS     not-accessible
   STATUS     mandatory
   DESCRIPTION
     "An entry in the tdmaCsStateTable."
   INDEX {
      tdmaCsCsIndex }
::= { tdmaCsStateTable 1 }

TdmaCsStateEntry ::= SEQUENCE {
   tdmaCsAdminState
      INTEGER,
   tdmaCsOperationalState
      INTEGER,
   tdmaCsUsageState
      INTEGER }

tdmaCsAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { tdmaCsStateEntry 1 }

tdmaCsOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { tdmaCsStateEntry 2 }

tdmaCsUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { tdmaCsStateEntry 3 }

tdmaCsStatsTable OBJECT-TYPE
   SYNTAX     SEQUENCE OF TdmaCsStatsEntry
   ACCESS     not-accessible
   STATUS     mandatory
   DESCRIPTION
     "This group contains operational attributes that measure the 
      performance used for the calls set up by this particular 
      TdmaIwfCallServer."
::= { tdmaCs 121 }

tdmaCsStatsEntry OBJECT-TYPE
   SYNTAX     TdmaCsStatsEntry
   ACCESS     not-accessible
   STATUS     mandatory
   DESCRIPTION
     "An entry in the tdmaCsStatsTable."
   INDEX {
      tdmaCsCsIndex }
::= { tdmaCsStatsTable 1 }

TdmaCsStatsEntry ::= SEQUENCE {
   tdmaCsCurrentCalls
      Gauge32,
   tdmaCsCallsRequested
      Counter32,
   tdmaCsCallsSetUp
      Counter32,
   tdmaCsCallsReleasedNormal
      Counter32,
   tdmaCsCallsReleasedAbnormal
      Counter32,
   tdmaCsErroredLFrames
      Counter32 }

tdmaCsCurrentCalls OBJECT-TYPE
   SYNTAX     Gauge32 (0..2047)
   ACCESS     read-only
   STATUS     mandatory
   DESCRIPTION
     "This attribute indicates the number of active calls currently serviced 
      by this particular TdmaIwfCallServer."
   DEFVAL     { 0 }
::= { tdmaCsStatsEntry 1 }

tdmaCsCallsRequested OBJECT-TYPE
   SYNTAX     Counter32 
   ACCESS     read-only
   STATUS     mandatory
   DESCRIPTION
     "This attribute counts the number of IWF call setup requests received 
      at this particular TdmaIwfCallServer from the DMS-MTX. The 
      counter wraps when it exceeds the maximum value."
::= { tdmaCsStatsEntry 2 }

tdmaCsCallsSetUp OBJECT-TYPE
   SYNTAX     Counter32 
   ACCESS     read-only
   STATUS     mandatory
   DESCRIPTION
     "This attribute counts the number of IWF calls successfully setup by 
      this particular TdmaIwfCallServer. A call is considered setup when 
      the IWF-Setup-Request message is received, indicating a request 
      for a data communications service, and the IWF has successfully 
      allocated the necessary resources to fulfill the request. The counter 
      wraps when it exceeds the maximum value."
::= { tdmaCsStatsEntry 3 }

tdmaCsCallsReleasedNormal OBJECT-TYPE
   SYNTAX     Counter32 
   ACCESS     read-only
   STATUS     mandatory
   DESCRIPTION
     "This attribute counts the number of IWF calls that have completed 
      successfully on this particular TdmaIwfCallServer. The counter 
      wraps when it exceeds the maximum value."
::= { tdmaCsStatsEntry 4 }

tdmaCsCallsReleasedAbnormal OBJECT-TYPE
   SYNTAX     Counter32 
   ACCESS     read-only
   STATUS     mandatory
   DESCRIPTION
     "This attribute counts the number of IWF calls that have been 
      released due to error conditions at this particular 
      TdmaIwfCallServer or one if its TdmaIwfBearerChannel(s). The 
      counter wraps when it exceeds the maximum value."
::= { tdmaCsStatsEntry 5 }

tdmaCsErroredLFrames OBJECT-TYPE
   SYNTAX     Counter32 
   ACCESS     read-only
   STATUS     mandatory
   DESCRIPTION
     "This attribute counts the number of CM/IWF Control Interface 
      (CCI) messages received from the DMS-MTX that have an 
      incorrect format. The counter wraps when it exceeds the maximum 
      value."
::= { tdmaCsStatsEntry 6 }


-- TdmaCs/<csIndex> Modem/<modem-type> 
-- This component represents an instance of a particular modem type 
-- that enables support of the various modem protocols on the DMS-
-- MTX IWF.

tdmaCsModem OBJECT IDENTIFIER ::= { tdmaCs 2 }



tdmaCsModemRowStatusTable OBJECT-TYPE
   SYNTAX     SEQUENCE OF TdmaCsModemRowStatusEntry
   ACCESS     not-accessible
   STATUS     mandatory
   DESCRIPTION
     "This entry controls the addition and deletion of 
      tdmaCsModem components."
::= { tdmaCsModem 1 }

tdmaCsModemRowStatusEntry OBJECT-TYPE
   SYNTAX     TdmaCsModemRowStatusEntry
   ACCESS     not-accessible
   STATUS     mandatory
   DESCRIPTION
     "A single entry in the table represents a single 
      tdmaCsModem component."
   INDEX {
      tdmaCsCsIndex,
      tdmaCsModemIndex }
::= { tdmaCsModemRowStatusTable 1 }

TdmaCsModemRowStatusEntry ::= SEQUENCE {
   tdmaCsModemRowStatus
      RowStatus,
   tdmaCsModemComponentName
      DisplayString,
   tdmaCsModemStorageType
      StorageType,
   tdmaCsModemIndex
      NonReplicated }

tdmaCsModemRowStatus OBJECT-TYPE
   SYNTAX     RowStatus 
   ACCESS     read-only
   STATUS     mandatory
   DESCRIPTION
     "This variable is used as the basis for SNMP naming of
      tdmaCsModem components.
      These components cannot be added nor deleted."
::= { tdmaCsModemRowStatusEntry 1 }

tdmaCsModemComponentName OBJECT-TYPE
   SYNTAX     DisplayString 
   ACCESS     read-only
   STATUS     mandatory
   DESCRIPTION
     "This variable provides the component's string name for
      use with the ASCII Console Interface"
::= { tdmaCsModemRowStatusEntry 2 }

tdmaCsModemStorageType OBJECT-TYPE
   SYNTAX     StorageType 
   ACCESS     read-only
   STATUS     mandatory
   DESCRIPTION
     "This variable represents the storage type value for the
      tdmaCsModem tables."
::= { tdmaCsModemRowStatusEntry 4 }

tdmaCsModemIndex OBJECT-TYPE
   SYNTAX     NonReplicated 
   ACCESS     not-accessible
   STATUS     mandatory
   DESCRIPTION
     "This variable represents the index for the tdmaCsModem tables."
::= { tdmaCsModemRowStatusEntry 10 }


-- TdmaCs/<csIndex> Fax
-- This component represents an instance of fax attributes. These 
-- specify various default settings for aspects of the fax protocol, 
-- which may be used for a DMS-MTX IWF call.

tdmaCsFax OBJECT IDENTIFIER ::= { tdmaCs 3 }



tdmaCsFaxRowStatusTable OBJECT-TYPE
   SYNTAX     SEQUENCE OF TdmaCsFaxRowStatusEntry
   ACCESS     not-accessible
   STATUS     mandatory
   DESCRIPTION
     "This entry controls the addition and deletion of 
      tdmaCsFax components."
::= { tdmaCsFax 1 }

tdmaCsFaxRowStatusEntry OBJECT-TYPE
   SYNTAX     TdmaCsFaxRowStatusEntry
   ACCESS     not-accessible
   STATUS     mandatory
   DESCRIPTION
     "A single entry in the table represents a single 
      tdmaCsFax component."
   INDEX {
      tdmaCsCsIndex,
      tdmaCsFaxIndex }
::= { tdmaCsFaxRowStatusTable 1 }

TdmaCsFaxRowStatusEntry ::= SEQUENCE {
   tdmaCsFaxRowStatus
      RowStatus,
   tdmaCsFaxComponentName
      DisplayString,
   tdmaCsFaxStorageType
      StorageType,
   tdmaCsFaxIndex
      NonReplicated }

tdmaCsFaxRowStatus OBJECT-TYPE
   SYNTAX     RowStatus 
   ACCESS     read-only
   STATUS     mandatory
   DESCRIPTION
     "This variable is used as the basis for SNMP naming of
      tdmaCsFax components.
      These components cannot be added nor deleted."
::= { tdmaCsFaxRowStatusEntry 1 }

tdmaCsFaxComponentName OBJECT-TYPE
   SYNTAX     DisplayString 
   ACCESS     read-only
   STATUS     mandatory
   DESCRIPTION
     "This variable provides the component's string name for
      use with the ASCII Console Interface"
::= { tdmaCsFaxRowStatusEntry 2 }

tdmaCsFaxStorageType OBJECT-TYPE
   SYNTAX     StorageType 
   ACCESS     read-only
   STATUS     mandatory
   DESCRIPTION
     "This variable represents the storage type value for the
      tdmaCsFax tables."
::= { tdmaCsFaxRowStatusEntry 4 }

tdmaCsFaxIndex OBJECT-TYPE
   SYNTAX     NonReplicated 
   ACCESS     not-accessible
   STATUS     mandatory
   DESCRIPTION
     "This variable represents the index for the tdmaCsFax tables."
::= { tdmaCsFaxRowStatusEntry 10 }


-- TdmaCs/<csIndex> Dce
-- This component represents an instance of the Data Circuit-
-- Terminating Equipment (DCE). The DCE represents a layer of the 
-- protocol stack for the network-side connection to the Public 
-- Switched Telephone Network. It is responsible for call control, AT-
-- command handling, user-data transport, online-command signaling, 
-- break signaling, circuit/signal lead transport, and compression 
-- negotiation. The DCE is based on the BMI (BSC, MSC, IWF) 
-- portion of the IS-135 standard.

tdmaCsDce OBJECT IDENTIFIER ::= { tdmaCs 4 }



tdmaCsDceRowStatusTable OBJECT-TYPE
   SYNTAX     SEQUENCE OF TdmaCsDceRowStatusEntry
   ACCESS     not-accessible
   STATUS     mandatory
   DESCRIPTION
     "This entry controls the addition and deletion of 
      tdmaCsDce components."
::= { tdmaCsDce 1 }

tdmaCsDceRowStatusEntry OBJECT-TYPE
   SYNTAX     TdmaCsDceRowStatusEntry
   ACCESS     not-accessible
   STATUS     mandatory
   DESCRIPTION
     "A single entry in the table represents a single 
      tdmaCsDce component."
   INDEX {
      tdmaCsCsIndex,
      tdmaCsDceIndex }
::= { tdmaCsDceRowStatusTable 1 }

TdmaCsDceRowStatusEntry ::= SEQUENCE {
   tdmaCsDceRowStatus
      RowStatus,
   tdmaCsDceComponentName
      DisplayString,
   tdmaCsDceStorageType
      StorageType,
   tdmaCsDceIndex
      NonReplicated }

tdmaCsDceRowStatus OBJECT-TYPE
   SYNTAX     RowStatus 
   ACCESS     read-only
   STATUS     mandatory
   DESCRIPTION
     "This variable is used as the basis for SNMP naming of
      tdmaCsDce components.
      These components cannot be added nor deleted."
::= { tdmaCsDceRowStatusEntry 1 }

tdmaCsDceComponentName OBJECT-TYPE
   SYNTAX     DisplayString 
   ACCESS     read-only
   STATUS     mandatory
   DESCRIPTION
     "This variable provides the component's string name for
      use with the ASCII Console Interface"
::= { tdmaCsDceRowStatusEntry 2 }

tdmaCsDceStorageType OBJECT-TYPE
   SYNTAX     StorageType 
   ACCESS     read-only
   STATUS     mandatory
   DESCRIPTION
     "This variable represents the storage type value for the
      tdmaCsDce tables."
::= { tdmaCsDceRowStatusEntry 4 }

tdmaCsDceIndex OBJECT-TYPE
   SYNTAX     NonReplicated 
   ACCESS     not-accessible
   STATUS     mandatory
   DESCRIPTION
     "This variable represents the index for the tdmaCsDce tables."
::= { tdmaCsDceRowStatusEntry 10 }


-- TdmaCs/<csIndex> Dsc
-- This component represents an instance of the Data Service Control 
-- (DSC). The DSC represents a layer of the protocol stack for the 
-- mobile-side connection to the IWF. It is responsible for call control, 
-- AT-command handling, user-data transport, online-command 
-- signaling, break signaling, circuit/signal lead transport, and 
-- compression negotiation. The DSC is based on the BMI (BSC, 
-- MSC, IWF) portion of the IS-135 standard.

tdmaCsDsc OBJECT IDENTIFIER ::= { tdmaCs 5 }



tdmaCsDscRowStatusTable OBJECT-TYPE
   SYNTAX     SEQUENCE OF TdmaCsDscRowStatusEntry
   ACCESS     not-accessible
   STATUS     mandatory
   DESCRIPTION
     "This entry controls the addition and deletion of 
      tdmaCsDsc components."
::= { tdmaCsDsc 1 }

tdmaCsDscRowStatusEntry OBJECT-TYPE
   SYNTAX     TdmaCsDscRowStatusEntry
   ACCESS     not-accessible
   STATUS     mandatory
   DESCRIPTION
     "A single entry in the table represents a single 
      tdmaCsDsc component."
   INDEX {
      tdmaCsCsIndex,
      tdmaCsDscIndex }
::= { tdmaCsDscRowStatusTable 1 }

TdmaCsDscRowStatusEntry ::= SEQUENCE {
   tdmaCsDscRowStatus
      RowStatus,
   tdmaCsDscComponentName
      DisplayString,
   tdmaCsDscStorageType
      StorageType,
   tdmaCsDscIndex
      NonReplicated }

tdmaCsDscRowStatus OBJECT-TYPE
   SYNTAX     RowStatus 
   ACCESS     read-only
   STATUS     mandatory
   DESCRIPTION
     "This variable is used as the basis for SNMP naming of
      tdmaCsDsc components.
      These components cannot be added nor deleted."
::= { tdmaCsDscRowStatusEntry 1 }

tdmaCsDscComponentName OBJECT-TYPE
   SYNTAX     DisplayString 
   ACCESS     read-only
   STATUS     mandatory
   DESCRIPTION
     "This variable provides the component's string name for
      use with the ASCII Console Interface"
::= { tdmaCsDscRowStatusEntry 2 }

tdmaCsDscStorageType OBJECT-TYPE
   SYNTAX     StorageType 
   ACCESS     read-only
   STATUS     mandatory
   DESCRIPTION
     "This variable represents the storage type value for the
      tdmaCsDsc tables."
::= { tdmaCsDscRowStatusEntry 4 }

tdmaCsDscIndex OBJECT-TYPE
   SYNTAX     NonReplicated 
   ACCESS     not-accessible
   STATUS     mandatory
   DESCRIPTION
     "This variable represents the index for the tdmaCsDsc tables."
::= { tdmaCsDscRowStatusEntry 10 }

tdmaCsDscProvTable OBJECT-TYPE
   SYNTAX     SEQUENCE OF TdmaCsDscProvEntry
   ACCESS     not-accessible
   STATUS     mandatory
   DESCRIPTION
     "This group contains the provisionable attributes for Data Service 
      Control Asynchronous Data Service portion of the wireless protocol 
      stack used for the calls set up by this particular TdmaIwfCallServer."
::= { tdmaCsDsc 10 }

tdmaCsDscProvEntry OBJECT-TYPE
   SYNTAX     TdmaCsDscProvEntry
   ACCESS     not-accessible
   STATUS     mandatory
   DESCRIPTION
     "An entry in the tdmaCsDscProvTable."
   INDEX {
      tdmaCsCsIndex,
      tdmaCsDscIndex }
::= { tdmaCsDscProvTable 1 }

TdmaCsDscProvEntry ::= SEQUENCE {
   tdmaCsDscLl0BufferSize
      Unsigned32,
   tdmaCsDscLl1BufferSize
      Unsigned32,
   tdmaCsDscK0Ll0WindowSize
      Unsigned32,
   tdmaCsDscK1Ll1WindowSize
      Unsigned32,
   tdmaCsDscP0CompressionDirection
      INTEGER,
   tdmaCsDscP1CompressionMaximumCodewords
      Unsigned32,
   tdmaCsDscP2CompressionMaximumCharacters
      Unsigned32 }

tdmaCsDscLl0BufferSize OBJECT-TYPE
   SYNTAX     Unsigned32 (80..65535)
   ACCESS     read-write
   STATUS     obsolete
   DESCRIPTION
     "This attribute specifies the maximum size of the DSC logical link 0 
      control buffer. Changes impact the amount of memory used (more 
      memory is used when increasing the attribute). The gain in 
      performance obtained from the selection of a larger buffer size may 
      be offset by less memory being available. The customer might wish 
      to increase the buffer size when a degradation in throughput of the 
      system is seen."
   DEFVAL     { 80 }
::= { tdmaCsDscProvEntry 1 }

tdmaCsDscLl1BufferSize OBJECT-TYPE
   SYNTAX     Unsigned32 (160..65535)
   ACCESS     read-write
   STATUS     obsolete
   DESCRIPTION
     "This attribute specifies the maximum size of the DSC logical link 1 
      data buffer. Changes impact the amount of memory used (more 
      memory is used when increasing the attribute). The gain in 
      performance obtained from the selection of a larger buffer size may 
      be offset by less memory being available. The customer might wish 
      to increase the buffer size when a degradation in throughput of the 
      system is seen."
   DEFVAL     { 160 }
::= { tdmaCsDscProvEntry 2 }

tdmaCsDscK0Ll0WindowSize OBJECT-TYPE
   SYNTAX     Unsigned32 (1..64)
   ACCESS     read-write
   STATUS     mandatory
   DESCRIPTION
     "This attribute specifies the maximum size of the DSC logical link 0 
      window."
   DEFVAL     { 64 }
::= { tdmaCsDscProvEntry 3 }

tdmaCsDscK1Ll1WindowSize OBJECT-TYPE
   SYNTAX     Unsigned32 (1..64)
   ACCESS     read-write
   STATUS     mandatory
   DESCRIPTION
     "This attribute specifies the maximum size of the DSC logical link 1 
      window."
   DEFVAL     { 64 }
::= { tdmaCsDscProvEntry 4 }

tdmaCsDscP0CompressionDirection OBJECT-TYPE
   SYNTAX     INTEGER  {
                 noCompression(0),
                 compInitrResp(1),
                 compRespInitr(2),
                 compBoth(3) }
   ACCESS     read-write
   STATUS     obsolete
   DESCRIPTION
     "This attribute specifies the compression configuration for DSC. This 
      attribute has one of the following values:
      noCompression: No compression.
      compInitrResp: Compression initiator to responder.
      compRespInitr: Compression responder to initiator.
      compBoth: Compression both directions."
   DEFVAL     { noCompression }
::= { tdmaCsDscProvEntry 5 }

tdmaCsDscP1CompressionMaximumCodewords OBJECT-TYPE
   SYNTAX     Unsigned32 (512..4096)
   ACCESS     read-write
   STATUS     obsolete
   DESCRIPTION
     "This attribute specifies the maximum number of codewords to be 
      used for compression. A codeword is a binary number that 
      represents a string of characters. Changes to this attribute impact the 
      amount of memory used (more memory is used when increasing the 
      attribute). The gain in performance obtained from the selection of a 
      larger dictionary may be offset by the larger codeword size needed, 
      and for certain types of data, better performance may be obtained 
      by using a smaller dictionary.
      Changes to this attribute do not affect existing calls."
   DEFVAL     { 512 }
::= { tdmaCsDscProvEntry 6 }

tdmaCsDscP2CompressionMaximumCharacters OBJECT-TYPE
   SYNTAX     Unsigned32 (6..150)
   ACCESS     read-write
   STATUS     obsolete
   DESCRIPTION
     "This attribute specifies the maximum number of characters that can 
      be represented by a single codeword to be used for compression 
      from logical link 0."
   DEFVAL     { 6 }
::= { tdmaCsDscProvEntry 7 }


-- TdmaCs/<csIndex> Rlp1/<radio-channel-type>
-- This component represents an instance of Radio Link Protocol 1 
-- (RLP1), indexed by radio channel type. Valid radio channel types 
-- are:
-- 
-- halfRate, Half rate channel. 
-- fullRate, Full rate channel.
-- doubleRate, Double rate channel.
-- tripleRate, Triple rate channel.
-- 
-- Many RLP1 attributes are dependent on the frame rate and frame 
-- size, that is dictated by the radio channel type. When a 
-- TdmaIwfCallServer is added, a RadioLinkProtocol1 instance is 
-- added automatically for each possible instance value. The attributes 
-- are set to default values, dependent on the radio channel type of the 
-- component instance.

tdmaCsRlp1 OBJECT IDENTIFIER ::= { tdmaCs 6 }



tdmaCsRlp1RowStatusTable OBJECT-TYPE
   SYNTAX     SEQUENCE OF TdmaCsRlp1RowStatusEntry
   ACCESS     not-accessible
   STATUS     mandatory
   DESCRIPTION
     "This entry controls the addition and deletion of 
      tdmaCsRlp1 components."
::= { tdmaCsRlp1 1 }

tdmaCsRlp1RowStatusEntry OBJECT-TYPE
   SYNTAX     TdmaCsRlp1RowStatusEntry
   ACCESS     not-accessible
   STATUS     mandatory
   DESCRIPTION
     "A single entry in the table represents a single 
      tdmaCsRlp1 component."
   INDEX {
      tdmaCsCsIndex,
      tdmaCsRlp1Index }
::= { tdmaCsRlp1RowStatusTable 1 }

TdmaCsRlp1RowStatusEntry ::= SEQUENCE {
   tdmaCsRlp1RowStatus
      RowStatus,
   tdmaCsRlp1ComponentName
      DisplayString,
   tdmaCsRlp1StorageType
      StorageType,
   tdmaCsRlp1Index
      INTEGER }

tdmaCsRlp1RowStatus OBJECT-TYPE
   SYNTAX     RowStatus 
   ACCESS     read-write
   STATUS     mandatory
   DESCRIPTION
     "This variable is used as the basis for SNMP naming of
      tdmaCsRlp1 components.
      These components can be added."
::= { tdmaCsRlp1RowStatusEntry 1 }

tdmaCsRlp1ComponentName OBJECT-TYPE
   SYNTAX     DisplayString 
   ACCESS     read-only
   STATUS     mandatory
   DESCRIPTION
     "This variable provides the component's string name for
      use with the ASCII Console Interface"
::= { tdmaCsRlp1RowStatusEntry 2 }

tdmaCsRlp1StorageType OBJECT-TYPE
   SYNTAX     StorageType 
   ACCESS     read-only
   STATUS     mandatory
   DESCRIPTION
     "This variable represents the storage type value for the
      tdmaCsRlp1 tables."
::= { tdmaCsRlp1RowStatusEntry 4 }

tdmaCsRlp1Index OBJECT-TYPE
   SYNTAX     INTEGER  {
                 halfRate(0),
                 fullRate(1),
                 doubleRate(2),
                 tripleRate(3) }
   ACCESS     not-accessible
   STATUS     mandatory
   DESCRIPTION
     "This variable represents the index for the tdmaCsRlp1 tables."
::= { tdmaCsRlp1RowStatusEntry 10 }

tdmaCsRlp1ProvTable OBJECT-TYPE
   SYNTAX     SEQUENCE OF TdmaCsRlp1ProvEntry
   ACCESS     not-accessible
   STATUS     mandatory
   DESCRIPTION
     "This group contains provisionable attributes for the Radio Link 
      Protocol 1 (RLP1) parameters used for the calls set up by this 
      particular TdmaIwfCallServer. Changes to these attributes do not 
      affect existing calls."
::= { tdmaCsRlp1 10 }

tdmaCsRlp1ProvEntry OBJECT-TYPE
   SYNTAX     TdmaCsRlp1ProvEntry
   ACCESS     not-accessible
   STATUS     mandatory
   DESCRIPTION
     "An entry in the tdmaCsRlp1ProvTable."
   INDEX {
      tdmaCsCsIndex,
      tdmaCsRlp1Index }
::= { tdmaCsRlp1ProvTable 1 }

TdmaCsRlp1ProvEntry ::= SEQUENCE {
   tdmaCsRlp1T1ResponseTimer
      Unsigned32,
   tdmaCsRlp1T2LinkActivityTimer
      Unsigned32,
   tdmaCsRlp1T3PeerAckTimer
      Unsigned32 }

tdmaCsRlp1T1ResponseTimer OBJECT-TYPE
   SYNTAX     Unsigned32 (5..20)
   ACCESS     read-write
   STATUS     mandatory
   DESCRIPTION
     "This attribute specifies the time the receiving Radio Link Protocol 
      (RLP1) entity shall wait for a response from the peer TIA-136-310 
      (formerly IS-130) application.
      During the Exchange Information (XID) negotiation, both RLP1 
      entities (mobile station and IWF) can agree to use a specific value 
      for this timer (T1). The IWF attempts to negotiate to the value 
      specified by this attribute.
      Changes to this attribute do not affect existing calls."
   DEFVAL     { 5 }
::= { tdmaCsRlp1ProvEntry 1 }

tdmaCsRlp1T2LinkActivityTimer OBJECT-TYPE
   SYNTAX     Unsigned32 (10..120)
   ACCESS     read-write
   STATUS     mandatory
   DESCRIPTION
     "This attribute specifies the maximum time the receiving Radio Link 
      Protocol (RLP1) entity shall wait for link activity.
      During the Exchange Information (XID) negotiation, both RLP1 
      entities (mobile station and IWF) can agree to use a specific value 
      for this timer (T2). The IWF attempts to negotiate to the value 
      specified by this attribute.
      Changes to this attribute do not affect existing calls."
   DEFVAL     { 10 }
::= { tdmaCsRlp1ProvEntry 2 }

tdmaCsRlp1T3PeerAckTimer OBJECT-TYPE
   SYNTAX     Unsigned32 (5..20)
   ACCESS     read-write
   STATUS     mandatory
   DESCRIPTION
     "This attribute specifies the maximum time the receiving Radio Link 
      Protocol (RLP1) entity shall wait for the peer to ACK or NAK data.
      During the Exchange Information (XID) negotiation, both RLP1 
      entities (mobile station and IWF) can agree to use a specific value 
      for this timer (T3). The IWF attempts to negotiate to the value 
      specified by this attribute.
      Changes to this attribute do not affect existing calls."
   DEFVAL     { 5 }
::= { tdmaCsRlp1ProvEntry 3 }


-- TdmaCs/<csIndex> V42
-- This component represents an instance of ITU-T V.42 error 
-- correcting data link protocol. Its attributes specify various default 
-- settings for aspects of the V.42 protocol, that may be used for an 
-- IWF call for the IWF to PSTN modem link.

tdmaCsV42 OBJECT IDENTIFIER ::= { tdmaCs 7 }



tdmaCsV42RowStatusTable OBJECT-TYPE
   SYNTAX     SEQUENCE OF TdmaCsV42RowStatusEntry
   ACCESS     not-accessible
   STATUS     mandatory
   DESCRIPTION
     "This entry controls the addition and deletion of 
      tdmaCsV42 components."
::= { tdmaCsV42 1 }

tdmaCsV42RowStatusEntry OBJECT-TYPE
   SYNTAX     TdmaCsV42RowStatusEntry
   ACCESS     not-accessible
   STATUS     mandatory
   DESCRIPTION
     "A single entry in the table represents a single 
      tdmaCsV42 component."
   INDEX {
      tdmaCsCsIndex,
      tdmaCsV42Index }
::= { tdmaCsV42RowStatusTable 1 }

TdmaCsV42RowStatusEntry ::= SEQUENCE {
   tdmaCsV42RowStatus
      RowStatus,
   tdmaCsV42ComponentName
      DisplayString,
   tdmaCsV42StorageType
      StorageType,
   tdmaCsV42Index
      NonReplicated }

tdmaCsV42RowStatus OBJECT-TYPE
   SYNTAX     RowStatus 
   ACCESS     read-only
   STATUS     mandatory
   DESCRIPTION
     "This variable is used as the basis for SNMP naming of
      tdmaCsV42 components.
      These components cannot be added nor deleted."
::= { tdmaCsV42RowStatusEntry 1 }

tdmaCsV42ComponentName OBJECT-TYPE
   SYNTAX     DisplayString 
   ACCESS     read-only
   STATUS     mandatory
   DESCRIPTION
     "This variable provides the component's string name for
      use with the ASCII Console Interface"
::= { tdmaCsV42RowStatusEntry 2 }

tdmaCsV42StorageType OBJECT-TYPE
   SYNTAX     StorageType 
   ACCESS     read-only
   STATUS     mandatory
   DESCRIPTION
     "This variable represents the storage type value for the
      tdmaCsV42 tables."
::= { tdmaCsV42RowStatusEntry 4 }

tdmaCsV42Index OBJECT-TYPE
   SYNTAX     NonReplicated 
   ACCESS     not-accessible
   STATUS     mandatory
   DESCRIPTION
     "This variable represents the index for the tdmaCsV42 tables."
::= { tdmaCsV42RowStatusEntry 10 }

tdmaCsV42ProvTable OBJECT-TYPE
   SYNTAX     SEQUENCE OF TdmaCsV42ProvEntry
   ACCESS     not-accessible
   STATUS     mandatory
   DESCRIPTION
     "This group contains the provisionable attributes for the V.42 
      protocol used for the calls set up by this particular IwfCallServer. 
      Changes to these attributes do not affect existing calls."
::= { tdmaCsV42 10 }

tdmaCsV42ProvEntry OBJECT-TYPE
   SYNTAX     TdmaCsV42ProvEntry
   ACCESS     not-accessible
   STATUS     mandatory
   DESCRIPTION
     "An entry in the tdmaCsV42ProvTable."
   INDEX {
      tdmaCsCsIndex,
      tdmaCsV42Index }
::= { tdmaCsV42ProvTable 1 }

TdmaCsV42ProvEntry ::= SEQUENCE {
   tdmaCsV42T400DetectTimer
      FixedPoint2,
   tdmaCsV42T401AckTimer
      FixedPoint2,
   tdmaCsV42T402AckDelayTimer
      FixedPoint2,
   tdmaCsV42T403IdleProbeTimer
      Unsigned32,
   tdmaCsV42TxN401FrameSize
      Unsigned32,
   tdmaCsV42RxN401FrameSize
      Unsigned32,
   tdmaCsV42TxKWindowSize
      Unsigned32,
   tdmaCsV42RxKWindowSize
      Unsigned32,
   tdmaCsV42N400RetransLimit
      Unsigned32,
   tdmaCsV42FcsLength
      INTEGER }

tdmaCsV42T400DetectTimer OBJECT-TYPE
   SYNTAX     FixedPoint2 (75..254)
   ACCESS     read-write
   STATUS     mandatory
   DESCRIPTION
     "This attribute specifies the maximum amount of time that the IWF 
      waits for an Originator Detection Pattern (ODP) or Answerer 
      Detection Pattern (ADP). ODP/ADP is a series of special bit 
      patterns used during the call setup procedures.
      If the IWF is the originator of the call, it starts sending ODP 
      patterns and waits for an ADP for the duration of T400 from the 
      answerer at call setup time.
      If the IWF is the answerer of the call, it waits for an ODP for T400 
      seconds from the originator and if it receives during that time it 
      sends an ADP pattern to the originator at the call setup time. Since 
      both sides operate with different values of T400 timer, a higher 
      value increases the chance of a successful call setup.
      Changes to this attribute do not affect existing calls."
   DEFVAL     { 75 }
::= { tdmaCsV42ProvEntry 1 }

tdmaCsV42T401AckTimer OBJECT-TYPE
   SYNTAX     FixedPoint2 (50..900)
   ACCESS     read-write
   STATUS     mandatory
   DESCRIPTION
     "This attribute specifies the maximum amount of time that the IWF 
      waits for an acknowledgment before retransmitting a frame. Since 
      information about the T401 timer is not carried in the Exchange 
      Identification (XID) negotiations at call setup time, both sides 
      operate with different timer values. The value for T401 depends on 
      many factors, such as propagation delay or frame processing time. 
      A frame is retransmitted up to N400 times if the timer T401 expires 
      before an acknowledgment for a frame is actually received. The 
      performance of the data link layer can be impacted by the value of 
      this timer as retransmissions of frames occur on expiry of timer 
      T401. 
      Changes to this attribute do not affect existing calls."
   DEFVAL     { 400 }
::= { tdmaCsV42ProvEntry 2 }

tdmaCsV42T402AckDelayTimer OBJECT-TYPE
   SYNTAX     FixedPoint2 (25..450)
   ACCESS     read-write
   STATUS     mandatory
   DESCRIPTION
     "This attribute specifies the maximum amount of time that the IWF 
      may wait following the receipt of any frame requiring a reply before 
      it initiates transmission of an appropriate reply in order to ensure 
      that the reply frame is received by the remote error-correcting entity 
      prior to expiration of the T401 timer of the remote error-correcting 
      entity. Since information about the T402 timer is not carried in the 
      Exchange Identification (XID) negotiations at call setup, both sides 
      operate with different timer values. If this timer expires, then the 
      reply that would have been returned prior to its expiration is not 
      sent. The performance of the data link layer can be impacted by the 
      value of this timer as retransmissions of frames occur on expiry of 
      timer T401. For better performance, a value of t402AckDelayTimer 
      (T402) equal to half the value of t401AckTimer (T401) is 
      recommended.
      Changes to this attribute do not affect existing calls."
   DEFVAL     { 200 }
::= { tdmaCsV42ProvEntry 3 }

tdmaCsV42T403IdleProbeTimer OBJECT-TYPE
   SYNTAX     Unsigned32 (30..90)
   ACCESS     read-write
   STATUS     mandatory
   DESCRIPTION
     "This attribute specifies the maximum amount of time that the IWF 
      allows to elapse without frames being exchanged. The link is 
      permitted to remain idle with no frames being exchanged on the 
      data link. Upon expiry of this timer, the IWF polls its peer for 
      status. Since information about the T403 timer is not carried in the 
      Exchange Identification (XID) negotiations at call setup time, both 
      sides operate with different timer values. 
      Changes to this attribute do not affect existing calls."
   DEFVAL     { 60 }
::= { tdmaCsV42ProvEntry 4 }

tdmaCsV42TxN401FrameSize OBJECT-TYPE
   SYNTAX     Unsigned32 (1..255)
   ACCESS     read-write
   STATUS     mandatory
   DESCRIPTION
     "This attribute specifies the maximum number of octets that can be 
      carried in the information field of an Information (I) frame, 
      Exchange Identification (XID) frame, and a Unnumbered 
      Information (UI) frame from the IWF to the remote entity. The 
      default value is 128 octets, and no XID negotiations required for 
      txN401FrameSize. If the value for txN401FrameSize value is set to 
      other than 128 octets, then XID frames are exchanged to negotiate a 
      value. The value provided for txN401FrameSize sets up the bounds 
      during XID negotiations. The IWF performs XID negotiations with 
      this value as a minimum or maximum value. If a value greater than 
      128 is specified, then the IWF negotiates or attempts to negotiate a 
      value between the 128 (as a minimum) and the given value (as a 
      maximum). If a value less than 128 is specified, then the IWF 
      attempts to negotiate a value between the given value (as a 
      minimum) and 128 (as a maximum). Any value can be specified as 
      long as it is within the provisionable limits. However, a value equal 
      to or close to 128 is recommended.
      Changes to this attribute do not affect existing calls."
   DEFVAL     { 128 }
::= { tdmaCsV42ProvEntry 5 }

tdmaCsV42RxN401FrameSize OBJECT-TYPE
   SYNTAX     Unsigned32 (1..255)
   ACCESS     read-write
   STATUS     mandatory
   DESCRIPTION
     "This attribute specifies the maximum number of octets that can be 
      carried in the information field of an Information (I) frame, 
      Exchange Identification (XID) frame, and a Unnumbered 
      Information (UI) frame from the remote entity to the IWF. The 
      default value is 128 octets, and no XID negotiations are required for 
      rxN401FrameSize. If the value set for rxN401FrameSize is other 
      than 128, XID frames are exchanged to negotiate a value. The value 
      provided for rxN401FrameSize sets up the bounds during XID 
      negotiations. The IWF performs XID negotiations with this value as 
      a minimum or maximum value. If a value greater than 128 is 
      specified, then the IWF attempts to negotiate for a value between 
      128 (as a minimum) and the given value (as a maximum). If a value 
      less than 128 value is specified, then the IWF attempts to negotiate 
      for a value between the given value (as a minimum) and 128 (as a 
      maximum). Any value can be specified as long as it is within the 
      provisionable limits. However, a value equal to or close to the 
      default is recommended.
      Changes to this attribute do not affect existing calls."
   DEFVAL     { 128 }
::= { tdmaCsV42ProvEntry 6 }

tdmaCsV42TxKWindowSize OBJECT-TYPE
   SYNTAX     Unsigned32 (1..255)
   ACCESS     read-write
   STATUS     mandatory
   DESCRIPTION
     "This attribute specifies the maximum number of outstanding 
      unacknowledged sequenced Information (I) frames from the IWF to 
      the remote entity. The default value is 15 frames, and if this value is 
      used then no Exchange Identification (XID) negotiations are 
      required for txKWindowSize. If the value set for txKWindowSize is 
      other than 15, then XID frames are exchanged to negotiate a value. 
      The value provided for txKWindowSize sets up the bounds during 
      XID negotiations. The IWF performs XID negotiations with this 
      value as a minimum or maximum value. If a value greater than 15 is 
      specified, then the IWF attempts to negotiate a value between 15 (as 
      a minimum) and the given value (as a maximum). If a value less 
      than 15 is specified, then the IWF attempts to negotiate for a value 
      between the given value (as a minimum) and 15 (as a maximum). 
      Any value can be specified as long at it is within the provisionable 
      limits. However, a value equal to or close to the default is 
      recommended.
      Changes to this attribute do not affect existing calls."
   DEFVAL     { 15 }
::= { tdmaCsV42ProvEntry 7 }

tdmaCsV42RxKWindowSize OBJECT-TYPE
   SYNTAX     Unsigned32 (1..255)
   ACCESS     read-write
   STATUS     mandatory
   DESCRIPTION
     "This attribute specifies the maximum number of outstanding 
      unacknowledged sequenced Information (I) frames from the remote 
      entity to the IWF. The default value is 15 frames, and if this value is 
      used then no Exchange Identification (XID) negotiations are 
      required for rxKWindowSize. If the value set for rxKWindowSize is 
      other than 15, then XID frames are exchanged to negotiate a value. 
      The value provided for rxKWindowSize sets up the bounds during 
      XID negotiations. The IWF performs XID negotiations with this 
      value as a minimum or maximum value. If a value greater than 15 is 
      specified, then the IWF attempts to negotiate a value between 15 (as 
      a minimum) and the given value (as a maximum). If a value less 
      than 15 is specified, then the IWF attempts to negotiate for a value 
      between the given value (as a minimum) and 15 (as a maximum). 
      Any value can be specified as long as it is within the provisionable 
      limits. However, a value equal to or close to the default is 
      recommended.
      Changes to this attribute do not affect existing calls."
   DEFVAL     { 15 }
::= { tdmaCsV42ProvEntry 8 }

tdmaCsV42N400RetransLimit OBJECT-TYPE
   SYNTAX     Unsigned32 (0..255)
   ACCESS     read-write
   STATUS     mandatory
   DESCRIPTION
     "This attribute specifies the maximum number of times the IWF 
      retransmits a frame upon expiry of t401AckTimer before 
      appropriate recovery action is taken. Information about N400 
      (Retransmission Limit) is not carried in the Exchange Identification 
      (XID) negotiation at call setup time so both sides operate with 
      different N400 values.
      Changes to this attribute do not affect existing calls."
   DEFVAL     { 1 }
::= { tdmaCsV42ProvEntry 9 }

tdmaCsV42FcsLength OBJECT-TYPE
   SYNTAX     INTEGER  {
                 fcs16(0),
                 fcs32Or16(1),
                 fcs32(2) }
   ACCESS     read-write
   STATUS     mandatory
   DESCRIPTION
     "This attribute specifies whether a 16 bit or a 32 bit Frame Check 
      Sequence (FCS) will be used for the link between the IWF and the 
      far end DCE. This attribute has one of the following values:
      fcs16: Use only a 16 bit FCS.
      fcs32Or16: 32 bit FCS is preferred; Use a 16 bit FCS if needed.
      fcs32Only: Use only a 32 it FCS; If unavailable, drop the 
      connection."
   DEFVAL     { fcs32Or16 }
::= { tdmaCsV42ProvEntry 10 }


-- TdmaCs/<csIndex> V42bis
-- This component represents an instance of ITU-T V.42bis data 
-- compression protocol. Its attributes specify various default settings 
-- for aspects of the V.42bis protocol, which may be used in an IWF 
-- call on the mobile station to IWF link or the IWF to PSTN modem 
-- link or both.

tdmaCsV42Bis OBJECT IDENTIFIER ::= { tdmaCs 8 }



tdmaCsV42BisRowStatusTable OBJECT-TYPE
   SYNTAX     SEQUENCE OF TdmaCsV42BisRowStatusEntry
   ACCESS     not-accessible
   STATUS     mandatory
   DESCRIPTION
     "This entry controls the addition and deletion of 
      tdmaCsV42Bis components."
::= { tdmaCsV42Bis 1 }

tdmaCsV42BisRowStatusEntry OBJECT-TYPE
   SYNTAX     TdmaCsV42BisRowStatusEntry
   ACCESS     not-accessible
   STATUS     mandatory
   DESCRIPTION
     "A single entry in the table represents a single 
      tdmaCsV42Bis component."
   INDEX {
      tdmaCsCsIndex,
      tdmaCsV42BisIndex }
::= { tdmaCsV42BisRowStatusTable 1 }

TdmaCsV42BisRowStatusEntry ::= SEQUENCE {
   tdmaCsV42BisRowStatus
      RowStatus,
   tdmaCsV42BisComponentName
      DisplayString,
   tdmaCsV42BisStorageType
      StorageType,
   tdmaCsV42BisIndex
      NonReplicated }

tdmaCsV42BisRowStatus OBJECT-TYPE
   SYNTAX     RowStatus 
   ACCESS     read-only
   STATUS     mandatory
   DESCRIPTION
     "This variable is used as the basis for SNMP naming of
      tdmaCsV42Bis components.
      These components cannot be added nor deleted."
::= { tdmaCsV42BisRowStatusEntry 1 }

tdmaCsV42BisComponentName OBJECT-TYPE
   SYNTAX     DisplayString 
   ACCESS     read-only
   STATUS     mandatory
   DESCRIPTION
     "This variable provides the component's string name for
      use with the ASCII Console Interface"
::= { tdmaCsV42BisRowStatusEntry 2 }

tdmaCsV42BisStorageType OBJECT-TYPE
   SYNTAX     StorageType 
   ACCESS     read-only
   STATUS     mandatory
   DESCRIPTION
     "This variable represents the storage type value for the
      tdmaCsV42Bis tables."
::= { tdmaCsV42BisRowStatusEntry 4 }

tdmaCsV42BisIndex OBJECT-TYPE
   SYNTAX     NonReplicated 
   ACCESS     not-accessible
   STATUS     mandatory
   DESCRIPTION
     "This variable represents the index for the tdmaCsV42Bis tables."
::= { tdmaCsV42BisRowStatusEntry 10 }

tdmaCsV42BisProvTable OBJECT-TYPE
   SYNTAX     SEQUENCE OF TdmaCsV42BisProvEntry
   ACCESS     not-accessible
   STATUS     mandatory
   DESCRIPTION
     "This group contains the provisionable attributes for the V.42bis data 
      compression protocol parameters used for the calls set up by this 
      particular CallServer. Changes to these attributes do not affect 
      existing calls."
::= { tdmaCsV42Bis 10 }

tdmaCsV42BisProvEntry OBJECT-TYPE
   SYNTAX     TdmaCsV42BisProvEntry
   ACCESS     not-accessible
   STATUS     mandatory
   DESCRIPTION
     "An entry in the tdmaCsV42BisProvTable."
   INDEX {
      tdmaCsCsIndex,
      tdmaCsV42BisIndex }
::= { tdmaCsV42BisProvTable 1 }

TdmaCsV42BisProvEntry ::= SEQUENCE {
   tdmaCsV42BisP0CompressionDirection
      INTEGER,
   tdmaCsV42BisP1MaximumCodewords
      Unsigned32,
   tdmaCsV42BisP2MaximumStringSize
      Unsigned32,
   tdmaCsV42BisActionOnError
      INTEGER }

tdmaCsV42BisP0CompressionDirection OBJECT-TYPE
   SYNTAX     INTEGER  {
                 noCompression(0),
                 compInitrResp(1),
                 compRespInitr(2),
                 compBoth(3) }
   ACCESS     read-write
   STATUS     mandatory
   DESCRIPTION
     "This attribute specifies the V.42bis data compression direction to be 
      supported. The value for compression direction is negotiated at link 
      setup by the data link protocol by way of the Exchange 
      Identification (XID) negotiation of parameter P0 (compression 
      direction).
      During XID negotiation of parameter P0, both sides (IWF and 
      mobile or IWF and PSTN) agree on the compression direction.
      This attribute has one of the following values:
      noCompression: No compression is present.
      compInitrResp: The data sent by the IWF to the other entity is 
      compressed.
      compRespInitr: The data received by the IWF from the other entity 
      is compressed.
      compBoth: The data sent and received by the IWF is compressed.
      Changes to this attribute do not affect existing calls."
   DEFVAL     { compBoth }
::= { tdmaCsV42BisProvEntry 1 }

tdmaCsV42BisP1MaximumCodewords OBJECT-TYPE
   SYNTAX     Unsigned32 (512..4096)
   ACCESS     read-write
   STATUS     mandatory
   DESCRIPTION
     "This attribute specifies the maximum number of V.42bis codewords 
      the IWF supports. A codeword is a binary number that represents a 
      string of characters in compressed form. V.42bis keeps a dictionary 
      of codewords for each compression direction. Changes to this 
      attribute impact the compression ratio for the encoder (component 
      TdmaBc V42Bis attribute compRatioEncoder). Changes also impact 
      the amount of memory used (more memory is used when increasing 
      the attribute). The gain in performance obtained from the selection 
      of a larger dictionary may be offset by the larger codeword size 
      needed, and for certain types of data, better performance may be 
      obtained by using a smaller dictionary. 
      Changes to this attribute do not affect existing calls."
   DEFVAL     { 512 }
::= { tdmaCsV42BisProvEntry 2 }

tdmaCsV42BisP2MaximumStringSize OBJECT-TYPE
   SYNTAX     Unsigned32 (6..250)
   ACCESS     read-write
   STATUS     mandatory
   DESCRIPTION
     "This attribute specifies the maximum number of characters allowed 
      in a string represented by a codeword that the IWF supports. Each 
      codeword in a V.42bis dictionary represents a string of characters. 
      Changes to this attribute impact the compression ratio for the 
      encoder.
      Changes to this attribute do not affect existing calls."
   DEFVAL     { 6 }
::= { tdmaCsV42BisProvEntry 3 }

tdmaCsV42BisActionOnError OBJECT-TYPE
   SYNTAX     INTEGER  {
                 resetLink(0),
                 takeDownCall(1) }
   ACCESS     read-write
   STATUS     mandatory
   DESCRIPTION
     "This attribute specifies whether or not V.42bis takes down the call 
      or resets the link when any of the following errors occur: 
      1.Receipt of STEPUP (step up codeword size) codeword when it 
      would cause C2 (current code word size) to exceed N1 (maximum 
      code word size).
      2. Receipt of a codeword, at any time, equal to C1 (next empty 
      dictionary entry).
      3. Receipt of a codeword representing an empty dictionary entry.
      4. Receipt of a reserved command code.
      5. Receipt of any other error.
      If the value is resetLink, the error corrected connection and V.42bis 
      dictionaries are reset. Some data is lost but the call continues. If the 
      value is takeDownCall, the call is taken down.
      Changes to this attribute do not affect existing calls."
   DEFVAL     { resetLink }
::= { tdmaCsV42BisProvEntry 4 }


-- TdmaCs/<csIndex> Lp/n
-- The TdmaIwfLogicalProcessor component represents an instance of 
-- a TdmaIwfLogicalProcessor that may be linked to this 
-- TdmaIwfCallServer. A TdmaIwfBearerChannel is indirectly linked 
-- to this TdmaIwfLogicalProcessor by way of the TdmaIwfFramer 
-- component. This component must be added to the 
-- TdmaIwfCallServer (and the change activated) prior to adding the 
-- TdmaIwfBearerChannel(s). This component can only be 
-- provisioned for one TdmaIwfCallServer.

tdmaCsLp OBJECT IDENTIFIER ::= { tdmaCs 9 }



tdmaCsLpRowStatusTable OBJECT-TYPE
   SYNTAX     SEQUENCE OF TdmaCsLpRowStatusEntry
   ACCESS     not-accessible
   STATUS     mandatory
   DESCRIPTION
     "This entry controls the addition and deletion of 
      tdmaCsLp components."
::= { tdmaCsLp 1 }

tdmaCsLpRowStatusEntry OBJECT-TYPE
   SYNTAX     TdmaCsLpRowStatusEntry
   ACCESS     not-accessible
   STATUS     mandatory
   DESCRIPTION
     "A single entry in the table represents a single 
      tdmaCsLp component."
   INDEX {
      tdmaCsCsIndex,
      tdmaCsLpIndex }
::= { tdmaCsLpRowStatusTable 1 }

TdmaCsLpRowStatusEntry ::= SEQUENCE {
   tdmaCsLpRowStatus
      RowStatus,
   tdmaCsLpComponentName
      DisplayString,
   tdmaCsLpStorageType
      StorageType,
   tdmaCsLpIndex
      Integer32 }

tdmaCsLpRowStatus OBJECT-TYPE
   SYNTAX     RowStatus 
   ACCESS     read-write
   STATUS     mandatory
   DESCRIPTION
     "This variable is used as the basis for SNMP naming of
      tdmaCsLp components.
      These components can be added and deleted."
::= { tdmaCsLpRowStatusEntry 1 }

tdmaCsLpComponentName OBJECT-TYPE
   SYNTAX     DisplayString 
   ACCESS     read-only
   STATUS     mandatory
   DESCRIPTION
     "This variable provides the component's string name for
      use with the ASCII Console Interface"
::= { tdmaCsLpRowStatusEntry 2 }

tdmaCsLpStorageType OBJECT-TYPE
   SYNTAX     StorageType 
   ACCESS     read-only
   STATUS     mandatory
   DESCRIPTION
     "This variable represents the storage type value for the
      tdmaCsLp tables."
::= { tdmaCsLpRowStatusEntry 4 }

tdmaCsLpIndex OBJECT-TYPE
   SYNTAX     Integer32 (0..15)
   ACCESS     not-accessible
   STATUS     mandatory
   DESCRIPTION
     "This variable represents the index for the tdmaCsLp tables."
::= { tdmaCsLpRowStatusEntry 10 }

tdmaCsLpOperTable OBJECT-TYPE
   SYNTAX     SEQUENCE OF TdmaCsLpOperEntry
   ACCESS     not-accessible
   STATUS     mandatory
   DESCRIPTION
     "This group contains operational attributes pertaining to information 
      about TdmaIwfBearerChannels and TdmaIwfLogicalProcessor 
      associated with a TdmaIwfCallServer from a high-level view."
::= { tdmaCsLp 10 }

tdmaCsLpOperEntry OBJECT-TYPE
   SYNTAX     TdmaCsLpOperEntry
   ACCESS     not-accessible
   STATUS     mandatory
   DESCRIPTION
     "An entry in the tdmaCsLpOperTable."
   INDEX {
      tdmaCsCsIndex,
      tdmaCsLpIndex }
::= { tdmaCsLpOperTable 1 }

TdmaCsLpOperEntry ::= SEQUENCE {
   tdmaCsLpConfiguredBearerChannels
      Unsigned32,
   tdmaCsLpActiveCalls
      Gauge32,
   tdmaCsLpModemsSupported
      INTEGER }

tdmaCsLpConfiguredBearerChannels OBJECT-TYPE
   SYNTAX     Unsigned32 (0..124)
   ACCESS     read-only
   STATUS     mandatory
   DESCRIPTION
     "This attribute indicates the number of TdmaIwfBearerChannel 
      components provisioned for the TdmaIwfLogicalProcessor 
      represented by this component."
::= { tdmaCsLpOperEntry 1 }

tdmaCsLpActiveCalls OBJECT-TYPE
   SYNTAX     Gauge32 (0..124)
   ACCESS     read-only
   STATUS     mandatory
   DESCRIPTION
     "This attribute indicates the number of calls currently active on this 
      LogicalProcessor."
::= { tdmaCsLpOperEntry 2 }

tdmaCsLpModemsSupported OBJECT-TYPE
   SYNTAX     INTEGER  {
                 yes(0),
                 no(1) }
   ACCESS     read-only
   STATUS     mandatory
   DESCRIPTION
     "This attribute indicates if modems are supported with this 
      TdmaIwfLogicalProcessor. This attribute has one of the following 
      values:
      yes: Modems are supported with this TdmaIwfLogicalProcessor.
      no: Modems are not supported with this TdmaIwfLogicalProcessor."
::= { tdmaCsLpOperEntry 3 }


-- TdmaBc/<csIndex>,<bcIndex>
-- This component represents an individual bearer channel resource 
-- for a given TdmaIwfCallServer. Depending on the call type 
-- requested, the TdmaIwfCallServer links one or more 
-- TdmaIwfBearerChannels in a single DMS-MTX InterWorking 
-- Function (IWF) call. Each TdmaIwfBearerChannel is linked to a 
-- channel on a DS1 or E1 port on a TdmaIwfLogicalProcessor (one 
-- TdmaIwfBearerChannel per channel). 
-- The instance value csIndex is the logical identifier for the DMS-
-- MTX and is used for associating the call server with this 
-- TdmaIwfBearerChannel instance.
-- The instance value bcIndex is the logical identifier for the 
-- TdmaIwfBearerChannel. It and the csIndex together define a unique 
-- TdmaIwfBearerChannel.
-- 
-- This component is specific to the tdmaIwfBearerChannel feature 
-- of the tdmaIwf application.

tdmaBc OBJECT IDENTIFIER ::= { components 136 }



tdmaBcRowStatusTable OBJECT-TYPE
   SYNTAX     SEQUENCE OF TdmaBcRowStatusEntry
   ACCESS     not-accessible
   STATUS     mandatory
   DESCRIPTION
     "This entry controls the addition and deletion of 
      tdmaBc components."
::= { tdmaBc 1 }

tdmaBcRowStatusEntry OBJECT-TYPE
   SYNTAX     TdmaBcRowStatusEntry
   ACCESS     not-accessible
   STATUS     mandatory
   DESCRIPTION
     "A single entry in the table represents a single 
      tdmaBc component."
   INDEX {
      tdmaBcCsIndex,
      tdmaBcBcIndex }
::= { tdmaBcRowStatusTable 1 }

TdmaBcRowStatusEntry ::= SEQUENCE {
   tdmaBcRowStatus
      RowStatus,
   tdmaBcComponentName
      DisplayString,
   tdmaBcStorageType
      StorageType,
   tdmaBcCsIndex
      Integer32,
   tdmaBcBcIndex
      Integer32 }

tdmaBcRowStatus OBJECT-TYPE
   SYNTAX     RowStatus 
   ACCESS     read-write
   STATUS     mandatory
   DESCRIPTION
     "This variable is used as the basis for SNMP naming of
      tdmaBc components.
      These components can be added and deleted."
::= { tdmaBcRowStatusEntry 1 }

tdmaBcComponentName OBJECT-TYPE
   SYNTAX     DisplayString 
   ACCESS     read-only
   STATUS     mandatory
   DESCRIPTION
     "This variable provides the component's string name for
      use with the ASCII Console Interface"
::= { tdmaBcRowStatusEntry 2 }

tdmaBcStorageType OBJECT-TYPE
   SYNTAX     StorageType 
   ACCESS     read-only
   STATUS     mandatory
   DESCRIPTION
     "This variable represents the storage type value for the
      tdmaBc tables."
::= { tdmaBcRowStatusEntry 4 }

tdmaBcCsIndex OBJECT-TYPE
   SYNTAX     Integer32 (1..10)
   ACCESS     not-accessible
   STATUS     mandatory
   DESCRIPTION
     "This variable represents an index for the tdmaBc tables."
::= { tdmaBcRowStatusEntry 10 }

tdmaBcBcIndex OBJECT-TYPE
   SYNTAX     Integer32 (1..1024)
   ACCESS     not-accessible
   STATUS     mandatory
   DESCRIPTION
     "This variable represents an index for the tdmaBc tables."
::= { tdmaBcRowStatusEntry 11 }

tdmaBcOperTable OBJECT-TYPE
   SYNTAX     SEQUENCE OF TdmaBcOperEntry
   ACCESS     not-accessible
   STATUS     mandatory
   DESCRIPTION
     "This group contains operational attributes concerning the operation 
      of this particular TdmaIwfBearerChannel for the current or most 
      recent call."
::= { tdmaBc 101 }

tdmaBcOperEntry OBJECT-TYPE
   SYNTAX     TdmaBcOperEntry
   ACCESS     not-accessible
   STATUS     mandatory
   DESCRIPTION
     "An entry in the tdmaBcOperTable."
   INDEX {
      tdmaBcCsIndex,
      tdmaBcBcIndex }
::= { tdmaBcOperTable 1 }

TdmaBcOperEntry ::= SEQUENCE {
   tdmaBcState
      INTEGER,
   tdmaBcCallType
      INTEGER,
   tdmaBcLastResponseCode
      INTEGER,
   tdmaBcMateBearerChannel
      RowPointer }

tdmaBcState OBJECT-TYPE
   SYNTAX     INTEGER  {
                 idle(0),
                 setup(1),
                 active(2),
                 release(3) }
   ACCESS     read-only
   STATUS     mandatory
   DESCRIPTION
     "This attribute indicates the current state of the MSC/IWF Interface 
      Protocol (MIP) Message Router (MMR) for an IWF element. This 
      attribute has one of the following values:
      idle: Startup state of IWF element.
      setup: This call half is being set up.
      active: This call half has been connected by both the MTX and IWF 
      and is active.
      release: This call half is being released."
::= { tdmaBcOperEntry 1 }

tdmaBcCallType OBJECT-TYPE
   SYNTAX     INTEGER  {
                 analogSpeech(0),
                 digitalSpeech(1),
                 analogPrefSpeech(2),
                 digitalPrefSpeech(3),
                 asyncData(4),
                 g3Fax(5),
                 rejected(6),
                 stuIII(7),
                 notUsedYet(8) }
   ACCESS     read-only
   STATUS     mandatory
   DESCRIPTION
     "This attribute indicates the current call type. This attribute has one 
      of the following values:
      analogSpeech: Analog speech calls.
      digitalSpeech: Digital speech calls.
      analogPrefSpeech: Analog preferred speech calls.
      digitalPrefSpeech: Digital preferred speech calls.
      asyncData: Asynchronous data service calls.
      g3Fax: Group 3 fax calls.
      rejected: Rejected calls.
      stuIII: STU III calls.
      notUsedYet: Bearer Channel has not been used in a call yet."
::= { tdmaBcOperEntry 2 }

tdmaBcLastResponseCode OBJECT-TYPE
   SYNTAX     INTEGER  {
                 noCause(0),
                 unassignedNumber(129),
                 noRouteToDest(131),
                 normalClearing(144),
                 userBusy(145),
                 noResponse(146),
                 userNoAnswer(147),
                 invalidNumberFormat(156),
                 unspecNormal(159),
                 temporaryFailure(169),
                 channelUnavailable(172),
                 resourceUnavailable(175),
                 qosUnavailable(177),
                 serviceUnavailable(191),
                 unimplementedOption(207),
                 invalidCallRefValue(209),
                 invalidChannel(210),
                 unspecInvalidMessage(223),
                 missingMandatoryIe(224),
                 invalidMessageType(225),
                 incompatibleMessage(226),
                 timerRecovery(230),
                 unspecProtocolError(239) }
   ACCESS     read-only
   STATUS     mandatory
   DESCRIPTION
     "This attribute indicates the MSC/IWF Interface Protocol (MIP) 
      Message Router (MMR) response code returned for the last call 
      which was active on this particular TdmaIwfBearerChannel. This 
      attribute has one of the following values:
      noCause: No cause available.
      unassignedNumber: Unallocated or unassigned number.
      noRouteToDest: No route to destination.
      normalClearing: The call was terminated normally.
      userBusy: User busy.
      noResponse: No carrier.
      userNoAnswer: No answer from user.
      invalidNumberFormat: Translation or routing problem.
      unspecNormal: Normal, unspecified.
      temporaryFailure: Temporary failure.
      channelUnavailable: Channel unavailable.
      resourceUnavailable: Resources unavailable to handle call.
      qosUnavailabled: Specified rate of call unavailable.
      serviceUnavailable: Service not implemented.
      unimplementedOption: Option not implemented.
      invalidCallRefValue: Invalid call reference value.
      invalidChannel: Identified channel does not exist.
      unspecInvalidMessage: Invalid message, unspecified.
      missingMandatoryIe: Missing mandatory information element.
      invalidMessageType: Message type not implemented.
      incompatibleMessage: Message not compatible with call state.
      timerRecovery: Recovery on timer expiration.
      protocolError: Protocol error, unspecified."
::= { tdmaBcOperEntry 3 }

tdmaBcMateBearerChannel OBJECT-TYPE
   SYNTAX     RowPointer 
   ACCESS     read-only
   STATUS     mandatory
   DESCRIPTION
     "This attribute contains the name of the mate 
      TdmaIwfBearerChannel that this TdmaIwfBearerChannel is 
      involved with in the currently active call. In the case of a 
      FastConnect call, this mate is a TdmaIwfFcBearerChannel."
::= { tdmaBcOperEntry 4 }

tdmaBcCidDataTable OBJECT-TYPE
   SYNTAX     SEQUENCE OF TdmaBcCidDataEntry
   ACCESS     not-accessible
   STATUS     mandatory
   DESCRIPTION
     "This group contains the attribute for a component's Customer 
      Identifier (CID). Refer to the attribute description for a detailed 
      explanation of CIDs."
::= { tdmaBc 103 }

tdmaBcCidDataEntry OBJECT-TYPE
   SYNTAX     TdmaBcCidDataEntry
   ACCESS     not-accessible
   STATUS     mandatory
   DESCRIPTION
     "An entry in the tdmaBcCidDataTable."
   INDEX {
      tdmaBcCsIndex,
      tdmaBcBcIndex }
::= { tdmaBcCidDataTable 1 }

TdmaBcCidDataEntry ::= SEQUENCE {
   tdmaBcCustomerIdentifier
      Unsigned32 }

tdmaBcCustomerIdentifier OBJECT-TYPE
   SYNTAX     Unsigned32 (0 | 1..8191)
   ACCESS     read-write
   STATUS     mandatory
   DESCRIPTION
     "This attribute holds the Customer Identifier (CID).
      
      Every component has a CID. If a component has a cid attribute, the 
      component's CID is the provisioned value of that attribute; 
      otherwise the component inherits the CID of its parent. The top-
      level component has a CID of 0.
      
      Every operator session also has a CID, which is the CID 
      provisioned for the operator's user ID. An operator will see only the 
      stream data for components having a matching CID. Also, the 
      operator will be allowed to issue commands for only those 
      components which have a matching CID.
      
      An operator CID of 0 is used to identify the Network Manager 
      (referred to as 'NetMan' in DPN). This CID matches the CID of 
      any component. Values 1 to 8191 inclusive (equivalent to 'basic 
      CIDs' in DPN) may be assigned to specific customers."
   DEFVAL     { 0 }
::= { tdmaBcCidDataEntry 1 }

tdmaBcStateTable OBJECT-TYPE
   SYNTAX     SEQUENCE OF TdmaBcStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { tdmaBc 104 }

tdmaBcStateEntry OBJECT-TYPE
   SYNTAX     TdmaBcStateEntry
   ACCESS     not-accessible
   STATUS     mandatory
   DESCRIPTION
     "An entry in the tdmaBcStateTable."
   INDEX {
      tdmaBcCsIndex,
      tdmaBcBcIndex }
::= { tdmaBcStateTable 1 }

TdmaBcStateEntry ::= SEQUENCE {
   tdmaBcAdminState
      INTEGER,
   tdmaBcOperationalState
      INTEGER,
   tdmaBcUsageState
      INTEGER }

tdmaBcAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { tdmaBcStateEntry 1 }

tdmaBcOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { tdmaBcStateEntry 2 }

tdmaBcUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { tdmaBcStateEntry 3 }


-- TdmaBc/<csIndex>,<bcIndex> Framer
-- The TdmaIwfFramer component controls link layer framing for 
-- application components sending and receiving data on a link 
-- interface. The TdmaIwfFramer component provides provisionable 
-- attributes related to datapath aspects of the hardware interface rather 
-- than interface specific attributes which are associated with hardware 
-- components. The TdmaIwfFramer component also provides a 
-- provisionable attribute which binds the application component to a 
-- specific hardware component.

tdmaBcFramer OBJECT IDENTIFIER ::= { tdmaBc 2 }



tdmaBcFramerRowStatusTable OBJECT-TYPE
   SYNTAX     SEQUENCE OF TdmaBcFramerRowStatusEntry
   ACCESS     not-accessible
   STATUS     mandatory
   DESCRIPTION
     "This entry controls the addition and deletion of 
      tdmaBcFramer components."
::= { tdmaBcFramer 1 }

tdmaBcFramerRowStatusEntry OBJECT-TYPE
   SYNTAX     TdmaBcFramerRowStatusEntry
   ACCESS     not-accessible
   STATUS     mandatory
   DESCRIPTION
     "A single entry in the table represents a single 
      tdmaBcFramer component."
   INDEX {
      tdmaBcCsIndex,
      tdmaBcBcIndex,
      tdmaBcFramerIndex }
::= { tdmaBcFramerRowStatusTable 1 }

TdmaBcFramerRowStatusEntry ::= SEQUENCE {
   tdmaBcFramerRowStatus
      RowStatus,
   tdmaBcFramerComponentName
      DisplayString,
   tdmaBcFramerStorageType
      StorageType,
   tdmaBcFramerIndex
      NonReplicated }

tdmaBcFramerRowStatus OBJECT-TYPE
   SYNTAX     RowStatus 
   ACCESS     read-only
   STATUS     mandatory
   DESCRIPTION
     "This variable is used as the basis for SNMP naming of
      tdmaBcFramer components.
      These components cannot be added nor deleted."
::= { tdmaBcFramerRowStatusEntry 1 }

tdmaBcFramerComponentName OBJECT-TYPE
   SYNTAX     DisplayString 
   ACCESS     read-only
   STATUS     mandatory
   DESCRIPTION
     "This variable provides the component's string name for
      use with the ASCII Console Interface"
::= { tdmaBcFramerRowStatusEntry 2 }

tdmaBcFramerStorageType OBJECT-TYPE
   SYNTAX     StorageType 
   ACCESS     read-only
   STATUS     mandatory
   DESCRIPTION
     "This variable represents the storage type value for the
      tdmaBcFramer tables."
::= { tdmaBcFramerRowStatusEntry 4 }

tdmaBcFramerIndex OBJECT-TYPE
   SYNTAX     NonReplicated 
   ACCESS     not-accessible
   STATUS     mandatory
   DESCRIPTION
     "This variable represents the index for the tdmaBcFramer tables."
::= { tdmaBcFramerRowStatusEntry 10 }

tdmaBcFramerProvTable OBJECT-TYPE
   SYNTAX     SEQUENCE OF TdmaBcFramerProvEntry
   ACCESS     not-accessible
   STATUS     mandatory
   DESCRIPTION
     "This group contains the base provisioning data for the Framer 
      component. Application or hardware interface specific provisioning 
      data is contained in other provisionable Framer groups."
::= { tdmaBcFramer 10 }

tdmaBcFramerProvEntry OBJECT-TYPE
   SYNTAX     TdmaBcFramerProvEntry
   ACCESS     not-accessible
   STATUS     mandatory
   DESCRIPTION
     "An entry in the tdmaBcFramerProvTable."
   INDEX {
      tdmaBcCsIndex,
      tdmaBcBcIndex,
      tdmaBcFramerIndex }
::= { tdmaBcFramerProvTable 1 }

TdmaBcFramerProvEntry ::= SEQUENCE {
   tdmaBcFramerInterfaceName
      Link }

tdmaBcFramerInterfaceName OBJECT-TYPE
   SYNTAX     Link 
   ACCESS     read-write
   STATUS     mandatory
   DESCRIPTION
     "This attribute contains a hardware component name.
      
      The attribute associates the application with a specific link. This 
      defines the module processor on which Framer's parent component 
      (as well as Framer itself) will run."
::= { tdmaBcFramerProvEntry 1 }

tdmaBcFramerStatsTable OBJECT-TYPE
   SYNTAX     SEQUENCE OF TdmaBcFramerStatsEntry
   ACCESS     not-accessible
   STATUS     mandatory
   DESCRIPTION
     "This group contains the operational statistics data for a 
      TdmaIwfFramer component."
::= { tdmaBcFramer 11 }

tdmaBcFramerStatsEntry OBJECT-TYPE
   SYNTAX     TdmaBcFramerStatsEntry
   ACCESS     not-accessible
   STATUS     mandatory
   DESCRIPTION
     "An entry in the tdmaBcFramerStatsTable."
   INDEX {
      tdmaBcCsIndex,
      tdmaBcBcIndex,
      tdmaBcFramerIndex }
::= { tdmaBcFramerStatsTable 1 }

TdmaBcFramerStatsEntry ::= SEQUENCE {
   tdmaBcFramerTxFrames
      Counter32,
   tdmaBcFramerRxFrames
      Counter32,
   tdmaBcFramerRxBytes
      Counter32 }

tdmaBcFramerTxFrames OBJECT-TYPE
   SYNTAX     Counter32 
   ACCESS     read-only
   STATUS     mandatory
   DESCRIPTION
     "This attribute counts the number of frames transmitted to the link 
      interface by TdmaIwfFramer.
      The counter wraps when it exceeds the maximum value."
::= { tdmaBcFramerStatsEntry 1 }

tdmaBcFramerRxFrames OBJECT-TYPE
   SYNTAX     Counter32 
   ACCESS     read-only
   STATUS     mandatory
   DESCRIPTION
     "This attribute counts the number of frames received from the link 
      interface by TdmaIwfFramer.
      The counter wraps when it exceeds the maximum value."
::= { tdmaBcFramerStatsEntry 2 }

tdmaBcFramerRxBytes OBJECT-TYPE
   SYNTAX     Counter32 
   ACCESS     read-only
   STATUS     mandatory
   DESCRIPTION
     "This attribute counts the number of bytes received from the link 
      interface by TdmaIwfFramer.
      The counter wraps when it exceeds the maximum value."
::= { tdmaBcFramerStatsEntry 3 }

tdmaBcFramerLinkTable OBJECT-TYPE
   SYNTAX     SEQUENCE OF TdmaBcFramerLinkEntry
   ACCESS     not-accessible
   STATUS     mandatory
   DESCRIPTION
     "This group contains provisionable attributes for the TdmaIwfFramer 
      which controls link layer framing for application components 
      sending and receiving data on a link interface for this particular 
      TdmaIwfBearerChannel."
::= { tdmaBcFramer 12 }

tdmaBcFramerLinkEntry OBJECT-TYPE
   SYNTAX     TdmaBcFramerLinkEntry
   ACCESS     not-accessible
   STATUS     mandatory
   DESCRIPTION
     "An entry in the tdmaBcFramerLinkTable."
   INDEX {
      tdmaBcCsIndex,
      tdmaBcBcIndex,
      tdmaBcFramerIndex }
::= { tdmaBcFramerLinkTable 1 }

TdmaBcFramerLinkEntry ::= SEQUENCE {
   tdmaBcFramerFramingType
      INTEGER }

tdmaBcFramerFramingType OBJECT-TYPE
   SYNTAX     INTEGER  {
                 btdsFraming(2),
                 mtxFraming(8) }
   ACCESS     read-write
   STATUS     mandatory
   DESCRIPTION
     "This attribute indicates the type of framing for the link layer data 
      received and transmitted on this channel. This attribute has one of 
      the following values:
      btdsFraming: Bit transparent framing for the 
      TdmaIwfBearerChannel components on MVP cards.
      mtxFraming: DMS-MTX InterSystem Link Protocol (ISLP) 
      framing required for the TdmaIwfBearerChannel components on 
      DS1C/E1C cards."
::= { tdmaBcFramerLinkEntry 1 }

tdmaBcFramerStateTable OBJECT-TYPE
   SYNTAX     SEQUENCE OF TdmaBcFramerStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { tdmaBcFramer 13 }

tdmaBcFramerStateEntry OBJECT-TYPE
   SYNTAX     TdmaBcFramerStateEntry
   ACCESS     not-accessible
   STATUS     mandatory
   DESCRIPTION
     "An entry in the tdmaBcFramerStateTable."
   INDEX {
      tdmaBcCsIndex,
      tdmaBcBcIndex,
      tdmaBcFramerIndex }
::= { tdmaBcFramerStateTable 1 }

TdmaBcFramerStateEntry ::= SEQUENCE {
   tdmaBcFramerAdminState
      INTEGER,
   tdmaBcFramerOperationalState
      INTEGER,
   tdmaBcFramerUsageState
      INTEGER }

tdmaBcFramerAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { tdmaBcFramerStateEntry 1 }

tdmaBcFramerOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { tdmaBcFramerStateEntry 2 }

tdmaBcFramerUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { tdmaBcFramerStateEntry 3 }


-- TdmaBc/<csIndex>,<bcIndex> Modem
-- This component represents the group of measurements for the 
-- modem protocol established for a DMS-MTX IWF call (on the IWF 
-- to PSTN modem link) on this particular TdmaIwfBearerChannel.
-- Note that this component is present only if the current or most 
-- recent call involved this protocol.

tdmaBcModem OBJECT IDENTIFIER ::= { tdmaBc 3 }



tdmaBcModemRowStatusTable OBJECT-TYPE
   SYNTAX     SEQUENCE OF TdmaBcModemRowStatusEntry
   ACCESS     not-accessible
   STATUS     mandatory
   DESCRIPTION
     "This entry controls the addition and deletion of 
      tdmaBcModem components."
::= { tdmaBcModem 1 }

tdmaBcModemRowStatusEntry OBJECT-TYPE
   SYNTAX     TdmaBcModemRowStatusEntry
   ACCESS     not-accessible
   STATUS     mandatory
   DESCRIPTION
     "A single entry in the table represents a single 
      tdmaBcModem component."
   INDEX {
      tdmaBcCsIndex,
      tdmaBcBcIndex,
      tdmaBcModemIndex }
::= { tdmaBcModemRowStatusTable 1 }

TdmaBcModemRowStatusEntry ::= SEQUENCE {
   tdmaBcModemRowStatus
      RowStatus,
   tdmaBcModemComponentName
      DisplayString,
   tdmaBcModemStorageType
      StorageType,
   tdmaBcModemIndex
      NonReplicated }

tdmaBcModemRowStatus OBJECT-TYPE
   SYNTAX     RowStatus 
   ACCESS     read-only
   STATUS     mandatory
   DESCRIPTION
     "This variable is used as the basis for SNMP naming of
      tdmaBcModem components.
      These components cannot be added nor deleted."
::= { tdmaBcModemRowStatusEntry 1 }

tdmaBcModemComponentName OBJECT-TYPE
   SYNTAX     DisplayString 
   ACCESS     read-only
   STATUS     mandatory
   DESCRIPTION
     "This variable provides the component's string name for
      use with the ASCII Console Interface"
::= { tdmaBcModemRowStatusEntry 2 }

tdmaBcModemStorageType OBJECT-TYPE
   SYNTAX     StorageType 
   ACCESS     read-only
   STATUS     mandatory
   DESCRIPTION
     "This variable represents the storage type value for the
      tdmaBcModem tables."
::= { tdmaBcModemRowStatusEntry 4 }

tdmaBcModemIndex OBJECT-TYPE
   SYNTAX     NonReplicated 
   ACCESS     not-accessible
   STATUS     mandatory
   DESCRIPTION
     "This variable represents the index for the tdmaBcModem tables."
::= { tdmaBcModemRowStatusEntry 10 }

tdmaBcModemOperTable OBJECT-TYPE
   SYNTAX     SEQUENCE OF TdmaBcModemOperEntry
   ACCESS     not-accessible
   STATUS     mandatory
   DESCRIPTION
     "This group contains operational attributes that measure performance 
      of the modem component for this particular 
      TdmaIwfBearerChannel."
::= { tdmaBcModem 10 }

tdmaBcModemOperEntry OBJECT-TYPE
   SYNTAX     TdmaBcModemOperEntry
   ACCESS     not-accessible
   STATUS     mandatory
   DESCRIPTION
     "An entry in the tdmaBcModemOperTable."
   INDEX {
      tdmaBcCsIndex,
      tdmaBcBcIndex,
      tdmaBcModemIndex }
::= { tdmaBcModemOperTable 1 }

TdmaBcModemOperEntry ::= SEQUENCE {
   tdmaBcModemVoiceLaw
      INTEGER,
   tdmaBcModemRate
      INTEGER,
   tdmaBcModemModemAlgorithmInUse
      OCTET STRING,
   tdmaBcModemProtocolState
      INTEGER,
   tdmaBcModemMobileSideFlowControlState
      INTEGER,
   tdmaBcModemPstnSideFlowControlState
      INTEGER,
   tdmaBcModemAsyncMode
      INTEGER,
   tdmaBcModemOutbandFlowControl
      INTEGER,
   tdmaBcModemOutbandBreak
      INTEGER,
   tdmaBcModemAutobaud
      INTEGER }

tdmaBcModemVoiceLaw OBJECT-TYPE
   SYNTAX     INTEGER  {
                 aLaw(0),
                 muLaw(1) }
   ACCESS     read-only
   STATUS     mandatory
   DESCRIPTION
     "This attribute indicates the active voice law associated with the 
      modem component. This attribute has one of the following values: 
      aLaw and muLaw. Both protocols are utilized for encoding voice-
      band audio. For additional information on each, refer to ITU-T 
      G.711 'Pulse Code Modulation (PCM) of Voice Frequencies'."
::= { tdmaBcModemOperEntry 1 }

tdmaBcModemRate OBJECT-TYPE
   SYNTAX     INTEGER  {
                 n50(0),
                 n300(1),
                 n600(2),
                 n1200(3),
                 n2400(4),
                 n4800(5),
                 n7200(6),
                 n9600(7),
                 n12000(8),
                 n14400(9),
                 n16800(10),
                 n19200(11),
                 n21600(12),
                 n24000(13),
                 n26400(14),
                 n28800(15),
                 n31200(16),
                 n32000(17),
                 n33600(18),
                 n38400(19),
                 n43200(20),
                 n48000(21),
                 n56000(22),
                 n57600(23),
                 n64000(24) }
   ACCESS     read-only
   STATUS     mandatory
   DESCRIPTION
     "This attribute indicates the transmission rate of the current modem 
      in use. All rates are the same in both the transmit and receive 
      directions."
::= { tdmaBcModemOperEntry 2 }

tdmaBcModemModemAlgorithmInUse OBJECT-TYPE
   SYNTAX     OCTET STRING (SIZE (2))
   ACCESS     read-only
   STATUS     mandatory
   DESCRIPTION
     "This attribute indicates the current modem algorithm(s) active for 
      the channel. This attribute has one of the following values:
      t30: T.30 is active. T.30 is the Group 3 fax protocol.
      v17: V.17 is active.V.17 is an ITU-T 14400bit/s modem standard. 
      v21: V.21 is active. V.21 is an ITU-4 300bit/s modem standard. 
      v22: V.22 ia active. V.22 is an ITU-T modem standard that operates 
      at 1200bit/s and 600 baud. 
      v22bis: V.22bis is active. V.22bis is an ITU-T modem standard that 
      operates at 2400bit/s and 600 baud. 
      v27ter: V.27ter is active. V.27ter is an ITU-T 7200bit/s modem 
      standard.
      v29: V.29 is active. V.29 is an ITU-T 9600bit/s modem standard. 
      v32: V.32 is active. V.32 is an ITU-T modem standard that operates 
      at 9600bit/s and 2400 baud. 
      v32bis: V.32bis is an ITU-T modem standard that operates at a 
      speed of 14.4kbit/s.

      Description of bits:
      t30(0)
      v17(1)
      v21(2)
      v22(3)
      v22bis(4)
      v27ter(5)
      v29(6)
      v32(7)
      v32bis(8)"
::= { tdmaBcModemOperEntry 3 }

tdmaBcModemProtocolState OBJECT-TYPE
   SYNTAX     INTEGER  {
                 idle(0),
                 training(1),
                 connected(2),
                 releasing(3) }
   ACCESS     read-only
   STATUS     mandatory
   DESCRIPTION
     "This attribute indicates the active protocol state of the modem in 
      use.This attribute has one of the following values:
      idle: Modem is in an inactive state and has no current connection 
      established.
      training: Modem is attempting to establish a connection with the 
      far end modem via handshaking.
      connected: Modem has establish a connection with the far end 
      modem.
      releasing: Modem has begun tearing down the connection."
::= { tdmaBcModemOperEntry 4 }

tdmaBcModemMobileSideFlowControlState OBJECT-TYPE
   SYNTAX     INTEGER  {
                 on(0),
                 off(1) }
   ACCESS     read-only
   STATUS     mandatory
   DESCRIPTION
     "This attribute indicates the state of flow control based on whether 
      flow control was requested by the mobile side of the connection and 
      an indication was sent to an upper layer protocol. This attribute has 
      one of the following values:
      on: Flow control is active towards the mobile side of the call.
      off: Flow control is not active towards the mobile side of the call.
      DESCRIPTION"
::= { tdmaBcModemOperEntry 5 }

tdmaBcModemPstnSideFlowControlState OBJECT-TYPE
   SYNTAX     INTEGER  {
                 on(0),
                 off(1) }
   ACCESS     read-only
   STATUS     mandatory
   DESCRIPTION
     "This attribute indicates the state of flow control based on whether 
      flow control was requested by the PSTN side of the connection and 
      an indication was sent to the Digital Signal Processor. This attribute 
      has one of the following values:
      on: Flow control is active towards the DSP (PSTN side of the call).
      off: Flow control is not active towards the DSP (PSTN side of the 
      call)."
::= { tdmaBcModemOperEntry 6 }

tdmaBcModemAsyncMode OBJECT-TYPE
   SYNTAX     INTEGER  {
                 on(0),
                 off(1) }
   ACCESS     read-only
   STATUS     mandatory
   DESCRIPTION
     "This attribute indicates whether conversion between synchronous 
      and asynchronous data format (specifically, the stripping or 
      insertion of start and stop bits) is being performed. The value is on 
      unless the V.42 layer is active or it is a fax call. This attribute has 
      one of the following values:
      on: Conversion between synchronous and asynchronous data is 
      being performed.
      off: Conversion between synchronous and asynchronous data is not 
      being performed."
::= { tdmaBcModemOperEntry 7 }

tdmaBcModemOutbandFlowControl OBJECT-TYPE
   SYNTAX     INTEGER  {
                 on(0),
                 off(1) }
   ACCESS     read-only
   STATUS     mandatory
   DESCRIPTION
     "This attribute indicates whether outband flow control conversions 
      are being performed. If outband flow control is on, then when the 
      Modem Application Layer (MAL) receives an xon or xoff from the 
      PSTN, the MAL converts the instruction into a primitive and sends 
      it to the Data Service Control (DSC). In the opposite direction with 
      outband flow control on, when the MAL receives a primitive from 
      the DSC, the MAL converts the primitive into an xon or xoff and 
      forwards it to the PSTN. If outband flow control is off, then all flow 
      control is handled inband. The modem performs either inband or 
      outband flow control unless V.42 layer is active, it is a fax call, or 
      no flow control was specified by the DMS-MTX. This attribute has 
      one of the following values:
      on: Conversion to and from out-of-band signaling is enabled.
      off: Conversion to and from out-of-band signaling is disabled."
::= { tdmaBcModemOperEntry 8 }

tdmaBcModemOutbandBreak OBJECT-TYPE
   SYNTAX     INTEGER  {
                 on(0),
                 off(1) }
   ACCESS     read-only
   STATUS     mandatory
   DESCRIPTION
     "This attribute indicates whether inband or outband break control 
      conversions are being performed. If outband break control is on, 
      when the modem detects a break condition coming from the PSTN, 
      the Modem Application Layer (MAL) converts the instruction into a 
      primitive and forwards it to the Data Service Control (DSC). In the 
      opposite direction with outband break control on, when the MAL 
      receives a primitive from the DSC, the MAL converts the primitive 
      into a break and forwards it to the PSTN. When a break condition is 
      discovered all subsequent incoming data is discarded until a start bit 
      is received."
::= { tdmaBcModemOperEntry 9 }

tdmaBcModemAutobaud OBJECT-TYPE
   SYNTAX     INTEGER  {
                 on(0),
                 off(1) }
   ACCESS     read-only
   STATUS     mandatory
   DESCRIPTION
     "This attribute indicates whether autobaud is active. 
      The modem is instructed at call setup time by the DMS-MTX on 
      the following:
      (1) the initial modem data rate value, and
      (2) whether a modem is allowed to perform autobauding (on) or not 
      (off).
      With autobauding on, the modem is allowed to connect using a 
      valid modem data rate less than or equal to the initial rate specified 
      to the modem by the DMS-MTX. If a modem cannot perform 
      autobauding and the carrier cannot be established at the initial data 
      rate, the modem is disabled."
::= { tdmaBcModemOperEntry 10 }

tdmaBcModemStatsTable OBJECT-TYPE
   SYNTAX     SEQUENCE OF TdmaBcModemStatsEntry
   ACCESS     not-accessible
   STATUS     mandatory
   DESCRIPTION
     "This group contains operational attributes that measure performance 
      of the modem component for this particular 
      TdmaIwfBearerChannel."
::= { tdmaBcModem 11 }

tdmaBcModemStatsEntry OBJECT-TYPE
   SYNTAX     TdmaBcModemStatsEntry
   ACCESS     not-accessible
   STATUS     mandatory
   DESCRIPTION
     "An entry in the tdmaBcModemStatsTable."
   INDEX {
      tdmaBcCsIndex,
      tdmaBcBcIndex,
      tdmaBcModemIndex }
::= { tdmaBcModemStatsTable 1 }

TdmaBcModemStatsEntry ::= SEQUENCE {
   tdmaBcModemTxBytes
      Counter32,
   tdmaBcModemRxBytes
      Counter32,
   tdmaBcModemFramingErrors
      Counter32 }

tdmaBcModemTxBytes OBJECT-TYPE
   SYNTAX     Counter32 
   ACCESS     read-only
   STATUS     mandatory
   DESCRIPTION
     "This attribute counts the number of payload bytes transmitted.
      The counter wraps when it exceeds the maximum value."
::= { tdmaBcModemStatsEntry 1 }

tdmaBcModemRxBytes OBJECT-TYPE
   SYNTAX     Counter32 
   ACCESS     read-only
   STATUS     mandatory
   DESCRIPTION
     "This attribute counts the number of payload bytes received.
      The counter wraps when it exceeds the maximum value."
::= { tdmaBcModemStatsEntry 2 }

tdmaBcModemFramingErrors OBJECT-TYPE
   SYNTAX     Counter32 
   ACCESS     read-only
   STATUS     mandatory
   DESCRIPTION
     "This attribute counts the number of framing errors detected by the 
      hardware. This is the absence of a stop bit after a start bit and eight 
      bits of data. All incoming data is discarded until the next start bit is 
      received.
      The counter wraps when it exceeds the maximum value."
::= { tdmaBcModemStatsEntry 3 }


-- TdmaBc/<csIndex>,<bcIndex> Fax
-- This component represents the group of measurements for the fax 
-- protocol established for a DMS-MTX IWF call (on the mobile 
-- station to IWF link or the IWF to PSTN fax modem/machine link) 
-- on this particular TdmaIwfBearerChannel.
-- Note that this component is present only if the current or most 
-- recent call involved this protocol.

tdmaBcFax OBJECT IDENTIFIER ::= { tdmaBc 4 }



tdmaBcFaxRowStatusTable OBJECT-TYPE
   SYNTAX     SEQUENCE OF TdmaBcFaxRowStatusEntry
   ACCESS     not-accessible
   STATUS     mandatory
   DESCRIPTION
     "This entry controls the addition and deletion of 
      tdmaBcFax components."
::= { tdmaBcFax 1 }

tdmaBcFaxRowStatusEntry OBJECT-TYPE
   SYNTAX     TdmaBcFaxRowStatusEntry
   ACCESS     not-accessible
   STATUS     mandatory
   DESCRIPTION
     "A single entry in the table represents a single 
      tdmaBcFax component."
   INDEX {
      tdmaBcCsIndex,
      tdmaBcBcIndex,
      tdmaBcFaxIndex }
::= { tdmaBcFaxRowStatusTable 1 }

TdmaBcFaxRowStatusEntry ::= SEQUENCE {
   tdmaBcFaxRowStatus
      RowStatus,
   tdmaBcFaxComponentName
      DisplayString,
   tdmaBcFaxStorageType
      StorageType,
   tdmaBcFaxIndex
      NonReplicated }

tdmaBcFaxRowStatus OBJECT-TYPE
   SYNTAX     RowStatus 
   ACCESS     read-only
   STATUS     mandatory
   DESCRIPTION
     "This variable is used as the basis for SNMP naming of
      tdmaBcFax components.
      These components cannot be added nor deleted."
::= { tdmaBcFaxRowStatusEntry 1 }

tdmaBcFaxComponentName OBJECT-TYPE
   SYNTAX     DisplayString 
   ACCESS     read-only
   STATUS     mandatory
   DESCRIPTION
     "This variable provides the component's string name for
      use with the ASCII Console Interface"
::= { tdmaBcFaxRowStatusEntry 2 }

tdmaBcFaxStorageType OBJECT-TYPE
   SYNTAX     StorageType 
   ACCESS     read-only
   STATUS     mandatory
   DESCRIPTION
     "This variable represents the storage type value for the
      tdmaBcFax tables."
::= { tdmaBcFaxRowStatusEntry 4 }

tdmaBcFaxIndex OBJECT-TYPE
   SYNTAX     NonReplicated 
   ACCESS     not-accessible
   STATUS     mandatory
   DESCRIPTION
     "This variable represents the index for the tdmaBcFax tables."
::= { tdmaBcFaxRowStatusEntry 10 }

tdmaBcFaxOperTable OBJECT-TYPE
   SYNTAX     SEQUENCE OF TdmaBcFaxOperEntry
   ACCESS     not-accessible
   STATUS     mandatory
   DESCRIPTION
     "This group contains operational attributes which measure the 
      performance of the fax protocol."
::= { tdmaBcFax 10 }

tdmaBcFaxOperEntry OBJECT-TYPE
   SYNTAX     TdmaBcFaxOperEntry
   ACCESS     not-accessible
   STATUS     mandatory
   DESCRIPTION
     "An entry in the tdmaBcFaxOperTable."
   INDEX {
      tdmaBcCsIndex,
      tdmaBcBcIndex,
      tdmaBcFaxIndex }
::= { tdmaBcFaxOperTable 1 }

TdmaBcFaxOperEntry ::= SEQUENCE {
   tdmaBcFaxActiveMode
      INTEGER,
   tdmaBcFaxProtocolState
      INTEGER,
   tdmaBcFaxMessageRate
      Unsigned32 }

tdmaBcFaxActiveMode OBJECT-TYPE
   SYNTAX     INTEGER  {
                 normal(0),
                 ecm(1) }
   ACCESS     read-only
   STATUS     mandatory
   DESCRIPTION
     "This attribute indicates the mode of the fax T.30 protocol, 
      determined during Exchange Identification (XID) negotiations. The 
      following modes are supported:
      normal: Normal T.30 protocol, Error Correction Mode (ECM) not 
      used.
      ecm: Error Correction Mode used. Fax error correction is done 
      using a half-duplex page selective repeat technique."
::= { tdmaBcFaxOperEntry 1 }

tdmaBcFaxProtocolState OBJECT-TYPE
   SYNTAX     INTEGER  {
                 setup(0),
                 idle(1),
                 bcsRx(2),
                 bcsTx(3),
                 msgRx(4),
                 msgTx(5) }
   ACCESS     read-only
   STATUS     mandatory
   DESCRIPTION
     "This attribute indicates the protocol state of the fax adaptor. This 
      attribute has one of the following values:
      setup: Call setup state.
      idle: Idle state only transmitting Synchronize (SYNC) frames.
      bcsRx: Receiving Binary Coded Signal (BCS) packet from modem.
      bcsTx: Transmitting BCS packet to modem.
      msgRx: Receiving fax message from modem.
      msgTx: Transmitting fax message to modem."
::= { tdmaBcFaxOperEntry 2 }

tdmaBcFaxMessageRate OBJECT-TYPE
   SYNTAX     Unsigned32 (0..65000)
   ACCESS     read-only
   STATUS     mandatory
   DESCRIPTION
     "This attribute indicates the fax message rate used for sending fax 
      documents."
::= { tdmaBcFaxOperEntry 3 }

tdmaBcFaxStatsTable OBJECT-TYPE
   SYNTAX     SEQUENCE OF TdmaBcFaxStatsEntry
   ACCESS     not-accessible
   STATUS     mandatory
   DESCRIPTION
     "This group contains statistical attributes which measure the 
      performance of the fax protocol."
::= { tdmaBcFax 11 }

tdmaBcFaxStatsEntry OBJECT-TYPE
   SYNTAX     TdmaBcFaxStatsEntry
   ACCESS     not-accessible
   STATUS     mandatory
   DESCRIPTION
     "An entry in the tdmaBcFaxStatsTable."
   INDEX {
      tdmaBcCsIndex,
      tdmaBcBcIndex,
      tdmaBcFaxIndex }
::= { tdmaBcFaxStatsTable 1 }

TdmaBcFaxStatsEntry ::= SEQUENCE {
   tdmaBcFaxTxPagesToMobile
      Counter32,
   tdmaBcFaxRxPagesFromMobile
      Counter32 }

tdmaBcFaxTxPagesToMobile OBJECT-TYPE
   SYNTAX     Counter32 
   ACCESS     read-only
   STATUS     mandatory
   DESCRIPTION
     "The attribute counts the number of fax pages transmitted to the 
      mobile.
      The counter wraps when it exceeds the maximum value."
::= { tdmaBcFaxStatsEntry 1 }

tdmaBcFaxRxPagesFromMobile OBJECT-TYPE
   SYNTAX     Counter32 
   ACCESS     read-only
   STATUS     mandatory
   DESCRIPTION
     "This attribute counts the number of fax pages received from the 
      mobile.
      The counter wraps when it exceeds the maximum value."
::= { tdmaBcFaxStatsEntry 2 }


-- TdmaBc/<csIndex>,<bcIndex> Dce
-- This component represents the group of measurements for the 
-- DMS-MTX DCE Protocol established for a DMS-MTX IWF call 
-- (on the Public Switched Telephone Network to the IWF link) on 
-- this particular TdmaIwfBearerChannel.
-- Note that this component is present only if the current or most 
-- recent call involved this protocol.

tdmaBcDce OBJECT IDENTIFIER ::= { tdmaBc 5 }



tdmaBcDceRowStatusTable OBJECT-TYPE
   SYNTAX     SEQUENCE OF TdmaBcDceRowStatusEntry
   ACCESS     not-accessible
   STATUS     obsolete
   DESCRIPTION
     "This entry controls the addition and deletion of 
      tdmaBcDce components."
::= { tdmaBcDce 1 }

tdmaBcDceRowStatusEntry OBJECT-TYPE
   SYNTAX     TdmaBcDceRowStatusEntry
   ACCESS     not-accessible
   STATUS     obsolete
   DESCRIPTION
     "A single entry in the table represents a single 
      tdmaBcDce component."
   INDEX {
      tdmaBcCsIndex,
      tdmaBcBcIndex,
      tdmaBcDceIndex }
::= { tdmaBcDceRowStatusTable 1 }

TdmaBcDceRowStatusEntry ::= SEQUENCE {
   tdmaBcDceRowStatus
      RowStatus,
   tdmaBcDceComponentName
      DisplayString,
   tdmaBcDceStorageType
      StorageType,
   tdmaBcDceIndex
      NonReplicated }

tdmaBcDceRowStatus OBJECT-TYPE
   SYNTAX     RowStatus 
   ACCESS     read-only
   STATUS     obsolete
   DESCRIPTION
     "This variable is used as the basis for SNMP naming of
      tdmaBcDce components.
      These components cannot be added nor deleted."
::= { tdmaBcDceRowStatusEntry 1 }

tdmaBcDceComponentName OBJECT-TYPE
   SYNTAX     DisplayString 
   ACCESS     read-only
   STATUS     obsolete
   DESCRIPTION
     "This variable provides the component's string name for
      use with the ASCII Console Interface"
::= { tdmaBcDceRowStatusEntry 2 }

tdmaBcDceStorageType OBJECT-TYPE
   SYNTAX     StorageType 
   ACCESS     read-only
   STATUS     obsolete
   DESCRIPTION
     "This variable represents the storage type value for the
      tdmaBcDce tables."
::= { tdmaBcDceRowStatusEntry 4 }

tdmaBcDceIndex OBJECT-TYPE
   SYNTAX     NonReplicated 
   ACCESS     not-accessible
   STATUS     obsolete
   DESCRIPTION
     "This variable represents the index for the tdmaBcDce tables."
::= { tdmaBcDceRowStatusEntry 10 }


-- TdmaBc/<csIndex>,<bcIndex> Dsc
-- This component represents the group of measurements for the 
-- DMS-MTX DSC Protocol established for a DMS-MTX IWF call 
-- (on the mobile station to the IWF link) on this particular 
-- TdmaIwfBearerChannel.
-- Note that this component is present only if the current or most 
-- recent call involved this protocol.

tdmaBcDsc OBJECT IDENTIFIER ::= { tdmaBc 6 }



tdmaBcDscRowStatusTable OBJECT-TYPE
   SYNTAX     SEQUENCE OF TdmaBcDscRowStatusEntry
   ACCESS     not-accessible
   STATUS     mandatory
   DESCRIPTION
     "This entry controls the addition and deletion of 
      tdmaBcDsc components."
::= { tdmaBcDsc 1 }

tdmaBcDscRowStatusEntry OBJECT-TYPE
   SYNTAX     TdmaBcDscRowStatusEntry
   ACCESS     not-accessible
   STATUS     mandatory
   DESCRIPTION
     "A single entry in the table represents a single 
      tdmaBcDsc component."
   INDEX {
      tdmaBcCsIndex,
      tdmaBcBcIndex,
      tdmaBcDscIndex }
::= { tdmaBcDscRowStatusTable 1 }

TdmaBcDscRowStatusEntry ::= SEQUENCE {
   tdmaBcDscRowStatus
      RowStatus,
   tdmaBcDscComponentName
      DisplayString,
   tdmaBcDscStorageType
      StorageType,
   tdmaBcDscIndex
      NonReplicated }

tdmaBcDscRowStatus OBJECT-TYPE
   SYNTAX     RowStatus 
   ACCESS     read-only
   STATUS     mandatory
   DESCRIPTION
     "This variable is used as the basis for SNMP naming of
      tdmaBcDsc components.
      These components cannot be added nor deleted."
::= { tdmaBcDscRowStatusEntry 1 }

tdmaBcDscComponentName OBJECT-TYPE
   SYNTAX     DisplayString 
   ACCESS     read-only
   STATUS     mandatory
   DESCRIPTION
     "This variable provides the component's string name for
      use with the ASCII Console Interface"
::= { tdmaBcDscRowStatusEntry 2 }

tdmaBcDscStorageType OBJECT-TYPE
   SYNTAX     StorageType 
   ACCESS     read-only
   STATUS     mandatory
   DESCRIPTION
     "This variable represents the storage type value for the
      tdmaBcDsc tables."
::= { tdmaBcDscRowStatusEntry 4 }

tdmaBcDscIndex OBJECT-TYPE
   SYNTAX     NonReplicated 
   ACCESS     not-accessible
   STATUS     mandatory
   DESCRIPTION
     "This variable represents the index for the tdmaBcDsc tables."
::= { tdmaBcDscRowStatusEntry 10 }

tdmaBcDscOperTable OBJECT-TYPE
   SYNTAX     SEQUENCE OF TdmaBcDscOperEntry
   ACCESS     not-accessible
   STATUS     mandatory
   DESCRIPTION
     "This group contains operational attributes that measure the 
      performance of the DSC asynchronous data service."
::= { tdmaBcDsc 10 }

tdmaBcDscOperEntry OBJECT-TYPE
   SYNTAX     TdmaBcDscOperEntry
   ACCESS     not-accessible
   STATUS     mandatory
   DESCRIPTION
     "An entry in the tdmaBcDscOperTable."
   INDEX {
      tdmaBcCsIndex,
      tdmaBcBcIndex,
      tdmaBcDscIndex }
::= { tdmaBcDscOperTable 1 }

TdmaBcDscOperEntry ::= SEQUENCE {
   tdmaBcDscP0CompressionDirection
      INTEGER,
   tdmaBcDscP1CompressionMaximumCodewords
      Unsigned32,
   tdmaBcDscP2CompressionMaximumCharacters
      Unsigned32 }

tdmaBcDscP0CompressionDirection OBJECT-TYPE
   SYNTAX     INTEGER  {
                 noCompression(0),
                 compInitrResp(1),
                 compRespInitr(2),
                 compBoth(3) }
   ACCESS     read-only
   STATUS     mandatory
   DESCRIPTION
     "This attribute indicates the direction of compression requested from 
      logical link 0 (LL0). This attribute has one of the following values:
      noCpmpression: No data compression.
      compInitrResp: Compression initiator to responder.
      compRespInitr: compression responder to initiator.
      compBoth: compression in both directions."
::= { tdmaBcDscOperEntry 1 }

tdmaBcDscP1CompressionMaximumCodewords OBJECT-TYPE
   SYNTAX     Unsigned32 (512..65535)
   ACCESS     read-only
   STATUS     mandatory
   DESCRIPTION
     "This attribute indicates the maximum number of codewords to be 
      requested from logical link 0 (LL0) for compression. A codeword is 
      a binary number that represents a string of characters."
::= { tdmaBcDscOperEntry 2 }

tdmaBcDscP2CompressionMaximumCharacters OBJECT-TYPE
   SYNTAX     Unsigned32 (6..250)
   ACCESS     read-only
   STATUS     mandatory
   DESCRIPTION
     "This attribute indicates the maximum number of characters that can 
      be represented by a single codeword to be requested from logical 
      link 0 (LL0) for compression."
::= { tdmaBcDscOperEntry 3 }

tdmaBcDscStatsTable OBJECT-TYPE
   SYNTAX     SEQUENCE OF TdmaBcDscStatsEntry
   ACCESS     not-accessible
   STATUS     mandatory
   DESCRIPTION
     "This group contains statistical attributes that measure the 
      performance of the DSC asynchronous data service."
::= { tdmaBcDsc 11 }

tdmaBcDscStatsEntry OBJECT-TYPE
   SYNTAX     TdmaBcDscStatsEntry
   ACCESS     not-accessible
   STATUS     mandatory
   DESCRIPTION
     "An entry in the tdmaBcDscStatsTable."
   INDEX {
      tdmaBcCsIndex,
      tdmaBcBcIndex,
      tdmaBcDscIndex }
::= { tdmaBcDscStatsTable 1 }

TdmaBcDscStatsEntry ::= SEQUENCE {
   tdmaBcDscTxBytes
      Counter32,
   tdmaBcDscRxBytes
      Counter32 }

tdmaBcDscTxBytes OBJECT-TYPE
   SYNTAX     Counter32 
   ACCESS     read-only
   STATUS     mandatory
   DESCRIPTION
     "This attribute counts the number of data bytes relayed by DSC in 
      the transmit direction (towards the mobile).
      The counter wraps when it exceeds the maximum value."
::= { tdmaBcDscStatsEntry 1 }

tdmaBcDscRxBytes OBJECT-TYPE
   SYNTAX     Counter32 
   ACCESS     read-only
   STATUS     mandatory
   DESCRIPTION
     "This attribute counts the number of data bytes relayed by DSC in 
      the receive direction (from the mobile).
      The counter wraps when it exceeds the maximum value."
::= { tdmaBcDscStatsEntry 2 }


-- TdmaBc/<csIndex>,<bcIndex> Rlp1
-- This component represents the group of measurements for the 
-- Radio Link Protocol 1 (RLP1) established for a DMS-MTX IWF 
-- call (on the mobile station to IWF link) on this particular 
-- TdmaIwfBearerChannel.
-- Note that this component is present only if the current or most 
-- recent call involved this protocol.

tdmaBcRlp1 OBJECT IDENTIFIER ::= { tdmaBc 7 }



tdmaBcRlp1RowStatusTable OBJECT-TYPE
   SYNTAX     SEQUENCE OF TdmaBcRlp1RowStatusEntry
   ACCESS     not-accessible
   STATUS     mandatory
   DESCRIPTION
     "This entry controls the addition and deletion of 
      tdmaBcRlp1 components."
::= { tdmaBcRlp1 1 }

tdmaBcRlp1RowStatusEntry OBJECT-TYPE
   SYNTAX     TdmaBcRlp1RowStatusEntry
   ACCESS     not-accessible
   STATUS     mandatory
   DESCRIPTION
     "A single entry in the table represents a single 
      tdmaBcRlp1 component."
   INDEX {
      tdmaBcCsIndex,
      tdmaBcBcIndex,
      tdmaBcRlp1Index }
::= { tdmaBcRlp1RowStatusTable 1 }

TdmaBcRlp1RowStatusEntry ::= SEQUENCE {
   tdmaBcRlp1RowStatus
      RowStatus,
   tdmaBcRlp1ComponentName
      DisplayString,
   tdmaBcRlp1StorageType
      StorageType,
   tdmaBcRlp1Index
      NonReplicated }

tdmaBcRlp1RowStatus OBJECT-TYPE
   SYNTAX     RowStatus 
   ACCESS     read-only
   STATUS     mandatory
   DESCRIPTION
     "This variable is used as the basis for SNMP naming of
      tdmaBcRlp1 components.
      These components cannot be added nor deleted."
::= { tdmaBcRlp1RowStatusEntry 1 }

tdmaBcRlp1ComponentName OBJECT-TYPE
   SYNTAX     DisplayString 
   ACCESS     read-only
   STATUS     mandatory
   DESCRIPTION
     "This variable provides the component's string name for
      use with the ASCII Console Interface"
::= { tdmaBcRlp1RowStatusEntry 2 }

tdmaBcRlp1StorageType OBJECT-TYPE
   SYNTAX     StorageType 
   ACCESS     read-only
   STATUS     mandatory
   DESCRIPTION
     "This variable represents the storage type value for the
      tdmaBcRlp1 tables."
::= { tdmaBcRlp1RowStatusEntry 4 }

tdmaBcRlp1Index OBJECT-TYPE
   SYNTAX     NonReplicated 
   ACCESS     not-accessible
   STATUS     mandatory
   DESCRIPTION
     "This variable represents the index for the tdmaBcRlp1 tables."
::= { tdmaBcRlp1RowStatusEntry 10 }

tdmaBcRlp1OperTable OBJECT-TYPE
   SYNTAX     SEQUENCE OF TdmaBcRlp1OperEntry
   ACCESS     not-accessible
   STATUS     mandatory
   DESCRIPTION
     "This group contains operational attributes that measure performance 
      of the TdmaIwfBearerChannel."
::= { tdmaBcRlp1 10 }

tdmaBcRlp1OperEntry OBJECT-TYPE
   SYNTAX     TdmaBcRlp1OperEntry
   ACCESS     not-accessible
   STATUS     mandatory
   DESCRIPTION
     "An entry in the tdmaBcRlp1OperTable."
   INDEX {
      tdmaBcCsIndex,
      tdmaBcBcIndex,
      tdmaBcRlp1Index }
::= { tdmaBcRlp1OperTable 1 }

TdmaBcRlp1OperEntry ::= SEQUENCE {
   tdmaBcRlp1Layer3L0ReqWinSize
      Unsigned32,
   tdmaBcRlp1Layer3L1ReqWinSize1
      Unsigned32,
   tdmaBcRlp1T1ResponseTimer
      Unsigned32,
   tdmaBcRlp1T2LinkActivityTimer
      Unsigned32,
   tdmaBcRlp1T3PeerAckTimer
      Unsigned32 }

tdmaBcRlp1Layer3L0ReqWinSize OBJECT-TYPE
   SYNTAX     Unsigned32 (1..64)
   ACCESS     read-only
   STATUS     mandatory
   DESCRIPTION
     "This attribute indicates the window size for Service Access Point 
      (SAP) 0 requested by layer 3. The window size is the maximum 
      number of sequentially numbered Information (I) frames that may 
      be unacknowledged at any given time."
::= { tdmaBcRlp1OperEntry 1 }

tdmaBcRlp1Layer3L1ReqWinSize1 OBJECT-TYPE
   SYNTAX     Unsigned32 (1..64)
   ACCESS     read-only
   STATUS     mandatory
   DESCRIPTION
     "This attribute indicates the window size for Service Access Point 
      (SAP) 1 requested by layer 3. The window size is the maximum 
      number of sequentially numbered Information (I) frames that may 
      be unacknowledged at any given time."
::= { tdmaBcRlp1OperEntry 2 }

tdmaBcRlp1T1ResponseTimer OBJECT-TYPE
   SYNTAX     Unsigned32 (5..20)
   ACCESS     read-only
   STATUS     mandatory
   DESCRIPTION
     "This attribute indicates the current T1 timer for Service Access 
      Points (SAP) 0 and 1 negotiated by the Radio Link Protocol 1 
      (RLP1), during Exchange Information (XID). This attribute 
      specifies the time the receiving RLP1 entity shall wait for a 
      response from the peer TIA-136-310 (formerly IS-130) application. 
      The value used for XID negotiations can be provisioned in the 
      TdmaCs/* Rlp1 t1ResponseTimer attribute."
::= { tdmaBcRlp1OperEntry 3 }

tdmaBcRlp1T2LinkActivityTimer OBJECT-TYPE
   SYNTAX     Unsigned32 (10..120)
   ACCESS     read-only
   STATUS     mandatory
   DESCRIPTION
     "This attribute indicates the current T2 timer for Service Access 
      Points (SAP) 0 and 1 negotiated by the Radio Link Protocol 1 
      (RLP1), during Exchange Information (XID). This attribute 
      specifies the maximum time the receiving RLP1 entity shall wait for 
      link activity. The value used for XID negotiations can be 
      provisioned in the TdmaCs/* Rlp1 t2LinkActivityTimer attribute."
::= { tdmaBcRlp1OperEntry 4 }

tdmaBcRlp1T3PeerAckTimer OBJECT-TYPE
   SYNTAX     Unsigned32 (5..20)
   ACCESS     read-only
   STATUS     mandatory
   DESCRIPTION
     "This attribute indicates the current T3 timer for Service Access 
      Points (SAP) 0 and 1 negotiated by the Radio Link Protocol 1 
      (RLP1), during Exchange Information (XID). The attribute specifies 
      the maximum time the receiving RLP1 entity shall wait for the peer 
      to ACK or NAK data. The value used for XID negotiations can be 
      provisioned in the TdmaCs/* Rlp1 t3PeerAckTimer attribute."
::= { tdmaBcRlp1OperEntry 5 }

tdmaBcRlp1StatsTable OBJECT-TYPE
   SYNTAX     SEQUENCE OF TdmaBcRlp1StatsEntry
   ACCESS     not-accessible
   STATUS     mandatory
   DESCRIPTION
     "This group contains operational attributes that measure performance 
      of the TdmaIwfBearerChannel."
::= { tdmaBcRlp1 11 }

tdmaBcRlp1StatsEntry OBJECT-TYPE
   SYNTAX     TdmaBcRlp1StatsEntry
   ACCESS     not-accessible
   STATUS     mandatory
   DESCRIPTION
     "An entry in the tdmaBcRlp1StatsTable."
   INDEX {
      tdmaBcCsIndex,
      tdmaBcBcIndex,
      tdmaBcRlp1Index }
::= { tdmaBcRlp1StatsTable 1 }

TdmaBcRlp1StatsEntry ::= SEQUENCE {
   tdmaBcRlp1TxFrames
      Counter32,
   tdmaBcRlp1RxFrames
      Counter32,
   tdmaBcRlp1BadRxFrames
      Counter32 }

tdmaBcRlp1TxFrames OBJECT-TYPE
   SYNTAX     Counter32 
   ACCESS     read-only
   STATUS     mandatory
   DESCRIPTION
     "This attribute counts the number of valid frames transmitted to the 
      mobile.
      The counter wraps when it exceeds the maximum value."
::= { tdmaBcRlp1StatsEntry 1 }

tdmaBcRlp1RxFrames OBJECT-TYPE
   SYNTAX     Counter32 
   ACCESS     read-only
   STATUS     mandatory
   DESCRIPTION
     "This attributes counts the number of valid frames received from the 
      mobile.
      The counter wraps when it exceeds the maximum value."
::= { tdmaBcRlp1StatsEntry 2 }

tdmaBcRlp1BadRxFrames OBJECT-TYPE
   SYNTAX     Counter32 
   ACCESS     read-only
   STATUS     mandatory
   DESCRIPTION
     "This attribute count the total number of bad RLP1 frames received 
      from the mobile.
      The counter wraps when it exceeds the maximum value."
::= { tdmaBcRlp1StatsEntry 3 }


-- TdmaBc/<csIndex>,<bcIndex> V42
-- This component represents the group of measurements for the ITU-
-- T V.42 error correcting protocol established for a DMS-MTX IWF 
-- call (on the IWF to PSTN modem link) on this particular 
-- TdmaIwfBearerChannel. 
-- Note that this component is present only if the current or most 
-- recent call involved this protocol.

tdmaBcV42 OBJECT IDENTIFIER ::= { tdmaBc 8 }



tdmaBcV42RowStatusTable OBJECT-TYPE
   SYNTAX     SEQUENCE OF TdmaBcV42RowStatusEntry
   ACCESS     not-accessible
   STATUS     mandatory
   DESCRIPTION
     "This entry controls the addition and deletion of 
      tdmaBcV42 components."
::= { tdmaBcV42 1 }

tdmaBcV42RowStatusEntry OBJECT-TYPE
   SYNTAX     TdmaBcV42RowStatusEntry
   ACCESS     not-accessible
   STATUS     mandatory
   DESCRIPTION
     "A single entry in the table represents a single 
      tdmaBcV42 component."
   INDEX {
      tdmaBcCsIndex,
      tdmaBcBcIndex,
      tdmaBcV42Index }
::= { tdmaBcV42RowStatusTable 1 }

TdmaBcV42RowStatusEntry ::= SEQUENCE {
   tdmaBcV42RowStatus
      RowStatus,
   tdmaBcV42ComponentName
      DisplayString,
   tdmaBcV42StorageType
      StorageType,
   tdmaBcV42Index
      NonReplicated }

tdmaBcV42RowStatus OBJECT-TYPE
   SYNTAX     RowStatus 
   ACCESS     read-only
   STATUS     mandatory
   DESCRIPTION
     "This variable is used as the basis for SNMP naming of
      tdmaBcV42 components.
      These components cannot be added nor deleted."
::= { tdmaBcV42RowStatusEntry 1 }

tdmaBcV42ComponentName OBJECT-TYPE
   SYNTAX     DisplayString 
   ACCESS     read-only
   STATUS     mandatory
   DESCRIPTION
     "This variable provides the component's string name for
      use with the ASCII Console Interface"
::= { tdmaBcV42RowStatusEntry 2 }

tdmaBcV42StorageType OBJECT-TYPE
   SYNTAX     StorageType 
   ACCESS     read-only
   STATUS     mandatory
   DESCRIPTION
     "This variable represents the storage type value for the
      tdmaBcV42 tables."
::= { tdmaBcV42RowStatusEntry 4 }

tdmaBcV42Index OBJECT-TYPE
   SYNTAX     NonReplicated 
   ACCESS     not-accessible
   STATUS     mandatory
   DESCRIPTION
     "This variable represents the index for the tdmaBcV42 tables."
::= { tdmaBcV42RowStatusEntry 10 }

tdmaBcV42OperTable OBJECT-TYPE
   SYNTAX     SEQUENCE OF TdmaBcV42OperEntry
   ACCESS     not-accessible
   STATUS     mandatory
   DESCRIPTION
     "This group contains operational attributes which measure V.42 error 
      detection and correction performance."
::= { tdmaBcV42 10 }

tdmaBcV42OperEntry OBJECT-TYPE
   SYNTAX     TdmaBcV42OperEntry
   ACCESS     not-accessible
   STATUS     mandatory
   DESCRIPTION
     "An entry in the tdmaBcV42OperTable."
   INDEX {
      tdmaBcCsIndex,
      tdmaBcBcIndex,
      tdmaBcV42Index }
::= { tdmaBcV42OperTable 1 }

TdmaBcV42OperEntry ::= SEQUENCE {
   tdmaBcV42ProtocolState
      INTEGER,
   tdmaBcV42TxN401FrameSize
      Unsigned32,
   tdmaBcV42RxN401FrameSize
      Unsigned32,
   tdmaBcV42TxKWindowSize
      Unsigned32,
   tdmaBcV42RxKWindowSize
      Unsigned32,
   tdmaBcV42V42ActiveInCall
      INTEGER,
   tdmaBcV42V42BisActiveInCall
      INTEGER }

tdmaBcV42ProtocolState OBJECT-TYPE
   SYNTAX     INTEGER  {
                 notActive(0),
                 disconnected(1),
                 linkSetup(2),
                 frameReject(3),
                 disconnectRequest(4),
                 informationTransfer(5),
                 waitingAck(6) }
   ACCESS     read-only
   STATUS     mandatory
   DESCRIPTION
     "This attribute indicates the state of V.42. Valid states are:
      
      notActive: The V.42 link connection with the PSTN modem is not 
      established. None of the V.42 functions including the error 
      detection, error correction, and flow control is provided to the data 
      call. This is the initial state of V.42.
      disconnected: This means that the V42 link is disconnected.
      linkSetup: The V.42 operation enters this state from the 
      disconnected state after the V.42 sends to the PSTN modem a Set 
      Asynchronous Balanced Mode Extended (SABME) frame in an 
      attempt to establish the error control connection with the PSTN 
      modem.
      frameReject: The V.42 operation enters into this state after it 
      identifies an invalid frame sent by the peer and it sends back a frame 
      reject (FRMR) frame to the peer.
      disconnectRequest: The V.42 operation enters into this state after it 
      sends to the peer a disconnect (DISC) frame with the attempt to 
      disconnect the V.42 error control link.
      informationTransfer: The V.42 enters into this state after it receives 
      a UA (unnumbered acknowledgment) frame which the peer sent 
      upon receipt of the SAMBE frame from IWF V.42. Once in this 
      state, the V.42 can exchange data and supervisory information with 
      its peer.
      waitingAck: The V.42 enters this state after it sends polling enquiry 
      to its peer. The V.42 sends the polling enquiry when it receives a 
      reject frame (REJ) from its peer or either its acknowledgment timer 
      or inactivity timer timed out on the information frames sent out."
::= { tdmaBcV42OperEntry 1 }

tdmaBcV42TxN401FrameSize OBJECT-TYPE
   SYNTAX     Unsigned32 (0..65355)
   ACCESS     read-only
   STATUS     mandatory
   DESCRIPTION
     "This attribute indicates the current value of parameter N401 for 
      V.42 which is negotiated during Exchange Information (XID). This 
      is the maximum number of octets that can be carried in the 
      information field of an information frame that the IWF V.42 
      transmits to the PSTN modem. The IWF V.42 puts this or even 
      smaller size of data into the outgoing information frame. The value 
      used for XID negotiations can be provisioned via TdmaCs/* V42."
::= { tdmaBcV42OperEntry 2 }

tdmaBcV42RxN401FrameSize OBJECT-TYPE
   SYNTAX     Unsigned32 (1..255)
   ACCESS     read-only
   STATUS     mandatory
   DESCRIPTION
     "This attribute indicates the current value of N401, that is negotiated 
      during Exchange Identification (XID). This is the maximum number 
      of octets that can be carried in the information field of an 
      information frame received from the PSTN modem. An incoming 
      information frame carrying data octets more than this size shall be 
      rejected by the IWF V.42. The value used for XID negotiations can 
      be provisioned via TdmaCs/* V42."
::= { tdmaBcV42OperEntry 3 }

tdmaBcV42TxKWindowSize OBJECT-TYPE
   SYNTAX     Unsigned32 (0..127)
   ACCESS     read-only
   STATUS     mandatory
   DESCRIPTION
     "This attribute indicates the current value of k, that is negotiated 
      during Exchange Identification (XID). This is the size of flow 
      control sliding window used for the information frames that the 
      V.42 transmits to the PSTN modem. This size governs the 
      maximum number of information frames that the IWF V.42 error-
      correcting entity can have outstanding (that is, unacknowledged). 
      The value used for XID negotiations can be provisioned via 
      TdmaCs/* V42."
::= { tdmaBcV42OperEntry 4 }

tdmaBcV42RxKWindowSize OBJECT-TYPE
   SYNTAX     Unsigned32 (1..127)
   ACCESS     read-only
   STATUS     mandatory
   DESCRIPTION
     "This attribute indicates the current value of k that is negotiated 
      during Exchange Identification (XID). This is the size of flow 
      control sliding window used for information frames transmitted 
      from the PSTN modem. This size governs the maximum number of 
      information frames that the peer of the IWF V.42 error-correcting 
      entity can have outstanding (that is, unacknowledged). The value 
      used for XID negotiations can be provisioned via TdmaCs/* V42."
::= { tdmaBcV42OperEntry 5 }

tdmaBcV42V42ActiveInCall OBJECT-TYPE
   SYNTAX     INTEGER  {
                 notActiveInCall(0),
                 activeInCall(1) }
   ACCESS     read-only
   STATUS     mandatory
   DESCRIPTION
     "This attribute indicates whether V42 is really being used in this data 
      call."
   DEFVAL     { notActiveInCall }
::= { tdmaBcV42OperEntry 6 }

tdmaBcV42V42BisActiveInCall OBJECT-TYPE
   SYNTAX     INTEGER  {
                 notActiveInCall(0),
                 activeInCall(1) }
   ACCESS     read-only
   STATUS     mandatory
   DESCRIPTION
     "This attribute indicates whether V42bis is really being used in this 
      data call."
   DEFVAL     { notActiveInCall }
::= { tdmaBcV42OperEntry 7 }

tdmaBcV42StatsTable OBJECT-TYPE
   SYNTAX     SEQUENCE OF TdmaBcV42StatsEntry
   ACCESS     not-accessible
   STATUS     mandatory
   DESCRIPTION
     "This group contains statistical attributes that measure the V.42 error 
      detection and correction performance."
::= { tdmaBcV42 11 }

tdmaBcV42StatsEntry OBJECT-TYPE
   SYNTAX     TdmaBcV42StatsEntry
   ACCESS     not-accessible
   STATUS     mandatory
   DESCRIPTION
     "An entry in the tdmaBcV42StatsTable."
   INDEX {
      tdmaBcCsIndex,
      tdmaBcBcIndex,
      tdmaBcV42Index }
::= { tdmaBcV42StatsTable 1 }

TdmaBcV42StatsEntry ::= SEQUENCE {
   tdmaBcV42RxIBytes
      Counter32,
   tdmaBcV42TxIBytes
      Counter32,
   tdmaBcV42RxIFrames
      Counter32,
   tdmaBcV42TxIFrames
      Counter32,
   tdmaBcV42RetransmittedFrames
      Counter32,
   tdmaBcV42T1AckTimeouts
      Counter32,
   tdmaBcV42RemoteBusyIndications
      Counter32,
   tdmaBcV42LocalBusyIndications
      Counter32,
   tdmaBcV42BadFramesRx
      Counter32,
   tdmaBcV42CrcErrorsRx
      Counter32 }

tdmaBcV42RxIBytes OBJECT-TYPE
   SYNTAX     Counter32 
   ACCESS     read-only
   STATUS     mandatory
   DESCRIPTION
     "This attribute counts the total number of bytes that the V.42 actually 
      received from the PSTN modem in a data call.
      The counter wraps when it exceeds the maximum value."
::= { tdmaBcV42StatsEntry 1 }

tdmaBcV42TxIBytes OBJECT-TYPE
   SYNTAX     Counter32 
   ACCESS     read-only
   STATUS     mandatory
   DESCRIPTION
     "This attribute counts the total number of bytes that the V.42 
      transmitted to the PSTN modem in a data call.
      The counter wraps when it exceeds the maximum value."
::= { tdmaBcV42StatsEntry 2 }

tdmaBcV42RxIFrames OBJECT-TYPE
   SYNTAX     Counter32 
   ACCESS     read-only
   STATUS     mandatory
   DESCRIPTION
     "This attribute counts the total number of Information (I) frames that 
      the V.42 received from the PSTN modem in a data call.
      The counter wraps when it exceeds the maximum value."
::= { tdmaBcV42StatsEntry 3 }

tdmaBcV42TxIFrames OBJECT-TYPE
   SYNTAX     Counter32 
   ACCESS     read-only
   STATUS     mandatory
   DESCRIPTION
     "This attribute counts the total number of information frames that the 
      V.42 transmitted to the PSTN modem in a data call.
      The counter wraps when it exceeds the maximum value."
::= { tdmaBcV42StatsEntry 4 }

tdmaBcV42RetransmittedFrames OBJECT-TYPE
   SYNTAX     Counter32 
   ACCESS     read-only
   STATUS     mandatory
   DESCRIPTION
     "This attribute counts the total number of frames retransmitted by the 
      IWF V.42 entity in a data call. The V.42 retransmits the same frame 
      when the associated T401 acknowledgment timer timeouts or when 
      a Reject (REJ) supervisory frame has been received from the PSTN 
      modem.
      The counter wraps when it exceeds the maximum value."
::= { tdmaBcV42StatsEntry 5 }

tdmaBcV42T1AckTimeouts OBJECT-TYPE
   SYNTAX     Counter32 
   ACCESS     read-only
   STATUS     mandatory
   DESCRIPTION
     "This attribute counts the total number of times that the T401 timer 
      has timed out within a data call. If this timer times-out frequently, 
      the operator may need to adjust the provisioned parameter T401 
      acknowledgment timer to a larger time amount, since every time 
      that V.42 sends out a frame it sets the T401 timer to wait for the 
      peer's acknowledgment of the frame. When the timer times-out and 
      no acknowledgment has been received, the V.42 sends the same 
      frame to its peer.
      The counter wraps when it exceeds the maximum value."
::= { tdmaBcV42StatsEntry 6 }

tdmaBcV42RemoteBusyIndications OBJECT-TYPE
   SYNTAX     Counter32 
   ACCESS     read-only
   STATUS     mandatory
   DESCRIPTION
     "This attribute counts the total number of times the PSTN modem 
      enters a busy state (the IWF has received a Receive Not Ready 
      message) and asks the IWF V.42 not to send Information (I) frames 
      to it until it is ready to receive information frames again (indicated 
      by receipt of a Receive Ready message or a data message).
      The counter wraps when it exceeds the maximum value."
::= { tdmaBcV42StatsEntry 7 }

tdmaBcV42LocalBusyIndications OBJECT-TYPE
   SYNTAX     Counter32 
   ACCESS     read-only
   STATUS     mandatory
   DESCRIPTION
     "This attribute counts the total number of times the IWF V.42 enters 
      in a busy condition and asks the peer to stop sending information 
      frames until it has cleared up from the busy condition. The V.42 
      enters busy condition when its data buffer is about to be overflowed 
      by the incoming Information (I) frames.
      The counter wraps when it exceeds the maximum value."
::= { tdmaBcV42StatsEntry 8 }

tdmaBcV42BadFramesRx OBJECT-TYPE
   SYNTAX     Counter32 
   ACCESS     read-only
   STATUS     mandatory
   DESCRIPTION
     "This attribute counts the total number of bad frames the IWF V.42 
      has received from the PSTN remote modem within the data call. In 
      this instance, 'bad frames' refer to the V.42 protocol error frames 
      other than the check sequence error frames.
      The counter wraps when it exceeds the maximum value."
::= { tdmaBcV42StatsEntry 9 }

tdmaBcV42CrcErrorsRx OBJECT-TYPE
   SYNTAX     Counter32 
   ACCESS     read-only
   STATUS     mandatory
   DESCRIPTION
     "This attribute counts the total number of frames received from the 
      remote PSTN modem that contain incorrect frame check sequence. 
      A high value signifies the condition of the physical medium is poor.
      The counter wraps when it exceeds the maximum value."
::= { tdmaBcV42StatsEntry 10 }


-- TdmaBc/<csIndex>,<bcIndex> V42bis
-- This component represents the group of measurements for the ITU-
-- T V.42bis data compression protocol established for an IWF call (on 
-- the mobile station to the IWF link or the IWF to PSTN fax modem 
-- link) on this particular TdmaIwfBearerChannel.
-- Note that this component is present only if the current or most 
-- recent call involved this protocol. 

tdmaBcV42Bis OBJECT IDENTIFIER ::= { tdmaBc 9 }



tdmaBcV42BisRowStatusTable OBJECT-TYPE
   SYNTAX     SEQUENCE OF TdmaBcV42BisRowStatusEntry
   ACCESS     not-accessible
   STATUS     mandatory
   DESCRIPTION
     "This entry controls the addition and deletion of 
      tdmaBcV42Bis components."
::= { tdmaBcV42Bis 1 }

tdmaBcV42BisRowStatusEntry OBJECT-TYPE
   SYNTAX     TdmaBcV42BisRowStatusEntry
   ACCESS     not-accessible
   STATUS     mandatory
   DESCRIPTION
     "A single entry in the table represents a single 
      tdmaBcV42Bis component."
   INDEX {
      tdmaBcCsIndex,
      tdmaBcBcIndex,
      tdmaBcV42BisIndex }
::= { tdmaBcV42BisRowStatusTable 1 }

TdmaBcV42BisRowStatusEntry ::= SEQUENCE {
   tdmaBcV42BisRowStatus
      RowStatus,
   tdmaBcV42BisComponentName
      DisplayString,
   tdmaBcV42BisStorageType
      StorageType,
   tdmaBcV42BisIndex
      NonReplicated }

tdmaBcV42BisRowStatus OBJECT-TYPE
   SYNTAX     RowStatus 
   ACCESS     read-only
   STATUS     mandatory
   DESCRIPTION
     "This variable is used as the basis for SNMP naming of
      tdmaBcV42Bis components.
      These components cannot be added nor deleted."
::= { tdmaBcV42BisRowStatusEntry 1 }

tdmaBcV42BisComponentName OBJECT-TYPE
   SYNTAX     DisplayString 
   ACCESS     read-only
   STATUS     mandatory
   DESCRIPTION
     "This variable provides the component's string name for
      use with the ASCII Console Interface"
::= { tdmaBcV42BisRowStatusEntry 2 }

tdmaBcV42BisStorageType OBJECT-TYPE
   SYNTAX     StorageType 
   ACCESS     read-only
   STATUS     mandatory
   DESCRIPTION
     "This variable represents the storage type value for the
      tdmaBcV42Bis tables."
::= { tdmaBcV42BisRowStatusEntry 4 }

tdmaBcV42BisIndex OBJECT-TYPE
   SYNTAX     NonReplicated 
   ACCESS     not-accessible
   STATUS     mandatory
   DESCRIPTION
     "This variable represents the index for the tdmaBcV42Bis tables."
::= { tdmaBcV42BisRowStatusEntry 10 }

tdmaBcV42BisOperTable OBJECT-TYPE
   SYNTAX     SEQUENCE OF TdmaBcV42BisOperEntry
   ACCESS     not-accessible
   STATUS     mandatory
   DESCRIPTION
     "This group contains operational attributes that measure the 
      performance of IwfV42bis."
::= { tdmaBcV42Bis 10 }

tdmaBcV42BisOperEntry OBJECT-TYPE
   SYNTAX     TdmaBcV42BisOperEntry
   ACCESS     not-accessible
   STATUS     mandatory
   DESCRIPTION
     "An entry in the tdmaBcV42BisOperTable."
   INDEX {
      tdmaBcCsIndex,
      tdmaBcBcIndex,
      tdmaBcV42BisIndex }
::= { tdmaBcV42BisOperTable 1 }

TdmaBcV42BisOperEntry ::= SEQUENCE {
   tdmaBcV42BisProtocolModeEncoder
      INTEGER,
   tdmaBcV42BisProtocolModeDecoder
      INTEGER,
   tdmaBcV42BisP0CompressionDirection
      INTEGER,
   tdmaBcV42BisP1MaximumCodewords
      Unsigned32,
   tdmaBcV42BisP2MaximumStringSize
      Unsigned32,
   tdmaBcV42BisLastDecodeError
      INTEGER,
   tdmaBcV42BisCompRatioEncoder
      FixedPoint2,
   tdmaBcV42BisCompRatioDecoder
      FixedPoint2 }

tdmaBcV42BisProtocolModeEncoder OBJECT-TYPE
   SYNTAX     INTEGER  {
                 transparent(0),
                 compressed(1) }
   ACCESS     read-only
   STATUS     mandatory
   DESCRIPTION
     "This attribute indicates the current mode of the IwfV42bis encoder. 
      This mode can be either:
      transparent: A mode of operation in which compression has been 
      selected but data is being transmitted in uncompressed form. 
      Transparent mode command sequences may be inserted into the 
      data stream. 
      compressed: A mode of operation in which data is transmitted in 
      codewords.
      The encoder switches between the two modes depending on 
      whether the data coming from the Date Terminal Equipment (DTE) 
      is suitable for compression. The data compression function 
      periodically determines the compressibility of the data based on a 
      comparison of the number of bits required to represent a segment of 
      the data stream before and after compression."
::= { tdmaBcV42BisOperEntry 1 }

tdmaBcV42BisProtocolModeDecoder OBJECT-TYPE
   SYNTAX     INTEGER  {
                 transparent(0),
                 compressed(1) }
   ACCESS     read-only
   STATUS     mandatory
   DESCRIPTION
     "This attribute indicates the current mode of the V.42bis decoder. 
      This mode can be either: 
      transparent: A mode of operation in which compression has been 
      selected but data is being transmitted in uncompressed form. 
      Transparent mode command sequences may be inserted into the 
      data stream.
      compressed: A mode of operation in which data is transmitted in 
      codewords.
      The encoder (at the mobile or PSTN) switches between the two 
      modes depending on whether the data coming from the Date 
      Terminal Equipment (DTE) is suitable for compression. The data 
      compression function periodically determines the compressibility of 
      the data based on a comparison of the number of bits required to 
      represent a segment of the data stream before and after 
      compression."
::= { tdmaBcV42BisOperEntry 2 }

tdmaBcV42BisP0CompressionDirection OBJECT-TYPE
   SYNTAX     INTEGER  {
                 noCompression(0),
                 compInitrResp(1),
                 compRespInitr(2),
                 compBoth(3) }
   ACCESS     read-only
   STATUS     mandatory
   DESCRIPTION
     "This attribute indicates the direction in which V.42bis is active, 
      negotiated at link setup by the data link protocol through Exchange 
      Identification (XID) negotiation of parameter P0 (compression 
      direction). The value used for XID negotiations can be provisioned 
      via TdmaCs/* V42bis. This attribute has one of the following 
      values:
      noCompression: No data compression.
      compInitrResp: The data sent by the IWF to the other entity is 
      compressed.
      compRespInitr: The data received by the IWF from the other entity 
      is compressed.
      compBoth: compression in both directions."
::= { tdmaBcV42BisOperEntry 3 }

tdmaBcV42BisP1MaximumCodewords OBJECT-TYPE
   SYNTAX     Unsigned32 (0..4096)
   ACCESS     read-only
   STATUS     mandatory
   DESCRIPTION
     "This attribute indicates the maximum number of codewords in the 
      dictionary negotiated at link setup by the data link protocol by way 
      of the Exchange Identification (XID) negotiation of parameter P1 
      (number of codewords). The value used for XID negotiations can be 
      provisioned via TdmaCs/* V42bis."
::= { tdmaBcV42BisOperEntry 4 }

tdmaBcV42BisP2MaximumStringSize OBJECT-TYPE
   SYNTAX     Unsigned32 (6..250)
   ACCESS     read-only
   STATUS     mandatory
   DESCRIPTION
     "This attribute indicates the maximum number of characters allowed 
      in a string represented by a codeword negotiated at link setup by the 
      data link protocol by way of the Exchange Identification (XID) 
      negotiation of parameter P2 (maximum string size). The value used 
      for XID negotiations can be provisioned via TdmaCs/* V42bis."
::= { tdmaBcV42BisOperEntry 5 }

tdmaBcV42BisLastDecodeError OBJECT-TYPE
   SYNTAX     INTEGER  {
                 none(0),
                 badStepup(1),
                 codewordEqC1(2),
                 emptyCodeword(3),
                 rsvdCommand(4),
                 generalError(5) }
   ACCESS     read-only
   STATUS     mandatory
   DESCRIPTION
     "This attribute indicates last error found by the decoder. This 
      attribute has one of the following values:
      none: No errors found.
      badStepup: Receipt of STEPUP (step up codeword size) codeword 
      when it would cause C2 (current code word size) to exceed N1 
      (maximum code word size).
      codewordEqC1: Receipt of a codeword, at any time, equal to C1 
      (next empty dictionary entry).
      emptyCodeword: Receipt of a codeword representing an empty 
      dictionary entry. 
      reservedCommand: Receipt of a reserved command code.
      generalError: Receipt of any other error.
      The action taken by V.42bis on detecting an error is provisioned via 
      TdmaCs/* V42bis."
   DEFVAL     { none }
::= { tdmaBcV42BisOperEntry 6 }

tdmaBcV42BisCompRatioEncoder OBJECT-TYPE
   SYNTAX     FixedPoint2 (0..30000)
   ACCESS     read-only
   STATUS     mandatory
   DESCRIPTION
     "This attribute indicates the number of uncompressed bytes divided 
      by the number of compressed bytes. A value greater than one means 
      that the data is being compressed. This is the compression ratio 
      achieved by the V.42bis encoder running on the Passport. This 
      attribute is relevant for both protocol modes transparent and 
      compressed as the encoder switches between the two modes."
::= { tdmaBcV42BisOperEntry 7 }

tdmaBcV42BisCompRatioDecoder OBJECT-TYPE
   SYNTAX     FixedPoint2 (0..30000)
   ACCESS     read-only
   STATUS     mandatory
   DESCRIPTION
     "This attribute indicates the number of uncompressed bytes divided 
      by the number of compressed bytes. A value greater than one means 
      that the data is being compressed. This is the compression ratio 
      achieved by the V.42bis encoder at the mobile or PSTN. This 
      attribute is relevant for both protocol modes transparent and 
      compressed as the encoder switches between the two modes."
::= { tdmaBcV42BisOperEntry 8 }

tdmaBcV42BisStatsTable OBJECT-TYPE
   SYNTAX     SEQUENCE OF TdmaBcV42BisStatsEntry
   ACCESS     not-accessible
   STATUS     mandatory
   DESCRIPTION
     "This group contains statistical attributes that measure the 
      performance of IwfV42bis."
::= { tdmaBcV42Bis 11 }

tdmaBcV42BisStatsEntry OBJECT-TYPE
   SYNTAX     TdmaBcV42BisStatsEntry
   ACCESS     not-accessible
   STATUS     mandatory
   DESCRIPTION
     "An entry in the tdmaBcV42BisStatsTable."
   INDEX {
      tdmaBcCsIndex,
      tdmaBcBcIndex,
      tdmaBcV42BisIndex }
::= { tdmaBcV42BisStatsTable 1 }

TdmaBcV42BisStatsEntry ::= SEQUENCE {
   tdmaBcV42BisModeChangesEncode
      Counter32,
   tdmaBcV42BisModeChangesDecode
      Counter32,
   tdmaBcV42BisResetsEncode
      Counter32,
   tdmaBcV42BisResetsDecode
      Counter32,
   tdmaBcV42BisReinitializations
      Counter32,
   tdmaBcV42BisErrorsInDecode
      Counter32 }

tdmaBcV42BisModeChangesEncode OBJECT-TYPE
   SYNTAX     Counter32 
   ACCESS     read-only
   STATUS     mandatory
   DESCRIPTION
     "This attribute counts the number of mode changes (from transparent 
      to compressed or from compressed to transparent) by the encoder.
      The counter wraps when it exceeds the maximum value."
::= { tdmaBcV42BisStatsEntry 1 }

tdmaBcV42BisModeChangesDecode OBJECT-TYPE
   SYNTAX     Counter32 
   ACCESS     read-only
   STATUS     mandatory
   DESCRIPTION
     "This attribute counts the number of mode changes (from transparent 
      to compressed or from compressed to transparent) by the decoder. 
      The mode changes are determined by the encoder at the mobile or 
      the PSTN.
      The counter wraps when it exceeds the maximum value."
::= { tdmaBcV42BisStatsEntry 2 }

tdmaBcV42BisResetsEncode OBJECT-TYPE
   SYNTAX     Counter32 
   ACCESS     read-only
   STATUS     mandatory
   DESCRIPTION
     "This attribute counts the number of resets sent by the encoder. A 
      reset is a command code sent by the encoder to force dictionary 
      reinitialization.
      The counter wraps when it exceeds the maximum value."
::= { tdmaBcV42BisStatsEntry 3 }

tdmaBcV42BisResetsDecode OBJECT-TYPE
   SYNTAX     Counter32 
   ACCESS     read-only
   STATUS     mandatory
   DESCRIPTION
     "This attribute counts the number of resets received by the decoder. 
      A reset is a command code sent by the encoder to force dictionary 
      reinitialization. The resets of the decoder are determined by the 
      encoder at the mobile or PSTN.
      The counter wraps when it exceeds the maximum value."
::= { tdmaBcV42BisStatsEntry 4 }

tdmaBcV42BisReinitializations OBJECT-TYPE
   SYNTAX     Counter32 
   ACCESS     read-only
   STATUS     mandatory
   DESCRIPTION
     "This attribute counts the number of times V.42bis is reinitialized 
      because of a destructive break (a destructive break is a break that 
      causes data to be discarded) occurring on the error-corrected 
      connection initiated by either the mobile or PSTN.
      The counter wraps when it exceeds the maximum value."
::= { tdmaBcV42BisStatsEntry 5 }

tdmaBcV42BisErrorsInDecode OBJECT-TYPE
   SYNTAX     Counter32 
   ACCESS     read-only
   STATUS     mandatory
   DESCRIPTION
     "This attribute counts the number of errors found by the decoder. 
      The errors could be any of the following:
      1.Receipt of STEPUP (step up codeword size) codeword when it 
      would cause C2 (current code word size) to exceed N1 (maximum 
      code word size).
      2. Receipt of a codeword, at any time, equal to C1 (next empty 
      dictionary entry).
      3. Receipt of a codeword representing an empty dictionary entry.
      4. Receipt of a reserved command code.
      5. Receipt of any other error.
      The counter wraps when it exceeds the maximum value.
      The action taken by V.42bis on detecting any of these errors is 
      provisioned via TdmaCs/* V42bis."
::= { tdmaBcV42BisStatsEntry 6 }


-- TdmaBc/<csIndex>,<bcIndex> UpperRelay
-- This component represents the group of measurements for the 
-- Upper Relay function established for each half of a DMS-MTX 
-- IWF asynchronous data or fax call (internally between the two 
-- TdmaIwfBearerChannels involved in a call) from this particular 
-- TdmaIwfBearerChannel perspective.

tdmaBcUr OBJECT IDENTIFIER ::= { tdmaBc 10 }



tdmaBcUrRowStatusTable OBJECT-TYPE
   SYNTAX     SEQUENCE OF TdmaBcUrRowStatusEntry
   ACCESS     not-accessible
   STATUS     mandatory
   DESCRIPTION
     "This entry controls the addition and deletion of 
      tdmaBcUr components."
::= { tdmaBcUr 1 }

tdmaBcUrRowStatusEntry OBJECT-TYPE
   SYNTAX     TdmaBcUrRowStatusEntry
   ACCESS     not-accessible
   STATUS     mandatory
   DESCRIPTION
     "A single entry in the table represents a single 
      tdmaBcUr component."
   INDEX {
      tdmaBcCsIndex,
      tdmaBcBcIndex,
      tdmaBcUrIndex }
::= { tdmaBcUrRowStatusTable 1 }

TdmaBcUrRowStatusEntry ::= SEQUENCE {
   tdmaBcUrRowStatus
      RowStatus,
   tdmaBcUrComponentName
      DisplayString,
   tdmaBcUrStorageType
      StorageType,
   tdmaBcUrIndex
      NonReplicated }

tdmaBcUrRowStatus OBJECT-TYPE
   SYNTAX     RowStatus 
   ACCESS     read-only
   STATUS     mandatory
   DESCRIPTION
     "This variable is used as the basis for SNMP naming of
      tdmaBcUr components.
      These components cannot be added nor deleted."
::= { tdmaBcUrRowStatusEntry 1 }

tdmaBcUrComponentName OBJECT-TYPE
   SYNTAX     DisplayString 
   ACCESS     read-only
   STATUS     mandatory
   DESCRIPTION
     "This variable provides the component's string name for
      use with the ASCII Console Interface"
::= { tdmaBcUrRowStatusEntry 2 }

tdmaBcUrStorageType OBJECT-TYPE
   SYNTAX     StorageType 
   ACCESS     read-only
   STATUS     mandatory
   DESCRIPTION
     "This variable represents the storage type value for the
      tdmaBcUr tables."
::= { tdmaBcUrRowStatusEntry 4 }

tdmaBcUrIndex OBJECT-TYPE
   SYNTAX     NonReplicated 
   ACCESS     not-accessible
   STATUS     mandatory
   DESCRIPTION
     "This variable represents the index for the tdmaBcUr tables."
::= { tdmaBcUrRowStatusEntry 10 }

tdmaBcUrOperTable OBJECT-TYPE
   SYNTAX     SEQUENCE OF TdmaBcUrOperEntry
   ACCESS     not-accessible
   STATUS     mandatory
   DESCRIPTION
     "This group contains operational attributes that measure the 
      performance of the UpperRelay."
::= { tdmaBcUr 10 }

tdmaBcUrOperEntry OBJECT-TYPE
   SYNTAX     TdmaBcUrOperEntry
   ACCESS     not-accessible
   STATUS     mandatory
   DESCRIPTION
     "An entry in the tdmaBcUrOperTable."
   INDEX {
      tdmaBcCsIndex,
      tdmaBcBcIndex,
      tdmaBcUrIndex }
::= { tdmaBcUrOperTable 1 }

TdmaBcUrOperEntry ::= SEQUENCE {
   tdmaBcUrRxBufferSize
      Unsigned32,
   tdmaBcUrTxFlowControlState
      INTEGER,
   tdmaBcUrRxFlowControlState
      INTEGER }

tdmaBcUrRxBufferSize OBJECT-TYPE
   SYNTAX     Unsigned32 (0..65535)
   ACCESS     read-only
   STATUS     mandatory
   DESCRIPTION
     "This attribute indicates the size of the receive flow control buffer.
      This attribute may be viewed via TdmaBc/*,*,*,* UpperRelay."
::= { tdmaBcUrOperEntry 1 }

tdmaBcUrTxFlowControlState OBJECT-TYPE
   SYNTAX     INTEGER  {
                 active(0),
                 inactive(1) }
   ACCESS     read-only
   STATUS     mandatory
   DESCRIPTION
     "This attribute indicates whether the transmit flow control is active or 
      not. This attribute has one of the following values:
      active: The transmit flow control is active.
      inactive: The transmit flow control is inactive.
      This attribute may be viewed via TdmaBc/*,*,*,* UpperRelay."
::= { tdmaBcUrOperEntry 2 }

tdmaBcUrRxFlowControlState OBJECT-TYPE
   SYNTAX     INTEGER  {
                 active(0),
                 inactive(1) }
   ACCESS     read-only
   STATUS     mandatory
   DESCRIPTION
     "This attribute indicates whether the receive flow control is active or 
      not. This attribute has one of the following values:
      active: The receive flow control is active.
      inactive: The receive flow control is inactive.
      This attribute may be viewed via TdmaBc/*,*,*,* UpperRelay."
::= { tdmaBcUrOperEntry 3 }

tdmaBcUrStatsTable OBJECT-TYPE
   SYNTAX     SEQUENCE OF TdmaBcUrStatsEntry
   ACCESS     not-accessible
   STATUS     mandatory
   DESCRIPTION
     "This group contains operational attributes that measure the 
      performance of the UpperRelay."
::= { tdmaBcUr 11 }

tdmaBcUrStatsEntry OBJECT-TYPE
   SYNTAX     TdmaBcUrStatsEntry
   ACCESS     not-accessible
   STATUS     mandatory
   DESCRIPTION
     "An entry in the tdmaBcUrStatsTable."
   INDEX {
      tdmaBcCsIndex,
      tdmaBcBcIndex,
      tdmaBcUrIndex }
::= { tdmaBcUrStatsTable 1 }

TdmaBcUrStatsEntry ::= SEQUENCE {
   tdmaBcUrTxFrames
      Counter32,
   tdmaBcUrRxFrames
      Counter32,
   tdmaBcUrUnacknowledgedFrames
      Counter32,
   tdmaBcUrCumUnacknowledgedFrames
      Counter32 }

tdmaBcUrTxFrames OBJECT-TYPE
   SYNTAX     Counter32 
   ACCESS     read-only
   STATUS     mandatory
   DESCRIPTION
     "This attribute counts the number of frames that are sent in the 
      transmit direction. The counter wraps when it exceeds the 
      maximum value.
      The counter wraps when it exceeds the maximum value."
::= { tdmaBcUrStatsEntry 1 }

tdmaBcUrRxFrames OBJECT-TYPE
   SYNTAX     Counter32 
   ACCESS     read-only
   STATUS     mandatory
   DESCRIPTION
     "This attribute counts the number of frames that are sent in the 
      receive direction.
      The counter wraps when it exceeds the maximum value."
::= { tdmaBcUrStatsEntry 2 }

tdmaBcUrUnacknowledgedFrames OBJECT-TYPE
   SYNTAX     Counter32 
   ACCESS     read-only
   STATUS     mandatory
   DESCRIPTION
     "This attribute indicates the current number of frames sent that have 
      not been acknowledged for this instance of the UpperRelay.
      The counter wraps when it exceeds the maximum value."
::= { tdmaBcUrStatsEntry 3 }

tdmaBcUrCumUnacknowledgedFrames OBJECT-TYPE
   SYNTAX     Counter32 
   ACCESS     read-only
   STATUS     mandatory
   DESCRIPTION
     "This attribute is the total number of unacknowledged frames for this 
      instance of the UpperRelay. It is not reset when a new call starts."
::= { tdmaBcUrStatsEntry 4 }




-- 
-- Version and Compliance statements
-- 



-- Object-Group Statement:
-- A list of all current accessible leaf objects.

-- OBJECTS { tdmaBcCustomerIdentifier,
--           tdmaCsVirtualRouterName,
--           tdmaBcV42BisStorageType,
--           tdmaCsLpStorageType,
--           tdmaBcFramerUsageState,
--           tdmaCsV42TxN401FrameSize,
--           tdmaCsFaxStorageType,
--           tdmaBcRlp1RxFrames,
--           tdmaCsCallsReleasedAbnormal,
--           tdmaBcUsageState,
--           tdmaBcRlp1RowStatus,
--           tdmaBcFaxActiveMode,
--           tdmaBcModemTxBytes,
--           tdmaBcFramerInterfaceName,
--           tdmaBcRlp1T1ResponseTimer,
--           tdmaBcFramerFramingType,
--           tdmaCsSupportedService,
--           tdmaBcUrComponentName,
--           tdmaCsV42TxKWindowSize,
--           tdmaBcFramerOperationalState,
--           tdmaCsV42ComponentName,
--           tdmaBcModemComponentName,
--           tdmaCsV42FcsLength,
--           tdmaBcFaxMessageRate,
--           tdmaBcV42T1AckTimeouts,
--           tdmaCsModemStorageType,
--           tdmaBcOperationalState,
--           tdmaCsLpRowStatus,
--           tdmaBcModemFramingErrors,
--           tdmaCsLpModemsSupported,
--           tdmaBcModemRxBytes,
--           tdmaBcV42BisP0CompressionDirection,
--           tdmaBcV42BisProtocolModeDecoder,
--           tdmaCsFaxRowStatus,
--           tdmaCsDceComponentName,
--           tdmaBcV42RemoteBusyIndications,
--           tdmaCsV42RxN401FrameSize,
--           tdmaBcV42V42BisActiveInCall,
--           tdmaCsLpComponentName,
--           tdmaBcModemModemAlgorithmInUse,
--           tdmaCsTIwf1,
--           tdmaBcLastResponseCode,
--           tdmaCsCurrentCalls,
--           tdmaBcV42BisModeChangesDecode,
--           tdmaCsDscK0Ll0WindowSize,
--           tdmaBcV42BisProtocolModeEncoder,
--           tdmaCsT999,
--           tdmaCsV42RxKWindowSize,
--           tdmaBcV42ComponentName,
--           tdmaCsModemRowStatus,
--           tdmaBcModemMobileSideFlowControlState,
--           tdmaBcRlp1Layer3L1ReqWinSize1,
--           tdmaCsRlp1T3PeerAckTimer,
--           tdmaCsLpActiveCalls,
--           tdmaBcDscComponentName,
--           tdmaBcV42BisReinitializations,
--           tdmaBcV42TxN401FrameSize,
--           tdmaBcFaxStorageType,
--           tdmaCsComponentName,
--           tdmaBcV42TxKWindowSize,
--           tdmaCsV42BisP1MaximumCodewords,
--           tdmaBcCallType,
--           tdmaBcModemProtocolState,
--           tdmaBcModemAutobaud,
--           tdmaBcV42BisLastDecodeError,
--           tdmaBcUrRowStatus,
--           tdmaBcModemOutbandBreak,
--           tdmaCsVoiceLaw,
--           tdmaCsModemComponentName,
--           tdmaCsRlp1ComponentName,
--           tdmaCsV42StorageType,
--           tdmaBcModemStorageType,
--           tdmaCsCallsSetUp,
--           tdmaBcModemRate,
--           tdmaCsV42BisP0CompressionDirection,
--           tdmaCsDscStorageType,
--           tdmaBcFramerTxFrames,
--           tdmaBcV42ProtocolState,
--           tdmaBcV42RxIFrames,
--           tdmaCsV42T402AckDelayTimer,
--           tdmaCsV42BisActionOnError,
--           tdmaCsT308,
--           tdmaCsV42T400DetectTimer,
--           tdmaCsDceStorageType,
--           tdmaBcV42BisCompRatioDecoder,
--           tdmaBcV42V42ActiveInCall,
--           tdmaBcV42CrcErrorsRx,
--           tdmaCsV42N400RetransLimit,
--           tdmaCsRlp1T2LinkActivityTimer,
--           tdmaCsV42BisRowStatus,
--           tdmaBcV42BisModeChangesEncode,
--           tdmaBcDscRxBytes,
--           tdmaBcFaxComponentName,
--           tdmaBcV42RxKWindowSize,
--           tdmaCsCommentText,
--           tdmaBcModemRowStatus,
--           tdmaBcRlp1T3PeerAckTimer,
--           tdmaCsV42BisP2MaximumStringSize,
--           tdmaBcModemOutbandFlowControl,
--           tdmaCsDscRowStatus,
--           tdmaBcUrRxFrames,
--           tdmaBcFramerComponentName,
--           tdmaBcUrTxFlowControlState,
--           tdmaBcV42BisResetsDecode,
--           tdmaBcFramerRxFrames,
--           tdmaBcComponentName,
--           tdmaCsDceRowStatus,
--           tdmaCsDscK1Ll1WindowSize,
--           tdmaBcV42BisP1MaximumCodewords,
--           tdmaCsStorageType,
--           tdmaCsCallsRequested,
--           tdmaCsDscComponentName,
--           tdmaBcRlp1ComponentName,
--           tdmaBcV42BadFramesRx,
--           tdmaCsLpConfiguredBearerChannels,
--           tdmaCsTIwf2,
--           tdmaCsV42BisComponentName,
--           tdmaBcV42TxIFrames,
--           tdmaBcFramerRxBytes,
--           tdmaCsSupportedTechnology,
--           tdmaBcRlp1TxFrames,
--           tdmaCsT305,
--           tdmaCsRlp1StorageType,
--           tdmaBcUrCumUnacknowledgedFrames,
--           tdmaBcDscStorageType,
--           tdmaCsAdminState,
--           tdmaBcDscTxBytes,
--           tdmaBcRlp1BadRxFrames,
--           tdmaBcUrRxFlowControlState,
--           tdmaBcDscRowStatus,
--           tdmaBcV42BisCompRatioEncoder,
--           tdmaCsRowStatus,
--           tdmaBcFaxProtocolState,
--           tdmaCsT313,
--           tdmaBcState,
--           tdmaCsV42T401AckTimer,
--           tdmaBcUrTxFrames,
--           tdmaBcModemAsyncMode,
--           tdmaCsFaxComponentName,
--           tdmaCsCustomerIdentifier,
--           tdmaCsCallsReleasedNormal,
--           tdmaBcV42RowStatus,
--           tdmaCsMscIpAddress,
--           tdmaCsUsageState,
--           tdmaCsRlp1RowStatus,
--           tdmaBcMateBearerChannel,
--           tdmaBcModemPstnSideFlowControlState,
--           tdmaCsT303,
--           tdmaBcV42BisResetsEncode,
--           tdmaCsRlp1T1ResponseTimer,
--           tdmaBcDscP1CompressionMaximumCodewords,
--           tdmaCsV42T403IdleProbeTimer,
--           tdmaBcFramerStorageType,
--           tdmaCsErroredLFrames,
--           tdmaBcFaxRowStatus,
--           tdmaBcV42BisRowStatus,
--           tdmaBcUrUnacknowledgedFrames,
--           tdmaBcV42BisErrorsInDecode,
--           tdmaBcStorageType,
--           tdmaBcV42LocalBusyIndications,
--           tdmaCsOperationalState,
--           tdmaBcRlp1StorageType,
--           tdmaBcV42StorageType,
--           tdmaBcV42RxN401FrameSize,
--           tdmaBcV42RxIBytes,
--           tdmaCsV42RowStatus,
--           tdmaBcV42TxIBytes,
--           tdmaBcV42BisComponentName,
--           tdmaCsV42BisStorageType,
--           tdmaBcFramerAdminState,
--           tdmaBcDscP2CompressionMaximumCharacters,
--           tdmaBcFaxTxPagesToMobile,
--           tdmaBcV42BisP2MaximumStringSize,
--           tdmaBcV42RetransmittedFrames,
--           tdmaBcRlp1Layer3L0ReqWinSize,
--           tdmaBcAdminState,
--           tdmaBcRlp1T2LinkActivityTimer,
--           tdmaBcFramerRowStatus,
--           tdmaBcUrStorageType,
--           tdmaBcDscP0CompressionDirection,
--           tdmaBcModemVoiceLaw,
--           tdmaBcRowStatus,
--           tdmaBcFaxRxPagesFromMobile,
--           tdmaBcUrRxBufferSize }
-- STATUS  mandatory
-- DESCRIPTION
--   "A list of all current accessible leaf objects."

tdmaIwfGroup OBJECT IDENTIFIER ::= { tdmaIwfMIB 1 }
tdmaIwfGroupBE OBJECT IDENTIFIER ::= { tdmaIwfGroup 5 }
tdmaIwfGroupBE01 OBJECT IDENTIFIER ::= { tdmaIwfGroupBE 2 }
tdmaIwfGroupBE01A OBJECT IDENTIFIER ::= { tdmaIwfGroupBE01 2 }



-- Agent-Capabilities Statement:

-- PRODUCT-RELEASE "Passport Release 7.0 TdmaIwf."
-- STATUS          mandatory
-- DESCRIPTION     "TdmaIwf MIB: MIB Version BE01A,
--                  Software Version BG00S4C."
-- SUPPORTS        Nortel-Magellan-Passport-TdmaIwfMIB
--    INCLUDES     { tdmaIwfGroupBE01A }

tdmaIwfCapabilities OBJECT IDENTIFIER ::= { tdmaIwfMIB 3 }
tdmaIwfCapabilitiesBE OBJECT IDENTIFIER ::= { tdmaIwfCapabilities 5 }
tdmaIwfCapabilitiesBE01 OBJECT IDENTIFIER ::= { tdmaIwfCapabilitiesBE 2 }
tdmaIwfCapabilitiesBE01A OBJECT IDENTIFIER ::= { tdmaIwfCapabilitiesBE01 2 }





END
