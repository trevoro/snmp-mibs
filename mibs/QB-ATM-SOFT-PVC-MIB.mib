--	Quantum Bridge ATM Management Information Base
--	Version 1.0.0
--	July 7, 2000
--
--	Quantum Bridge Corporation
--	One High Street
--	North Andover, MA 01845
--	(978) 688-9100
--
----------------------------------------------------------------------------------------
--				
--  09/1/2000 - akoifman    	Original version
--
----------------------------------------------------------------------------------------
--

QB-ATM-SOFT-PVC-MIB DEFINITIONS ::= BEGIN

IMPORTS
	enterprises				FROM RFC1155-SMI
	MODULE-IDENTITY, OBJECT-TYPE,
	NOTIFICATION-TYPE,
	Counter32, Gauge32			FROM SNMPv2-SMI
	TEXTUAL-CONVENTION, DisplayString, RowStatus,
	TruthValue, TimeStamp			FROM SNMPv2-TC
	MODULE-COMPLIANCE, OBJECT-GROUP		FROM SNMPv2-CONF
	ifIndex,InterfaceIndex			FROM IF-MIB
	atmVplVpi, atmVclVpi,
	atmVclVci				FROM ATM-MIB
	qbVTConfVTId                            FROM QB-VT15-MIB
	
	AtmVpIdentifier, AtmVcIdentifier,
	AtmVorXAdminStatus, AtmVorXLastChange,
	AtmVorXOperStatus, atmNoClpNoScr        FROM ATM-TC-MIB
	atmSoftPVccEntry, atmSoftPVpcEntry	FROM ATM-SOFT-PVC-MIB
	qbMibs
						FROM QUANTUMBRIDGE-REG
        AtmAddr, AtmConnKind, AtmConnCastType,
        AtmServiceCategory, AtmTrafficDescrParamIndex,
        AtmVpIdentifier, AtmVcIdentifier,
        AtmVorXAdminStatus, AtmVorXLastChange,
        AtmVorXOperStatus, atmNoClpNoScr
						FROM ATM-TC-MIB
	qbSysModuleSlot				FROM QBSYS-SYSTEM-MIB;

qbAtmSoftPvcMIB MODULE-IDENTITY
	LAST-UPDATED	"9606210000Z"
	ORGANIZATION	"Quantum Bridge Inc."
	CONTACT-INFO
		"akoifman@quantumbridge.com"
	DESCRIPTION
		"QB ATM Soft PVC MIB"
	::= { qbMibs 12 }


qbAtmSoftPvcMIBObjects  OBJECT IDENTIFIER ::= { qbAtmSoftPvcMIB 1 }
qbAtmSoftPvcConformance OBJECT IDENTIFIER ::= { qbAtmSoftPvcMIB 2 }


qbAtmSoftPvcBaseGroup	OBJECT IDENTIFIER ::= { qbAtmSoftPvcMIB 3}


--
-- Table to map ifIndex to VPI/VCI for non-native interfaces
--

qbIfIndexToVclTable	OBJECT-TYPE
	SYNTAX	SEQUENCE OF QbIfIndexToVclEntry
	MAX-ACCESS	not-accessible
	STATUS	current
	DESCRIPTION
		"The QB table to map ifIndex to VPI/VCI for 
		 non-native interfaces "
	::= { qbAtmSoftPvcMIBObjects 1 }


qbIfIndexToVclEntry OBJECT-TYPE
        SYNTAX  QbIfIndexToVclEntry
	MAX-ACCESS	not-accessible
	STATUS		current
	DESCRIPTION
		"Contains VPI, VCI for hidden interfaces"
	INDEX { ifIndex, qbVTConfVTId }
	::= {qbIfIndexToVclTable 1}

QbIfIndexToVclEntry ::=
	SEQUENCE {
		qbIfIndexToVclIfIndex		InterfaceIndex,
		qbIfIndexToVclVpi		AtmVpIdentifier,
		qbIfIndexToVclVci		AtmVcIdentifier
		}

qbIfIndexToVclIfIndex OBJECT-TYPE
	SYNTAX      InterfaceIndex
	MAX-ACCESS  read-only
	STATUS      current
	DESCRIPTION
		"ifIndex value for non-native ATM interfaces."
    ::= { qbIfIndexToVclEntry 1 }

qbIfIndexToVclVpi     OBJECT-TYPE
    SYNTAX         AtmVpIdentifier
    MAX-ACCESS     read-only
    STATUS         current
    DESCRIPTION
           "The VPI value of the VCL."
    ::= { qbIfIndexToVclEntry 2}

qbIfIndexToVclVci        OBJECT-TYPE
    SYNTAX         AtmVcIdentifier
    MAX-ACCESS     read-only
    STATUS         current
    DESCRIPTION
           "The VCI value of the VCL."
    ::= { qbIfIndexToVclEntry 3}



--
-- QB Extension of the Table to manage Soft PVCCs.
--
qbAtmSoftPVccTable	OBJECT-TYPE
	SYNTAX	SEQUENCE OF QbAtmSoftPVccEntry
	MAX-ACCESS	not-accessible
	STATUS	current
	DESCRIPTION
		"The QB table with extensions to atmSoftPVccTable"
	::= { qbAtmSoftPvcMIBObjects 2 }



qbAtmSoftPVccEntry OBJECT-TYPE 
	SYNTAX QbAtmSoftPVccEntry 
        MAX-ACCESS not-accessible 
        STATUS current 
        DESCRIPTION "Entry in qbAtmSoftPVccTable" 
	AUGMENTS { atmSoftPVccEntry }
	::= { qbAtmSoftPVccTable 1 }


QbAtmSoftPVccEntry ::=
	SEQUENCE	{
		qbAtmSoftPVccName		DisplayString,
		qbAtmSoftPVccType		INTEGER,
		qbAtmSoftPVccIfIndex		InterfaceIndex,
		qbAtmSoftPVccVtIndex		INTEGER
		}


qbAtmSoftPVccName OBJECT-TYPE
	SYNTAX      DisplayString (SIZE (0..20))
	MAX-ACCESS  read-create
	STATUS      current
	DESCRIPTION
		"A textual description for the SPVC name."
	DEFVAL  { "" }
    ::= { qbAtmSoftPVccEntry 1 }


qbAtmSoftPVccType OBJECT-TYPE
	SYNTAX      INTEGER {
			 native (1),
			 non-native (2)
		    }
	MAX-ACCESS  read-create
	STATUS      current
	DESCRIPTION
		"Value for the interface type.  
                 Native ATM - Q155, S622; 
		 non-native - E1, DS1, ENET, VT"
    ::= { qbAtmSoftPVccEntry 2 }


qbAtmSoftPVccIfIndex OBJECT-TYPE
	SYNTAX      InterfaceIndex
	MAX-ACCESS  read-create
	STATUS      current
	DESCRIPTION
		"ifIndex value for IOT interface.  This
	         value is not used for native ATM interfaces."
    ::= { qbAtmSoftPVccEntry 3 }

qbAtmSoftPVccVtIndex OBJECT-TYPE
	SYNTAX      INTEGER (0..2147483647)
	MAX-ACCESS  read-create
	STATUS      current
	DESCRIPTION
		"Address information for a VT card.  This
	         value is used for VT card only."
    ::= { qbAtmSoftPVccEntry 4 }

--
-- QB Extension of the Table to manage Soft PVpcs.
--

qbAtmSoftPVpcTable	OBJECT-TYPE
	SYNTAX	SEQUENCE OF QbAtmSoftPVpcEntry
	MAX-ACCESS	not-accessible
	STATUS	current
	DESCRIPTION
		"The QB table with extensions to atmSoftPVpcTable"
	::= { qbAtmSoftPvcMIBObjects 3 }


qbAtmSoftPVpcEntry	OBJECT-TYPE
	SYNTAX	QbAtmSoftPVpcEntry
	MAX-ACCESS	not-accessible
	STATUS	current
	DESCRIPTION
		"Entry in qbAtmSoftPVpcTable"
	AUGMENTS    { atmSoftPVpcEntry }
	::= { qbAtmSoftPVpcTable 1 }


QbAtmSoftPVpcEntry ::=
	SEQUENCE	{
			qbAtmSoftPVpcName			DisplayString
			}


qbAtmSoftPVpcName OBJECT-TYPE
	SYNTAX      DisplayString (SIZE (0..20))
	MAX-ACCESS  read-create
	STATUS      current
	DESCRIPTION
		"A textual description for the SPVC name."
	DEFVAL  { "" }
    ::= { qbAtmSoftPVpcEntry 1 }


-- ****************************************************************
-- Conformance Information
-- ****************************************************************


   qbSpvcCompliances OBJECT IDENTIFIER ::= { qbAtmSoftPvcConformance 1 }
   qbAtmGroups       OBJECT IDENTIFIER ::= { qbAtmSoftPvcConformance 2 }

--
-- Compliance Statements   ???
--

   qbSpvcCompliance MODULE-COMPLIANCE
    STATUS      current
    DESCRIPTION
        "The compliance statement for all agents that support this
        MIB. A compliant agent implements all objects defined in this
        MIB."
    MODULE  -- this module
    MANDATORY-GROUPS {
        qbSpvcAllGroup
    }
    ::= { qbSpvcCompliances 1 }

--
-- All Object Groups
--
   qbSpvcAllGroup OBJECT-GROUP
		 OBJECTS {
		 qbAtmSoftPVccName,
		 qbAtmSoftPVpcName
    }
    STATUS      current
    DESCRIPTION
        "The set of all accessible objects in this MIB."
    ::= { qbAtmGroups 1 }



END
