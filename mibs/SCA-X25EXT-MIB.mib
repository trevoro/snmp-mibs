SCA-X25EXT-MIB DEFINITIONS ::= BEGIN

-- Copyright (C) 1997 Intel Corporation. All rights reserved.
--
-- X.25 MIB extentions, 06-04-1997
--
-- This mib is an Intel specific extension to RFC 1382.
--
-- Change History:
-- <date> <change>
--

IMPORTS
	Counter FROM RFC1155-SMI
    scanet                     FROM SCANET-MIB
    OBJECT-TYPE                FROM RFC-1212;


    IfIndexType     ::= INTEGER (1..2147483647)


  x25ext             OBJECT IDENTIFIER ::= { scanet 51 }
  x25extCircuit      OBJECT IDENTIFIER ::= { x25ext 1 }


x25extCircuitTable OBJECT-TYPE
    SYNTAX SEQUENCE OF X25extCircuitEntry
    ACCESS not-accessible
    STATUS mandatory
    DESCRIPTION "These objects contain general information
                 about a specific circuit of an X.25 PLE."
    ::= { x25extCircuit 1 }

x25extCircuitEntry OBJECT-TYPE
    SYNTAX X25extCircuitEntry
    ACCESS not-accessible
    STATUS mandatory
    DESCRIPTION "Entries of x25extCircuitTable."
    INDEX { x25extCircuitIndex, x25extCircuitChannel }
    ::= { x25extCircuitTable 1 }

X25extCircuitEntry ::= SEQUENCE {
                        x25extCircuitIndex
                           IfIndexType,
                        x25extCircuitChannel
                           INTEGER,
                        x25extCircuitLogicalIndex
                           IfIndexType,
                        x25extCircuitPacketSize
                           INTEGER,
                        x25extCircuitWindowSize
                           INTEGER,
                        x25extCircuitTimeout
                           INTEGER,
                        x25extCircuitOutResets
                           Counter,
                        x25extCircuitOutFlowStuckResets
                           Counter
                        }

x25extCircuitIndex OBJECT-TYPE
    SYNTAX IfIndexType
    ACCESS read-only
    STATUS mandatory
    DESCRIPTION "The ifIndex value for the X.25 PLE Interface."
    ::= { x25extCircuitEntry 1 }

x25extCircuitChannel OBJECT-TYPE
    SYNTAX INTEGER (0..4095)
    ACCESS read-only
    STATUS mandatory
    DESCRIPTION "The channel number for this circuit."
    ::= { x25extCircuitEntry 2 }

x25extCircuitLogicalIndex OBJECT-TYPE
    SYNTAX IfIndexType
    ACCESS read-only
    STATUS mandatory
    DESCRIPTION "The ifIndex for a virtual ifEntry accociatedwith this circuit.
                 The same as x25extCircuitIndex if no ifEntry is associated
                 with the circuit."
    ::= { x25extCircuitEntry 3 }

x25extCircuitPacketSize OBJECT-TYPE
    SYNTAX INTEGER (0..4096)
    ACCESS read-only
    STATUS mandatory
    DESCRIPTION "The packet size in octets used by this circuit."
    ::= { x25extCircuitEntry 4 }

x25extCircuitWindowSize OBJECT-TYPE
    SYNTAX INTEGER (0..127)
    ACCESS read-only
    STATUS mandatory
    DESCRIPTION "The window size used by this circuit."
    ::= { x25extCircuitEntry 5 }

x25extCircuitTimeout OBJECT-TYPE
    SYNTAX INTEGER
    ACCESS read-only
    STATUS mandatory
    DESCRIPTION "Seconds left before timeout of the current state.
                 If a call request is sent but no reply received
                 x25extCircuitTimeout will show how many seconds remains
                 before the call request is retransmitted.
                 If the link is up but the current window is 0
                 x25extCircuitTimeout will show how many seconds remains
                 before the link is reset and x25extCircuitOutFlowStuckResets
                 is incremented."
    ::= { x25extCircuitEntry 6 }

x25extCircuitOutResets OBJECT-TYPE
    SYNTAX Counter
    ACCESS read-only
    STATUS mandatory
    DESCRIPTION "Total number of resets sent on this circuit."
    ::= { x25extCircuitEntry 7 }

x25extCircuitOutFlowStuckResets OBJECT-TYPE
    SYNTAX Counter
    ACCESS read-only
    STATUS mandatory
    DESCRIPTION "Number of resets sent on this circuit because
                 the remote end did not acknoledge packets for a long time."
    ::= { x25extCircuitEntry 8 }

END
