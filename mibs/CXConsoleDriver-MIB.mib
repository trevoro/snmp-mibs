CXConsoleDriver-MIB DEFINITIONS ::= BEGIN

IMPORTS
	OBJECT-TYPE     FROM RFC-1212

--  Proprietary Imports
	cxConsoleDriver FROM CXProduct-SMI;

cxCdBaudRate    OBJECT-TYPE
	SYNTAX  INTEGER
	ACCESS  read-write
	STATUS  mandatory
	DESCRIPTION
"Determines the baud rate of the console port.

The setting of this object is dynamic. The console port immediately 
implements the option you enter.

Options:
9600

19200

38400

115200

Default Value: 9600

Configuration Changed: operative"

	DEFVAL          { 9600 }
	::= { cxConsoleDriver 1 }


cxCdCharSize            OBJECT-TYPE
	SYNTAX  INTEGER (7..8)
	ACCESS  read-write
	STATUS  mandatory
	DESCRIPTION
"Determines how many bits constitute a character for the console port.

Options: none - the value is fixed at 8

 Default Value: 8

Configuration Changed: none "
	DEFVAL          { 8 }
	::= { cxConsoleDriver 2 }


cxCdParity              OBJECT-TYPE
	SYNTAX  INTEGER {
				noParity        (1),
				evenParity      (2),
				oddParity       (3)
				}
	ACCESS  read-write
	STATUS  mandatory
	DESCRIPTION
"Determines the parity scheme the CPU uses to validate the characters it 
receives through the console port.

Options: none - the value is fixed at noParity

 Default Value: noParity

Configuration Changed: none "
	DEFVAL          { noParity }
	::= { cxConsoleDriver 3 }


cxCdStopBit             OBJECT-TYPE
	SYNTAX  INTEGER (1..2)
	ACCESS  read-write
	STATUS  mandatory
	DESCRIPTION
"Determines how many stop bits are at the end of each character the console 
port receives.

Options: none - the value is fixed at 1

Default Value: 1

Configuration Changed: none "
	DEFVAL          { 1 }
	::= { cxConsoleDriver 4 }
	
cxCdProtocol     OBJECT-TYPE
   SYNTAX   INTEGER  {
			localConsole (1),
			ppp  (2)
		     }
   ACCESS   read-write
   STATUS   mandatory
   DESCRIPTION
"Determines the protocol (configuration method) for the console port.

The setting of this object is dynamic. The console port immediately 
implements the option you enter. However, if you change the protocol you are 
currently using to configure the port your connection will be lost.

Options:
localConsole (1): you use this protocol when you attach a TTY terminal 
directly to the console port. This protocol requires you to use command line 
configuration. You also must enter a password to gain access to the 
configuration tables. You can define the password using the object 
uiPassword of the CXUserInterface Table.

ppp (2): you use this protocol when you are configuring via a windows-based 
application such as HP/OV (Hewlett Packard-OpenView).

Default Value: ppp (2)

Configuration Changed: operative"
   DEFVAL   { localConsole }
   ::= { cxConsoleDriver 5 }    


END
