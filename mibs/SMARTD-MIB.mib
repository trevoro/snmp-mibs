--==========================================================
--
-- MIB      : Smart devices                           Lucent Technologies 
--
-- Version  : 8.1.0	                                        02 May 1999
--
-- RCS Id   : Yigal Nehaysi
--
--==========================================================
--
-- Copyright 1999 Lucent Technologies, Ltd.
-- All Rights Reserved.
--
-- Reproduction of this document is authorized on condition
-- that the foregoing copyright notice is included.
--
-- This Lucent Technologies SNMP Management Information Base 
-- Specification embodies Lucent Technologies confidential and
-- proprietary intellectual property.  Lucent Technologies retains all
-- title and ownership in the Specification, including any revisions
--
-- It is Lucent Technologies intent to encourage the widespread use of this
-- Specification in connection with the management of Lucent Technologies
-- products.
-- Lucent Technologies grants vendors, end-users, and other interested parties
-- a non-exclusive license to use this Specification in connection
-- with the management of Lucent Technologies products.
--
-- This Specification is supplied "as is," and Lucent Technologies makes
-- no warranty, either express or implied, as to the use,
-- operation, condition, or performance of the Specification.
--
--==========================================================
--
-- RCS
--
-- Version 8.1.0
-- 02 May 1999
-- 1. Add new mib items to support by agents that are not a master 
-- smartGenSlotNumber, smartGenHubMgmtIfType and smartGenHubAddr - Yigal N. 
--
-- Revision A.    - 1. Change file name, new header file.
-- 15-Nov-1996   2. Submit smartDevices OIDs to gen.mib file
--
--==========================================================

SMARTD-MIB DEFINITIONS ::= BEGIN

IMPORTS
      Counter,TimeTicks
    FROM RFC1155-SMI
      OBJECT-TYPE
    FROM RFC-1212
      DisplayString, ifIndex
    FROM RFC1213-MIB
      lannet
    FROM GEN-MIB;

-- Some MIB Compilers need these two lines:
--  enterprises  OBJECT IDENTIFIER ::= 
--                { iso org(3) dod(6) internet(1) private(4) 1 }

-- The status of a table entry, according to the definitions in the
-- IETF draft: Row creation with SNMPv1, from 19 October 1993.
-- The createAndGo value is not supported.

-- Textual Conventions

Timeout ::= INTEGER           -- a STP timer in units of 1/100 seconds
MacAddress ::= OCTET STRING (SIZE (6))    -- rfc1286
-- AtmAddress ::= OCTET STRING (SIZE (0..20))
-- Counter64 ::= INTEGER    - Counter   until SNMPV2 support.


-- Smart Devices Group - attributes of SNMP agents that are
-- managing all devices except boxes.

smartDevices OBJECT IDENTIFIER ::= { lannet 27 }
 
-- General Attributes concerning the device

smartGeneral OBJECT IDENTIFIER ::= { smartDevices  1 }

smartGenSWVersion OBJECT-TYPE
	SYNTAX  DisplayString
	ACCESS  read-only
	STATUS  mandatory
	DESCRIPTION
	"ASCII string for description and display of the smart device software version."
	::= { smartGeneral 1 }

smartGenOSVersion OBJECT-TYPE
	SYNTAX  DisplayString
	ACCESS  read-only
	STATUS  mandatory
	DESCRIPTION
	"ASCII string for description and display of the smart device operating system (kernel) version."
	::= { smartGeneral 2 }

smartGenSoftwareDscr OBJECT-TYPE
	SYNTAX  DisplayString
	ACCESS  read-only
	STATUS  mandatory 
	DESCRIPTION
	"ASCII string for description and display of the smart device software information."
	::= { smartGeneral 3 }

smartGenBootVersion OBJECT-TYPE
	SYNTAX  DisplayString
	ACCESS  read-only
	STATUS  mandatory
	DESCRIPTION
	"ASCII string for description and display of the smart device boot software version."
	::= { smartGeneral 4 }

smartGenReset OBJECT-TYPE
	SYNTAX  INTEGER {  
		on(1),
		off(2)
		}
	ACCESS  read-write    
	STATUS  mandatory
	DESCRIPTION
	"Setting the value of this attribute to ON is interpreted as a reset
	command for the whole device. It initiates a complete re-initialization of the device."
	DEFVAL {off } 
	::= { smartGeneral  5 }

smartGenHardwareVersion OBJECT-TYPE
      SYNTAX  DisplayString
      ACCESS  read-only
      STATUS  mandatory
      DESCRIPTION
      "ASCII string for description and 
       display of the agent hardware version."
      ::= { smartGeneral  6 }

smartGenMonitoringPort OBJECT-TYPE
      SYNTAX  INTEGER 
      ACCESS  read-only
      STATUS  mandatory
      DESCRIPTION
      "Enables a user to fix one port to monitor
	other segment ports. For the moment,
	the monitoring port is port 16.
	In this case, this port doesn't participate to
	any other functions of the device."
     DEFVAL { 16 }
      ::= { smartGeneral  7 }

smartGenMonitoredPort  OBJECT-TYPE
      SYNTAX  INTEGER 
      ACCESS  read-write
      STATUS  mandatory
      DESCRIPTION
      "Value '0' is illegal when Monitor Mode is on."
     DEFVAL { 0 }
      ::= { smartGeneral  8 }

smartGenLastChange OBJECT-TYPE
      SYNTAX  TimeTicks
     ACCESS  read-only
      STATUS  mandatory
      DESCRIPTION
      "This attribute contains the value of sysUpTime
	at the time any change pertaining to the device:
	The changes are regarding the parameters of this
	 group and any parameters of smartIfExtensionTable."
       ::= { smartGeneral  9 }

smartGenMonitorMode  OBJECT-TYPE
      SYNTAX  INTEGER {on(1), off(2), notSupported(255)}
      ACCESS  read-write
      STATUS  mandatory
      DESCRIPTION
      "Activates the monitor function."
     DEFVAL { off }
      ::= { smartGeneral  10 }

smartGenNetworkPrefix  OBJECT-TYPE
SYNTAX  OCTET STRING( SIZE(13))
ACCESS  read-write
STATUS  mandatory
DESCRIPTION
"For ATM devices, the prefix of the switch connected."
::= { smartGeneral 11 }

smartGenConnectMode OBJECT-TYPE
SYNTAX  INTEGER {
		lane10(1),
		pvc(2),
		notSupported(255)
		}
ACCESS  read-write
STATUS  mandatory
DESCRIPTION
"Enables the user to configure the ATM interface of the smart device to work in front another ATM 
port of a smart device: pvc or in front a switch with lane10. "
      DEFVAL {lane10 }
      ::= { smartGeneral 12 }

smartGenPvcVP OBJECT-TYPE
      SYNTAX  INTEGER 
      ACCESS  read-only
      STATUS  mandatory
      DESCRIPTION
      "When the smart device is in mode pvc,
       the VP on which the data is runing."
      DEFVAL {0 }
      ::= { smartGeneral 13 }

smartGenPvcVC OBJECT-TYPE
	SYNTAX  INTEGER
	ACCESS  read-only
	STATUS  mandatory
	DESCRIPTION
	"When the smart device is in mode pvc, the VC on which the data is runing."
	DEFVAL {100 }
	::= { smartGeneral 14 }

smartGenSlotNumber OBJECT-TYPE
	SYNTAX  INTEGER
	ACCESS  read-only
	STATUS  mandatory
	DESCRIPTION
	"Identifies the location (slot number) of the device in the chassis. The first slot is 1"
	::= { smartGeneral 15 }

smartGenHubMgmtIfType OBJECT-TYPE
	SYNTAX  INTEGER {
		none(1),
		regular1822(2),
		hdh1822(3),
		ddn-x25(4),
		rfc877-x25(5),
		ethernet-csmacd(6),
		iso88023-csmacd(7),
		iso88024-tokenBus(8),
		iso88025-tokenRing(9),
		iso88026-man(10),
		starLan(11),
		proteon-10MBit(12),
		proteon-80MBit(13),
		hyperchannel(14),
		fddi(15),
		lapb(16),
		sdlc(17),
		t1-carrier(18),
		cept(19),
		basicIsdn(20),
		primaryIsdn(21),
		propPointToPointSerial(22),    -- proprietary serial
		ppp(23),
		softwareLoopback(24),
		eon(25),    -- CLNP over IP
		ethernet-3Mbit(26),
		nsip(27),    -- XNS over IP
		slip(28),    -- generic SLIP
		ultra(29),    -- ULTRA technologies
		ds3(30),    -- T-3
		sip(31),    -- SMDS
		frameRelay(32),    -- DTE only
		rs232(33),
		para(34),    -- parallel-port
		arcnet(35),    -- arcnet
		arcnetPlus(36),    -- arcnet plus
		atm(37),    -- ATM cells
		miox25(38),
		sonet(39),    -- SONET or SDH
		x25ple(40),
		iso88022llc(41),
		localTalk(42),
		smdsDxi(43),
		frameRelayService(44),  -- Frame relay DCE
		v35(45),
		hssi(46),
		hippi(47),
		modem(48),    -- Generic modem
		aal5(49),    -- AAL5 over ATM
		sonetPath(50),
		sonetVT(51),
		smdsIcip(52),    -- SMDS InterCarrier Interface
		propVirtual(53),    -- proprietary virtual/internal
		propMultiplexor(54), -- proprietary multiplexing
		ip(255)
		}
	ACCESS  read-only 
	STATUS  mandatory
	DESCRIPTION
	"This attribute describes one of the interfaces of agents existing on
	modules and their type. Value 'none' defines the lack of an
	interface whose type is recognized by the management console.
	Any other value defines an interface whose type is recognized by 
	the management console and may be used as a management channel."
	::= { smartGeneral 16 }

smartGenHubAddr OBJECT-TYPE
	SYNTAX  OCTET STRING ( SIZE (0..20)) 
	ACCESS  read-write  
	STATUS  mandatory
	DESCRIPTION
	"This attribute defines an unique address by which the agent may be 
	addressed by the management console. The address format should be 
	consistent with the type defined by chAgHubMgmtIfType."
	::= { smartGeneral 17 }


-- Attributes concerning agent of the Smart Module

smartAgent OBJECT IDENTIFIER ::= { smartDevices  2 }

smartAgCoprocCommStatus OBJECT-TYPE
      SYNTAX  INTEGER {
	      ok(1),
	      commProblems(2),
	      timeout(3)
	 }
      ACCESS  read-only
      STATUS  mandatory
      DESCRIPTION
      "Attribute describing the status of the 
       communication between the
      agent and its coprocessor."
     DEFVAL { ok }
      ::= { smartAgent 1 }

smartAgCommDebugMode OBJECT-TYPE
      SYNTAX  INTEGER {
	      on(1),
	      off(2)
	 }
      ACCESS  read-write
      STATUS  mandatory
      DESCRIPTION
      "Attribute describing the agent mode in 
       which communication problem traps are 
       sent to managers (value 'on') or are not 
       sent to managers (value 'off')."
     DEFVAL { off }
      ::= { smartAgent 2 }

smartAgConfigChangeTraps OBJECT-TYPE
	SYNTAX  INTEGER {
		enabled(1),
		disabled(2)
	}
	ACCESS  read-write
	STATUS  mandatory
	DESCRIPTION
	"The value of this attributes 
	determines whether or not the agent
	sends Configuration Change traps
	 to the manager."
		 DEFVAL { enabled }
	::= {smartAgent 3 }

smartAgFaultTraps OBJECT-TYPE
	SYNTAX  INTEGER {
		enabled(1),
		disabled(2)
	}
	ACCESS  read-write
	STATUS  mandatory
	DESCRIPTION
	"The value of this attributes determines 
	whether or not the agent
	sends Fault traps to the manager."
		 DEFVAL { enabled }
	::= {smartAgent 4 }

smartAgLaneFaultTraps OBJECT-TYPE
	SYNTAX  INTEGER {
		enabled(1),
		disabled(2)
	}
	ACCESS  read-write
	STATUS  mandatory
	DESCRIPTION
	"The value of this attributes determines 
	whether or not the agent
	sends Fault traps when it cannot connect to some 
		ELAN to the manager."
		 DEFVAL { enabled }
	::= {smartAgent 5 }

smartAgSoftwareStatus OBJECT-TYPE
      SYNTAX  INTEGER {
	unLoadable(1),
	loaded(2),
	downLoading(3),
	downLoadOfDownload(4)
      }     
      ACCESS  read-write
      STATUS  mandatory
      DESCRIPTION
      "Describes configuration of the firmware on this agent.
      unLoadable(1) - is returned by agents which do not support the Software
      Download feature;
      loaded(2) - is returned by agents with loaded software;
      downLoading(3) - when the attribute is set to this value by manager,
      it triggers the Software Download procedure. When procedure finished,
      agent software will reestablish value 'loaded(2)'.
      downLoadOfDownload (4) - when the attribute is set to this value by manager,
      it causes the Agent to download the new download software. 
      When procedure finished, agent software will reestablish value 'loaded(2)'." 
      ::= { smartAgent 6 }


-- This group was mandatory for smart device translating to/from ATM. 
-- It deals with PVC setup. 
-- The following group is an extension of the interfaces tables

smartIfExtension OBJECT IDENTIFIER ::= { smartDevices   3 }

smartIfExtensionTable      OBJECT-TYPE
	      SYNTAX  SEQUENCE OF SmartIfExtensionEntry
	      ACCESS  not-accessible
	      STATUS  mandatory
	      DESCRIPTION
		      "This table contains additional information concerning physical 
		interfaces. (Ethernet and ATM ports.)"
	      ::= { smartIfExtension 1 }


smartIfExtensionEntry OBJECT-TYPE
	      SYNTAX  SmartIfExtensionEntry
	      ACCESS  not-accessible
	      STATUS  mandatory
	      DESCRIPTION
		      "Additional information"
	      INDEX   { ifIndex }
	      ::= { smartIfExtensionTable  1 }

SmartIfExtensionEntry ::=
	      SEQUENCE {
	smartIfExtensionEthStatus
		      INTEGER,
	smartIfExtensionActivity
		      INTEGER,
	smartIfExtensionViNet
	      INTEGER,
	smartIfExtensionPriorityLevel 
	     INTEGER,
	smartIfExtensionBridgeEnable
	     INTEGER,
	smartIfExtensionBackPressure
	     INTEGER,
	smartIfExtensionSTAEnable
	     INTEGER
	}
	
smartIfExtensionEthStatus OBJECT-TYPE
	      SYNTAX  INTEGER {
		ok(1),
		rld(2),            -- RxLinkDown (Link Test Fail)
		tld(4),            -- TxLinkDown (Remote Link Down)
		notSupported(255)
	     }
	      ACCESS  read-only
	      STATUS  mandatory
	      DESCRIPTION
	"Valid for Ethernet Type only"
	DEFVAL {ok }
::= { smartIfExtensionEntry  1}

smartIfExtensionActivity OBJECT-TYPE
	      SYNTAX  INTEGER {
		notActive(1),
		standby(2),
		active(3),
		notSupported(255)
	}
	      ACCESS  read-write
	      STATUS  mandatory
	      DESCRIPTION
	"Valid for ATM Type supporting redundancy."
	DEFVAL { active }
::= { smartIfExtensionEntry  2}

smartIfExtensionViNet OBJECT-TYPE
	      SYNTAX  INTEGER
	      ACCESS  read-write
	      STATUS  mandatory
	      DESCRIPTION
	"Virtual Net Number. 
	Value '0' for generic mode.
		The value for not supported is 511."
	DEFVAL {0}
::= { smartIfExtensionEntry  3}

smartIfExtensionPriorityLevel OBJECT-TYPE
      SYNTAX  INTEGER {
	video(3),
	default(5),
	notSupported(255)
	}
      ACCESS read-write
      STATUS mandatory
      DESCRIPTION
      "This attribute defines the priority levels of Ethernet ports.
      The highest priority is video."
	DEFVAL { default }
      ::= { smartIfExtensionEntry  4 }

smartIfExtensionBridgeEnable OBJECT-TYPE
	      SYNTAX  INTEGER {
		enabled(1),
		disabled(2),
		notSupported(255)
	}
	      ACCESS  read-only
	      STATUS  mandatory
	      DESCRIPTION
	"Valid for Ethernet port when in sniffer mode."
	DEFVAL { enabled }
::= { smartIfExtensionEntry 5}

smartIfExtensionBackPressure OBJECT-TYPE
      SYNTAX  INTEGER {
		enabled(1),
		disabled(2),
		notSupported(255)
	}
      ACCESS  read-write
      STATUS  mandatory
      DESCRIPTION
      "Enables a user to disable the backpressure
	mechanism."
      DEFVAL {disabled }
      ::= { smartIfExtensionEntry 6 }


smartIfExtensionSTAEnable OBJECT-TYPE
	      SYNTAX  INTEGER {
		enabled(1),
		disabled(2),
		notSupported(255)
	}
	      ACCESS  read-write
	      STATUS  mandatory
	      DESCRIPTION
	"Allows user to take out a port from the STA."
	DEFVAL { enabled }
::= { smartIfExtensionEntry 7}


--  Virtual Net

smartViNet OBJECT IDENTIFIER ::= { smartDevices   4}

smartViNetMaxNumOfNets OBJECT-TYPE
	SYNTAX  INTEGER 
	ACCESS   read-only
	STATUS  mandatory
		DESCRIPTION 
	"Maximum number of local ViNets supported." 
	DEFVAL { 16 }
	::= { smartViNet 1}

smartViNetCurrentBridge OBJECT-TYPE
	SYNTAX  INTEGER 
	ACCESS   read-write
	STATUS  mandatory
		DESCRIPTION 
	"ViNet that is the current owner 
	of the STA group, and forwarding table 
	in the bridge MIB."
	DEFVAL { 0 }
	::= { smartViNet 2}

smartViNetTable      OBJECT-TYPE
	      SYNTAX  SEQUENCE OF SmartViNetEntry
	      ACCESS  not-accessible
	      STATUS  mandatory
	      DESCRIPTION
	       "This table contains the number of members
	belonging to each virtual nets ."
	      ::= { smartViNet 3 }

smartViNetEntry OBJECT-TYPE
	      SYNTAX  SmartViNetEntry
	      ACCESS  not-accessible
	      STATUS  mandatory
	      DESCRIPTION
	      "Each Virtual Net will be an isolated entity.
	The first row of this table is the generic 
	virtual net and is read-only."
	      INDEX   { smartViNetNumberPlusOne}
	      ::= { smartViNetTable  1 }

SmartViNetEntry ::=
	      SEQUENCE {
	smartViNetNumberPlusOne
	      INTEGER,
	smartViNetNumOfMembers
	      INTEGER
}


smartViNetNumberPlusOne OBJECT-TYPE
	      SYNTAX  INTEGER
	      ACCESS   read-write
	      STATUS  mandatory
	      DESCRIPTION 
	"Correspondance for Virtual Net:
	  ViNet: zero is 'generic' "
	::= { smartViNetEntry 1}

smartViNetNumOfMembers OBJECT-TYPE
	      SYNTAX  INTEGER
	      ACCESS   read-only
	      STATUS  mandatory
	      DESCRIPTION 
	"Number of members."
	::= { smartViNetEntry 2}

smartViNetElanTable      OBJECT-TYPE
	      SYNTAX  SEQUENCE OF SmartViNetElanEntry
	      ACCESS  not-accessible
	      STATUS  mandatory
	      DESCRIPTION
	       "This table contains all the information 
	concerning the association between virtual nets
	and ELAN name."
	      ::= { smartViNet 4 }

smartViNetElanEntry OBJECT-TYPE
	      SYNTAX  SmartViNetElanEntry
	      ACCESS  not-accessible
	      STATUS  mandatory
	      DESCRIPTION
	      "Each Virtual Net will be associated to an
	ELAN. The vinet = 0 is the first entry of the
	device."
	      INDEX   { smartViNetElanAssociation}
	      ::= { smartViNetElanTable  1 }

SmartViNetElanEntry ::=
	      SEQUENCE {
	smartViNetElanAssociation
	      INTEGER,
	smartViNetElanViNet
	      INTEGER,
	smartViNetElanName
	      DisplayString,
	smartViNetElanEntryStatus
	       INTEGER,
	smartViNetElanIfIndex
	       INTEGER
}

smartViNetElanAssociation OBJECT-TYPE
	      SYNTAX  INTEGER
	      ACCESS   read-write
	      STATUS  mandatory
	      DESCRIPTION 
		"The association number. For the first
		   association, this entry is read-only."
	::= { smartViNetElanEntry 1}

smartViNetElanViNet OBJECT-TYPE
	      SYNTAX  INTEGER
	      ACCESS   read-write
	      STATUS  mandatory
	      DESCRIPTION 
		"The virtual net number. For the first
		   row, this entry is read-only."
	DEFVAL {511}
	::= { smartViNetElanEntry 2}

smartViNetElanName OBJECT-TYPE
	      SYNTAX  DisplayString
	      ACCESS   read-write
	      STATUS  mandatory
	      DESCRIPTION 
		"The ELAN name. For the first row,
		   this entry is 'default' and is read-only."
	     DEFVAL { "default"}
	::= { smartViNetElanEntry 3}

smartViNetElanEntryStatus OBJECT-TYPE
	SYNTAX  INTEGER {
			active(1),
			notInService(2),
			notReady(3),
			createAndWait(4),
			destroy(5)
		}
	ACCESS  read-write
	STATUS  mandatory
	DESCRIPTION
	"The status of the entry. When the console starts
	to set the parameters of the row, the agent sets the status to notReady.
	The status createAndWait is set by the console,
	when the row  is complete. After reset of the device, the row
	is 'active(1)'.
	When the console has to 
	delete a row, it sets the status to 'destroy'. After reset,
	the row should disappear. "
	DEFVAL {active}
	::= { smartViNetElanEntry 4 }

smartViNetElanIfIndex OBJECT-TYPE
	      SYNTAX  INTEGER
	      ACCESS   read-only
	      STATUS  mandatory
	      DESCRIPTION 
		"Creating a row in this table causes the agent to add 
	one row in the interface table. Before setting the row status to
	active, the agent fill this field with the value of the ifIndex of the
	new created row."
	DEFVAL {0}
	::= { smartViNetElanEntry 5}

smartViNetFdbTable      OBJECT-TYPE
	      SYNTAX  SEQUENCE OF SmartViNetFdbEntry
	      ACCESS  not-accessible
	      STATUS  mandatory
	      DESCRIPTION
	      "This table is the forwarding table per virtual net."
	      ::= { smartViNet 5 }


smartViNetFdbEntry OBJECT-TYPE
	      SYNTAX  SmartViNetFdbEntry
	      ACCESS  not-accessible
	      STATUS  mandatory
	      DESCRIPTION
	      "The forwarding tables. The 
	smartViNetFdbPlusOne = 1 corresponds to
	ViNet generic. "
	      INDEX   { smartViNetFdbPlusOne, smartViNetFdbAddress }
	      ::= { smartViNetFdbTable  1 }

SmartViNetFdbEntry ::=
	      SEQUENCE {
	   smartViNetFdbPlusOne
	INTEGER,
	   smartViNetFdbAddress
	       MacAddress,
	   smartViNetFdbPort
	       INTEGER,
	   smartViNetFdbStatus
	       INTEGER
}

smartViNetFdbPlusOne OBJECT-TYPE
	      SYNTAX  INTEGER
	      ACCESS   read-only
	      STATUS  mandatory
	      DESCRIPTION 
		"This table is indexed by the 
		   virtual net number plus 1,
		   since the first group is '0'."
	::= { smartViNetFdbEntry 1}

   smartViNetFdbAddress OBJECT-TYPE
       SYNTAX  MacAddress
       ACCESS  read-only
       STATUS  mandatory
       DESCRIPTION
	       "A unicast MAC address for which the bridge has
	       forwarding and/or filtering information."
       REFERENCE
	       "P802.1d/D9, July 14, 1989: Section 3.9.1, 3.9.2"
       ::= { smartViNetFdbEntry 2 }

   smartViNetFdbPort OBJECT-TYPE
       SYNTAX  INTEGER
       ACCESS  read-only
       STATUS  mandatory
       DESCRIPTION
	       "Either the value '0', or the port number of the
	       port on which a frame having a source address
	       equal to the value of the corresponding instance
	       of dot1dTpFdbAddress has been seen.  A value of
	       '0' indicates that the port number has not been
	       learned but that the bridge does have some
	       forwarding/filtering information about this
	       address (e.g. in the dot1dStaticTable).
	       Implementors are encouraged to assign the port
	       value to this object whenever it is learned even
	       for addresses for which the corresponding value of
	       dot1dTpFdbStatus is not learned(3)."
       ::= { smartViNetFdbEntry 3 }

   smartViNetFdbStatus OBJECT-TYPE
       SYNTAX  INTEGER {
		   other(1),
		   invalid(2),
		   learned(3),
		   self(4),
		   mgmt(5)
	       }
       ACCESS  read-only
       STATUS  mandatory
       DESCRIPTION
	       "see dot1dTpFdbStatus. "
       ::= {smartViNetFdbEntry 4 }


smartViNetStpTable      OBJECT-TYPE
	      SYNTAX  SEQUENCE OF SmartViNetStpEntry
	      ACCESS  not-accessible
	      STATUS  mandatory
	      DESCRIPTION
		      "This table contains all the information concerning the 
		 STA parameters per group."
	      ::= { smartViNet 6 }

smartViNetStpEntry OBJECT-TYPE
	      SYNTAX  SmartViNetStpEntry
	      ACCESS  not-accessible
	      STATUS  mandatory
	      DESCRIPTION
		      "The bridge will function between each of those entries."
	      INDEX   { smartViNetStpPlusOne}
	      ::= { smartViNetStpTable  1 }

SmartViNetStpEntry ::=
	      SEQUENCE {
	smartViNetStpPlusOne
	      INTEGER,
	smartViNetStpPriority 
	      INTEGER,
	smartViNetStpTimeSinceTopologyChange 
	      TimeTicks,
	smartViNetStpTopChanges 
	      Counter,
	smartViNetStpDesignatedRoot
	      OCTET STRING,
	smartViNetStpRootCost 
	      INTEGER,
	smartViNetStpRootPort
	      INTEGER,
	smartViNetStpMaxAge 
	      Timeout,
	smartViNetStpHelloTime 
	      Timeout,
	smartViNetStpHoldTime 
	      INTEGER,
	smartViNetStpForwardDelay 
	      Timeout,
	smartViNetStpBridgeMaxAge 
	      Timeout,
	smartViNetStpBridgeHelloTime 
	      Timeout,
	smartViNetStpBridgeForwardDelay 
	      Timeout,
	smartViNetStpLastChange
	      TimeTicks
}

smartViNetStpPlusOne OBJECT-TYPE
	      SYNTAX  INTEGER
	      ACCESS   read-only
	      STATUS  mandatory
	      DESCRIPTION 
		"This table is indexed by the 
		   virtual net number plus 1,
		   since the first group is '0'."
	::= { smartViNetStpEntry 1}

smartViNetStpPriority OBJECT-TYPE
       SYNTAX  INTEGER (0..65535)
       ACCESS  read-write
       STATUS  mandatory
       DESCRIPTION
	       ""
       REFERENCE
	       "P802.1d/D9, July 14, 1989: Section 4.5.3.7"
       ::= { smartViNetStpEntry 2 }

   smartViNetStpTimeSinceTopologyChange OBJECT-TYPE
       SYNTAX  TimeTicks
       ACCESS  read-only
       STATUS  mandatory
       DESCRIPTION
	       "The time (in hundredths of a second) since the
	       last time a topology change was detected by the
	       bridge entity."
       REFERENCE
	       "P802.1d/D9, July 14, 1989: Section 6.8.1.1.3"
       ::= {smartViNetStpEntry 3 }

   smartViNetStpTopChanges OBJECT-TYPE
       SYNTAX  Counter
       ACCESS  read-only
       STATUS  mandatory
       DESCRIPTION
	       "The total number of topology changes detected by
	       this bridge since the management entity was last
	       reset or initialized."
       REFERENCE
	       "P802.1d/D9, July 14, 1989: Section 6.8.1.1.3"
       ::= { smartViNetStpEntry 4 }

   smartViNetStpDesignatedRoot OBJECT-TYPE
       SYNTAX  OCTET STRING (SIZE (8))
       ACCESS  read-only
       STATUS  mandatory
       DESCRIPTION
	       "The bridge identifier of the root of the spanning
	       tree as determined by the Spanning Tree Protocol
	       as executed by this node.  This value is used as
	       the Root Identifier parameter in all Configuration
	       Bridge PDUs originated by this node."
       REFERENCE
	       "P802.1d/D9, July 14, 1989: Section 4.5.3.1"
       ::= { smartViNetStpEntry 5}

   smartViNetStpRootCost OBJECT-TYPE
       SYNTAX  INTEGER
       ACCESS  read-only
       STATUS  mandatory
       DESCRIPTION
	       "The cost of the path to the root as seen from
	       this bridge."
       REFERENCE
	       "P802.1d/D9, July 14, 1989: Section 4.5.3.2"
       ::= { smartViNetStpEntry 6 }

   smartViNetStpRootPort OBJECT-TYPE
       SYNTAX  INTEGER
       ACCESS  read-only
       STATUS  mandatory
       DESCRIPTION
	       "The port number of the port which offers the
	       lowest cost path from this bridge to the root
	       bridge."
       REFERENCE
	       "P802.1d/D9, July 14, 1989: Section 4.5.3.3"
       ::= { smartViNetStpEntry 7 }

   smartViNetStpMaxAge OBJECT-TYPE
       SYNTAX  Timeout
       ACCESS  read-only
       STATUS  mandatory
       DESCRIPTION
	       "The maximum age of Spanning Tree Protocol
	       information learned from the network on any port
	       before it is discarded, in units of hundredths of
	       a second.  This is the actual value that this
	       bridge is currently using."
       REFERENCE
	       "P802.1d/D9, July 14, 1989: Section 4.5.3.4"
       ::= { smartViNetStpEntry 8 }

  smartViNetStpHelloTime OBJECT-TYPE
       SYNTAX  Timeout
       ACCESS  read-only
       STATUS  mandatory
       DESCRIPTION
	       "The amount of time between the transmission of
	       Configuration bridge PDUs by this node on any port
	       when it is the root of the spanning tree or trying
	       to become so, in units of hundredths of a second.
	       This is the actual value that this bridge is
	       currently using."
       REFERENCE
	       "P802.1d/D9, July 14, 1989: Section 4.5.3.5"
       ::= { smartViNetStpEntry 9 }

   smartViNetStpHoldTime OBJECT-TYPE
       SYNTAX  INTEGER
       ACCESS  read-only
       STATUS  mandatory
       DESCRIPTION
	       "This time value determines the interval length
	       during which no more than two Configuration bridge
	       PDUs shall be transmitted by this node, in units
	       of hundredths of a second."
       REFERENCE
	       "P802.1d/D9, July 14, 1989: Section 4.5.3.14"
       ::= { smartViNetStpEntry  10 }

   smartViNetStpForwardDelay OBJECT-TYPE
       SYNTAX  Timeout
       ACCESS  read-only
       STATUS  mandatory
       DESCRIPTION
	       ""
       REFERENCE
	       "P802.1d/D9, July 14, 1989: Section 4.5.3.6"
       ::= { smartViNetStpEntry 11 }

   smartViNetStpBridgeMaxAge OBJECT-TYPE
       SYNTAX  Timeout (600..4000)
       ACCESS  read-write
       STATUS  mandatory
       DESCRIPTION
	       ""
       REFERENCE
	       "P802.1d/D9, July 14, 1989: Section 4.5.3.8"
       ::= { smartViNetStpEntry 12 }

   smartViNetStpBridgeHelloTime OBJECT-TYPE
       SYNTAX  Timeout (100..1000)
       ACCESS  read-write
       STATUS  mandatory
       DESCRIPTION
	       "The value that all bridges use for HelloTime when
	       this bridge is acting as the root.  The
	       granularity of this timer is specified by
	       802.1d/D9 to be 1 second.  An agent may return a
	       badValue error if a set is attempted to a value
	       which is not a whole number of seconds."
       REFERENCE
	       "P802.1d/D9, July 14, 1989: Section 4.5.3.9"
       ::= { smartViNetStpEntry 13}

   smartViNetStpBridgeForwardDelay OBJECT-TYPE
       SYNTAX  Timeout (400..3000)
       ACCESS  read-write
       STATUS  mandatory
       DESCRIPTION
	       ""
       REFERENCE
	       "P802.1d/D9, July 14, 1989: Section 4.5.3.10"
       ::= { smartViNetStpEntry 14 }

smartViNetStpLastChange OBJECT-TYPE
	SYNTAX  TimeTicks
	ACCESS  read-only
	STATUS  mandatory
	DESCRIPTION
	"This attribute contains the value of sysUpTime
	 at the time any change pertaining to the
	specified STA occurred."
	::= { smartViNetStpEntry 15 }


-- The following MIB variable indicates on which virtual net, the device
-- will be managed

smartViNetConsoleManagement OBJECT-TYPE
	SYNTAX  INTEGER 
	ACCESS   read-write
	STATUS  mandatory
		DESCRIPTION 
	"The ViNet to which the console 
	belongs to."
	DEFVAL { 0 }
	::= { smartViNet 7}


-- Some informations concerning the box enclosing the smart device
-- and is used by the management application.

smartFatherHub OBJECT IDENTIFIER ::= { smartDevices  5 }

smartFatherNumberOfMac OBJECT-TYPE
      SYNTAX  INTEGER (0 .. 6)
      ACCESS  read-only
      STATUS  mandatory
      DESCRIPTION
      "Number of MAC Addresses of the box agent."
     DEFVAL { 1 }
      ::= { smartFatherHub 1 }

smartFatherMacList OBJECT-TYPE
      SYNTAX  OCTET STRING (SIZE(0..36))
      ACCESS  read-only
      STATUS  mandatory
      DESCRIPTION
      "This variable is the list of Mac Addresses of
      the box agent."
      ::= { smartFatherHub 2 }


-- Group supported only by LSF100 devices and  also by FAT-PIPE-FDDI modules

smartLSFddi OBJECT IDENTIFIER ::= { smartDevices  6 }

smartLSFTable      OBJECT-TYPE
	      SYNTAX  SEQUENCE OF SmartLSFEntry
	      ACCESS  not-accessible
	      STATUS  mandatory
	      DESCRIPTION
		"This table contains the MAC addresses of all LSF100
	modules on the FDDI ring. 
	This information is needed for LANNET Topology application."
	      ::= { smartLSFddi 1 }


smartLSFEntry OBJECT-TYPE
	      SYNTAX  SmartLSFEntry
	      ACCESS  not-accessible
	      STATUS  mandatory
	      DESCRIPTION
		      "A table entry containing MAC addresses of all LSF100
	modules on the FDDI ring."
	INDEX     { smartLSFMACAddr }
	      ::= { smartLSFTable  1 }

SmartLSFEntry ::=
	      SEQUENCE {
	smartLSFMACAddr
	      OCTET STRING,
	smartLSFEntryStatus
	      INTEGER
}

smartLSFMACAddr  OBJECT-TYPE
      SYNTAX  OCTET STRING
      ACCESS read-only
      STATUS mandatory
      DESCRIPTION
	"This item defines the MAC address 
	 of an LSF100 connected to the FDDI ring."
      ::= { smartLSFEntry 1 }

smartLSFEntryStatus OBJECT-TYPE
	SYNTAX  INTEGER {
			active(1),
			notInService(2),
			notReady(3),
			createAndWait(4),
			destroy(5)
		}
	ACCESS  read-only
	STATUS  mandatory
	DESCRIPTION
"Only the status active(1) is relevant to this table."
	 ::= { smartLSFEntry 2 }

macInFrames OBJECT-TYPE
	   SYNTAX  Counter
	   ACCESS  read-only
	   STATUS  mandatory
	   DESCRIPTION
		   "A count of the number of frames received by this MAC."
	   ::= { smartLSFddi 2 }

	macCopiedFrames OBJECT-TYPE
	   SYNTAX  Counter
	   ACCESS  read-only
	   STATUS  mandatory
	   DESCRIPTION
		   "A count of the number of frames addressed to and
		    successfully copied into the station's receive
		    buffers by this MAC. This count does not include 
		    MAC frames."
	   ::= { smartLSFddi 3 }

	macOutFrames OBJECT-TYPE
	   SYNTAX  Counter
	   ACCESS  read-only
	   STATUS  mandatory
	   DESCRIPTION
		   "A count of the number of frames trasmitted by this MAC.
		    This count does not include MAC frames."
	  ::= { smartLSFddi 4 }

	macTokenRcvd OBJECT-TYPE
	   SYNTAX  Counter
	   ACCESS  read-only
	   STATUS  mandatory
	   DESCRIPTION
		   "A count of the number of times the station has received 
		    a token on this MAC."
	  ::= { smartLSFddi 5 }

	macErrFrames OBJECT-TYPE
	   SYNTAX  Counter
	   ACCESS  read-only
	   STATUS  mandatory
	   DESCRIPTION
		   "A count of the number of frames that were detected 
		    in error by this MAC that had not been detected 
		    in error by another MAC."
	   ::= { smartLSFddi 6 }

	macLostFrames OBJECT-TYPE
	   SYNTAX  Counter
	   ACCESS  read-only
	   STATUS  mandatory
	   DESCRIPTION
		   "A count of the number of instances that this MAC 
		    detected a format error during frame reception, such
		    that the frame was stripped."
	   ::= { smartLSFddi 7 }

	macNotCopiedFrames OBJECT-TYPE
	   SYNTAX  Counter
	   ACCESS  read-only
	   STATUS  mandatory
	   DESCRIPTION
		   "A count of the number of frames addressed to this MAC 
		    but were not copied into the station's receive buffers.
		    This count does not include MAC frames."
	   ::= { smartLSFddi 8 }

	macRingOpState OBJECT-TYPE
	   SYNTAX  Counter
	   ACCESS  read-only
	   STATUS  mandatory
	   DESCRIPTION
		   "A count of the number of times the ring has entered 
		    the Ring Operational state from the Ring Not Operational
		    state."
	  ::= { smartLSFddi 9 }

	fddiRingUtilization OBJECT-TYPE
	    SYNTAX  INTEGER
           	    ACCESS  read-only
                STATUS  mandatory
                DESCRIPTION
                   "A utilization of the FDDI ring, attached to the LSF100 modules (or other 			members in the family)."
              ::= { smartLSFddi 10 }


END
