--

-- Copyright (c) 1993 Chipcom Corporation.  All Rights Reserved.
--
-- Reproduction of this document is authorized on condition that this
-- copyright notice is included.  This SNMP MIB Specification
-- embodies proprietary intellectual property.  The copyright
-- retains all title and ownership in the specification, including any
-- revisions. 
--
-- It is the intent to encourage the widespread use of this
-- specification in connection with the management of our
-- products. The copyright grants vendor, end-users, and other interested
-- parties a non-exclusive license to use this specification in
-- connection with the management of our products.
--
-- This specification is supplied "AS IS," and no
-- warranty, either express or implied, as to the use, operation,
-- condition, or performance of the specification, is made.
--
-- Copyright text courtesy of Dave Perkins.
--
-- The right to change this MIB without notification is retained.
--


--
-- If you have any questions about this MIB, please call your
-- Technical Support Center, or call 1-800-228-6840.
--

--
-- MIB Version Information:
--
-- Version     Description
------------------------------------------------------------------
--   v1.0      Initial version of the chipmib02 branch.
--   v2.0      Version tracking initiated.
--   v2.1      Version release with TRMM v.2.10
--
-- 

--
-- Agents supporting this MIB:
--	Ethernet Management Module, Software rev: v3.2
--	Ethernet to Ethernet Bridge Module, Software Rev: v2.12
--	Ethernet to Ethernet Bridge Box, Software Rev: v2.12
--	Token Ring Management Module, Software Rev: v2.1
--	Ethernet Interconnect Module, Software Rev: v1.0
--


CHIPNET-MIB DEFINITIONS ::= BEGIN

IMPORTS
	enterprises, NetworkAddress, IpAddress,
	Counter, Gauge, TimeTicks, DisplayString
		FROM RFC1155-SMI
	OBJECT-TYPE
		FROM RFC-1212;

chipcom     	OBJECT IDENTIFIER ::= { enterprises 49 }

chipmib02 	OBJECT IDENTIFIER ::= { chipcom 2 }

--
-- Top level groups
--

chipGen    	OBJECT IDENTIFIER ::= { chipmib02 1 }
chipEcho   	OBJECT IDENTIFIER ::= { chipmib02 2 }
chipProducts   	OBJECT IDENTIFIER ::= { chipmib02 3 }
chipExperiment  OBJECT IDENTIFIER ::= { chipmib02 4 }
chipTTY	        OBJECT IDENTIFIER ::= { chipmib02 5 }
chipTFTP	OBJECT IDENTIFIER ::= { chipmib02 6 }
chipDownload	OBJECT IDENTIFIER ::= { chipmib02 7 }


--
-- Product specific branches.  Also used for sysObjectID.
--

online        	OBJECT IDENTIFIER ::= { chipProducts 1 }
oebm 	      	OBJECT IDENTIFIER ::= { chipProducts 2 }

midnight      	OBJECT IDENTIFIER ::= { chipProducts 3 }
workGroupHub    OBJECT IDENTIFIER ::= { chipProducts 4 }

emm		OBJECT IDENTIFIER ::= { chipProducts 5 }
chipBridge	OBJECT IDENTIFIER ::= { chipProducts 6 }
trmm		OBJECT IDENTIFIER ::= { chipProducts 7 }
fmm		OBJECT IDENTIFIER ::= { chipProducts 8 }
focus1		OBJECT IDENTIFIER ::= { chipProducts 9 }
oeim    	OBJECT IDENTIFIER ::= { chipProducts 10 }





--
-- Experimental Branches
--
-- When RFCs are still in the experimental stage, the MIB
-- is incorporated under the enterprise experimental branch
-- so that changes in the experimental MIB do not affect
-- the released product.  
--
-- As the RFC becomes standard and support is provided by the agents,
-- the support under this branch will be moved to the appropriate
-- standard branch.  That is, the support under this branch
-- for the MIB in question will be removed.
--

chipExpTokenRing OBJECT IDENTIFIER ::= { chipExperiment 1 }
dot1dBridge	OBJECT IDENTIFIER ::= { chipExperiment 14 }

dot5		OBJECT IDENTIFIER ::= { chipExpTokenRing 1}

--
-- ONline Groups 
--

olAgents   	OBJECT IDENTIFIER ::= { online   1 }
olConc    	OBJECT IDENTIFIER ::= { online   2 }
olEnv     	OBJECT IDENTIFIER ::= { online   3 }
olModules 	OBJECT IDENTIFIER ::= { online   4 }
olNets   	OBJECT IDENTIFIER ::= { online   5 }
olGroups   	OBJECT IDENTIFIER ::= { online   6 }
olAlarm   	OBJECT IDENTIFIER ::= { online   7 }

--
-- Value added module attributes 
--

olSpecMods	OBJECT IDENTIFIER ::= { olModules 4 }

--
-- A node for each module type  :
--

ol50nnMCTL  	OBJECT IDENTIFIER ::= { olSpecMods 3 }
ol51nnMMGT  	OBJECT IDENTIFIER ::= { olSpecMods 4 }
ol51nnMFIB  	OBJECT IDENTIFIER ::= { olSpecMods 5 }
ol51nnMUTP  	OBJECT IDENTIFIER ::= { olSpecMods 6 }
ol51nnMTP   	OBJECT IDENTIFIER ::= { olSpecMods 7 }
ol51nnMBNC  	OBJECT IDENTIFIER ::= { olSpecMods 8 }
ol51nnBEE   	OBJECT IDENTIFIER ::= { olSpecMods 9 }
ol51nnRES   	OBJECT IDENTIFIER ::= { olSpecMods 10 }
ol51nnREE   	OBJECT IDENTIFIER ::= { olSpecMods 11 }
ol51nnMAUIF 	OBJECT IDENTIFIER ::= { olSpecMods 12 }
ol51nnMAUIM 	OBJECT IDENTIFIER ::= { olSpecMods 13 }
ol5208MTP   	OBJECT IDENTIFIER ::= { olSpecMods 14 }
ol51nnMFP   	OBJECT IDENTIFIER ::= { olSpecMods 15 }
ol51nnMFBP  	OBJECT IDENTIFIER ::= { olSpecMods 16 }
ol51nnMTPL  	OBJECT IDENTIFIER ::= { olSpecMods 17 }
ol51nnMTPPL 	OBJECT IDENTIFIER ::= { olSpecMods 18 }
ol52nnMTP   	OBJECT IDENTIFIER ::= { olSpecMods 19 }
ol52nnMFR   	OBJECT IDENTIFIER ::= { olSpecMods 20 }
ol51nnMTS   	OBJECT IDENTIFIER ::= { olSpecMods 21 }
ol51nnMFL   	OBJECT IDENTIFIER ::= { olSpecMods 22 }
ol50nnMRCTL 	OBJECT IDENTIFIER ::= { olSpecMods 23 }
ol51nnMFB   	OBJECT IDENTIFIER ::= { olSpecMods 24 }
ol53nnMMGT  	OBJECT IDENTIFIER ::= { olSpecMods 25 }
ol53nnMFBMIC	OBJECT IDENTIFIER ::= { olSpecMods 26 }
ol53nnMFIBST	OBJECT IDENTIFIER ::= { olSpecMods 27 }
ol53nnMSTP  	OBJECT IDENTIFIER ::= { olSpecMods 28 }
ol51nnMTPCL 	OBJECT IDENTIFIER ::= { olSpecMods 29 }
ol52nnBTT 	OBJECT IDENTIFIER ::= { olSpecMods 30 }
ol51nnIx 	OBJECT IDENTIFIER ::= { olSpecMods 31 }
ol52nnMMGT  	OBJECT IDENTIFIER ::= { olSpecMods 32 }
ol50nnMHCTL 	OBJECT IDENTIFIER ::= { olSpecMods 33 }













--
-- Networking groups
--

olNet		OBJECT IDENTIFIER ::= { olNets 1 }
olEnet		OBJECT IDENTIFIER ::= { olNets 2 }
olTRnet 	OBJECT IDENTIFIER ::= { olNets 3 }
olFDDInet 	OBJECT IDENTIFIER ::= { olNets 4 }


--
-- Workgroup Hub
--

hubSysGroup        OBJECT IDENTIFIER ::= { workGroupHub 1 }
hardwareGroup      OBJECT IDENTIFIER ::= { workGroupHub 2 }
softwareGroup      OBJECT IDENTIFIER ::= { workGroupHub 3 }
hubGroup           OBJECT IDENTIFIER ::= { workGroupHub 4 }
boardGroup         OBJECT IDENTIFIER ::= { workGroupHub 5 }
portGroup          OBJECT IDENTIFIER ::= { workGroupHub 6 }
alarmGroup         OBJECT IDENTIFIER ::= { workGroupHub 7 }


--
-- Threshold group
--

olThresh	OBJECT IDENTIFIER ::= { olAlarm 1 }

olThreshControl	OBJECT IDENTIFIER ::= { olThresh 1 }
-- All representations of MAC addresses in this MIB Module use,
-- as a textual convention (i.e. this convention does not affect
-- their encoding), the data type:

MacAddress ::= OCTET STRING (SIZE (6))    -- a 6 octet address in
                                          -- the "canonical" order
-- defined by IEEE 802.1a, i.e., as if it were transmitted least
-- significant bit first, even though 802.5 (in contrast to other
-- 802.x protocols) requires MAC addresses to be transmitted most
-- significant bit first.
--
-- 16-bit addresses, if needed, are represented by setting their
-- upper 4 octets to all 0's, i.e., AAFF would be represented
-- as 00000000AAFF.


-- The olNet Group

-- This group represents information about ONline networks in general.

olNetDPTable OBJECT-TYPE
	SYNTAX SEQUENCE OF OlNetDPEntry
	ACCESS not-accessible
	STATUS mandatory
	DESCRIPTION
		"A table that contains information linking 
		physical backplane allocation to logical
		networks. This information is useful:

			(1) to determine the physical allocation 
			of networks on the backplane, and 

			(2) to determine the remaining capacity of
			the backplane for future network growth.
	
		Since unknown modules are managed via dip
		switches, this is useful in order to set the
		dips to the appropriate settings.

		Ethernet is a bus architecture.  Once a path is
		allocated, all modules and ports can access that
		path.

		Token Ring and FDDI are ring architectures.  
		Each module on a ring requires a path.  Therefore,
		4 paths could be used to link 4 modules together
		on one ring, or 2 modules on 2 separate rings.
		It is possible to have a module allocated to 
		a ring (and thus a data path) without linking
		to another module.  

		These rules can be used to determine the remaining
		capacity for network growth."
	::= { olNet 1 }

olNetDPEntry OBJECT-TYPE
	SYNTAX OlNetDPEntry
	ACCESS not-accessible
	STATUS mandatory
	DESCRIPTION
		"A list of information about each data path in the
		concentrator."
	INDEX { olNetDPDataPath }
	::= { olNetDPTable 1 }

OlNetDPEntry ::= 
	SEQUENCE {
		olNetDPDataPath
			INTEGER,
		olNetDPNetID
			INTEGER
		}

olNetDPDataPath OBJECT-TYPE
	SYNTAX INTEGER {
		ethernet-path-1(6), -- channel 1
		ethernet-path-2(7), -- channel 2
		ethernet-path-3(8), -- channel 3
		token-ring-path-1(9),
		token-ring-path-2(10),
		token-ring-path-3(11),
		token-ring-path-4(12),
		token-ring-path-5(13),
		token-ring-path-6(14),
		token-ring-path-7(15),
		token-ring-path-8(16),
		token-ring-path-9(17),
		token-ring-path-10(18),
		token-ring-path-11(19),
		token-ring-path-12(20),
		token-ring-path-13(21),
		token-ring-path-14(22),
		token-ring-path-15(23),
		fddi-path-1(24),		
		fddi-path-2(25),		
		fddi-path-3(26),		
		fddi-path-4(27),		
		fddi-path-5(28),		
		fddi-path-6(29),		
		fddi-path-7(30),		
		fddi-path-8(31)
		}
	ACCESS read-only
	STATUS mandatory
	DESCRIPTION
		"The data path on the backplane.  Data paths between
		different protocols overlap.  That is, an ethernet data
		path will overlap with multiple token ring and fddi data
		paths. "
	::= { olNetDPEntry 1 }

olNetDPNetID OBJECT-TYPE
	SYNTAX INTEGER {
		notUsed(1),		-- available for use
		otherProto(2),		-- another protocol is using
					-- these resources
		ethernet-1(6),		
		ethernet-2(7),
		ethernet-3(8),
		token-ring-1(9),
		token-ring-2(10),
		token-ring-3(11),
		token-ring-4(12),
		token-ring-5(13),
		token-ring-6(14),
		token-ring-7(15),
		fddi-1(16),
		fddi-2(17),
		fddi-3(18),
		fddi-4(19)
		}
	ACCESS	read-only
	STATUS mandatory
	DESCRIPTION
		"The network that this data path corresponds to.  
		If the data path is not being used at all, notUsed(1)
		is the return value.  If the data path is being used
		by another protocol, then otherProto(2) is the
		return value."
	::= { olNetDPEntry 2 }


--
-- The following objects comprise the oldest style of security.
-- They are left here for backward compatibility with existing
-- applications; however, this group will not be enhanced.
--
olNetSecurityMACTable OBJECT-TYPE
	SYNTAX SEQUENCE OF OlNetSecurityMACEntry
	ACCESS not-accessible
	STATUS mandatory
	DESCRIPTION
		"A table of security configuration parameters and MAC
		addresses associated with every port with security
		configured in the concentrator."
	::= { olNet 2 }

olNetSecurityMACEntry OBJECT-TYPE
	SYNTAX OlNetSecurityMACEntry
	ACCESS not-accessible
	STATUS mandatory
	DESCRIPTION
		"A list of security configuration parameters and MAC
		addresses associated with each port with security
		configured in the concentrator."
	INDEX { olNetSecurityMACSlotIndex, olNetSecurityMACPortIndex,
		olNetSecurityMACAddress }
	::= { olNetSecurityMACTable 1 }

OlNetSecurityMACEntry ::=
	SEQUENCE {
		olNetSecurityMACSlotIndex
			INTEGER,
		olNetSecurityMACPortIndex
			INTEGER,
		olNetSecurityMACAddress
		  	MacAddress,
		olNetSecurityMACMode
			INTEGER,
		olNetSecurityMACStatus
			INTEGER
		 }

olNetSecurityMACSlotIndex OBJECT-TYPE
	 SYNTAX INTEGER
	 ACCESS read-only
	 STATUS mandatory
	 DESCRIPTION
		 "The slot number that contains this port."
	 ::= { olNetSecurityMACEntry 1 }

olNetSecurityMACPortIndex OBJECT-TYPE
	 SYNTAX INTEGER
	 ACCESS read-only
	 STATUS mandatory
	 DESCRIPTION
		 "The port number within this slot."
	 ::= { olNetSecurityMACEntry 2 }

olNetSecurityMACAddress OBJECT-TYPE
	 SYNTAX MacAddress
	 ACCESS read-write
	 STATUS mandatory
	 DESCRIPTION
		 "The security MAC address assigned to this port."
	 ::= { olNetSecurityMACEntry 3 }

olNetSecurityMACMode OBJECT-TYPE
	SYNTAX INTEGER {
		enabled(1),
		disabled(2)
		}
	ACCESS read-write
	STATUS mandatory
	DESCRIPTION
		"The desired security mode for this port/address."
--	DEFVAL {disabled(2)}
	::= { olNetSecurityMACEntry 4 }

olNetSecurityMACStatus OBJECT-TYPE
	SYNTAX INTEGER {
		valid(1),
		invalid(2)
		}
	ACCESS read-write
	STATUS mandatory
	DESCRIPTION
		"Each instance of the olNetSecurityMACTable associated
		with this olNetSecurityMACEntry (slot, port, and address)
		will be deleted by the agent if this olNetSecurityMACEntry
		is not equal to valid(1).  Initial creation of instances
		occurs via a set operation on a specific slot/port/address."
--	DEFVAL {valid(1)}
	::= { olNetSecurityMACEntry 5 }







END
