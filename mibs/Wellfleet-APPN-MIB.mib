Wellfleet-APPN-MIB DEFINITIONS ::= BEGIN

-- Created by mdl2asn version 3.1
-- Creation date: Wed Aug 30 16:36:03 EDT 1995


    IMPORTS

      Counter, Gauge
        FROM RFC1155-SMI
      OBJECT-TYPE
        FROM RFC-1212
      DisplayString
        FROM RFC1213-MIB
      wfAppnGroup
        FROM Wellfleet-COMMON-MIB;

    wfAppnNode            OBJECT IDENTIFIER ::= { wfAppnGroup 1 }
    wfAppnNodeInfoAndCaps	OBJECT IDENTIFIER ::= { wfAppnNode 1 }
    wfAppnNn              OBJECT IDENTIFIER ::= { wfAppnGroup 2 }
    wfAppnNnTopology      OBJECT IDENTIFIER ::= { wfAppnNn 3 }
    wfAppnLocalTopology   OBJECT IDENTIFIER ::= { wfAppnGroup 3 }
    wfAppnLocalThisNode   OBJECT IDENTIFIER ::= { wfAppnLocalTopology 1 }
    wfAppnDirectory       OBJECT IDENTIFIER ::= { wfAppnGroup 4 }
    wfAppnCos             OBJECT IDENTIFIER ::= { wfAppnGroup 5 }
    wfAppnTps             OBJECT IDENTIFIER ::= { wfAppnGroup 6 }
    wfAppnDlu             OBJECT IDENTIFIER ::= { wfAppnGroup 7 }
  

    wfAppnNodeDelete OBJECT-TYPE
        SYNTAX	INTEGER {
    		    created(1),
    		    deleted(2)
    		}
        ACCESS	read-write
        STATUS	mandatory
        DESCRIPTION
                "Create/Delete parameter. Default is created.
                Users perform an SNMP SET operation on this
                object in order to create/delete the APPN Node."
        DEFVAL	{ created }
        ::= { wfAppnNodeInfoAndCaps 1 }

    wfAppnNodeDisable OBJECT-TYPE
        SYNTAX	INTEGER {
    		    enable(1),
    		    disable(2)
    		}
        ACCESS	read-write
        STATUS	mandatory
        DESCRIPTION
                "Enable/Disable parameter. Default is enabled.
                Users perform an SNMP SET operation on this
                object in order to enable/disable the APPN Node."
        DEFVAL	{ enable }
        ::= { wfAppnNodeInfoAndCaps 2 }

    wfAppnNodeState OBJECT-TYPE
        SYNTAX	INTEGER {
    		    up(1),
    		    down(2),
    		    init(3),
    		    notpresent(4)
    		}
        ACCESS	read-only
        STATUS	mandatory
        DESCRIPTION
                "The current state of the APPN CP."
        DEFVAL	{ notpresent }
        ::= { wfAppnNodeInfoAndCaps 3 }

    wfAppnNodeCpName OBJECT-TYPE
        SYNTAX	DisplayString
        ACCESS	read-write
        STATUS	mandatory
        DESCRIPTION
                "Administratively-assigned network name
                for this node in the format NETID.CPNAME."
        ::= { wfAppnNodeInfoAndCaps 4 }

    wfAppnNodeNetid OBJECT-TYPE
        SYNTAX	DisplayString
        ACCESS	read-only
        STATUS	mandatory
        DESCRIPTION
                "Administratively-assigned APPN network identification,
                which can be from one to eight characters.
                This ID is used with the control point name
                to create a fully-qualified control point name."
        ::= { wfAppnNodeInfoAndCaps 5 }

    wfAppnNodeBlockNum OBJECT-TYPE
        SYNTAX	DisplayString
        ACCESS	read-write
        STATUS	mandatory
        DESCRIPTION
                "The block number is the first three digits of the node_id.
                These 3 hexadecimal digits identify the product."
        ::= { wfAppnNodeInfoAndCaps 6 }

    wfAppnNodeIdNum OBJECT-TYPE
        SYNTAX	DisplayString
        ACCESS	read-write
        STATUS	mandatory
        DESCRIPTION
                "The ID number is the last 5 digits of the node_id.
                These 5 hexadecimal digits are administratively defined and
                combined with the 3 digit block number from the node_id.
                This node_id is used to identify the local node and is included
                in APPN alerts as well as being included in XIDs.  A unique
                value is required for connections to SNA sub-area."
        ::= { wfAppnNodeInfoAndCaps 7 }

    wfAppnNodeType OBJECT-TYPE
        SYNTAX	INTEGER {
    		    nn(1),
    		    en(2),
    		    len(4)
    		}
        ACCESS	read-only
        STATUS	mandatory
        DESCRIPTION
                "Type of APPN node, either Network Node, End Node, or Low Entry Networking Node.
                This node is always a Network Node."
        ::= { wfAppnNodeInfoAndCaps 8 }

    wfAppnNodeUpTime OBJECT-TYPE
        SYNTAX	INTEGER
        ACCESS	read-only
        STATUS	mandatory
        DESCRIPTION
                "Time (in hundredths of a second) since this APPN node
                was initialized."
        ::= { wfAppnNodeInfoAndCaps 9 }

    wfAppnNodeNegotLs OBJECT-TYPE
        SYNTAX	INTEGER {
    		    yes(1),
    		    no(2)
    		}
        ACCESS	read-only
        STATUS	mandatory
        DESCRIPTION
                "Indicates whether this node supports negotiable
                link stations."
        ::= { wfAppnNodeInfoAndCaps 10 }

    wfAppnNodeSegReasm OBJECT-TYPE
        SYNTAX	INTEGER {
    		    yes(1),
    		    no(2)
    		}
        ACCESS	read-only
        STATUS	mandatory
        DESCRIPTION
                "Indicates whether this node supports segment
                reassembly.  This is only supported when
                segment generation is also supported."
        ::= { wfAppnNodeInfoAndCaps 11 }

    wfAppnNodeBindReasm OBJECT-TYPE
        SYNTAX	INTEGER {
    		    yes(1),
    		    no(2)
    		}
        ACCESS	read-only
        STATUS	mandatory
        DESCRIPTION
                "Indicates whether this node supports Bind segment
                reassembly.  This will only be supported when Bind
                segment generation is also supported."
        ::= { wfAppnNodeInfoAndCaps 12 }

    wfAppnNodeParallelTg OBJECT-TYPE
        SYNTAX	INTEGER {
    		    yes(1),
    		    no(2)
    		}
        ACCESS	read-only
        STATUS	mandatory
        DESCRIPTION
                "Indicates whether this node supports parallel TGs."
        ::= { wfAppnNodeInfoAndCaps 13 }

    wfAppnNodeService OBJECT-TYPE
        SYNTAX	INTEGER {
    		    yes(1),
    		    no(2)
    		}
        ACCESS	read-only
        STATUS	mandatory
        DESCRIPTION
                "Indicates whether this node allows call-in from nodes not
                defined locally."
        ::= { wfAppnNodeInfoAndCaps 14 }

    wfAppnNodeAdaptiveBindPacing OBJECT-TYPE
        SYNTAX	INTEGER {
    		    yes(1),
    		    no(2)
    		}
        ACCESS	read-only
        STATUS	mandatory
        DESCRIPTION
                "Indicates whether this node supports adaptive bind pacing."
        ::= { wfAppnNodeInfoAndCaps 15 }

    wfAppnNodeNnRcvRegChar OBJECT-TYPE
        SYNTAX	INTEGER {
    		    yes(1),
    		    no(2)
    		}
        ACCESS	read-only
        STATUS	mandatory
        DESCRIPTION
                "Indicates whether this node supports receiving registered
                characteristics."
        ::= { wfAppnNodeInfoAndCaps 16 }

    wfAppnNodeNnGateway OBJECT-TYPE
        SYNTAX	INTEGER {
    		    yes(1),
    		    no(2)
    		}
        ACCESS	read-only
        STATUS	mandatory
        DESCRIPTION
                "Indicates whether this is a gateway node."
        ::= { wfAppnNodeInfoAndCaps 17 }

    wfAppnNodeNnCentralDirectory OBJECT-TYPE
        SYNTAX	INTEGER {
    		    yes(1),
    		    no(2)
    		}
        ACCESS	read-only
        STATUS	mandatory
        DESCRIPTION
                "Indicates whether this node supports central directory
                cache."
        ::= { wfAppnNodeInfoAndCaps 18 }

    wfAppnNodeNnTreeCache OBJECT-TYPE
        SYNTAX	INTEGER {
    		    yes(1),
    		    no(2)
    		}
        ACCESS	read-only
        STATUS	mandatory
        DESCRIPTION
                "Indicates whether this node supports Route Tree caching."
        ::= { wfAppnNodeInfoAndCaps 19 }

    wfAppnNodeNnTreeUpdate OBJECT-TYPE
        SYNTAX	INTEGER {
    		    yes(1),
    		    no(2)
    		}
        ACCESS	read-only
        STATUS	mandatory
        DESCRIPTION
                "Indicates whether this node supports
                incremental_tree_update, which is only
                supported when tree caching is supported."
        ::= { wfAppnNodeInfoAndCaps 20 }

    wfAppnNodeNnRouteAddResist OBJECT-TYPE
        SYNTAX	INTEGER(0..255)
        ACCESS	read-write
        STATUS	mandatory
        DESCRIPTION
                "Route addition resistance is a value that
                indicates the relative desirability
                of using this node for intermediate session traffic.
                The value, which can be any integer 0-255,
                is used in route computation.  The lower the value,
                the more desirable the node is for intermediate routing."
        DEFVAL	{ 128 }
        ::= { wfAppnNodeInfoAndCaps 21 }

    wfAppnNodeNnIsr OBJECT-TYPE
        SYNTAX	INTEGER {
    		    yes(1),
    		    no(2)
    		}
        ACCESS	read-only
        STATUS	mandatory
        DESCRIPTION
                "Indicates whether the node supports intermediate
                session routing."
        ::= { wfAppnNodeInfoAndCaps 22 }

    wfAppnNodeNnFrsn OBJECT-TYPE
        SYNTAX	INTEGER
        ACCESS	read-only
        STATUS	mandatory
        DESCRIPTION
                "Flow reduction sequence numbers (FRSNs) are associated
                with Topology Database Updates (TDUs) and are unique
                only within each APPN network node.  A TDU can be
                associated with multiple APPN resources. This object
                is the last FRSN sent in a topology update to
                adjacent network nodes."
        ::= { wfAppnNodeInfoAndCaps 23 }

    wfAppnNodeModeToCosDisable OBJECT-TYPE
        SYNTAX	INTEGER {
    		    enable(1),
    		    disable(2)
    		}
        ACCESS	read-only
        STATUS	mandatory
        DESCRIPTION
                "Indicates whether Mode to Cos mapping is supported"
        ::= { wfAppnNodeInfoAndCaps 24 }

    wfAppnNodeMdsDisable OBJECT-TYPE
        SYNTAX	INTEGER {
    		    enable(1),
    		    disable(2)
    		}
        ACCESS	read-write
        STATUS	mandatory
        DESCRIPTION
                "Enables Multiple Domain Support"
        DEFVAL	{ enable }
        ::= { wfAppnNodeInfoAndCaps 25 }

    wfAppnNodeRegWithCdsDisable OBJECT-TYPE
        SYNTAX	INTEGER {
    		    enable(1),
    		    disable(2)
    		}
        ACCESS	read-write
        STATUS	mandatory
        DESCRIPTION
                "Enable Registration of Local and Domain  resources with Central Directory Server"
        DEFVAL	{ enable }
        ::= { wfAppnNodeInfoAndCaps 26 }

    wfAppnNodeAlertQSize OBJECT-TYPE
        SYNTAX	INTEGER(2..2147483647)
        ACCESS	read-write
        STATUS	mandatory
        DESCRIPTION
                "Size of the MDS Send Alert Queue Size"
        DEFVAL	{ 10 }
        ::= { wfAppnNodeInfoAndCaps 27 }

    wfAppnNodeCosCacheSize OBJECT-TYPE
        SYNTAX	INTEGER(8..2147483647)
        ACCESS	read-write
        STATUS	mandatory
        DESCRIPTION
                "Size of the COS Database weights cache This should be set to the number of COSs defined"
        DEFVAL	{ 8 }
        ::= { wfAppnNodeInfoAndCaps 28 }

    wfAppnNodeStoreEndpointRscvsDisable OBJECT-TYPE
        SYNTAX	INTEGER {
    		    enable(1),
    		    disable(2)
    		}
        ACCESS	read-write
        STATUS	mandatory
        DESCRIPTION
                "Store RSCVs for Endpoint sessions?"
        DEFVAL	{ enable }
        ::= { wfAppnNodeInfoAndCaps 29 }

    wfAppnNodeNnMaxLocates OBJECT-TYPE
        SYNTAX	INTEGER(8..2147483647)
        ACCESS	read-write
        STATUS	mandatory
        DESCRIPTION
                "Maximum simultaneous Locates that this node will process"
        DEFVAL	{ 256 }
        ::= { wfAppnNodeInfoAndCaps 30 }

    wfAppnNodeNnDirCacheSize OBJECT-TYPE
        SYNTAX	INTEGER {
    		    def(100)
    		}
        ACCESS	read-write
        STATUS	mandatory
        DESCRIPTION
                "Maximum size (entry count) of the Directory Services cache."
        DEFVAL	{ def }
        ::= { wfAppnNodeInfoAndCaps 31 }

    wfAppnNodeNnMaxDirEntries OBJECT-TYPE
        SYNTAX	INTEGER
        ACCESS	read-write
        STATUS	mandatory
        DESCRIPTION
                "Maximum Number of entries in Directory Database. A value of zero means unlimited"
        ::= { wfAppnNodeInfoAndCaps 32 }

    wfAppnNodeNnLocateTimeout OBJECT-TYPE
        SYNTAX	INTEGER {
    		    def(60)
    		}
        ACCESS	read-write
        STATUS	mandatory
        DESCRIPTION
                "Specifies a time (in seconds) before a network search will timeout.
                A value of zero means no timeout"
        DEFVAL	{ def }
        ::= { wfAppnNodeInfoAndCaps 33 }

    wfAppnNodeNnTreeCacheSize OBJECT-TYPE
        SYNTAX	INTEGER(8..2147483647)
        ACCESS	read-write
        STATUS	mandatory
        DESCRIPTION
                "Size of the Topology Database routing tree cache."
        DEFVAL	{ 8 }
        ::= { wfAppnNodeInfoAndCaps 34 }

    wfAppnNodeNnTreeCacheUseLimit OBJECT-TYPE
        SYNTAX	INTEGER(1..2147483647)
        ACCESS	read-write
        STATUS	mandatory
        DESCRIPTION
                "Number of times a cached Routing Tree will be used before it is recalculated"
        DEFVAL	{ 8 }
        ::= { wfAppnNodeInfoAndCaps 35 }

    wfAppnNodeNnMaxTdmNodes OBJECT-TYPE
        SYNTAX	INTEGER
        ACCESS	read-write
        STATUS	mandatory
        DESCRIPTION
                "Maximum number of nodes in the topology database. A value of zero means unlimited"
        ::= { wfAppnNodeInfoAndCaps 36 }

    wfAppnNodeNnMaxTdmTgs OBJECT-TYPE
        SYNTAX	INTEGER
        ACCESS	read-write
        STATUS	mandatory
        DESCRIPTION
                "Maximum number of TGs in the topology database. A value of zero means unlimited"
        ::= { wfAppnNodeInfoAndCaps 37 }

    wfAppnNodeNnMaxIsrSessions OBJECT-TYPE
        SYNTAX	INTEGER(100..2147483647)
        ACCESS	read-write
        STATUS	mandatory
        DESCRIPTION
                "Maximum number of Intermediate Sessions that this node will route"
        DEFVAL	{ 1000 }
        ::= { wfAppnNodeInfoAndCaps 38 }

    wfAppnNodeNnIsrSessionUpperThresh OBJECT-TYPE
        SYNTAX	INTEGER {
    		    def(900)
    		}
        ACCESS	read-write
        STATUS	mandatory
        DESCRIPTION
                "ISR Session Threshold at which the node is considered congested.
                This value must be less than that of wfAppnNodeNnMaxIsrSessions"
        DEFVAL	{ def }
        ::= { wfAppnNodeInfoAndCaps 39 }

    wfAppnNodeNnIsrSessionLowerThresh OBJECT-TYPE
        SYNTAX	INTEGER {
    		    def(800)
    		}
        ACCESS	read-write
        STATUS	mandatory
        DESCRIPTION
                "ISR Session Threshold at which the node is no longer considered congested.
                This value must be less than that of wfAppnNodeNnIsrSessionUpperThresh"
        DEFVAL	{ def }
        ::= { wfAppnNodeInfoAndCaps 40 }

    wfAppnNodeNnIsrMaxRuSize OBJECT-TYPE
        SYNTAX	INTEGER(256..4096)
        ACCESS	read-write
        STATUS	mandatory
        DESCRIPTION
                "Maximum RU size supported for intermediate sessions"
        DEFVAL	{ 4096 }
        ::= { wfAppnNodeInfoAndCaps 41 }

    wfAppnNodeNnIsrRcvPacingWindow OBJECT-TYPE
        SYNTAX	INTEGER(1..63)
        ACCESS	read-write
        STATUS	mandatory
        DESCRIPTION
                "Receive Pacing window for intermediate sessions"
        DEFVAL	{ 7 }
        ::= { wfAppnNodeInfoAndCaps 42 }

    wfAppnNodeNnStoreIsrRscvsDisable OBJECT-TYPE
        SYNTAX	INTEGER {
    		    enable(1),
    		    disable(2)
    		}
        ACCESS	read-write
        STATUS	mandatory
        DESCRIPTION
                "Store RSCVs for intermediate sessions? (for network monitoring)"
        DEFVAL	{ enable }
        ::= { wfAppnNodeInfoAndCaps 43 }

    wfAppnNodeNnStoreDlurRscvsDisable OBJECT-TYPE
        SYNTAX	INTEGER {
    		    enable(1),
    		    disable(2)
    		}
        ACCESS	read-write
        STATUS	mandatory
        DESCRIPTION
                "Store RSCVs for DLUR sessions? (for network monitoring)"
        DEFVAL	{ enable }
        ::= { wfAppnNodeInfoAndCaps 44 }

    wfAppnNodeNnDlurDisable OBJECT-TYPE
        SYNTAX	INTEGER {
    		    enable(1),
    		    disable(2)
    		}
        ACCESS	read-write
        STATUS	mandatory
        DESCRIPTION
                "This enables DLUR support for the Node"
        DEFVAL	{ enable }
        ::= { wfAppnNodeInfoAndCaps 45 }

    wfAppnNodeTotalAvailableMemory OBJECT-TYPE
        SYNTAX	INTEGER
        ACCESS	read-only
        STATUS	mandatory
        DESCRIPTION
                "Total memory available to APPN"
        ::= { wfAppnNodeInfoAndCaps 46 }

    wfAppnNodeInUseMemory OBJECT-TYPE
        SYNTAX	INTEGER
        ACCESS	read-only
        STATUS	mandatory
        DESCRIPTION
                "Memory in use by APPN"
        ::= { wfAppnNodeInfoAndCaps 47 }

    wfAppnNodeMemoryWarningThreshold OBJECT-TYPE
        SYNTAX	INTEGER
        ACCESS	read-only
        STATUS	mandatory
        DESCRIPTION
                "Warning memory threshold"
        ::= { wfAppnNodeInfoAndCaps 48 }

    wfAppnNodeMemoryCriticalThreshold OBJECT-TYPE
        SYNTAX	INTEGER
        ACCESS	read-only
        STATUS	mandatory
        DESCRIPTION
                "Critical memory threshold"
        ::= { wfAppnNodeInfoAndCaps 49 }

    wfAppnNodeHprDisable OBJECT-TYPE
        SYNTAX	INTEGER {
    		    enable(1),
    		    disable(2)
    		}
        ACCESS	read-write
        STATUS	mandatory
        DESCRIPTION
                "This enables HPR support for the Node"
        DEFVAL	{ enable }
        ::= { wfAppnNodeInfoAndCaps 50 }

    wfAppnNodeHprPathSwitchCtrlrDisable OBJECT-TYPE
        SYNTAX	INTEGER {
    		    enable(1),
    		    disable(2)
    		}
        ACCESS	read-write
        STATUS	mandatory
        DESCRIPTION
                "This enables HPR Path Switch Controller support for the Node"
        DEFVAL	{ disable }
        ::= { wfAppnNodeInfoAndCaps 51 }

    wfAppnNodeDebugIpsTraceDisable OBJECT-TYPE
        SYNTAX	INTEGER {
    		    enable(1),
    		    disable(2)
    		}
        ACCESS	read-write
        STATUS	mandatory
        DESCRIPTION
                "This enables tracing of internal messages for debugging"
        DEFVAL	{ disable }
        ::= { wfAppnNodeInfoAndCaps 52 }

    wfAppnNodeDebugIpsTraceSize OBJECT-TYPE
        SYNTAX	INTEGER
        ACCESS	read-write
        STATUS	mandatory
        DESCRIPTION
                "This specifies the size of the IPS trace file for debugging"
        DEFVAL	{ 50000 }
        ::= { wfAppnNodeInfoAndCaps 53 }

    wfAppnNodeDefaultDlusName OBJECT-TYPE
        SYNTAX	DisplayString
        ACCESS	read-write
        STATUS	mandatory
        DESCRIPTION
                "Fully-qualified name of the default primary DLUS node."
        ::= { wfAppnNodeInfoAndCaps 54 }

    wfAppnNodeDefaultBackupDlusName OBJECT-TYPE
        SYNTAX	DisplayString
        ACCESS	read-write
        STATUS	mandatory
        DESCRIPTION
                "Fully-qualified name of the default backup DLUS node."
        ::= { wfAppnNodeInfoAndCaps 55 }

    wfAppnNodePdLogDisable OBJECT-TYPE
        SYNTAX	INTEGER {
    		    enable(1),
    		    disable(2)
    		}
        ACCESS	read-write
        STATUS	mandatory
        DESCRIPTION
                "This enables logging of problem determination messages"
        DEFVAL	{ disable }
        ::= { wfAppnNodeInfoAndCaps 56 }

    wfAppnNodeDlusRetryTimeout OBJECT-TYPE
        SYNTAX	INTEGER(5..90)
        ACCESS	read-write
        STATUS	mandatory
        DESCRIPTION
                "This controls the timeout between retying pipe to the DLUS"
        DEFVAL	{ 10 }
        ::= { wfAppnNodeInfoAndCaps 57 }

    wfAppnNodeDlusRetryLimit OBJECT-TYPE
        SYNTAX	INTEGER(10..65535)
        ACCESS	read-write
        STATUS	mandatory
        DESCRIPTION
                "This controls the nubmer of retries for the pipe to the DLUS; 65535 means forever"
        DEFVAL	{ 65535 }
        ::= { wfAppnNodeInfoAndCaps 58 }

    wfAppnNodeSoloistSlotNum OBJECT-TYPE
        SYNTAX	INTEGER(1..14)
        ACCESS	read-only
        STATUS	mandatory
        DESCRIPTION
                "Indicates the slot which runs the appn_cp soloist"    
        ::= { wfAppnNodeInfoAndCaps 59 }

    wfAppnNodeBrNNSupport OBJECT-TYPE
        SYNTAX  INTEGER {
                    enable(1),
                    disable(2)
                }
        ACCESS  read-write
        STATUS  mandatory
        DESCRIPTION
                "Enables the BrNN support for this node."
        DEFVAL  { disable }
        ::= { wfAppnNodeInfoAndCaps 60 }

     wfAppnNodeRegisterWithNN OBJECT-TYPE
	SYNTAX  INTEGER {
		    none(1),
                    all(2),
		    local(3)	
                }
        ACCESS  read-write
        STATUS  mandatory
        DESCRIPTION
                " Used for BrNN only. Indicates whether the resources will be registered with
		  the NNS. When register_local is selected only local LUs ( not domain-served )
		  will be registered. The NNS will forward all the broadcast searches to the 
		  Node. "
        DEFVAL  { none }
        ::= { wfAppnNodeInfoAndCaps 61 }	

     wfAppnNodeBranchAwarenessEnable OBJECT-TYPE
	 SYNTAX  INTEGER {
                    enable(1),
                    disable(2)
                }
        ACCESS  read-write
        STATUS  mandatory
        DESCRIPTION
                " Indicates whether the TG between the local Node and served BrNNs will appear
		  in the topology database "
        DEFVAL  { enable }
        ::= { wfAppnNodeInfoAndCaps 62 }	



    wfAppnNodeDlcTable OBJECT-TYPE
        SYNTAX	SEQUENCE OF WfAppnNodeDlcEntry
        ACCESS	not-accessible
        STATUS	mandatory
        DESCRIPTION
                "this table contains entries for each DLC configured for APPN use"
        ::= { wfAppnNode 2 }

    wfAppnNodeDlcEntry OBJECT-TYPE
        SYNTAX	WfAppnNodeDlcEntry
        ACCESS	not-accessible
        STATUS	mandatory
        DESCRIPTION
                "An entry in wfAppnNodeDlcTable."
        INDEX	{ wfAppnNodeDlcName }
        ::= { wfAppnNodeDlcTable 1 }

    WfAppnNodeDlcEntry ::= SEQUENCE {
    	    wfAppnNodeDlcDelete
    		INTEGER,
    	    wfAppnNodeDlcDisable
    		INTEGER,
    	    wfAppnNodeDlcName
    		DisplayString,
    	    wfAppnNodeDlcState
    		INTEGER,
    	    wfAppnNodeDlcType
    		INTEGER,
    	    wfAppnNodeDlcNegLsSupportDisable
    		INTEGER,
    	    wfAppnNodeDlcCct
    		INTEGER,
    	    wfAppnNodeDlcData
    		OCTET STRING
        }

    wfAppnNodeDlcDelete OBJECT-TYPE
        SYNTAX	INTEGER {
    		    created(1),
    		    deleted(2)
    		}
        ACCESS	read-write
        STATUS	mandatory
        DESCRIPTION
                "Create/Delete parameter. Default is created.
                Users perform an SNMP SET operation on this
                object in order to create/delete a DLC definition."
        DEFVAL	{ created }
        ::= { wfAppnNodeDlcEntry 1 }

    wfAppnNodeDlcDisable OBJECT-TYPE
        SYNTAX	INTEGER {
    		    enable(1),
    		    disable(2)
    		}
        ACCESS	read-write
        STATUS	mandatory
        DESCRIPTION
                "Enable/Disable parameter. Default is enabled.
                Users perform an SNMP SET operation on this
                object in order to enable/disable this DLC."
        DEFVAL	{ enable }
        ::= { wfAppnNodeDlcEntry 2 }

    wfAppnNodeDlcName OBJECT-TYPE
        SYNTAX	DisplayString
        ACCESS	read-only
        STATUS	mandatory
        DESCRIPTION
                "This is the 8-character name given to this DLC"
        ::= { wfAppnNodeDlcEntry 3 }

    wfAppnNodeDlcState OBJECT-TYPE
        SYNTAX	INTEGER {
    		    inactive(1),
    		    pendactive(2),
    		    active(3),
    		    pendinact(4)
    		}
        ACCESS	read-only
        STATUS	mandatory
        DESCRIPTION
                "Indicates the current state of this DLC."
        ::= { wfAppnNodeDlcEntry 4 }

    wfAppnNodeDlcType OBJECT-TYPE
        SYNTAX	INTEGER {
    		    sdlc(1),
    		    srb(2),
    		    tb(3),
    		    fr(4),
    		    dls(5),
    		    qllc(6)
    		}
        ACCESS	read-write
        STATUS	mandatory
        DESCRIPTION
                "This indicates the type of DLC"
        DEFVAL	{ srb }
        ::= { wfAppnNodeDlcEntry 5 }

    wfAppnNodeDlcNegLsSupportDisable OBJECT-TYPE
        SYNTAX	INTEGER {
    		    enable(1),
    		    disable(2)
    		}
        ACCESS	read-write
        STATUS	mandatory
        DESCRIPTION
                "This indicates if Link Station roles can be negotiated
                on this DLC"
        DEFVAL	{ enable }
        ::= { wfAppnNodeDlcEntry 6 }

    wfAppnNodeDlcCct OBJECT-TYPE
        SYNTAX	INTEGER
        ACCESS	read-write
        STATUS	mandatory
        DESCRIPTION
                "This is the circuit used by this DLC"
        ::= { wfAppnNodeDlcEntry 7 }

    wfAppnNodeDlcData OBJECT-TYPE
        SYNTAX	OCTET STRING
        ACCESS	read-write
        STATUS	mandatory
        DESCRIPTION
                "comment - Is this used? -P2"
        ::= { wfAppnNodeDlcEntry 8 }

    wfAppnNodePortTable OBJECT-TYPE
        SYNTAX	SEQUENCE OF WfAppnNodePortEntry
        ACCESS	not-accessible
        STATUS	mandatory
        DESCRIPTION
                "this table contains entries for each Port defined"
        ::= { wfAppnNode 3 }

    wfAppnNodePortEntry OBJECT-TYPE
        SYNTAX	WfAppnNodePortEntry
        ACCESS	not-accessible
        STATUS	mandatory
        DESCRIPTION
                "The Port Name is used as the index to this table."
        INDEX	{ wfAppnNodePortName }
        ::= { wfAppnNodePortTable 1 }

    WfAppnNodePortEntry ::= SEQUENCE {
    	    wfAppnNodePortDelete
    		INTEGER,
    	    wfAppnNodePortDisable
    		INTEGER,
    	    wfAppnNodePortName
    		DisplayString,
    	    wfAppnNodePortState
    		INTEGER,
    	    wfAppnNodePortDlcType
    		INTEGER,
    	    wfAppnNodePortPortType
    		INTEGER,
    	    wfAppnNodePortSIMRIM
    		INTEGER,
    	    wfAppnNodePortLsRole
    		INTEGER,
    	    wfAppnNodePortMaxRcvBtuSize
    		INTEGER,
    	    wfAppnNodePortMaxIframeWindow
    		INTEGER,
    	    wfAppnNodePortDefLsGoodXids
    		Counter,
    	    wfAppnNodePortDefLsBadXids
    		Counter,
    	    wfAppnNodePortDynLsGoodXids
    		Counter,
    	    wfAppnNodePortDynLsBadXids
    		Counter,
    	    wfAppnNodePortDlcName
    		DisplayString,
    	    wfAppnNodePortNumber
    		INTEGER,
    	    wfAppnNodePortTotLinkActLim
    		INTEGER,
    	    wfAppnNodePortInbLinkActLim
    		INTEGER,
    	    wfAppnNodePortOutLinkActLim
    		INTEGER,
    	    wfAppnNodePortActXidExchangeLimit
    		INTEGER,
    	    wfAppnNodePortNonActXidExchangeLimit
    		INTEGER,
    	    wfAppnNodePortLsXmitRcvCap
    		INTEGER,
    	    wfAppnNodePortTargetPacingCount
    		INTEGER,
    	    wfAppnNodePortMaxSendBtuSize
    		INTEGER,
    	    wfAppnNodePortImplicitCpSessions
    		INTEGER,
    	    wfAppnNodePortImplicitLimResource
    		INTEGER,
    	    wfAppnNodePortImplicitEffCap
    		INTEGER,
    	    wfAppnNodePortImplicitConnCost
    		INTEGER,
    	    wfAppnNodePortImplicitByteCost
    		INTEGER,
    	    wfAppnNodePortImplicitSecurity
    		INTEGER,
    	    wfAppnNodePortImplicitDelay
    		INTEGER,
    	    wfAppnNodePortImplicitUsr1
    		INTEGER,
    	    wfAppnNodePortImplicitUsr2
    		INTEGER,
    	    wfAppnNodePortImplicitUsr3
    		INTEGER,
    	    wfAppnNodePortImplicitHprDisable
    		INTEGER,
    	    wfAppnNodePortImplicitHprLlErrorDisable
    		INTEGER,
    	    wfAppnNodePortImplicitLinkDeactTime
    		INTEGER,
    	    wfAppnNodePortDlcData
    		OCTET STRING,
    	    wfAppnNodePortHprDlcData
    		OCTET STRING,
     	    wfAppnNodePortImplicitDlurDisable 
    		INTEGER,
	    wfAppnNodePortImplicitUplinkToEN
                INTEGER
       }

    wfAppnNodePortDelete OBJECT-TYPE
        SYNTAX	INTEGER {
    		    created(1),
    		    deleted(2)
    		}
        ACCESS	read-write
        STATUS	mandatory
        DESCRIPTION
                "Create/Delete parameter. Default is created.
                Users perform an SNMP SET operation on this
                object in order to create/delete a Port definition."
        DEFVAL	{ created }
        ::= { wfAppnNodePortEntry 1 }

    wfAppnNodePortDisable OBJECT-TYPE
        SYNTAX	INTEGER {
    		    enable(1),
    		    disable(2)
    		}
        ACCESS	read-write
        STATUS	mandatory
        DESCRIPTION
                "Enable/Disable parameter. Default is enabled.
                Users perform an SNMP SET operation on this
                object in order to enable/disable this Port."
        DEFVAL	{ enable }
        ::= { wfAppnNodePortEntry 2 }

    wfAppnNodePortName OBJECT-TYPE
        SYNTAX	DisplayString
        ACCESS	read-only
        STATUS	mandatory
        DESCRIPTION
                "Administratively-assigned name for this APPN port.
                The name can be from one to eight characters."
        ::= { wfAppnNodePortEntry 3 }

    wfAppnNodePortState OBJECT-TYPE
        SYNTAX	INTEGER {
    		    inactive(1),
    		    pendactive(2),
    		    active(3),
    		    pendinact(4)
    		}
        ACCESS	read-only
        STATUS	mandatory
        DESCRIPTION
                "Indicates the current state of this port."
        DEFVAL	{ inactive }
        ::= { wfAppnNodePortEntry 4 }

    wfAppnNodePortDlcType OBJECT-TYPE
        SYNTAX	INTEGER {
    		    other(1),
    		    sdlc(2),
    		    dls(3),
    		    socket(4),
    		    ethernet(5),
    		    tokenring(6)
    		}
        ACCESS	read-only
        STATUS	mandatory
        DESCRIPTION
                "Indicates the DLC type of this port."
        ::= { wfAppnNodePortEntry 5 }

    wfAppnNodePortPortType OBJECT-TYPE
        SYNTAX	INTEGER {
    		    leased(1),
    		    switched(2),
    		    fac(3)
    		}
        ACCESS	read-write
        STATUS	mandatory
        DESCRIPTION
                "Identifies the type of line used by this port."
        DEFVAL	{ fac }
        ::= { wfAppnNodePortEntry 6 }

    wfAppnNodePortSIMRIM OBJECT-TYPE
        SYNTAX	INTEGER {
    		    yes(1),
    		    no(2)
    		}
        ACCESS	read-only
        STATUS	mandatory
        DESCRIPTION
                "Indicates whether Set Initialization Mode (SIM) and
                Receive Initialization Mode (RIM) are supported."
        ::= { wfAppnNodePortEntry 7 }

    wfAppnNodePortLsRole OBJECT-TYPE
        SYNTAX	INTEGER {
    		    primary(1),
    		    secondary(2),
    		    negot(3),
    		    abm(4)
    		}
        ACCESS	read-write
        STATUS	mandatory
        DESCRIPTION
                "Initial role for LSs activated through this port,
                where 'abm' indicates asynchronous balance mode."
        DEFVAL	{ negot }
        ::= { wfAppnNodePortEntry 8 }

    wfAppnNodePortMaxRcvBtuSize OBJECT-TYPE
        SYNTAX	INTEGER(256..4105)
        ACCESS	read-write
        STATUS	mandatory
        DESCRIPTION
                "Maximum Basic Transmission Size (BTU) that a
                link station on this port can receive."
        DEFVAL	{ 1470 }
        ::= { wfAppnNodePortEntry 9 }

    wfAppnNodePortMaxIframeWindow OBJECT-TYPE
        SYNTAX	INTEGER(0..127)
        ACCESS	read-write
        STATUS	mandatory
        DESCRIPTION
                "Maximum number of I-frames that can be received
                by the XID sender before an acknowledgement is received."
        DEFVAL	{ 7 }
        ::= { wfAppnNodePortEntry 10 }

    wfAppnNodePortDefLsGoodXids OBJECT-TYPE
        SYNTAX	Counter
        ACCESS	read-only
        STATUS	mandatory
        DESCRIPTION
                "The total number of successful XIDs that have occurred
                on all defined link stations on this port since the last
                time this port was started."
        ::= { wfAppnNodePortEntry 11 }

    wfAppnNodePortDefLsBadXids OBJECT-TYPE
        SYNTAX	Counter
        ACCESS	read-only
        STATUS	mandatory
        DESCRIPTION
                "The total number of unsuccessful XIDs that have occurred
                on all defined link stations on this port since the last
                time this port was started."
        ::= { wfAppnNodePortEntry 12 }

    wfAppnNodePortDynLsGoodXids OBJECT-TYPE
        SYNTAX	Counter
        ACCESS	read-only
        STATUS	mandatory
        DESCRIPTION
                "The total number of successful XIDs that have occurred
                on all dynamic link stations on this port since the last
                time this port was started."
        ::= { wfAppnNodePortEntry 13 }

    wfAppnNodePortDynLsBadXids OBJECT-TYPE
        SYNTAX	Counter
        ACCESS	read-only
        STATUS	mandatory
        DESCRIPTION
                "The total number of unsuccessful XIDs that have occurred
                on all dynamic link stations on this port since the last
                time this port was started."
        ::= { wfAppnNodePortEntry 14 }

    wfAppnNodePortDlcName OBJECT-TYPE
        SYNTAX	DisplayString
        ACCESS	read-write
        STATUS	mandatory
        DESCRIPTION
                "This is the 8-character name of the DLC which supports this Port"
        ::= { wfAppnNodePortEntry 15 }

    wfAppnNodePortNumber OBJECT-TYPE
        SYNTAX	INTEGER
        ACCESS	read-write
        STATUS	mandatory
        DESCRIPTION
                "This is a unique number for this Port on the DLC"
        ::= { wfAppnNodePortEntry 16 }

    wfAppnNodePortTotLinkActLim OBJECT-TYPE
        SYNTAX	INTEGER {
    		    neg(1),
    		    pri(256)
    		}
        ACCESS	read-write
        STATUS	mandatory
        DESCRIPTION
                "This specifies the maximum link activation limit for this Port.
                The maximum value depends on the LS Role and Port Type, as follows:
                     Port Type       LS Role         Max Act Lim  Inb   Out
                     Switched        <any>                1        1     1
                     Leased          Secondary            1        1     0
                     Leased          Negotiable           1        0     0
                     Leased          Primary             256       0    256
                     SATF            <any>               256      128   128"
        DEFVAL	{ pri }
        ::= { wfAppnNodePortEntry 17 }

    wfAppnNodePortInbLinkActLim OBJECT-TYPE
        SYNTAX	INTEGER {
    		    sec(1),
    		    satf(128)
    		}
        ACCESS	read-write
        STATUS	mandatory
        DESCRIPTION
                "This specifies the maximum inbound link activation
                limit for this Port. This value plus next one must total
                less than or equal to the total link activation limit."
        DEFVAL	{ satf }
        ::= { wfAppnNodePortEntry 18 }

    wfAppnNodePortOutLinkActLim OBJECT-TYPE
        SYNTAX	INTEGER {
    		    switched(1),
    		    satf(128),
    		    pri(256)
    		}
        ACCESS	read-write
        STATUS	mandatory
        DESCRIPTION
                "This specifies the maximum outbound link activation
                limit for this Port. This value plus previous one must total
                less than or equal to the total link activation limit."
        DEFVAL	{ satf }
        ::= { wfAppnNodePortEntry 19 }

    wfAppnNodePortActXidExchangeLimit OBJECT-TYPE
        SYNTAX	INTEGER {
    		    def(12)
    		}
        ACCESS	read-write
        STATUS	mandatory
        DESCRIPTION
                "This specifies the maximum number of activation XIDs
                which will be sent before the Port is considered inoperable"
        DEFVAL	{ def }
        ::= { wfAppnNodePortEntry 20 }

    wfAppnNodePortNonActXidExchangeLimit OBJECT-TYPE
        SYNTAX	INTEGER {
    		    def(5)
    		}
        ACCESS	read-write
        STATUS	mandatory
        DESCRIPTION
                "This specifies the maximum number of non-activation XIDs
                which will be sent before the Port is considered inoperable"
        DEFVAL	{ def }
        ::= { wfAppnNodePortEntry 21 }

    wfAppnNodePortLsXmitRcvCap OBJECT-TYPE
        SYNTAX	INTEGER {
    		    tws(1),
    		    twa(2)
    		}
        ACCESS	read-write
        STATUS	mandatory
        DESCRIPTION
                "This specifies if the Port can receive Two-Way Simultaneous or
                Two-Way Alternate"
        DEFVAL	{ tws }
        ::= { wfAppnNodePortEntry 22 }

    wfAppnNodePortTargetPacingCount OBJECT-TYPE
        SYNTAX	INTEGER(1..32767)
        ACCESS	read-write
        STATUS	mandatory
        DESCRIPTION
                "This specifies the target pacing count for BINDs on this Port"
        DEFVAL	{ 32 }
        ::= { wfAppnNodePortEntry 23 }

    wfAppnNodePortMaxSendBtuSize OBJECT-TYPE
        SYNTAX	INTEGER(256..4105)
        ACCESS	read-write
        STATUS	mandatory
        DESCRIPTION
                "This specifies the Maximum BTU Size which can be sent out this Port"
        DEFVAL	{ 1470 }
        ::= { wfAppnNodePortEntry 24 }

    wfAppnNodePortImplicitCpSessions OBJECT-TYPE
        SYNTAX	INTEGER {
    		    yes(1),
    		    no(2)
    		}
        ACCESS	read-write
        STATUS	mandatory
        DESCRIPTION
                "This specifies whether CP-CP sessions are permitted with implicit link stations
                on this Port"
        DEFVAL	{ yes }
        ::= { wfAppnNodePortEntry 25 }

    wfAppnNodePortImplicitLimResource OBJECT-TYPE
        SYNTAX	INTEGER {
    		    yes(1),
    		    no(2)
    		}
        ACCESS	read-write
        STATUS	mandatory
        DESCRIPTION
                "This specifies whether implicit link stations on this Port should be defined as
                limited resources"
        DEFVAL	{ no }
        ::= { wfAppnNodePortEntry 26 }

    wfAppnNodePortImplicitEffCap OBJECT-TYPE
        SYNTAX	INTEGER(0..255)
        ACCESS	read-write
        STATUS	mandatory
        DESCRIPTION
                "The effective capacity is an integer value that indicates
                the kilo bits per second.
                It is derived from the link bandwidth and maximum load
                factor with the range of 0 thru 255.
                This is an administratively assigned value for use with TGs
                to implicit link stations on this Port.
                DEVIATION: 6611 mib uses range of 0 thru 603,979,776."
        DEFVAL	{ 133 }
        ::= { wfAppnNodePortEntry 27 }

    wfAppnNodePortImplicitConnCost OBJECT-TYPE
        SYNTAX	INTEGER(0..255)
        ACCESS	read-write
        STATUS	mandatory
        DESCRIPTION
                "Cost per connect time: a value representing
                the relative cost per unit of time to use
                the TG. Range is from 0, which means no cost,
                to 255, which indicates maximum cost.
                This is an administratively assigned value for use with TGs
                to implicit link stations on this Port."
        DEFVAL	{ 128 }
        ::= { wfAppnNodePortEntry 28 }

    wfAppnNodePortImplicitByteCost OBJECT-TYPE
        SYNTAX	INTEGER(0..255)
        ACCESS	read-write
        STATUS	mandatory
        DESCRIPTION
                "Relative cost of transmitting a byte over this link.
                Range is from 0 (lowest cost) to 255.
                This is an administratively assigned value for use with TGs
                to implicit link stations on this Port."
        DEFVAL	{ 128 }
        ::= { wfAppnNodePortEntry 29 }

    wfAppnNodePortImplicitSecurity OBJECT-TYPE
        SYNTAX	INTEGER(0..255)
        ACCESS	read-write
        STATUS	mandatory
        DESCRIPTION
                "The security is represented as an integer with a range of
                1 thru 255 with the most common values enumerated as
                defined above.
                This is an administratively assigned value for use with TGs
                to implicit link stations on this Port."
        DEFVAL	{ 1 }
        ::= { wfAppnNodePortEntry 30 }

    wfAppnNodePortImplicitDelay OBJECT-TYPE
        SYNTAX  INTEGER {
                negligible(1),
                terrestrial(2),
                packet(3),
                long(4),
                maximum(5)                
                }
        ACCESS	read-write
        STATUS	mandatory
        DESCRIPTION
                "Relative amount of time that it takes for a signal to
                travel the length of the logical link.
                This is an administratively assigned value for use with TGs
                to implicit link stations on this Port.
                DEVIATION: 6611 MIB, uses units of microseconds."
        DEFVAL  { negligible }
        ::= { wfAppnNodePortEntry 31 }

    wfAppnNodePortImplicitUsr1 OBJECT-TYPE
        SYNTAX	INTEGER(0..255)
        ACCESS	read-write
        STATUS	mandatory
        DESCRIPTION
                "First user-defined TG characteristic for this TG with
                a range of 0-255.
                This is an administratively assigned value for use with TGs
                to implicit link stations on this Port."
        DEFVAL	{ 128 }
        ::= { wfAppnNodePortEntry 32 }

    wfAppnNodePortImplicitUsr2 OBJECT-TYPE
        SYNTAX	INTEGER(0..255)
        ACCESS	read-write
        STATUS	mandatory
        DESCRIPTION
                "Second user-defined TG characteristic for this TG with
                a range of 0-255.
                This is an administratively assigned value for use with TGs
                to implicit link stations on this Port."
        DEFVAL	{ 128 }
        ::= { wfAppnNodePortEntry 33 }

    wfAppnNodePortImplicitUsr3 OBJECT-TYPE
        SYNTAX	INTEGER(0..255)
        ACCESS	read-write
        STATUS	mandatory
        DESCRIPTION
                "Third user-defined TG characteristic for this TG with
                a range of 0-255.
                This is an administratively assigned value for use with TGs
                to implicit link stations on this Port."
        DEFVAL	{ 128 }
        ::= { wfAppnNodePortEntry 34 }

    wfAppnNodePortImplicitHprDisable OBJECT-TYPE
        SYNTAX	INTEGER {
    		    enable(1),
    		    disable(2)
    		}
        ACCESS	read-write
        STATUS	mandatory
        DESCRIPTION
                "This specifies if HPR can be used with implicit
                link stations on this Port"
        DEFVAL	{ enable }
        ::= { wfAppnNodePortEntry 35 }

    wfAppnNodePortImplicitHprLlErrorDisable OBJECT-TYPE
        SYNTAX	INTEGER {
    		    enable(1),
    		    disable(2)
    		}
        ACCESS	read-write
        STATUS	mandatory
        DESCRIPTION
                "This specifies if Link-Level Error recovery is to be used on implicit
                link stations which support HPR on this Port.
                NOTE: This field does not enable/disable HPRs selective retransmission 
                algorithm. HPR will perform selective retransmission on data whether or not 
                error recovery is also done by the link level protocol."
        DEFVAL	{ disable }
        ::= { wfAppnNodePortEntry 36 }

    wfAppnNodePortImplicitLinkDeactTime OBJECT-TYPE
        SYNTAX	INTEGER(5..2147483647)
        ACCESS	read-write
        STATUS	mandatory
        DESCRIPTION
                "This indicates the time in seconds before implicit Link Stations on this Port
                 will be deactivated if it is an HPR limited Resource."
        DEFVAL	{ 120 }
        ::= { wfAppnNodePortEntry 37 }

    wfAppnNodePortDlcData OBJECT-TYPE
        SYNTAX	OCTET STRING
        ACCESS	read-write
        STATUS	mandatory
        DESCRIPTION
                "This specifies the local DLC address to be used by this port"
        ::= { wfAppnNodePortEntry 38 }

    wfAppnNodePortHprDlcData OBJECT-TYPE
        SYNTAX	OCTET STRING
        ACCESS	read-write
        STATUS	mandatory
        DESCRIPTION
                "This specifies the HPR address to be used by this port"
        DEFVAL	{ 'c8'h }
        ::= { wfAppnNodePortEntry 39 }

    wfAppnNodePortImplicitDlurDisable OBJECT-TYPE
        SYNTAX	INTEGER {
    		    enable(1),
    		    disable(2)
    		}
        ACCESS	read-write
        STATUS	mandatory   
        DESCRIPTION
                "This specifies if HPR can be used with implicit
                link stations on this Port"
        DEFVAL	{ disable }
        ::= { wfAppnNodePortEntry 40 }

    wfAppnNodePortImplicitUplinkToEN OBJECT-TYPE
        SYNTAX  INTEGER {
                    enable(1),
                    disable(2)
                }
        ACCESS  read-write
        STATUS  mandatory   
        DESCRIPTION
                " For BrNN specifies whether the implicit Link Stations off this port are 
                uplink or downlink if the adjacent node is an EN. "
        DEFVAL  { disable }
        ::= { wfAppnNodePortEntry 41 }
	

    wfAppnNodeLsTable OBJECT-TYPE
        SYNTAX	SEQUENCE OF WfAppnNodeLsEntry
        ACCESS	not-accessible
        STATUS	mandatory
        DESCRIPTION
                "This table contains detail information about
                link station configuration"
        ::= { wfAppnNode 4 }

    wfAppnNodeLsEntry OBJECT-TYPE
        SYNTAX	WfAppnNodeLsEntry
        ACCESS	not-accessible
        STATUS	mandatory
        DESCRIPTION
                "An entry in wfAppnNodePortTable.
                This table is indexed by the link station name"
        INDEX	{ wfAppnNodeLsName }
        ::= { wfAppnNodeLsTable 1 }

    WfAppnNodeLsEntry ::= SEQUENCE {
    	    wfAppnNodeLsDelete
    		INTEGER,
    	    wfAppnNodeLsDisable
    		INTEGER,
    	    wfAppnNodeLsName
    		DisplayString,
    	    wfAppnNodeLsPortName
    		DisplayString,
    	    wfAppnNodeLsState
    		INTEGER,
    	    wfAppnNodeLsCpName
    		DisplayString,
    	    wfAppnNodeLsTgNum
    		INTEGER,
    	    wfAppnNodeLsLimResource
    		INTEGER,
    	    wfAppnNodeLsMigration
    		INTEGER,
    	    wfAppnNodeLsBlockNum
    		DisplayString,
    	    wfAppnNodeLsIdNum
    		DisplayString,
    	    wfAppnNodeLsCpCpSession
    		INTEGER,
    	    wfAppnNodeLsTargetPacingCount
    		INTEGER,
    	    wfAppnNodeLsMaxSendBtuSize
    		INTEGER,
    	    wfAppnNodeLsEffCap
    		INTEGER,
    	    wfAppnNodeLsConnCost
    		INTEGER,
    	    wfAppnNodeLsByteCost
    		INTEGER,
    	    wfAppnNodeLsSecurity
    		INTEGER,
    	    wfAppnNodeLsDelay
    		INTEGER,
    	    wfAppnNodeLsUsr1
    		INTEGER,
    	    wfAppnNodeLsUsr2
    		INTEGER,
    	    wfAppnNodeLsUsr3
    		INTEGER,
    	    wfAppnNodeLsCpType
    		INTEGER,
    	    wfAppnNodeLsAutoActivateDisable
    		INTEGER,
    	    wfAppnNodeLsSolicitSscpSessionsDisable
    		INTEGER,
    	    wfAppnNodeLsUseDefaultTgChars
    		INTEGER,
    	    wfAppnNodeLsLinkData
    		OCTET STRING,
    	    wfAppnNodeLsDlurDisable
    		INTEGER,
    	    wfAppnNodeLsDspuName
    		DisplayString,
    	    wfAppnNodeLsDlusName
    		DisplayString,
    	    wfAppnNodeLsBackupDlusName
    		DisplayString,
    	    wfAppnNodeLsHprDisable
    		INTEGER,
    	    wfAppnNodeLsHprLlErrorDisable
    		INTEGER,
    	    wfAppnNodeLsLinkDeactTime
    		INTEGER,
	    wfAppnNodeLsLinkRetryCount
    		INTEGER,
            wfAppnNodeLsBranchLinkType
                INTEGER,
            wfAppnNodeLsAdjBrNNLinkSupp
                INTEGER,
	    wfAppnNodeLsDefaultNNS
	        INTEGER
        }

    wfAppnNodeLsDelete OBJECT-TYPE
        SYNTAX	INTEGER {
    		    created(1),
    		    deleted(2)
    		}
        ACCESS	read-write
        STATUS	mandatory
        DESCRIPTION
                "Create/Delete parameter. Default is created.
                Users perform an SNMP SET operation on this
                object in order to create/delete a Link Station definition."
        DEFVAL	{ created }
        ::= { wfAppnNodeLsEntry 1 }

    wfAppnNodeLsDisable OBJECT-TYPE
        SYNTAX	INTEGER {
    		    enable(1),
    		    disable(2)
    		}
        ACCESS	read-write
        STATUS	mandatory
        DESCRIPTION
                "Enable/Disable parameter. Default is enabled.
                Users perform an SNMP SET operation on this
                object in order to enable/disable this Link Station."
        DEFVAL	{ enable }
        ::= { wfAppnNodeLsEntry 2 }

    wfAppnNodeLsName OBJECT-TYPE
        SYNTAX	DisplayString
        ACCESS	read-only
        STATUS	mandatory
        DESCRIPTION
                "Administratively-assigned name for the link station.
                The name can be from one to eight characters."
        ::= { wfAppnNodeLsEntry 3 }

    wfAppnNodeLsPortName OBJECT-TYPE
        SYNTAX	DisplayString
        ACCESS	read-write
        STATUS	mandatory
        DESCRIPTION
                "Administratively-assigned name for the port.
                The name can be from one to eight characters."
        ::= { wfAppnNodeLsEntry 4 }

    wfAppnNodeLsState OBJECT-TYPE
        SYNTAX	INTEGER {
    		    inactive(1),
    		    pendactive(2),
    		    active(3),
    		    pendinact(4)
    		}
        ACCESS	read-only
        STATUS	mandatory
        DESCRIPTION
                "State of this link station."
        DEFVAL	{ inactive }
        ::= { wfAppnNodeLsEntry 5 }

    wfAppnNodeLsCpName OBJECT-TYPE
        SYNTAX	DisplayString
        ACCESS	read-write
        STATUS	mandatory
        DESCRIPTION
                "Fully-qualified name of the adjacent node for this link
                station.  The name can be from three to seventeen characters.
                Format is netid.cpname."
        ::= { wfAppnNodeLsEntry 6 }

    wfAppnNodeLsTgNum OBJECT-TYPE
        SYNTAX	INTEGER(1..20)
        ACCESS	read-write
        STATUS	mandatory
        DESCRIPTION
                "Number associated with the TG to this link station.
                Range (  1 -  20) Predefined values for auto-activation"
        DEFVAL	{ 1 }
        ::= { wfAppnNodeLsEntry 7 }

    wfAppnNodeLsLimResource OBJECT-TYPE
        SYNTAX	INTEGER {
    		    yes(1),
    		    no(2)
    		}
        ACCESS	read-write
        STATUS	mandatory
        DESCRIPTION
                "Indicates whether the link station is
                a limited resource.  If it is, the TG
                is deactivated when there are no sessions."
        DEFVAL	{ no }
        ::= { wfAppnNodeLsEntry 8 }

    wfAppnNodeLsMigration OBJECT-TYPE
        SYNTAX	INTEGER {
    		    xid0(1),
    		    uplevel(2),
    		    xid3(3),
    		    noxid(4)
    		}
        ACCESS	read-write
        STATUS	mandatory
        DESCRIPTION
                "Indicates whether this link station will be used
                for connections to down-level or migration partners.
                            1 Indicates that this is a back-level node supporting XID0
                 protocols.
                            2 Indicates that this is an up-level node supporting XID3
                 protocols including the Network Name CV
                            3 Indicates that this is a back-level node supporting XID3
                 protocols (but does not include the Network Name CV)
                            4 Indicates that this is a back-level node which does not
                 support XID protocols. (This is valid on NONSWITCHED
                 ports, and is not valid on negotiable ports."
        DEFVAL	{ uplevel }
        ::= { wfAppnNodeLsEntry 9 }

    wfAppnNodeLsBlockNum OBJECT-TYPE
        SYNTAX	DisplayString
        ACCESS	read-write
        STATUS	mandatory
        DESCRIPTION
                "The block number is the first three digits of the node_id.
                These 3 hexideimal digits identify the product and are not
                configurable."
        ::= { wfAppnNodeLsEntry 10 }

    wfAppnNodeLsIdNum OBJECT-TYPE
        SYNTAX	DisplayString
        ACCESS	read-write
        STATUS	mandatory
        DESCRIPTION
                "The ID number is the last 5 digits of the node_id.
                These 5 hexadecimal digits are administratively defined and
                combined with the 3 digit block number form the node_id.
                This node_id is used to identify the local node and is include
                in APPN alerts as well as being included in XIDs.  A unique
                value is required for connections to SNA sub-area."
        ::= { wfAppnNodeLsEntry 11 }

    wfAppnNodeLsCpCpSession OBJECT-TYPE
        SYNTAX	INTEGER {
    		    yes(1),
    		    no(2)
    		}
        ACCESS	read-write
        STATUS	mandatory
        DESCRIPTION
                "Indicates whether CP-CP sessions are
                supported by this link station."
        DEFVAL	{ yes }
        ::= { wfAppnNodeLsEntry 12 }

    wfAppnNodeLsTargetPacingCount OBJECT-TYPE
        SYNTAX	INTEGER(0..32767)
        ACCESS	read-write
        STATUS	mandatory
        DESCRIPTION
                "Numeric value between 0 and 32767 inclusive indicating
                the desired pacing window size for BINDs on this TG.
                The number is significant only when fixed bind pacing
                is being performed."
        DEFVAL	{ 4 }
        ::= { wfAppnNodeLsEntry 13 }

    wfAppnNodeLsMaxSendBtuSize OBJECT-TYPE
        SYNTAX	INTEGER(0..4105)
        ACCESS	read-write
        STATUS	mandatory
        DESCRIPTION
                "Numeric value between 0 and 4105 inclusive indicating
                the desired number of bytes in a Basic Transmission Unit
                (BTU) that can be sent on this TG.
                This is an administratively assigned value."
        DEFVAL	{ 1470 }
        ::= { wfAppnNodeLsEntry 14 }

    wfAppnNodeLsEffCap OBJECT-TYPE
        SYNTAX	INTEGER(0..255)
        ACCESS	read-write
        STATUS	mandatory
        DESCRIPTION
                "The effective capacity is an integer value that indicates
                the kilo bits per second.
                It is derived from the link bandwidth and maximum load
                factor with the range of 0 thru 255.
                This is an administratively assigned value for use with this TG.
                DEVIATION: 6611 mib uses range of 0 thru 603,979,776."
        DEFVAL	{ 133 }
        ::= { wfAppnNodeLsEntry 15 }

    wfAppnNodeLsConnCost OBJECT-TYPE
        SYNTAX	INTEGER(0..255)
        ACCESS	read-write
        STATUS	mandatory
        DESCRIPTION
                "Cost per connect time: a value representing
                the relative cost per unit of time to use
                the TG. Range is from 0, which means no cost,
                to 255, which indicates maximum cost.
                This is an administratively assigned value associated
                with the TG using this link station."
        DEFVAL	{ 128 }
        ::= { wfAppnNodeLsEntry 16 }

    wfAppnNodeLsByteCost OBJECT-TYPE
        SYNTAX	INTEGER(0..255)
        ACCESS	read-write
        STATUS	mandatory
        DESCRIPTION
                "Relative cost of transmitting a byte over this link.
                Range is from 0 (lowest cost) to 255.
                This is an administratively assigned value associated
                with the TG using this link station."
        DEFVAL	{ 128 }
        ::= { wfAppnNodeLsEntry 17 }

    wfAppnNodeLsSecurity OBJECT-TYPE
        SYNTAX	INTEGER(0..255)
        ACCESS	read-write
        STATUS	mandatory
        DESCRIPTION
                "The security is represented as an integer with a range of
                1 thru 255 with the most common values enumerated as
                defined above.
                This is an administratively assigned value associated
                with the TG using this link station."
        DEFVAL	{ 1 }
        ::= { wfAppnNodeLsEntry 18 }

    wfAppnNodeLsDelay OBJECT-TYPE
        SYNTAX  INTEGER {
                negligible(1),
                terrestrial(2),
                packet(3),
                long(4),
                maximum(5)                
                }
        ACCESS	read-write
        STATUS	mandatory
        DESCRIPTION
                "Relative amount of time that it takes for a signal to
                travel the length of the logical link.
                This is an administratively assigned value associated
                with the TG using this link station.
                DEVIATION: 6611 MIB, uses units of microseconds."
        DEFVAL  { negligible }
        ::= { wfAppnNodeLsEntry 19 }

    wfAppnNodeLsUsr1 OBJECT-TYPE
        SYNTAX	INTEGER(0..255)
        ACCESS	read-write
        STATUS	mandatory
        DESCRIPTION
                "First user-defined TG characteristic for this TG with
                a range of 0-255.
                This is an administratively assigned value associated
                with the TG using this link station."
        DEFVAL	{ 128 }
        ::= { wfAppnNodeLsEntry 20 }

    wfAppnNodeLsUsr2 OBJECT-TYPE
        SYNTAX	INTEGER(0..255)
        ACCESS	read-write
        STATUS	mandatory
        DESCRIPTION
                "Second user-defined TG characteristic for this TG with
                a range of 0-255.
                This is an administratively assigned value associated
                with the TG using this link station."
        DEFVAL	{ 128 }
        ::= { wfAppnNodeLsEntry 21 }

    wfAppnNodeLsUsr3 OBJECT-TYPE
        SYNTAX	INTEGER(0..255)
        ACCESS	read-write
        STATUS	mandatory
        DESCRIPTION
                "Third user-defined TG characteristic for this TG with
                a range of 0-255.
                This is an administratively assigned value associated
                with the TG using this link station."
        DEFVAL	{ 128 }
        ::= { wfAppnNodeLsEntry 22 }

    wfAppnNodeLsCpType OBJECT-TYPE
        SYNTAX	INTEGER {
    		    learn(1),
    		    nn(2),
    		    en(3),
                bllen(4),
                hostxid3(5),
                hostxid0(6),
                dspuxid(7),
                dspunoxid(8)
    		}
        ACCESS	read-write
        STATUS	mandatory
        DESCRIPTION
                "This specifies the APPN Node type of Link Station."
        DEFVAL	{ learn }
        ::= { wfAppnNodeLsEntry 23 }

    wfAppnNodeLsAutoActivateDisable OBJECT-TYPE
        SYNTAX	INTEGER {
    		    enable(1),
    		    disable(2)
    		}
        ACCESS	read-write
        STATUS	mandatory
        DESCRIPTION
                "This specifies if the link should be automatically activated
                when the Port becomes active.  Should be disabled if CP-CP sessions
                are enabled."
        DEFVAL	{ disable }
        ::= { wfAppnNodeLsEntry 24 }

    wfAppnNodeLsSolicitSscpSessionsDisable OBJECT-TYPE
        SYNTAX	INTEGER {
    		    enable(1),
    		    disable(2)
    		}
        ACCESS	read-write
        STATUS	mandatory
        DESCRIPTION
                "This specifies if SSCP Sessions should be solicited from this
                Link Station"
        DEFVAL	{ disable }
        ::= { wfAppnNodeLsEntry 25 }

    wfAppnNodeLsUseDefaultTgChars OBJECT-TYPE
        SYNTAX	INTEGER {
    		    yes(1),
    		    no(2)
    		}
        ACCESS	read-write
        STATUS	mandatory
        DESCRIPTION
                "Indicates whether the default TG characteristics specified
                for the Port should be used for this link station, or if explicit
                TG characteristics will be supplied."
        DEFVAL	{ yes }
        ::= { wfAppnNodeLsEntry 26 }

    wfAppnNodeLsLinkData OBJECT-TYPE
        SYNTAX	OCTET STRING
        ACCESS	read-write
        STATUS	mandatory
        DESCRIPTION
                "this for Link Address (MAC/SAP, SDLC Address)"
        ::= { wfAppnNodeLsEntry 27 }

    wfAppnNodeLsDlurDisable OBJECT-TYPE
        SYNTAX	INTEGER {
    		    enable(1),
    		    disable(2)
    		}
        ACCESS	read-write
        STATUS	mandatory
        DESCRIPTION
                "This specifies if the adjacent Link Station is a node to be serviced by DLUR."
        DEFVAL	{ disable }
        ::= { wfAppnNodeLsEntry 28 }

    wfAppnNodeLsDspuName OBJECT-TYPE
        SYNTAX	DisplayString
        ACCESS	read-write
        STATUS	mandatory
        DESCRIPTION
                "8-byte name of the downstream PU supported by DLUR."
        ::= { wfAppnNodeLsEntry 29 }

    wfAppnNodeLsDlusName OBJECT-TYPE
        SYNTAX	DisplayString
        ACCESS	read-write
        STATUS	mandatory
        DESCRIPTION
                "Fully-qualified name of the DLUS node which will serve this DLUR
                Link Station."
        ::= { wfAppnNodeLsEntry 30 }

    wfAppnNodeLsBackupDlusName OBJECT-TYPE
        SYNTAX	DisplayString
        ACCESS	read-write
        STATUS	mandatory
        DESCRIPTION
                "Fully-qualified name of the backup DLUS node which may serve this DLUR
                Link Station."
        ::= { wfAppnNodeLsEntry 31 }

    wfAppnNodeLsHprDisable OBJECT-TYPE
        SYNTAX	INTEGER {
    		    enable(1),
    		    disable(2)
    		}
        ACCESS	read-write
        STATUS	mandatory
        DESCRIPTION
                "This specifies if HPR is supported on this Link Station"
        DEFVAL	{ disable }
        ::= { wfAppnNodeLsEntry 32 }

    wfAppnNodeLsHprLlErrorDisable OBJECT-TYPE
        SYNTAX	INTEGER {
    		    enable(1),
    		    disable(2)
    		}
        ACCESS	read-write
        STATUS	mandatory
        DESCRIPTION
                "This specifies if Link-Level Error recovery is to be used on this
                link station.
                NOTE: This field does not enable/disable HPRs selective retransmission 
                algorithm. HPR will perform selective retransmission on data whether or not 
                error recovery is also done by the link level protocol."
        DEFVAL	{ disable }
        ::= { wfAppnNodeLsEntry 33 }

    wfAppnNodeLsLinkDeactTime OBJECT-TYPE
        SYNTAX	INTEGER(5..2147483647)
        ACCESS	read-write
        STATUS	mandatory
        DESCRIPTION
                "This indicates the time in seconds before this Link Station will be deactivated
                if it is an HPR limited Resource."
        DEFVAL	{ 120 }
        ::= { wfAppnNodeLsEntry 34 }

     wfAppnNodeLsLinkRetryCount OBJECT-TYPE
        SYNTAX	INTEGER(1..99)
        ACCESS	read-write
        STATUS	mandatory
        DESCRIPTION
		"This indicates for how many times will APPN CP component retry to
		restart the link station before it gives up, 99 default is forever."
        DEFVAL	{ 99 }
        ::= { wfAppnNodeLsEntry 35 }

     wfAppnNodeLsBranchLinkType OBJECT-TYPE
        SYNTAX  INTEGER {
                uplink(1),
                downlink(2)
        
        }
        ACCESS  read-write
        STATUS  mandatory
        DESCRIPTION
                " For BrNN specifies whether the link is an uplink or a downlink "
                                                                
        DEFVAL  { uplink }
        ::= { wfAppnNodeLsEntry 36 }

     wfAppnNodeLsAdjBrNNLinkSupp OBJECT-TYPE
        SYNTAX  INTEGER {
                allowed(1),
                required(2),
                prohibited(3)
                        }
        ACCESS  read-write
        STATUS  mandatory
        DESCRIPTION
                " Specifies whether the adjacent node is required, allowed or 
                  prohibited from being a BrNN ( i.e. an BrNN showing its NN face )."                                                           
        DEFVAL  { allowed }
        ::= { wfAppnNodeLsEntry 37 }

      wfAppnNodeLsDefaultNNS OBJECT-TYPE
        SYNTAX  INTEGER {
	            yes(1),
    		    no(2)        
        }
        ACCESS  read-write
        STATUS  mandatory
        DESCRIPTION
                " This field can be set to yes to indicate that the adjacent CP is the 
		preferred NN server "
                                                                
        DEFVAL  { no }
        ::= { wfAppnNodeLsEntry 38 }	
     



	
    wfAppnNodeLsStatusTable OBJECT-TYPE
        SYNTAX	SEQUENCE OF WfAppnNodeLsStatusEntry
        ACCESS	not-accessible
        STATUS	mandatory
        DESCRIPTION
                "This table contains detailed status information about link stations"
        ::= { wfAppnNode 5 }

    wfAppnNodeLsStatusEntry OBJECT-TYPE
        SYNTAX	WfAppnNodeLsStatusEntry
        ACCESS	not-accessible
        STATUS	mandatory
        DESCRIPTION
                "An entry in wfAppnNodeLsStatusTable.
                This table is indexed by the link station name"
        INDEX	{ wfAppnNodeLsStatusName }
        ::= { wfAppnNodeLsStatusTable 1 }

    WfAppnNodeLsStatusEntry ::= SEQUENCE {
    	    wfAppnNodeLsStatusName
    		DisplayString,
    	    wfAppnNodeLsStatusPortName
    		DisplayString,
    	    wfAppnNodeLsStatusDlcType
    		INTEGER,
    	    wfAppnNodeLsStatusDynamic
    		INTEGER,
    	    wfAppnNodeLsStatusState
    		INTEGER,
    	    wfAppnNodeLsStatusCpName
    		DisplayString,
    	    wfAppnNodeLsStatusTgNum
    		INTEGER,
    	    wfAppnNodeLsStatusLimResource
    		INTEGER,
    	    wfAppnNodeLsStatusMigration
    		INTEGER,
    	    wfAppnNodeLsStatusBlockNum
    		DisplayString,
    	    wfAppnNodeLsStatusIdNum
    		DisplayString,
    	    wfAppnNodeLsStatusCpCpSession
    		INTEGER,
    	    wfAppnNodeLsStatusTargetPacingCount
    		INTEGER,
    	    wfAppnNodeLsStatusMaxSendBtuSize
    		INTEGER,
    	    wfAppnNodeLsStatusEffCap
    		INTEGER,
    	    wfAppnNodeLsStatusConnCost
    		INTEGER,
    	    wfAppnNodeLsStatusByteCost
    		INTEGER,
    	    wfAppnNodeLsStatusSecurity
    		INTEGER,
    	    wfAppnNodeLsStatusDelay
    		INTEGER,
    	    wfAppnNodeLsStatusUsr1
    		INTEGER,
    	    wfAppnNodeLsStatusUsr2
    		INTEGER,
    	    wfAppnNodeLsStatusUsr3
    		INTEGER,
    	    wfAppnNodeLsStatusInXidBytes
    		Counter,
    	    wfAppnNodeLsStatusInMsgBytes
    		Counter,
    	    wfAppnNodeLsStatusInXidFrames
    		Counter,
    	    wfAppnNodeLsStatusInMsgFrames
    		Counter,
    	    wfAppnNodeLsStatusOutXidBytes
    		Counter,
    	    wfAppnNodeLsStatusOutMsgBytes
    		Counter,
    	    wfAppnNodeLsStatusOutXidFrames
    		Counter,
    	    wfAppnNodeLsStatusOutMsgFrames
    		Counter,
    	    wfAppnNodeLsStatusEchoRsps
    		Counter,
    	    wfAppnNodeLsStatusCurrentDelay
    		INTEGER,
    	    wfAppnNodeLsStatusMaxDelay
    		INTEGER,
    	    wfAppnNodeLsStatusMinDelay
    		INTEGER,
    	    wfAppnNodeLsStatusMaxDelayTime
    		INTEGER,
    	    wfAppnNodeLsStatusGoodXids
    		Counter,
    	    wfAppnNodeLsStatusBadXids
    		Counter,
    	    wfAppnNodeLsStatusActiveSessions
    		INTEGER,
    	    wfAppnNodeLsStatusInvalidSnaFrames
    		Counter,
    	    wfAppnNodeLsStatusInScFrames
    		Counter,
    	    wfAppnNodeLsStatusOutScFrames
    		Counter,
    	    wfAppnNodeLsStatusCpType
    		INTEGER,
    	    wfAppnNodeLsStatusStartTime
    		INTEGER,
    	    wfAppnNodeLsStatusStopTime
    		INTEGER,
    	    wfAppnNodeLsStatusUpTime
    		INTEGER,
    	    wfAppnNodeLsStatusDeactCause
    		INTEGER,
    	    wfAppnNodeLsStatusHprSupport
    		INTEGER,
    	    wfAppnNodeLsStatusHprLlErrSupport
    		INTEGER,
    	    wfAppnNodeLsStatusAnrLabel
    		INTEGER,
    	    wfAppnNodeLsStatusLinkData
    		OCTET STRING
        }

    wfAppnNodeLsStatusName OBJECT-TYPE
        SYNTAX	DisplayString
        ACCESS	read-only
        STATUS	mandatory
        DESCRIPTION
                "Administratively-assigned name for the link station.
                The name can be from one to eight characters."
        ::= { wfAppnNodeLsStatusEntry 1 }

    wfAppnNodeLsStatusPortName OBJECT-TYPE
        SYNTAX	DisplayString
        ACCESS	read-only
        STATUS	mandatory
        DESCRIPTION
                "Administratively-assigned name for the port.
                The name can be from one to eight characters."
        ::= { wfAppnNodeLsStatusEntry 2 }

    wfAppnNodeLsStatusDlcType OBJECT-TYPE
        SYNTAX	INTEGER {
    		    other(1),
    		    sdlc(2),
    		    dls(3),
    		    socket(4),
    		    ethernet(5),
    		    tokenring(6)
    		}
        ACCESS	read-only
        STATUS	mandatory
        DESCRIPTION
                "The type of DLC interface, distinguished according to
                the protocol immediately 'below' this layer."
        ::= { wfAppnNodeLsStatusEntry 3 }

    wfAppnNodeLsStatusDynamic OBJECT-TYPE
        SYNTAX	INTEGER {
    		    enable(1),
    		    disable(2)
    		}
        ACCESS	read-only
        STATUS	mandatory
        DESCRIPTION
                "Identifies whether this resource is a dynamic link station.
                Dynamic link stations are created when adjacent nodes
                that have not been locally defined establish a connection
                with this node."
        ::= { wfAppnNodeLsStatusEntry 4 }

    wfAppnNodeLsStatusState OBJECT-TYPE
        SYNTAX	INTEGER {
    		    inactive(1),
    		    pendactive(2),
    		    active(3),
    		    pendinact(4)
    		}
        ACCESS	read-only
        STATUS	mandatory
        DESCRIPTION
                "State of this link station."
        ::= { wfAppnNodeLsStatusEntry 5 }

    wfAppnNodeLsStatusCpName OBJECT-TYPE
        SYNTAX	DisplayString
        ACCESS	read-only
        STATUS	mandatory
        DESCRIPTION
                "Fully-qualified name of the adjacent node for this link
                station.  The name can be from three to seventeen characters.
                Format is netid.cpname."
        ::= { wfAppnNodeLsStatusEntry 6 }

    wfAppnNodeLsStatusTgNum OBJECT-TYPE
        SYNTAX	INTEGER
        ACCESS	read-only
        STATUS	mandatory
        DESCRIPTION
                "Number associated with the TG to this link station."
        ::= { wfAppnNodeLsStatusEntry 7 }

    wfAppnNodeLsStatusLimResource OBJECT-TYPE
        SYNTAX	INTEGER {
    		    yes(1),
    		    no(2)
    		}
        ACCESS	read-only
        STATUS	mandatory
        DESCRIPTION
                "Indicates whether the link station is
                a limited resource.  If it is, the TG
                is deactivated when there are no sessions."
        ::= { wfAppnNodeLsStatusEntry 8 }

    wfAppnNodeLsStatusMigration OBJECT-TYPE
        SYNTAX	INTEGER {
    		    xid0(1),
    		    uplevel(2),
    		    xid3(3),
    		    noxid(4)
    		}
        ACCESS	read-only
        STATUS	mandatory
        DESCRIPTION
                "Indicates whether this link station will be used
                for connections to down-level or migration partners.
                1 Indicates that this is a back-level node supporting XID0
                  protocols.
                2 Indicates that this is an up-level node supporting XID3
                  protocols including the Network Name CV
                3 Indicates that this is a back-level node supporting XID3
                  protocols (but does not include the Network Name CV)
                4 Indicates that this is a back-level node which does not
                  support XID protocols. (This is valid on NONSWITCHED
                  ports, and is not valid on negotiable ports."
        ::= { wfAppnNodeLsStatusEntry 9 }

    wfAppnNodeLsStatusBlockNum OBJECT-TYPE
        SYNTAX	DisplayString
        ACCESS	read-only
        STATUS	mandatory
        DESCRIPTION
                "The block number is the first three digits of the node_id.
                These 3 hexideimal digits identify the product and are not
                configurable."
        ::= { wfAppnNodeLsStatusEntry 10 }

    wfAppnNodeLsStatusIdNum OBJECT-TYPE
        SYNTAX	DisplayString
        ACCESS	read-only
        STATUS	mandatory
        DESCRIPTION
                "The ID number is the last 5 digits of the node_id.
                These 5 hexadecimal digits are administratively defined and
                combined with the 3 digit block number form the node_id.
                This node_id is used to identify the local node and is include
                in APPN alerts as well as being included in XIDs.  A unique
                value is required for connections to SNA sub-area."
        ::= { wfAppnNodeLsStatusEntry 11 }

    wfAppnNodeLsStatusCpCpSession OBJECT-TYPE
        SYNTAX	INTEGER {
    		    yes(1),
    		    no(2)
    		}
        ACCESS	read-only
        STATUS	mandatory
        DESCRIPTION
                "Indicates whether CP-CP sessions are
                supported by this link station."
        ::= { wfAppnNodeLsStatusEntry 12 }

    wfAppnNodeLsStatusTargetPacingCount OBJECT-TYPE
        SYNTAX	INTEGER
        ACCESS	read-only
        STATUS	mandatory
        DESCRIPTION
                "Numeric value between 0 and 32767 inclusive indicating
                the desired pacing window size for BINDs on this TG.
                The number is significant only when fixed bind pacing
                is being performed."
        ::= { wfAppnNodeLsStatusEntry 13 }

    wfAppnNodeLsStatusMaxSendBtuSize OBJECT-TYPE
        SYNTAX	INTEGER
        ACCESS	read-only
        STATUS	mandatory
        DESCRIPTION
                "Numeric value between 0 and 32767 inclusive indicating
                the desired number of bytes in a Basic Transmission Unit
                (BTU) that can be sent on this TG.
                This is an administratively assigned value."
        ::= { wfAppnNodeLsStatusEntry 14 }

    wfAppnNodeLsStatusEffCap OBJECT-TYPE
        SYNTAX	INTEGER(0..255)
        ACCESS	read-only
        STATUS	mandatory
        DESCRIPTION
                "The effective capacity is an integer value that indicates
                the kilo bits per second.
                It is derived from the link bandwidth and maximum load
                factor with the range of 0 thru 255.
                This is an administratively assigned value for use with this TG.
                DEVIATION: 6611 mib uses range of 0 thru 603,979,776."
        ::= { wfAppnNodeLsStatusEntry 15 }

    wfAppnNodeLsStatusConnCost OBJECT-TYPE
        SYNTAX	INTEGER(0..255)
        ACCESS	read-only
        STATUS	mandatory
        DESCRIPTION
                "Cost per connect time: a value representing
                the relative cost per unit of time to use
                the TG. Range is from 0, which means no cost,
                to 255, which indicates maximum cost.
                This is an administratively assigned value associated
                with the TG using this link station."
        ::= { wfAppnNodeLsStatusEntry 16 }

    wfAppnNodeLsStatusByteCost OBJECT-TYPE
        SYNTAX	INTEGER(0..255)
        ACCESS	read-only
        STATUS	mandatory
        DESCRIPTION
                "Relative cost of transmitting a byte over this link.
                Range is from 0 (lowest cost) to 255.
                This is an administratively assigned value associated
                with the TG using this link station."
        ::= { wfAppnNodeLsStatusEntry 17 }

    wfAppnNodeLsStatusSecurity OBJECT-TYPE
        SYNTAX	INTEGER(0..255)
        ACCESS	read-only
        STATUS	mandatory
        DESCRIPTION
                "The security is represented as an integer with a range of
                1 thru 255 with the most common values enumerated as
                defined above.
                This is an administratively assigned value associated
                with the TG using this link station."
        ::= { wfAppnNodeLsStatusEntry 18 }

    wfAppnNodeLsStatusDelay OBJECT-TYPE
        SYNTAX  INTEGER {
                negligible(1),
                terrestrial(2),
                packet(3),
                long(4),
                maximum(5)                
                }
        ACCESS	read-only
        STATUS	mandatory
        DESCRIPTION
                "Relative amount of time that it takes for a signal to
                travel the length of the logical link.
                This is an administratively assigned value associated
                with the TG using this link station.
                DEVIATION: 6611 MIB, uses units of microseconds."
        DEFVAL  { negligible }
        ::= { wfAppnNodeLsStatusEntry 19 }

    wfAppnNodeLsStatusUsr1 OBJECT-TYPE
        SYNTAX	INTEGER(0..255)
        ACCESS	read-only
        STATUS	mandatory
        DESCRIPTION
                "First user-defined TG characteristic for this TG with
                a range of 0-255.
                This is an administratively assigned value associated
                with the TG using this link station."
        ::= { wfAppnNodeLsStatusEntry 20 }

    wfAppnNodeLsStatusUsr2 OBJECT-TYPE
        SYNTAX	INTEGER(0..255)
        ACCESS	read-only
        STATUS	mandatory
        DESCRIPTION
                "Second user-defined TG characteristic for this TG with
                a range of 0-255.
                This is an administratively assigned value associated
                with the TG using this link station."
        ::= { wfAppnNodeLsStatusEntry 21 }

    wfAppnNodeLsStatusUsr3 OBJECT-TYPE
        SYNTAX	INTEGER(0..255)
        ACCESS	read-only
        STATUS	mandatory
        DESCRIPTION
                "Third user-defined TG characteristic for this TG with
                a range of 0-255.
                This is an administratively assigned value associated
                with the TG using this link station."
        ::= { wfAppnNodeLsStatusEntry 22 }

    wfAppnNodeLsStatusInXidBytes OBJECT-TYPE
        SYNTAX	Counter
        ACCESS	read-only
        STATUS	mandatory
        DESCRIPTION
                "Number of XID bytes received."
        ::= { wfAppnNodeLsStatusEntry 23 }

    wfAppnNodeLsStatusInMsgBytes OBJECT-TYPE
        SYNTAX	Counter
        ACCESS	read-only
        STATUS	mandatory
        DESCRIPTION
                "Number of message (I-frame) bytes received."
        ::= { wfAppnNodeLsStatusEntry 24 }

    wfAppnNodeLsStatusInXidFrames OBJECT-TYPE
        SYNTAX	Counter
        ACCESS	read-only
        STATUS	mandatory
        DESCRIPTION
                "Number of XID frames received."
        ::= { wfAppnNodeLsStatusEntry 25 }

    wfAppnNodeLsStatusInMsgFrames OBJECT-TYPE
        SYNTAX	Counter
        ACCESS	read-only
        STATUS	mandatory
        DESCRIPTION
                "Number of message (I-frame) frames received."
        ::= { wfAppnNodeLsStatusEntry 26 }

    wfAppnNodeLsStatusOutXidBytes OBJECT-TYPE
        SYNTAX	Counter
        ACCESS	read-only
        STATUS	mandatory
        DESCRIPTION
                "Number of XID bytes sent."
        ::= { wfAppnNodeLsStatusEntry 27 }

    wfAppnNodeLsStatusOutMsgBytes OBJECT-TYPE
        SYNTAX	Counter
        ACCESS	read-only
        STATUS	mandatory
        DESCRIPTION
                "Number of message (I-frame) bytes sent."
        ::= { wfAppnNodeLsStatusEntry 28 }

    wfAppnNodeLsStatusOutXidFrames OBJECT-TYPE
        SYNTAX	Counter
        ACCESS	read-only
        STATUS	mandatory
        DESCRIPTION
                "Number of XID frames sent."
        ::= { wfAppnNodeLsStatusEntry 29 }

    wfAppnNodeLsStatusOutMsgFrames OBJECT-TYPE
        SYNTAX	Counter
        ACCESS	read-only
        STATUS	mandatory
        DESCRIPTION
                "Number of message (I-frame) frames sent."
        ::= { wfAppnNodeLsStatusEntry 30 }

    wfAppnNodeLsStatusEchoRsps OBJECT-TYPE
        SYNTAX	Counter
        ACCESS	read-only
        STATUS	mandatory
        DESCRIPTION
                "Number of responses returned from adjacent link station.
                A response should be returned for each test frame sent by
                this node.
                Test frames are sent to adjacent nodes periodically to
                verify connectivity and to measure that actual round trip
                time, that is the time the test frame is sent until the
                response is received."
        ::= { wfAppnNodeLsStatusEntry 31 }

    wfAppnNodeLsStatusCurrentDelay OBJECT-TYPE
        SYNTAX	INTEGER
        ACCESS	read-only
        STATUS	mandatory
        DESCRIPTION
                "The time that it took for the last test signal to be
                sent and returned from this link station to the
                adjacent links station.
                This time is represented in milliseconds."
        ::= { wfAppnNodeLsStatusEntry 32 }

    wfAppnNodeLsStatusMaxDelay OBJECT-TYPE
        SYNTAX	INTEGER
        ACCESS	read-only
        STATUS	mandatory
        DESCRIPTION
                "The longest time it took for a test signal
                to be sent and returned from this link station to the
                adjacent links station.
                This time is represented in milliseconds ."
        ::= { wfAppnNodeLsStatusEntry 33 }

    wfAppnNodeLsStatusMinDelay OBJECT-TYPE
        SYNTAX	INTEGER
        ACCESS	read-only
        STATUS	mandatory
        DESCRIPTION
                "The shortest time it took for a test signal
                to be sent and returned from this link station to the
                adjacent links station.
                This time is represented in milliseconds."
        ::= { wfAppnNodeLsStatusEntry 34 }

    wfAppnNodeLsStatusMaxDelayTime OBJECT-TYPE
        SYNTAX	INTEGER
        ACCESS	read-only
        STATUS	mandatory
        DESCRIPTION
                "The time (since system up in hundredth of seconds)
                when the longest delay occurred.
                This time can be used to identify when this high
                water mark occurred in relation to the last initialization
                of the APPN node."
        ::= { wfAppnNodeLsStatusEntry 35 }

    wfAppnNodeLsStatusGoodXids OBJECT-TYPE
        SYNTAX	Counter
        ACCESS	read-only
        STATUS	mandatory
        DESCRIPTION
                "The total number of successful XIDs that have occurred
                on this link station since the time it was started."
        ::= { wfAppnNodeLsStatusEntry 36 }

    wfAppnNodeLsStatusBadXids OBJECT-TYPE
        SYNTAX	Counter
        ACCESS	read-only
        STATUS	mandatory
        DESCRIPTION
                "The total number of unsuccessful XIDs that have occurred
                on this link station since the time it was started."
        ::= { wfAppnNodeLsStatusEntry 37 }

    wfAppnNodeLsStatusActiveSessions OBJECT-TYPE
        SYNTAX	INTEGER
        ACCESS	read-only
        STATUS	mandatory
        DESCRIPTION
                "Number of Active Sessions (Endpoint and ISR) using this Link Station."
        ::= { wfAppnNodeLsStatusEntry 38 }

    wfAppnNodeLsStatusInvalidSnaFrames OBJECT-TYPE
        SYNTAX	Counter
        ACCESS	read-only
        STATUS	mandatory
        DESCRIPTION
                "Number of Invalid SNA Frames received from this Link Station."
        ::= { wfAppnNodeLsStatusEntry 39 }

    wfAppnNodeLsStatusInScFrames OBJECT-TYPE
        SYNTAX	Counter
        ACCESS	read-only
        STATUS	mandatory
        DESCRIPTION
                "Number of Session Control frames received from this Link Station."
        ::= { wfAppnNodeLsStatusEntry 40 }

    wfAppnNodeLsStatusOutScFrames OBJECT-TYPE
        SYNTAX	Counter
        ACCESS	read-only
        STATUS	mandatory
        DESCRIPTION
                "Number of Session Control frames sent to the Link Station."
        ::= { wfAppnNodeLsStatusEntry 41 }

    wfAppnNodeLsStatusCpType OBJECT-TYPE
        SYNTAX	INTEGER {
                learn(1),
    		    nn(2),
    		    en(3),
                bllen(4),
                hostxid3(5),
                hostxid0(6),
                dspuxid(7),
                dspunoxid(8)
    		}
        ACCESS	read-only
        STATUS	mandatory
        DESCRIPTION
                "This specifies the APPN Node type of Link Station"
        ::= { wfAppnNodeLsStatusEntry 42 }

    wfAppnNodeLsStatusStartTime OBJECT-TYPE
        SYNTAX	INTEGER
        ACCESS	read-only
        STATUS	mandatory
        DESCRIPTION
                "Time since system startup (in hundreths of seconds)
                when Link Station was activated."
        ::= { wfAppnNodeLsStatusEntry 43 }

    wfAppnNodeLsStatusStopTime OBJECT-TYPE
        SYNTAX	INTEGER
        ACCESS	read-only
        STATUS	mandatory
        DESCRIPTION
                "Time since system startup (in hundreths of seconds)
                when Link Station was deactivated."
        ::= { wfAppnNodeLsStatusEntry 44 }

    wfAppnNodeLsStatusUpTime OBJECT-TYPE
        SYNTAX	INTEGER
        ACCESS	read-only
        STATUS	mandatory
        DESCRIPTION
                "Time (in hundreths of seconds) that this Link Station has been up."
        ::= { wfAppnNodeLsStatusEntry 45 }

    wfAppnNodeLsStatusDeactCause OBJECT-TYPE
        SYNTAX	INTEGER
        ACCESS	read-only
        STATUS	mandatory
        DESCRIPTION
                "Deactivation Cause"
        ::= { wfAppnNodeLsStatusEntry 46 }

    wfAppnNodeLsStatusHprSupport OBJECT-TYPE
        SYNTAX	INTEGER {
    		    yes(1),
    		    no(2)
    		}
        ACCESS	read-only
        STATUS	mandatory
        DESCRIPTION
                "Indicates if HPR is supported by this Link Station"
        ::= { wfAppnNodeLsStatusEntry 47 }

    wfAppnNodeLsStatusHprLlErrSupport OBJECT-TYPE
        SYNTAX	INTEGER {
    		    yes(1),
    		    no(2)
    		}
        ACCESS	read-only
        STATUS	mandatory
        DESCRIPTION
                "Indicates if HPR Link-level Error recovery is supported
                by this Link Station"
        ::= { wfAppnNodeLsStatusEntry 48 }

    wfAppnNodeLsStatusAnrLabel OBJECT-TYPE
        SYNTAX	INTEGER
        ACCESS	read-only
        STATUS	mandatory
        DESCRIPTION
                "ANR Label of this Link Station"
        ::= { wfAppnNodeLsStatusEntry 49 }

    wfAppnNodeLsStatusLinkData OBJECT-TYPE
        SYNTAX	OCTET STRING
        ACCESS	read-only
        STATUS	mandatory
        DESCRIPTION
                "Link Address, e.g.Mac Address/SAP"
        ::= { wfAppnNodeLsStatusEntry 50 }

    wfAppnNodeCnTable OBJECT-TYPE
        SYNTAX	SEQUENCE OF WfAppnNodeCnEntry
        ACCESS	not-accessible
        STATUS	mandatory
        DESCRIPTION
                "This Table contains entries for each configured Connection Network"
        ::= { wfAppnNode 6 }

    wfAppnNodeCnEntry OBJECT-TYPE
        SYNTAX	WfAppnNodeCnEntry
        ACCESS	not-accessible
        STATUS	mandatory
        DESCRIPTION
                "An entry in wfAppnNodeCnTable."
        INDEX	{ wfAppnNodeCnFqName }
        ::= { wfAppnNodeCnTable 1 }

    WfAppnNodeCnEntry ::= SEQUENCE {
    	    wfAppnNodeCnDelete
    		INTEGER,
    	    wfAppnNodeCnDisable
    		INTEGER,
    	    wfAppnNodeCnFqName
    		DisplayString,
    	    wfAppnNodeCnState
    		INTEGER,
    	    wfAppnNodeCnEffCap
    		INTEGER,
    	    wfAppnNodeCnConnCost
    		INTEGER,
    	    wfAppnNodeCnByteCost
    		INTEGER,
    	    wfAppnNodeCnSecurity
    		INTEGER,
    	    wfAppnNodeCnDelay
    		INTEGER,
    	    wfAppnNodeCnUsr1
    		INTEGER,
    	    wfAppnNodeCnUsr2
    		INTEGER,
    	    wfAppnNodeCnUsr3
    		INTEGER
        }

    wfAppnNodeCnDelete OBJECT-TYPE
        SYNTAX	INTEGER {
    		    created(1),
    		    deleted(2)
    		}
        ACCESS	read-write
        STATUS	mandatory
        DESCRIPTION
                "Create/Delete parameter. Default is created.
                Users perform an SNMP SET operation on this
                object in order to create/delete a Connection
                Network definition."
        DEFVAL	{ created }
        ::= { wfAppnNodeCnEntry 1 }

    wfAppnNodeCnDisable OBJECT-TYPE
        SYNTAX	INTEGER {
    		    enable(1),
    		    disable(2)
    		}
        ACCESS	read-write
        STATUS	mandatory
        DESCRIPTION
                "Enable/Disable parameter. Default is enabled.
                Users perform an SNMP SET operation on this
                object in order to enable/disable this Connection Network."
        DEFVAL	{ enable }
        ::= { wfAppnNodeCnEntry 2 }

    wfAppnNodeCnFqName OBJECT-TYPE
        SYNTAX	DisplayString
        ACCESS	read-only
        STATUS	mandatory
        DESCRIPTION
                "The Fully-qualified name of the Connection Network"
        ::= { wfAppnNodeCnEntry 3 }

    wfAppnNodeCnState OBJECT-TYPE
        SYNTAX	INTEGER {
    		    inactive(1),
    		    pendactive(2),
    		    active(3),
    		    pendinact(4)
    		}
        ACCESS	read-only
        STATUS	mandatory
        DESCRIPTION
                "State of this connection network."
        DEFVAL	{ inactive }
        ::= { wfAppnNodeCnEntry 4 }

    wfAppnNodeCnEffCap OBJECT-TYPE
        SYNTAX	INTEGER(0..255)
        ACCESS	read-write
        STATUS	mandatory
        DESCRIPTION
                "The effective capacity is an integer value that indicates
                the kilo bits per second.
                It is derived from the link bandwidth and maximum load
                factor with the range of 0 thru 255.
                This is an administratively assigned value for use with this
                connection network.
                DEVIATION: 6611 mib uses range of 0 thru 603,979,776."
        DEFVAL	{ 133 }
        ::= { wfAppnNodeCnEntry 5 }

    wfAppnNodeCnConnCost OBJECT-TYPE
        SYNTAX	INTEGER(0..255)
        ACCESS	read-write
        STATUS	mandatory
        DESCRIPTION
                "Cost per connect time: a value representing
                the relative cost per unit of time to use
                the TG. Range is from 0, which means no cost,
                to 255, which indicates maximum cost.
                This is an administratively assigned value associated
                with the TG using this link station."
        DEFVAL	{ 128 }
        ::= { wfAppnNodeCnEntry 6 }

    wfAppnNodeCnByteCost OBJECT-TYPE
        SYNTAX	INTEGER(0..255)
        ACCESS	read-write
        STATUS	mandatory
        DESCRIPTION
                "Relative cost of transmitting a byte over this link.
                Range is from 0 (lowest cost) to 255.
                This is an administratively assigned value associated
                with the TG using this link station."
        DEFVAL	{ 128 }
        ::= { wfAppnNodeCnEntry 7 }

    wfAppnNodeCnSecurity OBJECT-TYPE
        SYNTAX	INTEGER(0..255)
        ACCESS	read-write
        STATUS	mandatory
        DESCRIPTION
                "The security is represented as an integer with a range of
                1 thru 255 with the most common values enumerated as
                defined above.
                This is an administratively assigned value associated
                with the TG using this link station."
        DEFVAL	{ 1 }
        ::= { wfAppnNodeCnEntry 8 }

    wfAppnNodeCnDelay OBJECT-TYPE
        SYNTAX  INTEGER {
                negligible(1),
                terrestrial(2),
                packet(3),
                long(4),
                maximum(5)                
                }
        ACCESS	read-write
        STATUS	mandatory
        DESCRIPTION
                "Relative amount of time that it takes for a signal to
                travel the length of the logical link.
                This is an administratively assigned value associated
                with this connection network.
                DEVIATION: 6611 MIB, uses units of microseconds."
        DEFVAL  { negligible }
        ::= { wfAppnNodeCnEntry 9 }

    wfAppnNodeCnUsr1 OBJECT-TYPE
        SYNTAX	INTEGER(0..255)
        ACCESS	read-write
        STATUS	mandatory
        DESCRIPTION
                "First user-defined TG characteristic for this TG with
                a range of 0-255.
                This is an administratively assigned value associated
                with the TG using this link station."
        DEFVAL	{ 128 }
        ::= { wfAppnNodeCnEntry 10 }

    wfAppnNodeCnUsr2 OBJECT-TYPE
        SYNTAX	INTEGER(0..255)
        ACCESS	read-write
        STATUS	mandatory
        DESCRIPTION
                "Second user-defined TG characteristic for this TG with
                a range of 0-255.
                This is an administratively assigned value associated
                with the TG using this link station."
        DEFVAL	{ 128 }
        ::= { wfAppnNodeCnEntry 11 }

    wfAppnNodeCnUsr3 OBJECT-TYPE
        SYNTAX	INTEGER(0..255)
        ACCESS	read-write
        STATUS	mandatory
        DESCRIPTION
                "Third user-defined TG characteristic for this TG with
                a range of 0-255.
                This is an administratively assigned value associated
                with the TG using this link station."
        DEFVAL	{ 128 }
        ::= { wfAppnNodeCnEntry 12 }

    wfAppnNodeCnPortTable OBJECT-TYPE
        SYNTAX	SEQUENCE OF WfAppnNodeCnPortEntry
        ACCESS	not-accessible
        STATUS	mandatory
        DESCRIPTION
                "Table containing an entry for every Port associated
                with a connection network."
        ::= { wfAppnNode 7 }

    wfAppnNodeCnPortEntry OBJECT-TYPE
        SYNTAX	WfAppnNodeCnPortEntry
        ACCESS	not-accessible
        STATUS	mandatory
        DESCRIPTION
                "an entry in wfAppnNodeCnPortTable"
        INDEX	{ wfAppnNodeCnPortCnName,
    		  wfAppnNodeCnPortPortName }
        ::= { wfAppnNodeCnPortTable 1 }

    WfAppnNodeCnPortEntry ::= SEQUENCE {
    	    wfAppnNodeCnPortDelete
    		INTEGER,
    	    wfAppnNodeCnPortDisable
    		INTEGER,
    	    wfAppnNodeCnPortCnName
    		DisplayString,
    	    wfAppnNodeCnPortPortName
    		DisplayString,
    	    wfAppnNodeCnPortState
    		INTEGER
        }

    wfAppnNodeCnPortDelete OBJECT-TYPE
        SYNTAX	INTEGER {
    		    created(1),
    		    deleted(2)
    		}
        ACCESS	read-write
        STATUS	mandatory
        DESCRIPTION
                "Create/Delete parameter. Default is created.
                Users perform an SNMP SET operation on this
                object in order to create/delete a Connection
                Network Port instance."
        DEFVAL	{ created }
        ::= { wfAppnNodeCnPortEntry 1 }

    wfAppnNodeCnPortDisable OBJECT-TYPE
        SYNTAX	INTEGER {
    		    enable(1),
    		    disable(2)
    		}
        ACCESS	read-write
        STATUS	mandatory
        DESCRIPTION
                "Enable/Disable parameter. Default is enabled.
                Users perform an SNMP SET operation on this
                object in order to enable/disable this Connection Network Port."
        DEFVAL	{ enable }
        ::= { wfAppnNodeCnPortEntry 2 }

    wfAppnNodeCnPortCnName OBJECT-TYPE
        SYNTAX	DisplayString
        ACCESS	read-only
        STATUS	mandatory
        DESCRIPTION
                "The name of the cn."
        ::= { wfAppnNodeCnPortEntry 3 }

    wfAppnNodeCnPortPortName OBJECT-TYPE
        SYNTAX	DisplayString
        ACCESS	read-write
        STATUS	mandatory
        DESCRIPTION
                "The name of the port.  FIX to READ_ONLY"
        ::= { wfAppnNodeCnPortEntry 4 }

    wfAppnNodeCnPortState OBJECT-TYPE
        SYNTAX	INTEGER {
    		    inactive(1),
    		    pendactive(2),
    		    active(3),
    		    pendinact(4)
    		}
        ACCESS	read-only
        STATUS	mandatory
        DESCRIPTION
                "State of this connection network."
        DEFVAL	{ inactive }
        ::= { wfAppnNodeCnPortEntry 5 }

    wfAppnNodeIsrSessionTable OBJECT-TYPE
        SYNTAX	SEQUENCE OF WfAppnNodeIsrSessionEntry
        ACCESS	not-accessible
        STATUS	mandatory
        DESCRIPTION
                "This table contains entries for every session that is currently
                being routed by this Node"
        ::= { wfAppnNode 8 }

    wfAppnNodeIsrSessionEntry OBJECT-TYPE
        SYNTAX	WfAppnNodeIsrSessionEntry
        ACCESS	not-accessible
        STATUS	mandatory
        DESCRIPTION
                "The fqpcid is the index for this table."
        INDEX	{ wfAppnNodeIsrSessionPcid,
    		  wfAppnNodeIsrSessionFqCpName }
        ::= { wfAppnNodeIsrSessionTable 1 }

    WfAppnNodeIsrSessionEntry ::= SEQUENCE {
    	    wfAppnNodeIsrSessionPcid
    		OCTET STRING,
    	    wfAppnNodeIsrSessionFqCpName
    		DisplayString,
    	    wfAppnNodeIsrSessionTransPriority
    		INTEGER,
    	    wfAppnNodeIsrSessionCos
    		DisplayString,
    	    wfAppnNodeIsrSessionLimResource
    		INTEGER,
    	    wfAppnNodeIsrSessionRscv
    		OCTET STRING,
    	    wfAppnNodeIsrSessionPriSendRuSize
    		INTEGER,
    	    wfAppnNodeIsrSessionPriRcvRuSize
    		INTEGER,
    	    wfAppnNodeIsrSessionPriMaxSendBtuSize
    		INTEGER,
    	    wfAppnNodeIsrSessionPriMaxRcvBtuSize
    		INTEGER,
    	    wfAppnNodeIsrSessionPriMaxSendPacing
    		INTEGER,
    	    wfAppnNodeIsrSessionPriCurSendPacing
    		INTEGER,
    	    wfAppnNodeIsrSessionPriMaxRcvPacing
    		INTEGER,
    	    wfAppnNodeIsrSessionPriCurRcvPacing
    		INTEGER,
    	    wfAppnNodeIsrSessionPriSendFrames
    		Counter,
    	    wfAppnNodeIsrSessionPriSendBytes
    		Counter,
    	    wfAppnNodeIsrSessionPriSendFmdFrames
    		Counter,
    	    wfAppnNodeIsrSessionPriRcvFrames
    		Counter,
    	    wfAppnNodeIsrSessionPriRcvBytes
    		Counter,
    	    wfAppnNodeIsrSessionPriRcvFmdFrames
    		Counter,
    	    wfAppnNodeIsrSessionPriSidh
    		INTEGER,
    	    wfAppnNodeIsrSessionPriSidl
    		INTEGER,
    	    wfAppnNodeIsrSessionPriOdai
    		INTEGER,
    	    wfAppnNodeIsrSessionPriLsName
    		DisplayString,
    	    wfAppnNodeIsrSessionSecSendRuSize
    		INTEGER,
    	    wfAppnNodeIsrSessionSecRcvRuSize
    		INTEGER,
    	    wfAppnNodeIsrSessionSecMaxSendBtuSize
    		INTEGER,
    	    wfAppnNodeIsrSessionSecMaxRcvBtuSize
    		INTEGER,
    	    wfAppnNodeIsrSessionSecMaxSendPacing
    		INTEGER,
    	    wfAppnNodeIsrSessionSecCurSendPacing
    		INTEGER,
    	    wfAppnNodeIsrSessionSecMaxRcvPacing
    		INTEGER,
    	    wfAppnNodeIsrSessionSecCurRcvPacing
    		INTEGER,
    	    wfAppnNodeIsrSessionSecSendFrames
    		Counter,
    	    wfAppnNodeIsrSessionSecSendBytes
    		Counter,
    	    wfAppnNodeIsrSessionSecSendFmdFrames
    		Counter,
    	    wfAppnNodeIsrSessionSecRcvFrames
    		Counter,
    	    wfAppnNodeIsrSessionSecRcvBytes
    		Counter,
    	    wfAppnNodeIsrSessionSecRcvFmdFrames
    		Counter,
    	    wfAppnNodeIsrSessionSecSidh
    		INTEGER,
    	    wfAppnNodeIsrSessionSecSidl
    		INTEGER,
    	    wfAppnNodeIsrSessionSecOdai
    		INTEGER,
    	    wfAppnNodeIsrSessionSecLsName
    		DisplayString,
    	    wfAppnNodeIsrSessionRscvText
    		DisplayString
        }

    wfAppnNodeIsrSessionPcid OBJECT-TYPE
        SYNTAX	OCTET STRING
        ACCESS	read-only
        STATUS	mandatory
        DESCRIPTION
                "This is the PCID of this session"
        ::= { wfAppnNodeIsrSessionEntry 1 }

    wfAppnNodeIsrSessionFqCpName OBJECT-TYPE
        SYNTAX	DisplayString
        ACCESS	read-only
        STATUS	mandatory
        DESCRIPTION
                "This is the Fully-qualified CP name of the node assigning the
                PCID for this session"
        ::= { wfAppnNodeIsrSessionEntry 2 }

    wfAppnNodeIsrSessionTransPriority OBJECT-TYPE
        SYNTAX	INTEGER {
    		    low(1),
    		    medium(2),
    		    high(3),
    		    network(4)
    		}
        ACCESS	read-only
        STATUS	mandatory
        DESCRIPTION
                "This indicates the transmission priority being used by this session"
        ::= { wfAppnNodeIsrSessionEntry 3 }

    wfAppnNodeIsrSessionCos OBJECT-TYPE
        SYNTAX	DisplayString
        ACCESS	read-only
        STATUS	mandatory
        DESCRIPTION
                "This indicates the Class-of-Service being used by this session"
        ::= { wfAppnNodeIsrSessionEntry 4 }

    wfAppnNodeIsrSessionLimResource OBJECT-TYPE
        SYNTAX	INTEGER {
    		    yes(1),
    		    no(2)
    		}
        ACCESS	read-only
        STATUS	mandatory
        DESCRIPTION
                "This indicates if this session is traversing a Limited Resource"
        ::= { wfAppnNodeIsrSessionEntry 5 }

    wfAppnNodeIsrSessionRscv OBJECT-TYPE
        SYNTAX	OCTET STRING
        ACCESS	read-only
        STATUS	mandatory
        DESCRIPTION
                "This is the Route Selection Control Vector in use by this session"
        ::= { wfAppnNodeIsrSessionEntry 6 }

    wfAppnNodeIsrSessionPriSendRuSize OBJECT-TYPE
        SYNTAX	INTEGER
        ACCESS	read-only
        STATUS	mandatory
        DESCRIPTION
                "This is the send RU size used on the primary hop of this session"
        ::= { wfAppnNodeIsrSessionEntry 7 }

    wfAppnNodeIsrSessionPriRcvRuSize OBJECT-TYPE
        SYNTAX	INTEGER
        ACCESS	read-only
        STATUS	mandatory
        DESCRIPTION
                "This is the receive RU size used on the primary hop of this session"
        ::= { wfAppnNodeIsrSessionEntry 8 }

    wfAppnNodeIsrSessionPriMaxSendBtuSize OBJECT-TYPE
        SYNTAX	INTEGER
        ACCESS	read-only
        STATUS	mandatory
        DESCRIPTION
                "This is the maximum send BTU size on the primary hop of this session"
        ::= { wfAppnNodeIsrSessionEntry 9 }

    wfAppnNodeIsrSessionPriMaxRcvBtuSize OBJECT-TYPE
        SYNTAX	INTEGER
        ACCESS	read-only
        STATUS	mandatory
        DESCRIPTION
                "This is the maximum receive BTU size on the primary hop of this session"
        ::= { wfAppnNodeIsrSessionEntry 10 }

    wfAppnNodeIsrSessionPriMaxSendPacing OBJECT-TYPE
        SYNTAX	INTEGER
        ACCESS	read-only
        STATUS	mandatory
        DESCRIPTION
                "This is the maximum send pacing on the primary hop of this session"
        ::= { wfAppnNodeIsrSessionEntry 11 }

    wfAppnNodeIsrSessionPriCurSendPacing OBJECT-TYPE
        SYNTAX	INTEGER
        ACCESS	read-only
        STATUS	mandatory
        DESCRIPTION
                "This is the current send pacing on the primary hop of this session"
        ::= { wfAppnNodeIsrSessionEntry 12 }

    wfAppnNodeIsrSessionPriMaxRcvPacing OBJECT-TYPE
        SYNTAX	INTEGER
        ACCESS	read-only
        STATUS	mandatory
        DESCRIPTION
                "This is the maximum receive pacing on the primary hop of this session"
        ::= { wfAppnNodeIsrSessionEntry 13 }

    wfAppnNodeIsrSessionPriCurRcvPacing OBJECT-TYPE
        SYNTAX	INTEGER
        ACCESS	read-only
        STATUS	mandatory
        DESCRIPTION
                "This is the current receive pacing on the primary hop of this session"
        ::= { wfAppnNodeIsrSessionEntry 14 }

    wfAppnNodeIsrSessionPriSendFrames OBJECT-TYPE
        SYNTAX	Counter
        ACCESS	read-only
        STATUS	mandatory
        DESCRIPTION
                "This is the number of Normal-flow frames sent on the primary hop of this session"
        ::= { wfAppnNodeIsrSessionEntry 15 }

    wfAppnNodeIsrSessionPriSendBytes OBJECT-TYPE
        SYNTAX	Counter
        ACCESS	read-only
        STATUS	mandatory
        DESCRIPTION
                "This is the number of bytes sent on the primary hop of this session"
        ::= { wfAppnNodeIsrSessionEntry 16 }

    wfAppnNodeIsrSessionPriSendFmdFrames OBJECT-TYPE
        SYNTAX	Counter
        ACCESS	read-only
        STATUS	mandatory
        DESCRIPTION
                "This is the number of FMD frames sent on the primary hop of this session"
        ::= { wfAppnNodeIsrSessionEntry 17 }

    wfAppnNodeIsrSessionPriRcvFrames OBJECT-TYPE
        SYNTAX	Counter
        ACCESS	read-only
        STATUS	mandatory
        DESCRIPTION
                "This is the number of Normal-flow frames received on the primary hop of this session"
        ::= { wfAppnNodeIsrSessionEntry 18 }

    wfAppnNodeIsrSessionPriRcvBytes OBJECT-TYPE
        SYNTAX	Counter
        ACCESS	read-only
        STATUS	mandatory
        DESCRIPTION
                "This is the number of bytes received on the primary hop of this session"
        ::= { wfAppnNodeIsrSessionEntry 19 }

    wfAppnNodeIsrSessionPriRcvFmdFrames OBJECT-TYPE
        SYNTAX	Counter
        ACCESS	read-only
        STATUS	mandatory
        DESCRIPTION
                "This is the number of FMD frames received on the primary hop of this session"
        ::= { wfAppnNodeIsrSessionEntry 20 }

    wfAppnNodeIsrSessionPriSidh OBJECT-TYPE
        SYNTAX	INTEGER
        ACCESS	read-only
        STATUS	mandatory
        DESCRIPTION
                "This is the SIDH value used on the primary hop of this session"
        ::= { wfAppnNodeIsrSessionEntry 21 }

    wfAppnNodeIsrSessionPriSidl OBJECT-TYPE
        SYNTAX	INTEGER
        ACCESS	read-only
        STATUS	mandatory
        DESCRIPTION
                "This is the SIDL value used on the primary hop of this session"
        ::= { wfAppnNodeIsrSessionEntry 22 }

    wfAppnNodeIsrSessionPriOdai OBJECT-TYPE
        SYNTAX	INTEGER
        ACCESS	read-only
        STATUS	mandatory
        DESCRIPTION
                "This is the ODAI value used on the primary hop of this session"
        ::= { wfAppnNodeIsrSessionEntry 23 }

    wfAppnNodeIsrSessionPriLsName OBJECT-TYPE
        SYNTAX	DisplayString
        ACCESS	read-only
        STATUS	mandatory
        DESCRIPTION
                "This is the adjacent Link Station used on the primary hop of this session"
        ::= { wfAppnNodeIsrSessionEntry 24 }

    wfAppnNodeIsrSessionSecSendRuSize OBJECT-TYPE
        SYNTAX	INTEGER
        ACCESS	read-only
        STATUS	mandatory
        DESCRIPTION
                "This is the send RU size used on the secondary hop of this session"
        ::= { wfAppnNodeIsrSessionEntry 25 }

    wfAppnNodeIsrSessionSecRcvRuSize OBJECT-TYPE
        SYNTAX	INTEGER
        ACCESS	read-only
        STATUS	mandatory
        DESCRIPTION
                "This is the receive RU size used on the secondary hop of this session"
        ::= { wfAppnNodeIsrSessionEntry 26 }

    wfAppnNodeIsrSessionSecMaxSendBtuSize OBJECT-TYPE
        SYNTAX	INTEGER
        ACCESS	read-only
        STATUS	mandatory
        DESCRIPTION
                "This is the maximum send BTU size on the secondary hop of this session"
        ::= { wfAppnNodeIsrSessionEntry 27 }

    wfAppnNodeIsrSessionSecMaxRcvBtuSize OBJECT-TYPE
        SYNTAX	INTEGER
        ACCESS	read-only
        STATUS	mandatory
        DESCRIPTION
                "This is the maximum receive BTU size on the secondary hop of this session"
        ::= { wfAppnNodeIsrSessionEntry 28 }

    wfAppnNodeIsrSessionSecMaxSendPacing OBJECT-TYPE
        SYNTAX	INTEGER
        ACCESS	read-only
        STATUS	mandatory
        DESCRIPTION
                "This is the maximum send pacing on the secondary hop of this session"
        ::= { wfAppnNodeIsrSessionEntry 29 }

    wfAppnNodeIsrSessionSecCurSendPacing OBJECT-TYPE
        SYNTAX	INTEGER
        ACCESS	read-only
        STATUS	mandatory
        DESCRIPTION
                "This is the current send pacing on the secondary hop of this session"
        ::= { wfAppnNodeIsrSessionEntry 30 }

    wfAppnNodeIsrSessionSecMaxRcvPacing OBJECT-TYPE
        SYNTAX	INTEGER
        ACCESS	read-only
        STATUS	mandatory
        DESCRIPTION
                "This is the maximum receive pacing on the secondary hop of this session"
        ::= { wfAppnNodeIsrSessionEntry 31 }

    wfAppnNodeIsrSessionSecCurRcvPacing OBJECT-TYPE
        SYNTAX	INTEGER
        ACCESS	read-only
        STATUS	mandatory
        DESCRIPTION
                "This is the current receive pacing on the secondary hop of this session"
        ::= { wfAppnNodeIsrSessionEntry 32 }

    wfAppnNodeIsrSessionSecSendFrames OBJECT-TYPE
        SYNTAX	Counter
        ACCESS	read-only
        STATUS	mandatory
        DESCRIPTION
                "This is the number of Normal-flow frames sent on the secondary hop of this session"
        ::= { wfAppnNodeIsrSessionEntry 33 }

    wfAppnNodeIsrSessionSecSendBytes OBJECT-TYPE
        SYNTAX	Counter
        ACCESS	read-only
        STATUS	mandatory
        DESCRIPTION
                "This is the number of bytes sent on the secondary hop of this session"
        ::= { wfAppnNodeIsrSessionEntry 34 }

    wfAppnNodeIsrSessionSecSendFmdFrames OBJECT-TYPE
        SYNTAX	Counter
        ACCESS	read-only
        STATUS	mandatory
        DESCRIPTION
                "This is the number of FMD frames sent on the secondary hop of this session"
        ::= { wfAppnNodeIsrSessionEntry 35 }

    wfAppnNodeIsrSessionSecRcvFrames OBJECT-TYPE
        SYNTAX	Counter
        ACCESS	read-only
        STATUS	mandatory
        DESCRIPTION
                "This is the number of Normal-flow frames received on the secondary hop of this session"
        ::= { wfAppnNodeIsrSessionEntry 36 }

    wfAppnNodeIsrSessionSecRcvBytes OBJECT-TYPE
        SYNTAX	Counter
        ACCESS	read-only
        STATUS	mandatory
        DESCRIPTION
                "This is the number of bytes received on the secondary hop of this session"
        ::= { wfAppnNodeIsrSessionEntry 37 }

    wfAppnNodeIsrSessionSecRcvFmdFrames OBJECT-TYPE
        SYNTAX	Counter
        ACCESS	read-only
        STATUS	mandatory
        DESCRIPTION
                "This is the number of FMD frames received on the secondary hop of this session"
        ::= { wfAppnNodeIsrSessionEntry 38 }

    wfAppnNodeIsrSessionSecSidh OBJECT-TYPE
        SYNTAX	INTEGER
        ACCESS	read-only
        STATUS	mandatory
        DESCRIPTION
                "This is the SIDH value used on the secondary hop of this session"
        ::= { wfAppnNodeIsrSessionEntry 39 }

    wfAppnNodeIsrSessionSecSidl OBJECT-TYPE
        SYNTAX	INTEGER
        ACCESS	read-only
        STATUS	mandatory
        DESCRIPTION
                "This is the SIDL value used on the secondary hop of this session"
        ::= { wfAppnNodeIsrSessionEntry 40 }

    wfAppnNodeIsrSessionSecOdai OBJECT-TYPE
        SYNTAX	INTEGER
        ACCESS	read-only
        STATUS	mandatory
        DESCRIPTION
                "This is the ODAI value used on the secondary hop of this session"
        ::= { wfAppnNodeIsrSessionEntry 41 }

    wfAppnNodeIsrSessionSecLsName OBJECT-TYPE
        SYNTAX	DisplayString
        ACCESS	read-only
        STATUS	mandatory
        DESCRIPTION
                "This is the adjacent Link Station used on the secondary hop of this session"
        ::= { wfAppnNodeIsrSessionEntry 42 }

    wfAppnNodeIsrSessionRscvText OBJECT-TYPE
        SYNTAX	DisplayString
        ACCESS	read-only
        STATUS	mandatory
        DESCRIPTION
                "This is the Route Selection Control Vector in use by this session, in a DSP_STR format"
        ::= { wfAppnNodeIsrSessionEntry 43 }

    wfAppnNodeEndptSessionTable OBJECT-TYPE
        SYNTAX	SEQUENCE OF WfAppnNodeEndptSessionEntry
        ACCESS	not-accessible
        STATUS	mandatory
        DESCRIPTION
                "This table contains entries for every endpoint session that is currently
                active on this Node"
        ::= { wfAppnNode 9 }

    wfAppnNodeEndptSessionEntry OBJECT-TYPE
        SYNTAX	WfAppnNodeEndptSessionEntry
        ACCESS	not-accessible
        STATUS	mandatory
        DESCRIPTION
                "The fqpcid is the index for this table."
        INDEX	{ wfAppnNodeEndptSessionId,
    		  wfAppnNodeEndptSessionFqPluName }
        ::= { wfAppnNodeEndptSessionTable 1 }

    WfAppnNodeEndptSessionEntry ::= SEQUENCE {
    	    wfAppnNodeEndptSessionId
    		OCTET STRING,
    	    wfAppnNodeEndptSessionPcid
    		OCTET STRING,
    	    wfAppnNodeEndptSessionFqCpName
    		DisplayString,
    	    wfAppnNodeEndptSessionFqPluName
    		DisplayString,
    	    wfAppnNodeEndptSessionTransPriority
    		INTEGER,
    	    wfAppnNodeEndptSessionMode
    		DisplayString,
    	    wfAppnNodeEndptSessionCos
    		DisplayString,
    	    wfAppnNodeEndptSessionLimResource
    		INTEGER,
    	    wfAppnNodeEndptSessionPolarity
    		INTEGER,
    	    wfAppnNodeEndptSessionContention
    		INTEGER,
    	    wfAppnNodeEndptSessionRscv
    		OCTET STRING,
    	    wfAppnNodeEndptSessionSendRuSize
    		INTEGER,
    	    wfAppnNodeEndptSessionRcvRuSize
    		INTEGER,
    	    wfAppnNodeEndptSessionMaxSendBtuSize
    		INTEGER,
    	    wfAppnNodeEndptSessionMaxRcvBtuSize
    		INTEGER,
    	    wfAppnNodeEndptSessionMaxSendPacing
    		INTEGER,
    	    wfAppnNodeEndptSessionCurSendPacing
    		INTEGER,
    	    wfAppnNodeEndptSessionMaxRcvPacing
    		INTEGER,
    	    wfAppnNodeEndptSessionCurRcvPacing
    		INTEGER,
    	    wfAppnNodeEndptSessionSendFrames
    		Counter,
    	    wfAppnNodeEndptSessionSendBytes
    		Counter,
    	    wfAppnNodeEndptSessionSendFmdFrames
    		Counter,
    	    wfAppnNodeEndptSessionRcvFrames
    		Counter,
    	    wfAppnNodeEndptSessionRcvBytes
    		Counter,
    	    wfAppnNodeEndptSessionRcvFmdFrames
    		Counter,
    	    wfAppnNodeEndptSessionSidh
    		INTEGER,
    	    wfAppnNodeEndptSessionSidl
    		INTEGER,
    	    wfAppnNodeEndptSessionOdai
    		INTEGER,
    	    wfAppnNodeEndptSessionLsName
    		DisplayString,
    	    wfAppnNodeEndptSessionRscvText
    		DisplayString
        }

    wfAppnNodeEndptSessionId OBJECT-TYPE
        SYNTAX	OCTET STRING
        ACCESS	read-only
        STATUS	mandatory
        DESCRIPTION
                "This is the session ID of this session"
        ::= { wfAppnNodeEndptSessionEntry 1 }

    wfAppnNodeEndptSessionPcid OBJECT-TYPE
        SYNTAX	OCTET STRING
        ACCESS	read-only
        STATUS	mandatory
        DESCRIPTION
                "This is the PCID of this session"
        ::= { wfAppnNodeEndptSessionEntry 2 }

    wfAppnNodeEndptSessionFqCpName OBJECT-TYPE
        SYNTAX	DisplayString
        ACCESS	read-only
        STATUS	mandatory
        DESCRIPTION
                "This is the Fully-qualified CP name of the node assigning the
                PCID for this session"
        ::= { wfAppnNodeEndptSessionEntry 3 }

    wfAppnNodeEndptSessionFqPluName OBJECT-TYPE
        SYNTAX	DisplayString
        ACCESS	read-only
        STATUS	mandatory
        DESCRIPTION
                "This is the name of the Partner LU being used by this session"
        ::= { wfAppnNodeEndptSessionEntry 4 }

    wfAppnNodeEndptSessionTransPriority OBJECT-TYPE
        SYNTAX	INTEGER {
    		    low(1),
    		    medium(2),
    		    high(3),
    		    network(4)
    		}
        ACCESS	read-only
        STATUS	mandatory
        DESCRIPTION
                "This indicates the transmission priority being used by this session"
        ::= { wfAppnNodeEndptSessionEntry 5 }

    wfAppnNodeEndptSessionMode OBJECT-TYPE
        SYNTAX	DisplayString
        ACCESS	read-only
        STATUS	mandatory
        DESCRIPTION
                "This indicates the Mode being used by this session"
        ::= { wfAppnNodeEndptSessionEntry 6 }

    wfAppnNodeEndptSessionCos OBJECT-TYPE
        SYNTAX	DisplayString
        ACCESS	read-only
        STATUS	mandatory
        DESCRIPTION
                "This indicates the Class-of-Service being used by this session"
        ::= { wfAppnNodeEndptSessionEntry 7 }

    wfAppnNodeEndptSessionLimResource OBJECT-TYPE
        SYNTAX	INTEGER {
    		    yes(1),
    		    no(2)
    		}
        ACCESS	read-only
        STATUS	mandatory
        DESCRIPTION
                "This indicates if this session is traversing a Limited Resource"
        ::= { wfAppnNodeEndptSessionEntry 8 }

    wfAppnNodeEndptSessionPolarity OBJECT-TYPE
        SYNTAX	INTEGER {
    		    primary(1),
    		    secondary(2)
    		}
        ACCESS	read-only
        STATUS	mandatory
        DESCRIPTION
                "This indicates whether the local LU was the BIND sender (Primary)
                or if the local LU was the BIND receiver (Secondary)"
        ::= { wfAppnNodeEndptSessionEntry 9 }

    wfAppnNodeEndptSessionContention OBJECT-TYPE
        SYNTAX	INTEGER {
    		    conwinner(1),
    		    conloser(2)
    		}
        ACCESS	read-only
        STATUS	mandatory
        DESCRIPTION
                "This indicates whether this session is a contention-winner or a
                contention-loser session"
        ::= { wfAppnNodeEndptSessionEntry 10 }

    wfAppnNodeEndptSessionRscv OBJECT-TYPE
        SYNTAX	OCTET STRING
        ACCESS	read-only
        STATUS	mandatory
        DESCRIPTION
                "This is the Route Selection Control Vector in use by this session"
        ::= { wfAppnNodeEndptSessionEntry 11 }

    wfAppnNodeEndptSessionSendRuSize OBJECT-TYPE
        SYNTAX	INTEGER
        ACCESS	read-only
        STATUS	mandatory
        DESCRIPTION
                "This is the maximum RU size sent on this session"
        ::= { wfAppnNodeEndptSessionEntry 12 }

    wfAppnNodeEndptSessionRcvRuSize OBJECT-TYPE
        SYNTAX	INTEGER
        ACCESS	read-only
        STATUS	mandatory
        DESCRIPTION
                "This is the maximum RU size received this session"
        ::= { wfAppnNodeEndptSessionEntry 13 }

    wfAppnNodeEndptSessionMaxSendBtuSize OBJECT-TYPE
        SYNTAX	INTEGER
        ACCESS	read-only
        STATUS	mandatory
        DESCRIPTION
                "This is the maximum send BTU size for this session"
        ::= { wfAppnNodeEndptSessionEntry 14 }

    wfAppnNodeEndptSessionMaxRcvBtuSize OBJECT-TYPE
        SYNTAX	INTEGER
        ACCESS	read-only
        STATUS	mandatory
        DESCRIPTION
                "This is the maximum receive BTU size for this session"
        ::= { wfAppnNodeEndptSessionEntry 15 }

    wfAppnNodeEndptSessionMaxSendPacing OBJECT-TYPE
        SYNTAX	INTEGER
        ACCESS	read-only
        STATUS	mandatory
        DESCRIPTION
                "This is the maximum send pacing for this session"
        ::= { wfAppnNodeEndptSessionEntry 16 }

    wfAppnNodeEndptSessionCurSendPacing OBJECT-TYPE
        SYNTAX	INTEGER
        ACCESS	read-only
        STATUS	mandatory
        DESCRIPTION
                "This is the current send pacing used by this session"
        ::= { wfAppnNodeEndptSessionEntry 17 }

    wfAppnNodeEndptSessionMaxRcvPacing OBJECT-TYPE
        SYNTAX	INTEGER
        ACCESS	read-only
        STATUS	mandatory
        DESCRIPTION
                "This is the maximum receive pacing for this session"
        ::= { wfAppnNodeEndptSessionEntry 18 }

    wfAppnNodeEndptSessionCurRcvPacing OBJECT-TYPE
        SYNTAX	INTEGER
        ACCESS	read-only
        STATUS	mandatory
        DESCRIPTION
                "This is the current receive pacing used by this session"
        ::= { wfAppnNodeEndptSessionEntry 19 }

    wfAppnNodeEndptSessionSendFrames OBJECT-TYPE
        SYNTAX	Counter
        ACCESS	read-only
        STATUS	mandatory
        DESCRIPTION
                "This is the number of data frames sent by this session"
        ::= { wfAppnNodeEndptSessionEntry 20 }

    wfAppnNodeEndptSessionSendBytes OBJECT-TYPE
        SYNTAX	Counter
        ACCESS	read-only
        STATUS	mandatory
        DESCRIPTION
                "This is the number of data bytes sent by this session"
        ::= { wfAppnNodeEndptSessionEntry 21 }

    wfAppnNodeEndptSessionSendFmdFrames OBJECT-TYPE
        SYNTAX	Counter
        ACCESS	read-only
        STATUS	mandatory
        DESCRIPTION
                "This is the number of FMD frames sent by this session"
        ::= { wfAppnNodeEndptSessionEntry 22 }

    wfAppnNodeEndptSessionRcvFrames OBJECT-TYPE
        SYNTAX	Counter
        ACCESS	read-only
        STATUS	mandatory
        DESCRIPTION
                "This is the number of data frames received by this session"
        ::= { wfAppnNodeEndptSessionEntry 23 }

    wfAppnNodeEndptSessionRcvBytes OBJECT-TYPE
        SYNTAX	Counter
        ACCESS	read-only
        STATUS	mandatory
        DESCRIPTION
                "This is the number of bytes received by this session"
        ::= { wfAppnNodeEndptSessionEntry 24 }

    wfAppnNodeEndptSessionRcvFmdFrames OBJECT-TYPE
        SYNTAX	Counter
        ACCESS	read-only
        STATUS	mandatory
        DESCRIPTION
                "This is the number of FMD frames received by this session"
        ::= { wfAppnNodeEndptSessionEntry 25 }

    wfAppnNodeEndptSessionSidh OBJECT-TYPE
        SYNTAX	INTEGER
        ACCESS	read-only
        STATUS	mandatory
        DESCRIPTION
                "This is the number of bytes received by this session"
        ::= { wfAppnNodeEndptSessionEntry 26 }

    wfAppnNodeEndptSessionSidl OBJECT-TYPE
        SYNTAX	INTEGER
        ACCESS	read-only
        STATUS	mandatory
        DESCRIPTION
                "This is the SIDL value used by this session"
        ::= { wfAppnNodeEndptSessionEntry 27 }

    wfAppnNodeEndptSessionOdai OBJECT-TYPE
        SYNTAX	INTEGER
        ACCESS	read-only
        STATUS	mandatory
        DESCRIPTION
                "This is the ODAI value used by this session"
        ::= { wfAppnNodeEndptSessionEntry 28 }

    wfAppnNodeEndptSessionLsName OBJECT-TYPE
        SYNTAX	DisplayString
        ACCESS	read-only
        STATUS	mandatory
        DESCRIPTION
                "This is the adjacent Link Station used by this session"
        ::= { wfAppnNodeEndptSessionEntry 29 }

    wfAppnNodeEndptSessionRscvText OBJECT-TYPE
        SYNTAX	DisplayString
        ACCESS	read-only
        STATUS	mandatory
        DESCRIPTION
                "This is a text string representing the RSCV used by this session"
        ::= { wfAppnNodeEndptSessionEntry 30 }

    wfAppnNodeTraceGroup	OBJECT IDENTIFIER ::= { wfAppnNode 10 }

    wfAppnNodeTraceDelete OBJECT-TYPE
        SYNTAX	INTEGER {
    		    created(1),
    		    deleted(2)
    		}
        ACCESS	read-write
        STATUS	mandatory
        DESCRIPTION
                "Create/Delete parameter. Default is created.
                Users perform an SNMP SET operation on this
                object in order to create/delete a Trace."
        DEFVAL	{ created }
        ::= { wfAppnNodeTraceGroup 1 }

    wfAppnNodeTraceDisable OBJECT-TYPE
        SYNTAX	INTEGER {
    		    enable(1),
    		    disable(2)
    		}
        ACCESS	read-write
        STATUS	mandatory
        DESCRIPTION
                "Enable/Disable parameter. Default is enabled.
                Users perform an SNMP SET operation on this
                object in order to enable/disable this Trace."
        DEFVAL	{ enable }
        ::= { wfAppnNodeTraceGroup 2 }

    wfAppnNodeTraceFile OBJECT-TYPE
        SYNTAX	DisplayString
        ACCESS	read-write
        STATUS	mandatory
        DESCRIPTION
                "This is the path and file name for the Trace file to be created"
        ::= { wfAppnNodeTraceGroup 3 }


    wfAppnNodeRtpConnectionTable OBJECT-TYPE
        SYNTAX	SEQUENCE OF WfAppnNodeRtpConnectionEntry
        ACCESS	not-accessible
        STATUS	mandatory
        DESCRIPTION
                "This table contains entries for every RTP connection that is currently
                active on this Node"
        ::= { wfAppnNode 11 }

    wfAppnNodeRtpConnectionEntry OBJECT-TYPE
        SYNTAX	WfAppnNodeRtpConnectionEntry
        ACCESS	not-accessible
        STATUS	mandatory
        DESCRIPTION
                "The fqpcid is the index for this table."
        INDEX	{ wfAppnNodeRtpConnectionName }
        ::= { wfAppnNodeRtpConnectionTable 1 }

    WfAppnNodeRtpConnectionEntry ::= SEQUENCE {
    	    wfAppnNodeRtpConnectionName
    		DisplayString,
    	    wfAppnNodeRtpConnectionDestName
    		DisplayString,
    	    wfAppnNodeRtpConnectionFirstHopLsName
    		DisplayString,
    	    wfAppnNodeRtpConnectionCosName
    		DisplayString,
    	    wfAppnNodeRtpConnectionMaxBtuSize
    		INTEGER,
    	    wfAppnNodeRtpConnectionLivenessTimer
    		INTEGER,
    	    wfAppnNodeRtpConnectionLivenessTimeouts
    		Counter,
    	    wfAppnNodeRtpConnectionLocalTcid
    		OCTET STRING,
    	    wfAppnNodeRtpConnectionRemoteTcid
    		OCTET STRING,
    	    wfAppnNodeRtpConnectionActiveSessions
    		INTEGER,
    	    wfAppnNodeRtpConnectionSendBytes
    		Counter,
    	    wfAppnNodeRtpConnectionSendPackets
    		Counter,
    	    wfAppnNodeRtpConnectionSendSessionControlFrames
    		Counter,
    	    wfAppnNodeRtpConnectionSendRate
    		Gauge,
    	    wfAppnNodeRtpConnectionMaxSendRate
    		INTEGER,
    	    wfAppnNodeRtpConnectionMinSendRate
    		INTEGER,
    	    wfAppnNodeRtpConnectionRcvBytes
    		Counter,
    	    wfAppnNodeRtpConnectionRcvPackets
    		Counter,
    	    wfAppnNodeRtpConnectionRcvSessionControlFrames
    		Counter,
    	    wfAppnNodeRtpConnectionRcvInvalidSnaFrames
    		Counter,
    	    wfAppnNodeRtpConnectionRcvRate
    		Gauge,
    	    wfAppnNodeRtpConnectionMaxRcvRate
    		INTEGER,
    	    wfAppnNodeRtpConnectionMinRcvRate
    		INTEGER,
    	    wfAppnNodeRtpConnectionDiscardedBytes
    		Counter,
    	    wfAppnNodeRtpConnectionDiscardedPackets
    		Counter,
    	    wfAppnNodeRtpConnectionResentBytes
    		Counter,
    	    wfAppnNodeRtpConnectionResentPackets
    		Counter,
    	    wfAppnNodeRtpConnectionUpTime
    		INTEGER,
    	    wfAppnNodeRtpConnectionRoundTripTime
    		INTEGER,
    	    wfAppnNodeRtpConnectionSmoothRoundTripTime
    		INTEGER,
    	    wfAppnNodeRtpConnectionBurstSize
    		INTEGER,
    	    wfAppnNodeRtpConnectionSrtExpiries
    		Counter,
    	    wfAppnNodeRtpConnectionShortReqTimer
    		INTEGER,
    	    wfAppnNodeRtpConnectionGapsDetected
    		Counter,
    	    wfAppnNodeRtpConnectionRscv
    		OCTET STRING,
    	    wfAppnNodeRtpConnectionRscvText
    		DisplayString
        }

    wfAppnNodeRtpConnectionName OBJECT-TYPE
        SYNTAX	DisplayString
        ACCESS	read-only
        STATUS	mandatory
        DESCRIPTION
                "This is the local name of the RTP connection"
        ::= { wfAppnNodeRtpConnectionEntry 1 }

    wfAppnNodeRtpConnectionDestName OBJECT-TYPE
        SYNTAX	DisplayString
        ACCESS	read-only
        STATUS	mandatory
        DESCRIPTION
                "This is the fully-qualified name of the node at the other
                end of this RTP connection"
        ::= { wfAppnNodeRtpConnectionEntry 2 }

    wfAppnNodeRtpConnectionFirstHopLsName OBJECT-TYPE
        SYNTAX	DisplayString
        ACCESS	read-only
        STATUS	mandatory
        DESCRIPTION
                "This is the LS name of the first hop for this RTP connection"
        ::= { wfAppnNodeRtpConnectionEntry 3 }

    wfAppnNodeRtpConnectionCosName OBJECT-TYPE
        SYNTAX	DisplayString
        ACCESS	read-only
        STATUS	mandatory
        DESCRIPTION
                "This is the Class-of-Service name for this RTP connection"
        ::= { wfAppnNodeRtpConnectionEntry 4 }

    wfAppnNodeRtpConnectionMaxBtuSize OBJECT-TYPE
        SYNTAX	INTEGER
        ACCESS	read-only
        STATUS	mandatory
        DESCRIPTION
                "This is the maximum size (in bytes) of packets which can be carried
                by this RTP connection"
        ::= { wfAppnNodeRtpConnectionEntry 5 }

    wfAppnNodeRtpConnectionLivenessTimer OBJECT-TYPE
        SYNTAX	INTEGER
        ACCESS	read-only
        STATUS	mandatory
        DESCRIPTION
                "This is the Liveness Timer (in seconds) for this RTP connection"
        ::= { wfAppnNodeRtpConnectionEntry 6 }

    wfAppnNodeRtpConnectionLivenessTimeouts OBJECT-TYPE
        SYNTAX	Counter
        ACCESS	read-only
        STATUS	mandatory
        DESCRIPTION
                "This is the number Liveness Timeouts for this RTP connection"
        ::= { wfAppnNodeRtpConnectionEntry 7 }

    wfAppnNodeRtpConnectionLocalTcid OBJECT-TYPE
        SYNTAX	OCTET STRING
        ACCESS	read-only
        STATUS	mandatory
        DESCRIPTION
                "This is the Local TCID for this RTP connection"
        ::= { wfAppnNodeRtpConnectionEntry 8 }

    wfAppnNodeRtpConnectionRemoteTcid OBJECT-TYPE
        SYNTAX	OCTET STRING
        ACCESS	read-only
        STATUS	mandatory
        DESCRIPTION
                "This is the remote TCID for this RTP connection"
        ::= { wfAppnNodeRtpConnectionEntry 9 }

    wfAppnNodeRtpConnectionActiveSessions OBJECT-TYPE
        SYNTAX	INTEGER
        ACCESS	read-only
        STATUS	mandatory
        DESCRIPTION
                "This is the number of sessions currently active on this RTP connection"
        ::= { wfAppnNodeRtpConnectionEntry 10 }

    wfAppnNodeRtpConnectionSendBytes OBJECT-TYPE
        SYNTAX	Counter
        ACCESS	read-only
        STATUS	mandatory
        DESCRIPTION
                "This is the number of bytes that have been sent on this RTP connection"
        ::= { wfAppnNodeRtpConnectionEntry 11 }

    wfAppnNodeRtpConnectionSendPackets OBJECT-TYPE
        SYNTAX	Counter
        ACCESS	read-only
        STATUS	mandatory
        DESCRIPTION
                "This is the number of packets that have been sent on this RTP connection"
        ::= { wfAppnNodeRtpConnectionEntry 12 }

    wfAppnNodeRtpConnectionSendSessionControlFrames OBJECT-TYPE
        SYNTAX	Counter
        ACCESS	read-only
        STATUS	mandatory
        DESCRIPTION
                "This is the number of Session Control that have been sent on this RTP connection"
        ::= { wfAppnNodeRtpConnectionEntry 13 }

    wfAppnNodeRtpConnectionSendRate OBJECT-TYPE
        SYNTAX	Gauge
        ACCESS	read-only
        STATUS	mandatory
        DESCRIPTION
                "This is the current sending rate (in Kbits per second) for this RTP connection"
        ::= { wfAppnNodeRtpConnectionEntry 14 }

    wfAppnNodeRtpConnectionMaxSendRate OBJECT-TYPE
        SYNTAX	INTEGER
        ACCESS	read-only
        STATUS	mandatory
        DESCRIPTION
                "This is the Maximum sending rate (in Kbits per second) for this RTP connection"
        ::= { wfAppnNodeRtpConnectionEntry 15 }

    wfAppnNodeRtpConnectionMinSendRate OBJECT-TYPE
        SYNTAX	INTEGER
        ACCESS	read-only
        STATUS	mandatory
        DESCRIPTION
                "This is the Minimum sending rate (in Kbits per second) for this RTP connection"
        ::= { wfAppnNodeRtpConnectionEntry 16 }

    wfAppnNodeRtpConnectionRcvBytes OBJECT-TYPE
        SYNTAX	Counter
        ACCESS	read-only
        STATUS	mandatory
        DESCRIPTION
                "This is the number of bytes that have been received on this RTP connection"
        ::= { wfAppnNodeRtpConnectionEntry 17 }

    wfAppnNodeRtpConnectionRcvPackets OBJECT-TYPE
        SYNTAX	Counter
        ACCESS	read-only
        STATUS	mandatory
        DESCRIPTION
                "This is the number of packets that have been received on this RTP connection"
        ::= { wfAppnNodeRtpConnectionEntry 18 }

    wfAppnNodeRtpConnectionRcvSessionControlFrames OBJECT-TYPE
        SYNTAX	Counter
        ACCESS	read-only
        STATUS	mandatory
        DESCRIPTION
                "This is the number of Session Control that have been received on this RTP connection"
        ::= { wfAppnNodeRtpConnectionEntry 19 }

    wfAppnNodeRtpConnectionRcvInvalidSnaFrames OBJECT-TYPE
        SYNTAX	Counter
        ACCESS	read-only
        STATUS	mandatory
        DESCRIPTION
                "This is the number of invalid SNA frames that have been received on this RTP connection"
        ::= { wfAppnNodeRtpConnectionEntry 20 }

    wfAppnNodeRtpConnectionRcvRate OBJECT-TYPE
        SYNTAX	Gauge
        ACCESS	read-only
        STATUS	mandatory
        DESCRIPTION
                "This is the current receiving rate (in Kbits per second) for this RTP connection"
        ::= { wfAppnNodeRtpConnectionEntry 21 }

    wfAppnNodeRtpConnectionMaxRcvRate OBJECT-TYPE
        SYNTAX	INTEGER
        ACCESS	read-only
        STATUS	mandatory
        DESCRIPTION
                "This is the Maximum receive rate (in Kbits per second) for this RTP connection"
        ::= { wfAppnNodeRtpConnectionEntry 22 }

    wfAppnNodeRtpConnectionMinRcvRate OBJECT-TYPE
        SYNTAX	INTEGER
        ACCESS	read-only
        STATUS	mandatory
        DESCRIPTION
                "This is the Minimum receive rate (in Kbits per second) for this RTP connection"
        ::= { wfAppnNodeRtpConnectionEntry 23 }

    wfAppnNodeRtpConnectionDiscardedBytes OBJECT-TYPE
        SYNTAX	Counter
        ACCESS	read-only
        STATUS	mandatory
        DESCRIPTION
                "This is the number of bytes that have been discarded on this RTP connection"
        ::= { wfAppnNodeRtpConnectionEntry 24 }

    wfAppnNodeRtpConnectionDiscardedPackets OBJECT-TYPE
        SYNTAX	Counter
        ACCESS	read-only
        STATUS	mandatory
        DESCRIPTION
                "This is the number of packets that have been discarded on this RTP connection"
        ::= { wfAppnNodeRtpConnectionEntry 25 }

    wfAppnNodeRtpConnectionResentBytes OBJECT-TYPE
        SYNTAX	Counter
        ACCESS	read-only
        STATUS	mandatory
        DESCRIPTION
                "This is the number of bytes that have been retransmitted this RTP connection"
        ::= { wfAppnNodeRtpConnectionEntry 26 }

    wfAppnNodeRtpConnectionResentPackets OBJECT-TYPE
        SYNTAX	Counter
        ACCESS	read-only
        STATUS	mandatory
        DESCRIPTION
                "This is the number of packets that have been retransmitted this RTP connection"
        ::= { wfAppnNodeRtpConnectionEntry 27 }

    wfAppnNodeRtpConnectionUpTime OBJECT-TYPE
        SYNTAX	INTEGER
        ACCESS	read-only
        STATUS	mandatory
        DESCRIPTION
                "This is the time (in seconds) that this RTP connection has been active"
        ::= { wfAppnNodeRtpConnectionEntry 28 }

    wfAppnNodeRtpConnectionRoundTripTime OBJECT-TYPE
        SYNTAX	INTEGER
        ACCESS	read-only
        STATUS	mandatory
        DESCRIPTION
                "This is the last round-trip time (in milliseconds) for this RTP connection"
        ::= { wfAppnNodeRtpConnectionEntry 29 }

    wfAppnNodeRtpConnectionSmoothRoundTripTime OBJECT-TYPE
        SYNTAX	INTEGER
        ACCESS	read-only
        STATUS	mandatory
        DESCRIPTION
                "This is the smoothed round-trip time (in milliseconds) for this RTP connection"
        ::= { wfAppnNodeRtpConnectionEntry 30 }

    wfAppnNodeRtpConnectionBurstSize OBJECT-TYPE
        SYNTAX	INTEGER
        ACCESS	read-only
        STATUS	mandatory
        DESCRIPTION
                "This is the current burst size for this RTP connection"
        ::= { wfAppnNodeRtpConnectionEntry 31 }

    wfAppnNodeRtpConnectionSrtExpiries OBJECT-TYPE
        SYNTAX	Counter
        ACCESS	read-only
        STATUS	mandatory
        DESCRIPTION
                "This is the number of times the SR Timer has expired on this RTP connection"
        ::= { wfAppnNodeRtpConnectionEntry 32 }

    wfAppnNodeRtpConnectionShortReqTimer OBJECT-TYPE
        SYNTAX	INTEGER
        ACCESS	read-only
        STATUS	mandatory
        DESCRIPTION
                "This is the SHORT_REQ timer duration (in seconds) for this RTP connection"
        ::= { wfAppnNodeRtpConnectionEntry 33 }

    wfAppnNodeRtpConnectionGapsDetected OBJECT-TYPE
        SYNTAX	Counter
        ACCESS	read-only
        STATUS	mandatory
        DESCRIPTION
                "This is the number of gaps detected for this RTP connection"
        ::= { wfAppnNodeRtpConnectionEntry 34 }

    wfAppnNodeRtpConnectionRscv OBJECT-TYPE
        SYNTAX	OCTET STRING
        ACCESS	read-only
        STATUS	mandatory
        DESCRIPTION
                "This is the RSCV (in hex) for this RTP connection"
        ::= { wfAppnNodeRtpConnectionEntry 35 }

    wfAppnNodeRtpConnectionRscvText OBJECT-TYPE
        SYNTAX	DisplayString
        ACCESS	read-only
        STATUS	mandatory
        DESCRIPTION
                "This is the RSCV (in a human-readable format) for this RTP connection"
        ::= { wfAppnNodeRtpConnectionEntry 36 }

    wfAppnNnTopo	OBJECT IDENTIFIER ::= { wfAppnNn 1 }

    wfAppnNnTopoMaxNodes OBJECT-TYPE
        SYNTAX	INTEGER
        ACCESS	read-only
        STATUS	mandatory
        DESCRIPTION
                "Maximum number of nodes allowed in the APPN topology database
                This administratively assigned value must be equal to or
                greater than the maximum total number of end nodes and
                network nodes.
                If the number of nodes exceeds this value, APPN will issue
                an Alert and the node can no longer participate as a network
                node."
        ::= { wfAppnNnTopo 1 }

    wfAppnNnTopoCurNumNodes OBJECT-TYPE
        SYNTAX	INTEGER
        ACCESS	read-only
        STATUS	mandatory
        DESCRIPTION
                "Current number of nodes in this node's topology database.
                If this value exceeds the maximum number of nodes allowed
                (NnTopoMaxNodes), APPN alert CPDB002 is
                issued."
        ::= { wfAppnNnTopo 2 }

    wfAppnNnTopoInTdus OBJECT-TYPE
        SYNTAX	Counter
        ACCESS	read-only
        STATUS	mandatory
        DESCRIPTION
                "Total number of TDUs received from
                all adjacent NN since last initialization."
        ::= { wfAppnNnTopo 3 }

    wfAppnNnTopoOutTdus OBJECT-TYPE
        SYNTAX	Counter
        ACCESS	read-only
        STATUS	mandatory
        DESCRIPTION
                "Total number of TDUs built by this node to be sent to
                all adjacent NN since last initialization."
        ::= { wfAppnNnTopo 4 }

    wfAppnNnTopoNodeLowRsns OBJECT-TYPE
        SYNTAX	Counter
        ACCESS	read-only
        STATUS	mandatory
        DESCRIPTION
                "Total number of topology node updates received by this
                node with a RSN less than the current RSN.  Both even and
                odd RSN are included in this count.
                These TDUs are not errors, but result when TDUs are
                broadcast to all adjacent network nodes.  No update to
                this node's topology database occurs, but this node will
                send a TDU with it's higher RSN to the adjacent node that
                sent this low RSN."
        ::= { wfAppnNnTopo 5 }

    wfAppnNnTopoNodeEqualRsns OBJECT-TYPE
        SYNTAX	Counter
        ACCESS	read-only
        STATUS	mandatory
        DESCRIPTION
                "Total number of topology node updates received by this
                node with a RSN equal to the current RSN.  Both even and
                odd RSN are included in this count.
                These TDUs are not errors, but result when TDUs are
                broadcast to all adjacent network nodes.  No update to
                this node's topology database occurs."
        ::= { wfAppnNnTopo 6 }

    wfAppnNnTopoNodeGoodHighRsns OBJECT-TYPE
        SYNTAX	Counter
        ACCESS	read-only
        STATUS	mandatory
        DESCRIPTION
                "Total number of topology node updates received by this
                node with a RSN greater than the current RSN.
                This results in updating this nodes topology and broadcasting
                a TDU to all adjacent network nodes.  It is not required to
                send a TDU to the sender of this update because that node
                already has the update."
        ::= { wfAppnNnTopo 7 }

    wfAppnNnTopoNodeBadHighRsns OBJECT-TYPE
        SYNTAX	Counter
        ACCESS	read-only
        STATUS	mandatory
        DESCRIPTION
                "Total number of topology node updates received by this
                node with an odd RSN greater than the current RSN.
                These updates represent a topology inconsistency detected
                by one of the APPN network nodes.
                This results in updating this nodes topology and broadcasting
                a TDU to all adjacent network nodes."
        ::= { wfAppnNnTopo 8 }

    wfAppnNnTopoNodeStateUpdates OBJECT-TYPE
        SYNTAX	Counter
        ACCESS	read-only
        STATUS	mandatory
        DESCRIPTION
                "Total number of topology Node records built as a result
                of internally detected node state changes that affect APPN
                topology and routing.  Updates are sent via TDUs to all
                adjacent network nodes."
        ::= { wfAppnNnTopo 9 }

    wfAppnNnTopoNodeErrors OBJECT-TYPE
        SYNTAX	Counter
        ACCESS	read-only
        STATUS	mandatory
        DESCRIPTION
                "Total number of topology node records inconsistencies
                detected by this node.  This occurs when this node attempts
                to update its topology database and detects a data
                inconsistency.  This node will create a TDU with the
                current RSN incremented to the next odd number and
                broadcast it to all adjacent NNs."
        ::= { wfAppnNnTopo 10 }

    wfAppnNnTopoNodeTimerUpdates OBJECT-TYPE
        SYNTAX	Counter
        ACCESS	read-only
        STATUS	mandatory
        DESCRIPTION
                "Total number of topology node records built for this
                node's resource due to timer updates. Updates are sent via
                TDUs to all adjacent network nodes. These updates insure
                other network nodes do not delete this node's resources
                from their topology database."
        ::= { wfAppnNnTopo 11 }

    wfAppnNnTopoNodePurges OBJECT-TYPE
        SYNTAX	Counter
        ACCESS	read-only
        STATUS	mandatory
        DESCRIPTION
                "Total number of topology node records purged from this
                node's topology database.  This occurs when a node has not
                been updated in a specified amount of time.  The owning
                node is responsible for broadcasting updates for its resource
                that it wants kept in the network topology."
        ::= { wfAppnNnTopo 12 }

    wfAppnNnTopoTgLowRsns OBJECT-TYPE
        SYNTAX	Counter
        ACCESS	read-only
        STATUS	mandatory
        DESCRIPTION
                "Total number of topology TG updates received by this
                node with a RSN less than the current RSN.  Both even and
                odd RSN are included in this count.
                These TDUs are not errors, but result when TDUs are
                broadcast to all adjacent network nodes.  No update to
                this node's topology database occurs, but this node will
                send a TDU with it's higher RSN to the sender of the low
                RSN."
        ::= { wfAppnNnTopo 13 }

    wfAppnNnTopoTgEqualRsns OBJECT-TYPE
        SYNTAX	Counter
        ACCESS	read-only
        STATUS	mandatory
        DESCRIPTION
                "Total number of topology TG updates received by this
                node with a RSN equal to the current RSN.  Both even and
                odd RSN are included in this count.
                These TDUs are not errors, but result when TDUs are
                broadcast to all adjacent network nodes.  No update to
                this node's topology database occurs."
        ::= { wfAppnNnTopo 14 }

    wfAppnNnTopoTgGoodHighRsns OBJECT-TYPE
        SYNTAX	Counter
        ACCESS	read-only
        STATUS	mandatory
        DESCRIPTION
                "Total number of topology TG updates received by this
                node with a RSN greater than the current RSN.
                This results in updating this nodes topology and broadcasting
                the update to all adjacent network nodes."
        ::= { wfAppnNnTopo 15 }

    wfAppnNnTopoTgBadHighRsns OBJECT-TYPE
        SYNTAX	Counter
        ACCESS	read-only
        STATUS	mandatory
        DESCRIPTION
                "Total number of topology TG updates received by this
                node with an odd RSN greater than the current RSN.
                These updates represent a topology inconsistency detected
                by one of the APPN network nodes.
                This results in updating this nodes topology and broadcasting
                a TDU to all adjacent network nodes."
        ::= { wfAppnNnTopo 16 }

    wfAppnNnTopoTgStateUpdates OBJECT-TYPE
        SYNTAX	Counter
        ACCESS	read-only
        STATUS	mandatory
        DESCRIPTION
                "Total number of topology TG records built as a result
                of internally detected node state changes that affect APPN
                topology and routing.  Updates are sent via TDUs to all
                adjacent network nodes."
        ::= { wfAppnNnTopo 17 }

    wfAppnNnTopoTgErrors OBJECT-TYPE
        SYNTAX	Counter
        ACCESS	read-only
        STATUS	mandatory
        DESCRIPTION
                "Total number of topology TG records inconsistencies
                detected by this node.  This occurs when this node attempts
                to update its topology database and detects a data
                inconsistency.  This node will create a TDU with the
                current RSN incremented to the next odd number and
                broadcast it to all adjacent NNs."
        ::= { wfAppnNnTopo 18 }

    wfAppnNnTopoTgTimerUpdates OBJECT-TYPE
        SYNTAX	Counter
        ACCESS	read-only
        STATUS	mandatory
        DESCRIPTION
                "Total number of topology TG records built for this
                node's resource due to timer updates. Updates are sent via
                TDUs to all adjacent network nodes. These updates insure
                other network nodes do not delete this node's resources
                from their topology database."
        ::= { wfAppnNnTopo 19 }

    wfAppnNnTopoTgPurges OBJECT-TYPE
        SYNTAX	Counter
        ACCESS	read-only
        STATUS	mandatory
        DESCRIPTION
                "Total number of topology TG records purged from this
                node's topology database.  This occurs when a TG has not
                been updated in a specified amount of time.  The owning
                node is responsible for broadcasting updates for its resource
                that it wants to keep in the network topology."
        ::= { wfAppnNnTopo 20 }

    wfAppnNnTopoTotalRouteCalcs OBJECT-TYPE
        SYNTAX	Counter
        ACCESS	read-only
        STATUS	mandatory
        DESCRIPTION
                "Number of routes calculated for all class of services
                since the last initialization."
        ::= { wfAppnNnTopo 21 }

    wfAppnNnTopoTotalRouteRejs OBJECT-TYPE
        SYNTAX	Counter
        ACCESS	read-only
        STATUS	mandatory
        DESCRIPTION
                "Number of route requests for all class of services that
                could not be calculated since last initialization."
        ::= { wfAppnNnTopo 22 }

    wfAppnNnAdjNodeTable OBJECT-TYPE
        SYNTAX	SEQUENCE OF WfAppnNnAdjNodeEntry
        ACCESS	not-accessible
        STATUS	mandatory
        DESCRIPTION
                "Table containing an entry for every adjacent node. The information
                kept in this table is the last FRSN sent and received,
                the status of the CP-CP sessions, and a gauge that indicates
                the number of outstanding TDUs."
        ::= { wfAppnNn 2 }

    wfAppnNnAdjNodeEntry OBJECT-TYPE
        SYNTAX	WfAppnNnAdjNodeEntry
        ACCESS	not-accessible
        STATUS	mandatory
        DESCRIPTION
                "The adjacent node name is the index for this table."
        INDEX	{ wfAppnNnAdjNodeAdjName }
        ::= { wfAppnNnAdjNodeTable 1 }

    WfAppnNnAdjNodeEntry ::= SEQUENCE {
    	    wfAppnNnAdjNodeAdjName
    		DisplayString,
    	    wfAppnNnAdjNodeCpCpSessStatus
    		INTEGER,
    	    wfAppnNnAdjNodeOutOfSeqTdus
    		Gauge,
    	    wfAppnNnAdjNodeLastFrsnSent
    		INTEGER,
    	    wfAppnNnAdjNodeLastFrsnRcvd
    		INTEGER
        }

    wfAppnNnAdjNodeAdjName OBJECT-TYPE
        SYNTAX	DisplayString
        ACCESS	read-only
        STATUS	mandatory
        DESCRIPTION
                "An administratively-assigned fully-qualified
                name of this node's adjacent network node."
        ::= { wfAppnNnAdjNodeEntry 1 }

    wfAppnNnAdjNodeCpCpSessStatus OBJECT-TYPE
        SYNTAX	INTEGER {
    		    active(1),
    		    loser(2),
    		    winner(3),
    		    inactive(4)
    		}
        ACCESS	read-only
        STATUS	mandatory
        DESCRIPTION
                "Indicates the state of CP-CP sessions between this node
                and adjacent network and end nodes.  Inactive indicates no
                CP-CP sessions exists between this node and the adjacent
                node.  Active indicates CP-CP sessons are active using both
                the ConWinner and ConLoser sessions. The session initiated
                by this node is referred to as the ConWinner session and is
                used by this node to send to the adjacent node.  The ConLoserr
                session is initiated by the adjacent node and is used by this
                node to receive from the adjacent node."
        DEFVAL	{ inactive }
        ::= { wfAppnNnAdjNodeEntry 2 }

    wfAppnNnAdjNodeOutOfSeqTdus OBJECT-TYPE
        SYNTAX	Gauge
        ACCESS	read-only
        STATUS	mandatory
        DESCRIPTION
                "Number of out of sequence Topology Database
                Updates (TDUs).  In a quiesced state, this value is
                zero.  In normal operation, the value varies
                depending on the network environment."
        ::= { wfAppnNnAdjNodeEntry 3 }

    wfAppnNnAdjNodeLastFrsnSent OBJECT-TYPE
        SYNTAX	INTEGER
        ACCESS	read-only
        STATUS	mandatory
        DESCRIPTION
                "Flow reduction sequence numbers (FRSNs) are associated
                with Topology Database Updates (TDUs) and are unique
                only within each APPN network node.  A TDU can be
                associated with multiple APPN resources. This FRSN
                indicates the last TDU sent to this adjacent node."
        ::= { wfAppnNnAdjNodeEntry 4 }

    wfAppnNnAdjNodeLastFrsnRcvd OBJECT-TYPE
        SYNTAX	INTEGER
        ACCESS	read-only
        STATUS	mandatory
        DESCRIPTION
                "Flow reduction sequence numbers (FRSNs) are associated
                with Topology Database Updates (TDUs) and are unique
                only within each APPN network node.  A TDU can be
                associated with multiple APPN resources. This FRSN
                indicates the last TDU received from this adjacent node."
        ::= { wfAppnNnAdjNodeEntry 5 }

    wfAppnNnTopologyTable OBJECT-TYPE
        SYNTAX	SEQUENCE OF WfAppnNnTopologyEntry
        ACCESS	not-accessible
        STATUS	mandatory
        DESCRIPTION
                "Portion of the APPN routing table
                that describes all of the APPN network nodes
                and virtual nodes known to this node."
        ::= { wfAppnNnTopology 1 }

    wfAppnNnTopologyEntry OBJECT-TYPE
        SYNTAX	WfAppnNnTopologyEntry
        ACCESS	not-accessible
        STATUS	mandatory
        DESCRIPTION
                "The fully-qualified node name is used to
                index this table."
        INDEX	{ wfAppnNnNodeName }
        ::= { wfAppnNnTopologyTable 1 }

    WfAppnNnTopologyEntry ::= SEQUENCE {
    	    wfAppnNnNodeName
    		DisplayString,
    	    wfAppnNnNodeFrsn
    		INTEGER,
    	    wfAppnNnNodeEntryTimeLeft
    		INTEGER,
    	    wfAppnNnNodeType
    		INTEGER,
    	    wfAppnNnNodeRsn
    		INTEGER,
    	    wfAppnNnNodeRouteAddResist
    		INTEGER,
    	    wfAppnNnNodeCongested
    		INTEGER,
    	    wfAppnNnNodeIsrDepleted
    		INTEGER,
    	    wfAppnNnNodeEndptDepleted
    		INTEGER,
    	    wfAppnNnNodeQuiescing
    		INTEGER,
    	    wfAppnNnNodeGateway
    		INTEGER,
    	    wfAppnNnNodeCentralDirectory
    		INTEGER,
    	    wfAppnNnNodeIsr
       		INTEGER,
            wfAppnNnNodeChainSupport
      		INTEGER,
    	    wfAppnNnNodeHprBase
    		INTEGER,
    	    wfAppnNnNodeRtpTower
    		INTEGER
        }

    wfAppnNnNodeName OBJECT-TYPE
        SYNTAX	DisplayString
        ACCESS	read-only
        STATUS	mandatory
        DESCRIPTION
                "Administratively-assigned network name that is locally
                defined at each network node in the format NETID.CPNAME."
        ::= { wfAppnNnTopologyEntry 1 }

    wfAppnNnNodeFrsn OBJECT-TYPE
        SYNTAX	INTEGER
        ACCESS	read-only
        STATUS	mandatory
        DESCRIPTION
                "Flow reduction sequence numbers (FRSNs) are associated
                with Topology Database Updates (TDUs) and are unique
                only within each APPN network node.  A TDU can be
                associated with multiple APPN resources. This FRSN
                indicates the last time this resource was updated at
                this node."
        ::= { wfAppnNnTopologyEntry 2 }

    wfAppnNnNodeEntryTimeLeft OBJECT-TYPE
        SYNTAX	INTEGER
        ACCESS	read-only
        STATUS	mandatory
        DESCRIPTION
                "Number of days before deletion of this
                network node entry. Range is 0-31."
        ::= { wfAppnNnTopologyEntry 3 }

    wfAppnNnNodeType OBJECT-TYPE
        SYNTAX	INTEGER {
    		    nn(1),
    		    vn(3)
    		}
        ACCESS	read-only
        STATUS	mandatory
        DESCRIPTION
                "Type of APPN node."
        ::= { wfAppnNnTopologyEntry 4 }

    wfAppnNnNodeRsn OBJECT-TYPE
        SYNTAX	INTEGER
        ACCESS	read-only
        STATUS	mandatory
        DESCRIPTION
                "Resource sequence number that is assigned and
                controlled by the network node that owns this
                resource. This is always an even 32-bit number
                unless an error has occurred."
        ::= { wfAppnNnTopologyEntry 5 }

    wfAppnNnNodeRouteAddResist OBJECT-TYPE
        SYNTAX	INTEGER
        ACCESS	read-only
        STATUS	mandatory
        DESCRIPTION
                "Route addition resistance
                indicates the relative desirability
                of using this node for intermediate session traffic.
                The value, which can be any integer 0-255,
                is used in route computation.  The lower the value,
                the more desirable the node is for intermediate routing."
        ::= { wfAppnNnTopologyEntry 6 }

    wfAppnNnNodeCongested OBJECT-TYPE
        SYNTAX	INTEGER {
    		    yes(1),
    		    no(2)
    		}
        ACCESS	read-only
        STATUS	mandatory
        DESCRIPTION
                "Indicates whether this node is congested.
                This node is not be included in route selection
                by other nodes when this congestion exists."
        ::= { wfAppnNnTopologyEntry 7 }

    wfAppnNnNodeIsrDepleted OBJECT-TYPE
        SYNTAX	INTEGER {
    		    yes(1),
    		    no(2)
    		}
        ACCESS	read-only
        STATUS	mandatory
        DESCRIPTION
                "Indicates whether intermediate session
                routing resources are depleted.  This node is
                not included in intermediate route selection
                by other nodes when resources are depleted."
        ::= { wfAppnNnTopologyEntry 8 }

    wfAppnNnNodeEndptDepleted OBJECT-TYPE
        SYNTAX	INTEGER {
    		    yes(1),
    		    no(2)
    		}
        ACCESS	read-only
        STATUS	mandatory
        DESCRIPTION
                "Indicates whether session endpoint resources are depleted."
        ::= { wfAppnNnTopologyEntry 9 }

    wfAppnNnNodeQuiescing OBJECT-TYPE
        SYNTAX	INTEGER {
    		    yes(1),
    		    no(2)
    		}
        ACCESS	read-only
        STATUS	mandatory
        DESCRIPTION
                "Indicates whether the node is quiescing.
                This node is not included in route selection
                by other nodes when the node is quiescing."
        ::= { wfAppnNnTopologyEntry 10 }

    wfAppnNnNodeGateway OBJECT-TYPE
        SYNTAX	INTEGER {
    		    yes(1),
    		    no(2)
    		}
        ACCESS	read-only
        STATUS	mandatory
        DESCRIPTION
                "Indicates whether the node provide gateway functions."
        ::= { wfAppnNnTopologyEntry 11 }

    wfAppnNnNodeCentralDirectory OBJECT-TYPE
        SYNTAX	INTEGER {
    		    yes(1),
    		    no(2)
    		}
        ACCESS	read-only
        STATUS	mandatory
        DESCRIPTION
                "Indicates whether the node is central directory."
        ::= { wfAppnNnTopologyEntry 12 }

    wfAppnNnNodeIsr OBJECT-TYPE
        SYNTAX	INTEGER {
    		    yes(1),
    		    no(2)
    		}
        ACCESS	read-only
        STATUS	mandatory
        DESCRIPTION
                "Indicates whether the node supports intermediate session
                routing (ISR)."
        ::= { wfAppnNnTopologyEntry 13 }

    wfAppnNnNodeChainSupport OBJECT-TYPE
        SYNTAX	INTEGER {
    		    yes(1),
    		    no(2)
    		}
        ACCESS	read-only
        STATUS	mandatory
        DESCRIPTION
                "Indicates whether this node supports chaining."
        ::= { wfAppnNnTopologyEntry 14 }

    wfAppnNnNodeHprBase OBJECT-TYPE
        SYNTAX	INTEGER {
    		    yes(1),
    		    no(2)
    		}
        ACCESS	read-only
        STATUS	mandatory
        DESCRIPTION
                "Indicates whether this node supports HPR base functionality."
        ::= { wfAppnNnTopologyEntry 15 }

    wfAppnNnNodeRtpTower OBJECT-TYPE
        SYNTAX	INTEGER {
    		    yes(1),
    		    no(2)
    		}
        ACCESS	read-only
        STATUS	mandatory
        DESCRIPTION
                "Indicates whether this node supports RTP tower functionality."
        ::= { wfAppnNnTopologyEntry 16 }


    wfAppnNnTgTopologyTable OBJECT-TYPE
        SYNTAX	SEQUENCE OF WfAppnNnTgTopologyEntry
        ACCESS	not-accessible
        STATUS	mandatory
        DESCRIPTION
                "Portion of the APPN topology database
                that describes all of the APPN transmissions groups
                used by the APPN network nodes."
        ::= { wfAppnNnTopology 2 }

    wfAppnNnTgTopologyEntry OBJECT-TYPE
        SYNTAX	WfAppnNnTgTopologyEntry
        ACCESS	not-accessible
        STATUS	mandatory
        DESCRIPTION
                "This table requires three indexes to provide a
                unique index.  The indexes are the owning or originating
                CPname, the destination CPname, and the TG number."
        INDEX	{ wfAppnNnTgOwner,
    		  wfAppnNnTgDest,
    		  wfAppnNnTgNum }
        ::= { wfAppnNnTgTopologyTable 1 }

    WfAppnNnTgTopologyEntry ::= SEQUENCE {
    	    wfAppnNnTgOwner
    		DisplayString,
    	    wfAppnNnTgDest
    		DisplayString,
    	    wfAppnNnTgNum
    		INTEGER,
    	    wfAppnNnTgFrsn
    		INTEGER,
    	    wfAppnNnTgEntryTimeLeft
    		INTEGER,
    	    wfAppnNnTgDestVirtual
    		INTEGER,
    	    wfAppnNnTgDlcData
    		OCTET STRING,
    	    wfAppnNnTgRsn
    		INTEGER,
    	    wfAppnNnTgOperational
    		INTEGER,
    	    wfAppnNnTgQuiescing
    		INTEGER,
    	    wfAppnNnTgCpCpSession
    		INTEGER,
    	    wfAppnNnTgEffCap
    		INTEGER,
    	    wfAppnNnTgConnCost
    		INTEGER,
    	    wfAppnNnTgByteCost
    		INTEGER,
    	    wfAppnNnTgSecurity
    		INTEGER,
    	    wfAppnNnTgDelay
    		INTEGER,
    	    wfAppnNnTgModemClass
    		INTEGER,
    	    wfAppnNnTgUsr1
    		INTEGER,
    	    wfAppnNnTgUsr2
    		INTEGER,
    	    wfAppnNnTgUsr3
    		INTEGER,
            wfAppnNnTgHprBase
    		INTEGER,
            wfAppnNnTgRtpTower
    		INTEGER
        }

    wfAppnNnTgOwner OBJECT-TYPE
        SYNTAX	DisplayString
        ACCESS	read-only
        STATUS	mandatory
        DESCRIPTION
                "Administratively-assigned name for the
                originating node for this TG. The format
                is NETID.CPNAME and is the same name
                specified in the node table."
        ::= { wfAppnNnTgTopologyEntry 1 }

    wfAppnNnTgDest OBJECT-TYPE
        SYNTAX	DisplayString
        ACCESS	read-only
        STATUS	mandatory
        DESCRIPTION
                "Administratively-assigned fully-qualified
                network name for the destination node for this TG."
        ::= { wfAppnNnTgTopologyEntry 2 }

    wfAppnNnTgNum OBJECT-TYPE
        SYNTAX	INTEGER
        ACCESS	read-only
        STATUS	mandatory
        DESCRIPTION
                "Number associated with this
                transmission group. Range is 0-255."
        ::= { wfAppnNnTgTopologyEntry 3 }

    wfAppnNnTgFrsn OBJECT-TYPE
        SYNTAX	INTEGER
        ACCESS	read-only
        STATUS	mandatory
        DESCRIPTION
                "Flow reduction sequence numbers (FRSNs) are associated
                with Topology Database Updates (TDUs) and are unique
                only within each APPN network node.  A TDU can be
                associated with multiple APPN resources.  This FRSN
                indicates the last time this resource was updated at
                this node."
        ::= { wfAppnNnTgTopologyEntry 4 }

    wfAppnNnTgEntryTimeLeft OBJECT-TYPE
        SYNTAX	INTEGER
        ACCESS	read-only
        STATUS	mandatory
        DESCRIPTION
                "Number of days before deletion of this
                network node TG entry. Range is 0-31."
        ::= { wfAppnNnTgTopologyEntry 5 }

    wfAppnNnTgDestVirtual OBJECT-TYPE
        SYNTAX	INTEGER
        ACCESS	read-only
        STATUS	mandatory
        DESCRIPTION
                "Indicates whether the destination node is
                a virtual node."
        ::= { wfAppnNnTgTopologyEntry 6 }

    wfAppnNnTgDlcData OBJECT-TYPE
        SYNTAX	OCTET STRING
        ACCESS	read-only
        STATUS	mandatory
        DESCRIPTION
                "DLC specific data related to the link connection
                network.
                Token-Ring    - MAC/SAP
                X.25 Switched - dial digits
                X.21 Switched - dial digits
                Circuit Swtch - dial digits."
        ::= { wfAppnNnTgTopologyEntry 7 }

    wfAppnNnTgRsn OBJECT-TYPE
        SYNTAX	INTEGER
        ACCESS	read-only
        STATUS	mandatory
        DESCRIPTION
                "Current owning node's resource sequence number
                for this resource."
        ::= { wfAppnNnTgTopologyEntry 8 }

    wfAppnNnTgOperational OBJECT-TYPE
        SYNTAX	INTEGER
        ACCESS	read-only
        STATUS	mandatory
        DESCRIPTION
                "Indicates whether the transmission group
                is operational."
        ::= { wfAppnNnTgTopologyEntry 9 }

    wfAppnNnTgQuiescing OBJECT-TYPE
        SYNTAX	INTEGER
        ACCESS	read-only
        STATUS	mandatory
        DESCRIPTION
                "Indicates whether the transmission group
                is quiescing."
        ::= { wfAppnNnTgTopologyEntry 10 }

    wfAppnNnTgCpCpSession OBJECT-TYPE
        SYNTAX	INTEGER
        ACCESS	read-only
        STATUS	mandatory
        DESCRIPTION
                "Indicates whether CP-CP sessions are supported on this TG."
        ::= { wfAppnNnTgTopologyEntry 11 }

    wfAppnNnTgEffCap OBJECT-TYPE
        SYNTAX	INTEGER(0..255)
        ACCESS	read-only
        STATUS	mandatory
        DESCRIPTION
                "The effective capacity is an integer value that indicates
                the kilo bits per second.
                It is derived from the link bandwidth and maximum load
                factor with the range of 0 thru 255.
                This is an administratively assigned value for this TG.
                DEVIATION: 6611 mib uses range of 0 thru 603,979,776."
        ::= { wfAppnNnTgTopologyEntry 12 }

    wfAppnNnTgConnCost OBJECT-TYPE
        SYNTAX	INTEGER
        ACCESS	read-only
        STATUS	mandatory
        DESCRIPTION
                "Cost per connect time: a value representing
                the relative cost per unit of time to use
                the TG. Range is from 0, which means no cost,
                to 255, which indicates maximum cost.
                This is an administratively assigned value associated
                with this TG."
        ::= { wfAppnNnTgTopologyEntry 13 }

    wfAppnNnTgByteCost OBJECT-TYPE
        SYNTAX	INTEGER
        ACCESS	read-only
        STATUS	mandatory
        DESCRIPTION
                "Relative cost of transmitting a byte over this link.
                Range is from 0 (lowest cost) to 255.
                This is an administratively assigned value associated
                with this TG."
        ::= { wfAppnNnTgTopologyEntry 14 }

    wfAppnNnTgSecurity OBJECT-TYPE
        SYNTAX	INTEGER(0..255)
        ACCESS	read-only
        STATUS	mandatory
        DESCRIPTION
                "The security is represented as an integer with a range of
                1 thru 255 with the most common values enumerated as
                defined above.
                This is an administratively assigned value associated
                with this TG."
        ::= { wfAppnNnTgTopologyEntry 15 }

    wfAppnNnTgDelay OBJECT-TYPE
        SYNTAX  INTEGER {
                negligible(1),
                terrestrial(2),
                packet(3),
                long(4),
                maximum(5)                
                }
        ACCESS	read-write
        STATUS	mandatory
        DESCRIPTION
                "Relative amount of time that it takes for a signal to
                travel the length of the logical link.
                This is an administratively assigned value associated
                with this TG.
                DEVIATION: 6611 MIB, uses units of microseconds."
        DEFVAL  { negligible }
        ::= { wfAppnNnTgTopologyEntry 16 }

    wfAppnNnTgModemClass OBJECT-TYPE
        SYNTAX	INTEGER
        ACCESS	read-only
        STATUS	mandatory
        DESCRIPTION
                "This is used to have multiple images for a
                connection network.  For a connection network
                           it is the same as in the TG vector; for
                           a non-connection network it is X'00'."
        ::= { wfAppnNnTgTopologyEntry 17 }

    wfAppnNnTgUsr1 OBJECT-TYPE
        SYNTAX	INTEGER
        ACCESS	read-only
        STATUS	mandatory
        DESCRIPTION
                "First user-defined TG characteristic for this TG with
                a range of 0-255.
                This is an administratively assigned value associated
                with this TG."
        ::= { wfAppnNnTgTopologyEntry 18 }

    wfAppnNnTgUsr2 OBJECT-TYPE
        SYNTAX	INTEGER
        ACCESS	read-only
        STATUS	mandatory
        DESCRIPTION
                "Second user-defined TG characteristic for this TG with
                a range of 0-255.
                This is an administratively assigned value associated
                with this TG."
        ::= { wfAppnNnTgTopologyEntry 19 }

    wfAppnNnTgUsr3 OBJECT-TYPE
        SYNTAX	INTEGER
        ACCESS	read-only
        STATUS	mandatory
        DESCRIPTION
                "Third user-defined TG characteristic for this TG with
                a range of 0-255.
                This is an administratively assigned value associated
                with this TG."
        ::= { wfAppnNnTgTopologyEntry 20 }

    wfAppnNnTgHprBase OBJECT-TYPE
        SYNTAX	INTEGER
        ACCESS	read-only
        STATUS	mandatory
        DESCRIPTION
                "Indicates whether HPR base functionality is supported 
                 on this TG." 
        ::= { wfAppnNnTgTopologyEntry 21 }

    wfAppnNnTgRtpTower OBJECT-TYPE
        SYNTAX	INTEGER
        ACCESS	read-only
        STATUS	mandatory
        DESCRIPTION
                "Indicates whether RTP Tower functionality is supported 
                 on this TG." 
        ::= { wfAppnNnTgTopologyEntry 22 }


    wfAppnNnTopologyFRTable OBJECT-TYPE
        SYNTAX	SEQUENCE OF WfAppnNnTopologyFREntry
        ACCESS	not-accessible
        STATUS	mandatory
        DESCRIPTION
                "Portion of the APPN routing table
                that describes all of the APPN network nodes
                and virtual nodes known to this node."
        ::= { wfAppnNnTopology 3 }

    wfAppnNnTopologyFREntry OBJECT-TYPE
        SYNTAX	WfAppnNnTopologyFREntry
        ACCESS	not-accessible
        STATUS	mandatory
        DESCRIPTION
                "The fully-qualified node name is used to
                index this table."
        INDEX	{ wfAppnNnNodeFRFrsn,
    		  wfAppnNnNodeFRName }
        ::= { wfAppnNnTopologyFRTable 1 }

    WfAppnNnTopologyFREntry ::= SEQUENCE {
    	    wfAppnNnNodeFRName
    		DisplayString,
    	    wfAppnNnNodeFRFrsn
    		INTEGER,
    	    wfAppnNnNodeFREntryTimeLeft
    		INTEGER,
    	    wfAppnNnNodeFRType
    		INTEGER,
    	    wfAppnNnNodeFRRsn
    		INTEGER,
    	    wfAppnNnNodeFRRouteAddResist
    		INTEGER,
    	    wfAppnNnNodeFRCongested
    		INTEGER,
    	    wfAppnNnNodeFRIsrDepleted
    		INTEGER,
    	    wfAppnNnNodeFREndptDepleted
    		INTEGER,
    	    wfAppnNnNodeFRQuiescing
    		INTEGER,
    	    wfAppnNnNodeFRGateway
    		INTEGER,
    	    wfAppnNnNodeFRCentralDirectory
    		INTEGER,
    	    wfAppnNnNodeFRIsr
    		INTEGER,
    	    wfAppnNnNodeFRChainSupport
    		INTEGER,
    	    wfAppnNnNodeFRHprBase
    		INTEGER,
    	    wfAppnNnNodeFRRtpTower
    		INTEGER

        }

    wfAppnNnNodeFRName OBJECT-TYPE
        SYNTAX	DisplayString
        ACCESS	read-only
        STATUS	mandatory
        DESCRIPTION
                "Administratively-assigned network name that is locally
                defined at each network node in the format NETID.CPNAME."
        ::= { wfAppnNnTopologyFREntry 1 }

    wfAppnNnNodeFRFrsn OBJECT-TYPE
        SYNTAX	INTEGER
        ACCESS	read-only
        STATUS	mandatory
        DESCRIPTION
                "Flow reduction sequence numbers (FRSNs) are associated
                with Topology Database Updates (TDUs) and are unique
                only within each APPN network node.  A TDU can be
                associated with multiple APPN resources. This FRSN
                indicates the last time this resource was updated at
                this node."
        ::= { wfAppnNnTopologyFREntry 2 }

    wfAppnNnNodeFREntryTimeLeft OBJECT-TYPE
        SYNTAX	INTEGER
        ACCESS	read-only
        STATUS	mandatory
        DESCRIPTION
                "Number of days before deletion of this
                network node entry. Range is 0-31."
        ::= { wfAppnNnTopologyFREntry 3 }

    wfAppnNnNodeFRType OBJECT-TYPE
        SYNTAX	INTEGER {
    		    nn(1),
    		    vn(3)
    		}
        ACCESS	read-only
        STATUS	mandatory
        DESCRIPTION
                "Type of APPN node."
        ::= { wfAppnNnTopologyFREntry 4 }

    wfAppnNnNodeFRRsn OBJECT-TYPE
        SYNTAX	INTEGER
        ACCESS	read-only
        STATUS	mandatory
        DESCRIPTION
                "Resource sequence number that is assigned and
                controlled by the network node that owns this
                resource. This is always an even 32-bit number
                unless an error has occurred."
        ::= { wfAppnNnTopologyFREntry 5 }

    wfAppnNnNodeFRRouteAddResist OBJECT-TYPE
        SYNTAX	INTEGER
        ACCESS	read-only
        STATUS	mandatory
        DESCRIPTION
                "Route addition resistance
                indicates the relative desirability
                of using this node for intermediate session traffic.
                The value, which can be any integer 0-255,
                is used in route computation.  The lower the value,
                the more desirable the node is for intermediate routing."
        ::= { wfAppnNnTopologyFREntry 6 }

    wfAppnNnNodeFRCongested OBJECT-TYPE
        SYNTAX	INTEGER {
    		    yes(1),
    		    no(2)
    		}
        ACCESS	read-only
        STATUS	mandatory
        DESCRIPTION
                "Indicates whether this node is congested.
                This node is not be included in route selection
                by other nodes when this congestion exists."
        ::= { wfAppnNnTopologyFREntry 7 }

    wfAppnNnNodeFRIsrDepleted OBJECT-TYPE
        SYNTAX	INTEGER {
    		    yes(1),
    		    no(2)
    		}
        ACCESS	read-only
        STATUS	mandatory
        DESCRIPTION
                "Indicates whether intermediate session
                routing resources are depleted.  This node is
                not included in intermediate route selection
                by other nodes when resources are depleted."
        ::= { wfAppnNnTopologyFREntry 8 }

    wfAppnNnNodeFREndptDepleted OBJECT-TYPE
        SYNTAX	INTEGER {
    		    yes(1),
    		    no(2)
    		}
        ACCESS	read-only
        STATUS	mandatory
        DESCRIPTION
                "Indicates whether session endpoint resources are depleted."
        ::= { wfAppnNnTopologyFREntry 9 }

    wfAppnNnNodeFRQuiescing OBJECT-TYPE
        SYNTAX	INTEGER {
    		    yes(1),
    		    no(2)
    		}
        ACCESS	read-only
        STATUS	mandatory
        DESCRIPTION
                "Indicates whether the node is quiescing.
                This node is not included in route selection
                by other nodes when the node is quiescing."
        ::= { wfAppnNnTopologyFREntry 10 }

    wfAppnNnNodeFRGateway OBJECT-TYPE
        SYNTAX	INTEGER {
    		    yes(1),
    		    no(2)
    		}
        ACCESS	read-only
        STATUS	mandatory
        DESCRIPTION
                "Indicates whether the node provide gateway functions."
        ::= { wfAppnNnTopologyFREntry 11 }

    wfAppnNnNodeFRCentralDirectory OBJECT-TYPE
        SYNTAX	INTEGER {
    		    yes(1),
    		    no(2)
    		}
        ACCESS	read-only
        STATUS	mandatory
        DESCRIPTION
                "Indicates whether the node is central directory."
        ::= { wfAppnNnTopologyFREntry 12 }

    wfAppnNnNodeFRIsr OBJECT-TYPE
        SYNTAX	INTEGER {
    		    yes(1),
    		    no(2)
    		}
        ACCESS	read-only
        STATUS	mandatory
        DESCRIPTION
                "Indicates whether the node supports intermediate session
                routing (ISR)."
        ::= { wfAppnNnTopologyFREntry 13 }

    wfAppnNnNodeFRChainSupport OBJECT-TYPE
        SYNTAX	INTEGER {
    		    yes(1),
    		    no(2)
    		}
        ACCESS	read-only
        STATUS	mandatory
        DESCRIPTION
                "Indicates whether this node supports chaining."
        ::= { wfAppnNnTopologyFREntry 14 }

    wfAppnNnNodeFRHprBase OBJECT-TYPE
        SYNTAX	INTEGER {
    		    yes(1),
    		    no(2)
    		}
        ACCESS	read-only
        STATUS	mandatory
        DESCRIPTION
                "Indicates whether this node supports HPR base functionality."
        ::= { wfAppnNnTopologyFREntry 15 }

    wfAppnNnNodeFRRtpTower OBJECT-TYPE
        SYNTAX	INTEGER {
    		    yes(1),
    		    no(2)
    		}
        ACCESS	read-only
        STATUS	mandatory
        DESCRIPTION
                "Indicates whether this node supports RTP tower functionality."
        ::= { wfAppnNnTopologyFREntry 16 }

 

    wfAppnNnTgTopologyFRTable OBJECT-TYPE
        SYNTAX	SEQUENCE OF WfAppnNnTgTopologyFREntry
        ACCESS	not-accessible
        STATUS	mandatory
        DESCRIPTION
                "This table contains entries which describes the TGs associated with
                the Network Nodes in the network"
        ::= { wfAppnNnTopology 4 }

    wfAppnNnTgTopologyFREntry OBJECT-TYPE
        SYNTAX	WfAppnNnTgTopologyFREntry
        ACCESS	not-accessible
        STATUS	mandatory
        DESCRIPTION
                "This table requires four indexes to provide a
                unique index.  The indexes are the FRSN, the owning or originating
                CPname, the destination CPname, and the TG number."
        INDEX	{ wfAppnNnTgFRFrsn,
    		  wfAppnNnTgFROwner,
    		  wfAppnNnTgFRDest,
    		  wfAppnNnTgFRNum }
        ::= { wfAppnNnTgTopologyFRTable 1 }

    WfAppnNnTgTopologyFREntry ::= SEQUENCE {
    	    wfAppnNnTgFROwner
    		DisplayString,
    	    wfAppnNnTgFRDest
    		DisplayString,
    	    wfAppnNnTgFRNum
    		INTEGER,
    	    wfAppnNnTgFRFrsn
    		INTEGER,
    	    wfAppnNnTgFREntryTimeLeft
    		INTEGER,
    	    wfAppnNnTgFRDestVirtual
    		INTEGER,
    	    wfAppnNnTgFRDlcData
    		OCTET STRING,
    	    wfAppnNnTgFRRsn
    		INTEGER,
    	    wfAppnNnTgFROperational
    		INTEGER,
    	    wfAppnNnTgFRQuiescing
    		INTEGER,
    	    wfAppnNnTgFRCpCpSession
    		INTEGER,
    	    wfAppnNnTgFREffCap
    		INTEGER,
    	    wfAppnNnTgFRConnCost
    		INTEGER,
    	    wfAppnNnTgFRByteCost
    		INTEGER,
    	    wfAppnNnTgFRSecurity
    		INTEGER,
    	    wfAppnNnTgFRDelay
    		INTEGER,
    	    wfAppnNnTgFRModemClass
    		INTEGER,
    	    wfAppnNnTgFRUsr1
    		INTEGER,
    	    wfAppnNnTgFRUsr2
    		INTEGER,
    	    wfAppnNnTgFRUsr3
    		INTEGER,
            wfAppnNnTgFRHprBase
    		INTEGER,
            wfAppnNnTgFRRtpTower
    		INTEGER
        }

    wfAppnNnTgFROwner OBJECT-TYPE
        SYNTAX	DisplayString
        ACCESS	read-only
        STATUS	mandatory
        DESCRIPTION
                "Administratively-assigned name for the
                originating node for this TG. The format
                is NETID.CPNAME and is the same name
                specified in the node table."
        ::= { wfAppnNnTgTopologyFREntry 1 }

    wfAppnNnTgFRDest OBJECT-TYPE
        SYNTAX	DisplayString
        ACCESS	read-only
        STATUS	mandatory
        DESCRIPTION
                "Administratively-assigned fully-qualified
                network name for the destination node for this TG."
        ::= { wfAppnNnTgTopologyFREntry 2 }

    wfAppnNnTgFRNum OBJECT-TYPE
        SYNTAX	INTEGER
        ACCESS	read-only
        STATUS	mandatory
        DESCRIPTION
                "Number associated with this
                transmission group. Range is 0-255."
        ::= { wfAppnNnTgTopologyFREntry 3 }

    wfAppnNnTgFRFrsn OBJECT-TYPE
        SYNTAX	INTEGER
        ACCESS	read-only
        STATUS	mandatory
        DESCRIPTION
                "Flow reduction sequence numbers (FRSNs) are associated
                with Topology Database Updates (TDUs) and are unique
                only within each APPN network node.  A TDU can be
                associated with multiple APPN resources.  This FRSN
                indicates the last time this resource was updated at
                this node."
        ::= { wfAppnNnTgTopologyFREntry 4 }

    wfAppnNnTgFREntryTimeLeft OBJECT-TYPE
        SYNTAX	INTEGER
        ACCESS	read-only
        STATUS	mandatory
        DESCRIPTION
                "Number of days before deletion of this
                network node TG entry. Range is 0-31."
        ::= { wfAppnNnTgTopologyFREntry 5 }

    wfAppnNnTgFRDestVirtual OBJECT-TYPE
        SYNTAX	INTEGER
        ACCESS	read-only
        STATUS	mandatory
        DESCRIPTION
                "Indicates whether the destination node is
                a virtual node."
        ::= { wfAppnNnTgTopologyFREntry 6 }

    wfAppnNnTgFRDlcData OBJECT-TYPE
        SYNTAX	OCTET STRING
        ACCESS	read-only
        STATUS	mandatory
        DESCRIPTION
                "DLC specific data related to the link connection
                network.
                Token-Ring    - MAC/SAP
                X.25 Switched - dial digits
                X.21 Switched - dial digits
                Circuit Swtch - dial digits."
        ::= { wfAppnNnTgTopologyFREntry 7 }

    wfAppnNnTgFRRsn OBJECT-TYPE
        SYNTAX	INTEGER
        ACCESS	read-only
        STATUS	mandatory
        DESCRIPTION
                "Current owning node's resource sequence number
                for this resource."
        ::= { wfAppnNnTgTopologyFREntry 8 }

    wfAppnNnTgFROperational OBJECT-TYPE
        SYNTAX	INTEGER
        ACCESS	read-only
        STATUS	mandatory
        DESCRIPTION
                "Indicates whether the transmission group
                is operational."
        ::= { wfAppnNnTgTopologyFREntry 9 }

    wfAppnNnTgFRQuiescing OBJECT-TYPE
        SYNTAX	INTEGER
        ACCESS	read-only
        STATUS	mandatory
        DESCRIPTION
                "Indicates whether the transmission group
                is quiescing."
        ::= { wfAppnNnTgTopologyFREntry 10 }

    wfAppnNnTgFRCpCpSession OBJECT-TYPE
        SYNTAX	INTEGER
        ACCESS	read-only
        STATUS	mandatory
        DESCRIPTION
                "Indicates whether CP-CP sessions are supported on this TG."
        ::= { wfAppnNnTgTopologyFREntry 11 }

    wfAppnNnTgFREffCap OBJECT-TYPE
        SYNTAX	INTEGER(0..255)
        ACCESS	read-only
        STATUS	mandatory
        DESCRIPTION
                "The effective capacity is an integer value that indicates
                the kilo bits per second.
                It is derived from the link bandwidth and maximum load
                factor with the range of 0 thru 255.
                This is an administratively assigned value for this TG.
                DEVIATION: 6611 mib uses range of 0 thru 603,979,776."
        ::= { wfAppnNnTgTopologyFREntry 12 }

    wfAppnNnTgFRConnCost OBJECT-TYPE
        SYNTAX	INTEGER
        ACCESS	read-only
        STATUS	mandatory
        DESCRIPTION
                "Cost per connect time: a value representing
                the relative cost per unit of time to use
                the TG. Range is from 0, which means no cost,
                to 255, which indicates maximum cost.
                This is an administratively assigned value associated
                with this TG."
        ::= { wfAppnNnTgTopologyFREntry 13 }

    wfAppnNnTgFRByteCost OBJECT-TYPE
        SYNTAX	INTEGER
        ACCESS	read-only
        STATUS	mandatory
        DESCRIPTION
                "Relative cost of transmitting a byte over this link.
                Range is from 0 (lowest cost) to 255.
                This is an administratively assigned value associated
                with this TG."
        ::= { wfAppnNnTgTopologyFREntry 14 }

    wfAppnNnTgFRSecurity OBJECT-TYPE
        SYNTAX	INTEGER(0..255)
        ACCESS	read-only
        STATUS	mandatory
        DESCRIPTION
                "The security is represented as an integer with a range of
                1 thru 255 with the most common values enumerated as
                defined above.
                This is an administratively assigned value associated
                with this TG."
        ::= { wfAppnNnTgTopologyFREntry 15 }

    wfAppnNnTgFRDelay OBJECT-TYPE
        SYNTAX  INTEGER {
                negligible(1),
                terrestrial(2),
                packet(3),
                long(4),
                maximum(5)                
                }
        ACCESS	read-write
        STATUS	mandatory
        DESCRIPTION
                "Relative amount of time that it takes for a signal to
                travel the length of the logical link.
                This is an administratively assigned value associated
                with this TG.
                DEVIATION: 6611 MIB, uses units of microseconds."
        DEFVAL  { negligible }
        ::= { wfAppnNnTgTopologyFREntry 16 }

    wfAppnNnTgFRModemClass OBJECT-TYPE
        SYNTAX	INTEGER
        ACCESS	read-only
        STATUS	mandatory
        DESCRIPTION
                "This is used to have multiple images for a
                connection network.  For a connection network
                           it is the same as in the TG vector; for
                           a non-connection network it is X'00'."
        ::= { wfAppnNnTgTopologyFREntry 17 }

    wfAppnNnTgFRUsr1 OBJECT-TYPE
        SYNTAX	INTEGER
        ACCESS	read-only
        STATUS	mandatory
        DESCRIPTION
                "First user-defined TG characteristic for this TG with
                a range of 0-255.
                This is an administratively assigned value associated
                with this TG."
        ::= { wfAppnNnTgTopologyFREntry 18 }

    wfAppnNnTgFRUsr2 OBJECT-TYPE
        SYNTAX	INTEGER
        ACCESS	read-only
        STATUS	mandatory
        DESCRIPTION
                "Second user-defined TG characteristic for this TG with
                a range of 0-255.
                This is an administratively assigned value associated
                with this TG."
        ::= { wfAppnNnTgTopologyFREntry 19 }

    wfAppnNnTgFRUsr3 OBJECT-TYPE
        SYNTAX	INTEGER
        ACCESS	read-only
        STATUS	mandatory
        DESCRIPTION
                "Third user-defined TG characteristic for this TG with
                a range of 0-255.
                This is an administratively assigned value associated
                with this TG."
        ::= { wfAppnNnTgTopologyFREntry 20 }

    wfAppnNnTgFRHprBase OBJECT-TYPE
        SYNTAX	INTEGER
        ACCESS	read-only
        STATUS	mandatory
        DESCRIPTION
                "Indicates whether HPR base functionality is supported 
                 on this TG." 
        ::= { wfAppnNnTgTopologyFREntry 21 }

    wfAppnNnTgFRRtpTower OBJECT-TYPE
        SYNTAX	INTEGER
        ACCESS	read-only
        STATUS	mandatory
        DESCRIPTION
                "Indicates whether RTP Tower functionality is supported 
                 on this TG." 
        ::= { wfAppnNnTgTopologyFREntry 22 }


    wfAppnLocalInfo	OBJECT IDENTIFIER ::= { wfAppnLocalThisNode 1 }

    wfAppnLocalNodeName OBJECT-TYPE
        SYNTAX	DisplayString
        ACCESS	read-only
        STATUS	mandatory
        DESCRIPTION
                "Administratively-assigned network name
                for this node in the format NETID.CPNAME."
        ::= { wfAppnLocalInfo 1 }

    wfAppnLocalNodeType OBJECT-TYPE
        SYNTAX	INTEGER {
    		    nn(1),
    		    en(2),
    		    len(4)
    		}
        ACCESS	read-only
        STATUS	mandatory
        DESCRIPTION
                "Type of APPN node."
        ::= { wfAppnLocalInfo 2 }

    wfAppnLocalNnRsn OBJECT-TYPE
        SYNTAX	INTEGER
        ACCESS	read-only
        STATUS	mandatory
        DESCRIPTION
                "Resource sequence number that is assigned and
                controlled by the network node that owns this
                resource. This is always an even 32-bit number
                unless an error has occurred."
        ::= { wfAppnLocalInfo 3 }

    wfAppnLocalNnRouteAddResist OBJECT-TYPE
        SYNTAX	INTEGER
        ACCESS	read-only
        STATUS	mandatory
        DESCRIPTION
                "Route addition resistance
                indicates the relative desirability
                of using this node for intermediate session traffic.
                The value, which can be any integer 0-255,
                is used in route computation.  The lower the value,
                the more desirable the node is for intermediate routing."
        ::= { wfAppnLocalInfo 4 }

    wfAppnLocalNnCongested OBJECT-TYPE
        SYNTAX	INTEGER {
    		    yes(1),
    		    no(2)
    		}
        ACCESS	read-only
        STATUS	mandatory
        DESCRIPTION
                "Indicates whether this node is congested.
                This node is not be included in route selection
                by other nodes when this congestion exists."
        ::= { wfAppnLocalInfo 5 }

    wfAppnLocalNnIsrDepleted OBJECT-TYPE
        SYNTAX	INTEGER {
    		    yes(1),
    		    no(2)
    		}
        ACCESS	read-only
        STATUS	mandatory
        DESCRIPTION
                "Indicates whether intermediate session
                routing resources are depleted.  This node is
                not included in intermediate route selection
                by other nodes when resources are depleted."
        ::= { wfAppnLocalInfo 6 }

    wfAppnLocalNnEndptDepleted OBJECT-TYPE
        SYNTAX	INTEGER {
    		    yes(1),
    		    no(2)
    		}
        ACCESS	read-only
        STATUS	mandatory
        DESCRIPTION
                "Indicates whether session endpoint resources are depleted."
        ::= { wfAppnLocalInfo 7 }

    wfAppnLocalNnQuiescing OBJECT-TYPE
        SYNTAX	INTEGER {
    		    yes(1),
    		    no(2)
    		}
        ACCESS	read-only
        STATUS	mandatory
        DESCRIPTION
                "Indicates whether the node is quiescing.
                This node is not included in route selection
                by other nodes when the node is quiescing."
        ::= { wfAppnLocalInfo 8 }

    wfAppnLocalNnGateway OBJECT-TYPE
        SYNTAX	INTEGER {
    		    yes(1),
    		    no(2)
    		}
        ACCESS	read-only
        STATUS	mandatory
        DESCRIPTION
                "Indicates whether the node provide gateway functions."
        ::= { wfAppnLocalInfo 9 }

    wfAppnLocalNnCentralDirectory OBJECT-TYPE
        SYNTAX	INTEGER {
    		    yes(1),
    		    no(2)
    		}
        ACCESS	read-only
        STATUS	mandatory
        DESCRIPTION
                "Indicates whether the node is central directory."
        ::= { wfAppnLocalInfo 10 }

    wfAppnLocalNnIsr OBJECT-TYPE
        SYNTAX	INTEGER {
    		    yes(1),
    		    no(2)
    		}
        ACCESS	read-only
        STATUS	mandatory
        DESCRIPTION
                "Indicates whether the node supports intermediate session
                routing (ISR)."
        ::= { wfAppnLocalInfo 11 }

    wfAppnLocalNnChainSupport OBJECT-TYPE
        SYNTAX	INTEGER {
    		    yes(1),
    		    no(2)
    		}
        ACCESS	read-only
        STATUS	mandatory
        DESCRIPTION
                "Indicates whether the node supports chaining."
        ::= { wfAppnLocalInfo 12 }

    wfAppnLocalNnFrsn OBJECT-TYPE
        SYNTAX	INTEGER
        ACCESS	read-only
        STATUS	mandatory
        DESCRIPTION
                "Flow reduction sequence numbers (FRSNs) are associated
                with Topology Database Updates (TDUs) and are unique
                only within each APPN network node.  A TDU can be
                associated with multiple APPN resources. This object
                is the last FRSN sent in a topology update to
                adjacent network nodes."
        ::= { wfAppnLocalInfo 13 }

    wfAppnLocalTgTable OBJECT-TYPE
        SYNTAX	SEQUENCE OF WfAppnLocalTgEntry
        ACCESS	not-accessible
        STATUS	mandatory
        DESCRIPTION
                "TG Table describes all of the TGs owned by this
                node.  The TG destination can be a virtual
                node, network node, len, or end node."
        ::= { wfAppnLocalThisNode 3 }

    wfAppnLocalTgEntry OBJECT-TYPE
        SYNTAX	WfAppnLocalTgEntry
        ACCESS	not-accessible
        STATUS	mandatory
        DESCRIPTION
                "This table is indexed by the destination CPname
                and the TG number."
        INDEX	{ wfAppnLocalTgDest,
    		  wfAppnLocalTgNum }
        ::= { wfAppnLocalTgTable 1 }

    WfAppnLocalTgEntry ::= SEQUENCE {
    	    wfAppnLocalTgDest
    		DisplayString,
    	    wfAppnLocalTgNum
    		INTEGER,
    	    wfAppnLocalTgDestVirtual
    		INTEGER,
    	    wfAppnLocalTgDlcData
    		OCTET STRING,
    	    wfAppnLocalTgRsn
    		INTEGER,
    	    wfAppnLocalTgOperational
    		INTEGER,
    	    wfAppnLocalTgQuiescing
    		INTEGER,
    	    wfAppnLocalTgCpCpSession
    		INTEGER,
    	    wfAppnLocalTgEffCap
    		INTEGER,
    	    wfAppnLocalTgConnCost
    		INTEGER,
    	    wfAppnLocalTgByteCost
    		INTEGER,
    	    wfAppnLocalTgSecurity
    		INTEGER,
    	    wfAppnLocalTgDelay
    		INTEGER,
    	    wfAppnLocalTgModemClass
    		INTEGER,
    	    wfAppnLocalTgUsr1
    		INTEGER,
    	    wfAppnLocalTgUsr2
    		INTEGER,
    	    wfAppnLocalTgUsr3
    		INTEGER
        }

    wfAppnLocalTgDest OBJECT-TYPE
        SYNTAX	DisplayString
        ACCESS	read-only
        STATUS	mandatory
        DESCRIPTION
                "Administratively-assigned fully-qualified
                network name for the destination node for this TG."
        ::= { wfAppnLocalTgEntry 1 }

    wfAppnLocalTgNum OBJECT-TYPE
        SYNTAX	INTEGER
        ACCESS	read-only
        STATUS	mandatory
        DESCRIPTION
                "Number associated with this
                transmission group. Range is 0-255."
        ::= { wfAppnLocalTgEntry 2 }

    wfAppnLocalTgDestVirtual OBJECT-TYPE
        SYNTAX	INTEGER
        ACCESS	read-only
        STATUS	mandatory
        DESCRIPTION
                "Indicates whether the destination node is
                a virtual node."
        ::= { wfAppnLocalTgEntry 3 }

    wfAppnLocalTgDlcData OBJECT-TYPE
        SYNTAX	OCTET STRING
        ACCESS	read-only
        STATUS	mandatory
        DESCRIPTION
                "DLC specific data related to the link connection
                network.
                Token-Ring    - MAC/SAP
                X.25 Switched - dial digits
                X.21 Switched - dial digits
                Circuit Swtch - dial digits."
        ::= { wfAppnLocalTgEntry 4 }

    wfAppnLocalTgRsn OBJECT-TYPE
        SYNTAX	INTEGER
        ACCESS	read-only
        STATUS	mandatory
        DESCRIPTION
                "Current owning node's resource sequence number
                for this resource."
        ::= { wfAppnLocalTgEntry 5 }

    wfAppnLocalTgOperational OBJECT-TYPE
        SYNTAX	INTEGER
        ACCESS	read-only
        STATUS	mandatory
        DESCRIPTION
                "Indicates whether the transmission group
                is operational."
        ::= { wfAppnLocalTgEntry 6 }

    wfAppnLocalTgQuiescing OBJECT-TYPE
        SYNTAX	INTEGER
        ACCESS	read-only
        STATUS	mandatory
        DESCRIPTION
                "Indicates whether the transmission group
                is quiescing."
        ::= { wfAppnLocalTgEntry 7 }

    wfAppnLocalTgCpCpSession OBJECT-TYPE
        SYNTAX	INTEGER
        ACCESS	read-only
        STATUS	mandatory
        DESCRIPTION
                "Indicates whether CP-CP sessions are supported on this TG."
        ::= { wfAppnLocalTgEntry 8 }

    wfAppnLocalTgEffCap OBJECT-TYPE
        SYNTAX	INTEGER(0..255)
        ACCESS	read-only
        STATUS	mandatory
        DESCRIPTION
                "The effective capacity is an integer value that indicates
                the kilo bits per second.
                It is derived from the link bandwidth and maximum load
                factor with the range of 0 thru 255.
                This is an administratively assigned value for this TG.
                DEVIATION: 6611 mib uses range of 0 thru 603,979,776."
        ::= { wfAppnLocalTgEntry 9 }

    wfAppnLocalTgConnCost OBJECT-TYPE
        SYNTAX	INTEGER
        ACCESS	read-only
        STATUS	mandatory
        DESCRIPTION
                "Cost per connect time: a value representing
                the relative cost per unit of time to use
                the TG. Range is from 0, which means no cost,
                to 255, which indicates maximum cost.
                This is an administratively assigned value associated
                with this TG."
        ::= { wfAppnLocalTgEntry 10 }

    wfAppnLocalTgByteCost OBJECT-TYPE
        SYNTAX	INTEGER
        ACCESS	read-only
        STATUS	mandatory
        DESCRIPTION
                "Relative cost of transmitting a byte over this link.
                Range is from 0 (lowest cost) to 255.
                This is an administratively assigned value associated
                with this TG."
        ::= { wfAppnLocalTgEntry 11 }

    wfAppnLocalTgSecurity OBJECT-TYPE
        SYNTAX	INTEGER(0..255)
        ACCESS	read-only
        STATUS	mandatory
        DESCRIPTION
                "The security is represented as an integer with a range of
                1 thru 255 with the most common values enumerated as
                defined above.
                This is an administratively assigned value associated
                with this TG."
        ::= { wfAppnLocalTgEntry 12 }

    wfAppnLocalTgDelay OBJECT-TYPE
        SYNTAX  INTEGER {
                negligible(1),
                terrestrial(2),
                packet(3),
                long(4),
                maximum(5)                
                }
        ACCESS	read-write
        STATUS	mandatory
        DESCRIPTION
                "Relative amount of time that it takes for a signal to
                travel the length of the logical link, with a range of
                0 through 255 with some of the more common values enumerated.
                This is an administratively assigned value associated
                with this TG.
                DEVIATION: 6611 MIB, uses units of microseconds."
        DEFVAL  { negligible }
        ::= { wfAppnLocalTgEntry 13 }

    wfAppnLocalTgModemClass OBJECT-TYPE
        SYNTAX	INTEGER
        ACCESS	read-only
        STATUS	mandatory
        DESCRIPTION
                "This is used to have multiple images for a
                connection network.  For a connection network
                           it is the same as in the TG vector; for
                           a non-connection network it is X'00'."
        ::= { wfAppnLocalTgEntry 14 }

    wfAppnLocalTgUsr1 OBJECT-TYPE
        SYNTAX	INTEGER
        ACCESS	read-only
        STATUS	mandatory
        DESCRIPTION
                "First user-defined TG characteristic for this TG with
                a range of 0-255.
                This is an administratively assigned value associated
                with this TG."
        ::= { wfAppnLocalTgEntry 15 }

    wfAppnLocalTgUsr2 OBJECT-TYPE
        SYNTAX	INTEGER
        ACCESS	read-only
        STATUS	mandatory
        DESCRIPTION
                "Second user-defined TG characteristic for this TG with
                a range of 0-255.
                This is an administratively assigned value associated
                with this TG."
        ::= { wfAppnLocalTgEntry 16 }

    wfAppnLocalTgUsr3 OBJECT-TYPE
        SYNTAX	INTEGER
        ACCESS	read-only
        STATUS	mandatory
        DESCRIPTION
                "Third user-defined TG characteristic for this TG with
                a range of 0-255.
                This is an administratively assigned value associated
                with this TG."
        ::= { wfAppnLocalTgEntry 17 }

    wfAppnDirectoryPerformance	OBJECT IDENTIFIER ::= { wfAppnDirectory 1 }

    wfAppnDirMaxCaches OBJECT-TYPE
        SYNTAX	INTEGER
        ACCESS	read-only
        STATUS	mandatory
        DESCRIPTION
                "Maximum number of cache entries allowed. This
                is an administratively assigned value."
        ::= { wfAppnDirectoryPerformance 1 }

    wfAppnDirCurCaches OBJECT-TYPE
        SYNTAX	Gauge
        ACCESS	read-only
        STATUS	mandatory
        DESCRIPTION
                "Current number of cache entries."
        ::= { wfAppnDirectoryPerformance 2 }

    wfAppnDirCurHomeEntries OBJECT-TYPE
        SYNTAX	Gauge
        ACCESS	read-only
        STATUS	mandatory
        DESCRIPTION
                "Current number of home entries."
        ::= { wfAppnDirectoryPerformance 3 }

    wfAppnDirRegEntries OBJECT-TYPE
        SYNTAX	Gauge
        ACCESS	read-only
        STATUS	mandatory
        DESCRIPTION
                "Current number of registered entries."
        ::= { wfAppnDirectoryPerformance 4 }

    wfAppnDirInLocates OBJECT-TYPE
        SYNTAX	Counter
        ACCESS	read-only
        STATUS	mandatory
        DESCRIPTION
                "Number of directed locates received."
        ::= { wfAppnDirectoryPerformance 5 }

    wfAppnDirInBcastLocates OBJECT-TYPE
        SYNTAX	Counter
        ACCESS	read-only
        STATUS	mandatory
        DESCRIPTION
                "Number of broadcast locates received."
        ::= { wfAppnDirectoryPerformance 6 }

    wfAppnDirOutLocates OBJECT-TYPE
        SYNTAX	Counter
        ACCESS	read-only
        STATUS	mandatory
        DESCRIPTION
                "Number of directed locates sent."
        ::= { wfAppnDirectoryPerformance 7 }

    wfAppnDirOutBcastLocates OBJECT-TYPE
        SYNTAX	Counter
        ACCESS	read-only
        STATUS	mandatory
        DESCRIPTION
                "Number of broadcast locates sent."
        ::= { wfAppnDirectoryPerformance 8 }

    wfAppnDirNotFoundLocates OBJECT-TYPE
        SYNTAX	Counter
        ACCESS	read-only
        STATUS	mandatory
        DESCRIPTION
                "Number of directed locates returned with a 'not found'."
        ::= { wfAppnDirectoryPerformance 9 }

    wfAppnDirNotFoundBcastLocates OBJECT-TYPE
        SYNTAX	Counter
        ACCESS	read-only
        STATUS	mandatory
        DESCRIPTION
                "Number of broadcast locates returned with
                a not found."
        ::= { wfAppnDirectoryPerformance 10 }

    wfAppnDirLocateOutstands OBJECT-TYPE
        SYNTAX	Gauge
        ACCESS	read-only
        STATUS	mandatory
        DESCRIPTION
                "Current number of outstanding locates,
                both directed and broadcast.  This value
                varies. A value of zero indicates
                that no locates are unanswered."
        ::= { wfAppnDirectoryPerformance 11 }

    wfAppnDirTable OBJECT-TYPE
        SYNTAX	SEQUENCE OF WfAppnDirEntry
        ACCESS	not-accessible
        STATUS	mandatory
        DESCRIPTION
                "Table containing information about
                all known LUs and TPs."
        ::= { wfAppnDirectory 2 }

    wfAppnDirEntry OBJECT-TYPE
        SYNTAX	WfAppnDirEntry
        ACCESS	not-accessible
        STATUS	mandatory
        DESCRIPTION
                "This table is indexed by the LU name."
        INDEX	{ wfAppnDirLuName }
        ::= { wfAppnDirTable 1 }

    WfAppnDirEntry ::= SEQUENCE {
    	    wfAppnDirLuName
    		DisplayString,
    	    wfAppnDirServerName
    		DisplayString,
    	    wfAppnDirLuOwnerName
    		DisplayString,
    	    wfAppnDirLocation
    		INTEGER,
    	    wfAppnDirType
    		INTEGER,
    	    wfAppnDirWildCard
    		INTEGER
        }

    wfAppnDirLuName OBJECT-TYPE
        SYNTAX	DisplayString
        ACCESS	read-only
        STATUS	mandatory
        DESCRIPTION
                "Fully-qualified network LU name in the
                domain of the serving network node."
        ::= { wfAppnDirEntry 1 }

    wfAppnDirServerName OBJECT-TYPE
        SYNTAX	DisplayString
        ACCESS	read-only
        STATUS	mandatory
        DESCRIPTION
                "Fully-qualified control point (CP) name of the
                network node server.  For unassociated end node
                entries, the end node fully-qualified name
                is returned."
        ::= { wfAppnDirEntry 2 }

    wfAppnDirLuOwnerName OBJECT-TYPE
        SYNTAX	DisplayString
        ACCESS	read-only
        STATUS	mandatory
        DESCRIPTION
                "Fully-qualified CP name of the node at which
                the LU is located.  This name is the same as the
                serving NN name when the LU is located at a
                network node or an unassociated end node.  It is
                also the same as the fully-qualified LU name
                when this is the control point LU for this node."
        ::= { wfAppnDirEntry 3 }

    wfAppnDirLocation OBJECT-TYPE
        SYNTAX	INTEGER {
    		    local(1),
    		    domain(2),
    		    xdomain(3)
    		}
        ACCESS	read-only
        STATUS	mandatory
        DESCRIPTION
                "Specifies the location of the LU."
        ::= { wfAppnDirEntry 4 }

    wfAppnDirType OBJECT-TYPE
        SYNTAX	INTEGER {
    		    home(1),
    		    cache(2),
    		    registered(3)
    		}
        ACCESS	read-only
        STATUS	mandatory
        DESCRIPTION
                "Directory types are:
                1 - Home
                      The LU is in the domain of the local network node
                      and the LU information has been configured at the
                      local node.

                2 - Cache
                      The LU has previously been located by a broadcast
                      search and the location information has been saved.

                3 - Register
                      The LU is at an end node that is in the domain
                      of the local network node.  Registered entries
                      are registered by the served end node."
        ::= { wfAppnDirEntry 5 }

    wfAppnDirWildCard OBJECT-TYPE
        SYNTAX	INTEGER {
    		    other(1),
    		    entry(2),
    		    partial(3),
    		    full(4)
    		}
        ACCESS	read-only
        STATUS	mandatory
        DESCRIPTION
                "1 - Other means unknown type of LU entry.
                2 - Expliced-entry means the full LUNAME will be used
                    for locating this LU.
                3 - Partial-wildcard means only the non-blank portions
                    of the LUNAME will be used for locating this LU.
                4 - Full-wildcard means all LUNAMES will be directed
                    to this LU."
        ::= { wfAppnDirEntry 6 }

    wfAppnDirDefineTable OBJECT-TYPE
        SYNTAX	SEQUENCE OF WfAppnDirDefineEntry
        ACCESS	not-accessible
        STATUS	mandatory
        DESCRIPTION
                "this table contains entries which define Directory entries"
        ::= { wfAppnDirectory 3 }

    wfAppnDirDefineEntry OBJECT-TYPE
        SYNTAX	WfAppnDirDefineEntry
        ACCESS	not-accessible
        STATUS	mandatory
        DESCRIPTION
                "An entry in wfAppnDirDefineTable."
        INDEX	{ wfAppnDirDefineResourceName }
        ::= { wfAppnDirDefineTable 1 }

    WfAppnDirDefineEntry ::= SEQUENCE {
    	    wfAppnDirDefineDelete
    		INTEGER,
    	    wfAppnDirDefineDisable
    		INTEGER,
    	    wfAppnDirDefineResourceName
    		DisplayString,
    	    wfAppnDirDefineResourceType
    		INTEGER,
    	    wfAppnDirDefineParentName
    		DisplayString,
    	    wfAppnDirDefineParentType
    		INTEGER
        }

    wfAppnDirDefineDelete OBJECT-TYPE
        SYNTAX	INTEGER {
    		    created(1),
    		    deleted(2)
    		}
        ACCESS	read-write
        STATUS	mandatory
        DESCRIPTION
                "Create/Delete parameter. Default is created.
                Users perform an SNMP SET operation on this
                object in order to create/delete a Directory
                Entry instance."
        DEFVAL	{ created }
        ::= { wfAppnDirDefineEntry 1 }

    wfAppnDirDefineDisable OBJECT-TYPE
        SYNTAX	INTEGER {
    		    enable(1),
    		    disable(2)
    		}
        ACCESS	read-write
        STATUS	mandatory
        DESCRIPTION
                "Enable/Disable parameter. Default is enabled.
                Users perform an SNMP SET operation on this
                object in order to enable/disable this Directory Entry."
        DEFVAL	{ enable }
        ::= { wfAppnDirDefineEntry 2 }

    wfAppnDirDefineResourceName OBJECT-TYPE
        SYNTAX	DisplayString
        ACCESS	read-only
        STATUS	mandatory
        DESCRIPTION
                "This specifies the resource name in the local Directory"
        ::= { wfAppnDirDefineEntry 3 }

    wfAppnDirDefineResourceType OBJECT-TYPE
        SYNTAX	INTEGER {
    		    lu(1),
    		    encp(2),
    		    nncp(3),
    		    wildcard(4)
    		}
        ACCESS	read-write
        STATUS	mandatory
        DESCRIPTION
                "This specifies the resource type in the local Directory"
        DEFVAL	{ lu }
        ::= { wfAppnDirDefineEntry 4 }

    wfAppnDirDefineParentName OBJECT-TYPE
        SYNTAX	DisplayString
        ACCESS	read-write
        STATUS	mandatory
        DESCRIPTION
                "This specifies the name of the parent of the resource, if the resource
                is an LU"
        ::= { wfAppnDirDefineEntry 5 }

    wfAppnDirDefineParentType OBJECT-TYPE
        SYNTAX	INTEGER {
    		    encp(2),
    		    nncp(3)
    		}
        ACCESS	read-write
        STATUS	mandatory
        DESCRIPTION
                "This specifies the type of the parent of the resource, if the resource
                is an LU"
        DEFVAL	{ nncp }
        ::= { wfAppnDirDefineEntry 6 }

    wfAppnCosModeTable OBJECT-TYPE
        SYNTAX	SEQUENCE OF WfAppnCosModeEntry
        ACCESS	not-accessible
        STATUS	mandatory
        DESCRIPTION
                "Table representing all of the defined
                mode names for this node.  The table
                contains the matching COS name."
        ::= { wfAppnCos 1 }

    wfAppnCosModeEntry OBJECT-TYPE
        SYNTAX	WfAppnCosModeEntry
        ACCESS	not-accessible
        STATUS	mandatory
        DESCRIPTION
                "This table is indexed by the Mode Name."
        INDEX	{ wfAppnCosModeName }
        ::= { wfAppnCosModeTable 1 }

    WfAppnCosModeEntry ::= SEQUENCE {
    	    wfAppnCosModeName
    		DisplayString,
    	    wfAppnCosModeCosName
    		DisplayString
        }

    wfAppnCosModeName OBJECT-TYPE
        SYNTAX	DisplayString
        ACCESS	read-only
        STATUS	mandatory
        DESCRIPTION
                "Administratively-assigned name for this
                mode entry."
        ::= { wfAppnCosModeEntry 1 }

    wfAppnCosModeCosName OBJECT-TYPE
        SYNTAX	DisplayString
        ACCESS	read-only
        STATUS	mandatory
        DESCRIPTION
                "An administratively assigned name for this
                Class of Service."
        ::= { wfAppnCosModeEntry 2 }

    wfAppnCosNameTable OBJECT-TYPE
        SYNTAX	SEQUENCE OF WfAppnCosNameEntry
        ACCESS	not-accessible
        STATUS	mandatory
        DESCRIPTION
                "Table representing all of the defined class-of-service
                names for this node.  The COS node and TG tables are
                accessed using the same index, which is the COS name."
        ::= { wfAppnCos 2 }

    wfAppnCosNameEntry OBJECT-TYPE
        SYNTAX	WfAppnCosNameEntry
        ACCESS	not-accessible
        STATUS	mandatory
        DESCRIPTION
                "The COS name is the index to this table."
        INDEX	{ wfAppnCosName }
        ::= { wfAppnCosNameTable 1 }

    WfAppnCosNameEntry ::= SEQUENCE {
    	    wfAppnCosName
    		DisplayString,
    	    wfAppnCosTransPriority
    		INTEGER
        }

    wfAppnCosName OBJECT-TYPE
        SYNTAX	DisplayString
        ACCESS	read-only
        STATUS	mandatory
        DESCRIPTION
                "Administratively-assigned name for this
                class of service."
        ::= { wfAppnCosNameEntry 1 }

    wfAppnCosTransPriority OBJECT-TYPE
        SYNTAX	INTEGER {
    		    low(1),
    		    medium(2),
    		    high(3),
    		    network(4)
    		}
        ACCESS	read-only
        STATUS	mandatory
        DESCRIPTION
                "Transmission priority for this
                class of service.  Values are:
                  Low
                  Medium
                  High
                  Network"
        DEFVAL	{ low }
        ::= { wfAppnCosNameEntry 2 }

    wfAppnCosNodeRowTable OBJECT-TYPE
        SYNTAX	SEQUENCE OF WfAppnCosNodeRowEntry
        ACCESS	not-accessible
        STATUS	mandatory
        DESCRIPTION
                "This table contains all node-row information for all
                class of service in this node."
        ::= { wfAppnCos 3 }

    wfAppnCosNodeRowEntry OBJECT-TYPE
        SYNTAX	WfAppnCosNodeRowEntry
        ACCESS	not-accessible
        STATUS	mandatory
        DESCRIPTION
                "The COS name is the first index and a integer
                is the second index to insure a unique index."
        INDEX	{ wfAppnCosNodeRowName,
    		  wfAppnCosNodeRowIndex }
        ::= { wfAppnCosNodeRowTable 1 }

    WfAppnCosNodeRowEntry ::= SEQUENCE {
    	    wfAppnCosNodeRowName
    		DisplayString,
    	    wfAppnCosNodeRowIndex
    		INTEGER,
    	    wfAppnCosNodeRowWgt
    		INTEGER,
    	    wfAppnCosNodeRowResistMin
    		INTEGER,
    	    wfAppnCosNodeRowResistMax
    		INTEGER,
    	    wfAppnCosNodeRowMinCongestAllow
    		INTEGER,
    	    wfAppnCosNodeRowMaxCongestAllow
    		INTEGER
        }

    wfAppnCosNodeRowName OBJECT-TYPE
        SYNTAX	DisplayString
        ACCESS	read-only
        STATUS	mandatory
        DESCRIPTION
                "Administratively-assigned name for this
                class of service."
        ::= { wfAppnCosNodeRowEntry 1 }

    wfAppnCosNodeRowIndex OBJECT-TYPE
        SYNTAX	INTEGER
        ACCESS	read-only
        STATUS	mandatory
        DESCRIPTION
                "Index of COS name. This same value is used
                to access the node and TG COS tables.
                Range of values is 0-255."
        ::= { wfAppnCosNodeRowEntry 2 }

    wfAppnCosNodeRowWgt OBJECT-TYPE
        SYNTAX	INTEGER
        ACCESS	read-only
        STATUS	mandatory
        DESCRIPTION
                "Weight to be associated with the nodes
                that fit the criteria specified by this node row."
        ::= { wfAppnCosNodeRowEntry 3 }

    wfAppnCosNodeRowResistMin OBJECT-TYPE
        SYNTAX	INTEGER
        ACCESS	read-only
        STATUS	mandatory
        DESCRIPTION
                "Minimum route addition resistance value
                for this node. Range of values is 0-255.
                The lower the value, the more desirable
                the node is for intermediate routing."
        ::= { wfAppnCosNodeRowEntry 4 }

    wfAppnCosNodeRowResistMax OBJECT-TYPE
        SYNTAX	INTEGER
        ACCESS	read-only
        STATUS	mandatory
        DESCRIPTION
                "Maximum route addition resistance value
                for this node. Range of values is 0-255.
                The lower the value, the more desirable
                the node is for intermediate routing."
        ::= { wfAppnCosNodeRowEntry 5 }

    wfAppnCosNodeRowMinCongestAllow OBJECT-TYPE
        SYNTAX	INTEGER {
    		    yes(1),
    		    no(2)
    		}
        ACCESS	read-only
        STATUS	mandatory
        DESCRIPTION
                "Indicates whether low congestion will be
                tolerated.  The minimum and maximum parameters
                will allow specifying either low-congested,
                high-congested, or either to be used."
        DEFVAL	{ yes }
        ::= { wfAppnCosNodeRowEntry 6 }

    wfAppnCosNodeRowMaxCongestAllow OBJECT-TYPE
        SYNTAX	INTEGER {
    		    yes(1),
    		    no(2)
    		}
        ACCESS	read-only
        STATUS	mandatory
        DESCRIPTION
                "Indicates whether high congestion will be
                tolerated.  The minimum and maximum parameters
                will allow specifying either low-congested,
                high-congested, or either to be used."
        DEFVAL	{ yes }
        ::= { wfAppnCosNodeRowEntry 7 }

    wfAppnCosTgRowTable OBJECT-TYPE
        SYNTAX	SEQUENCE OF WfAppnCosTgRowEntry
        ACCESS	not-accessible
        STATUS	mandatory
        DESCRIPTION
                "Table containing all the Tg-row information for all
                class of service defined in this node."
        ::= { wfAppnCos 4 }

    wfAppnCosTgRowEntry OBJECT-TYPE
        SYNTAX	WfAppnCosTgRowEntry
        ACCESS	not-accessible
        STATUS	mandatory
        DESCRIPTION
                "The TgRowName and the TgRowIndex are the index
                for this table."
        INDEX	{ wfAppnCosTgRowName,
    		  wfAppnCosTgRowIndex }
        ::= { wfAppnCosTgRowTable 1 }

    WfAppnCosTgRowEntry ::= SEQUENCE {
    	    wfAppnCosTgRowName
    		DisplayString,
    	    wfAppnCosTgRowIndex
    		INTEGER,
    	    wfAppnCosTgRowWgt
    		INTEGER,
    	    wfAppnCosTgRowEffCapMin
    		INTEGER,
    	    wfAppnCosTgRowEffCapMax
    		INTEGER,
    	    wfAppnCosTgRowConnCostMin
    		INTEGER,
    	    wfAppnCosTgRowConnCostMax
    		INTEGER,
    	    wfAppnCosTgRowByteCostMin
    		INTEGER,
    	    wfAppnCosTgRowByteCostMax
    		INTEGER,
    	    wfAppnCosTgRowSecurityMin
    		INTEGER,
    	    wfAppnCosTgRowSecurityMax
    		INTEGER,
    	    wfAppnCosTgRowDelayMin
    		INTEGER,
    	    wfAppnCosTgRowDelayMax
    		INTEGER,
    	    wfAppnCosTgRowUsr1Min
    		INTEGER,
    	    wfAppnCosTgRowUsr1Max
    		INTEGER,
    	    wfAppnCosTgRowUsr2Min
    		INTEGER,
    	    wfAppnCosTgRowUsr2Max
    		INTEGER,
    	    wfAppnCosTgRowUsr3Min
    		INTEGER,
    	    wfAppnCosTgRowUsr3Max
    		INTEGER
        }

    wfAppnCosTgRowName OBJECT-TYPE
        SYNTAX	DisplayString
        ACCESS	read-only
        STATUS	mandatory
        DESCRIPTION
                "Administratively-assigned name for this
                class of service."
        ::= { wfAppnCosTgRowEntry 1 }

    wfAppnCosTgRowIndex OBJECT-TYPE
        SYNTAX	INTEGER
        ACCESS	read-only
        STATUS	mandatory
        DESCRIPTION
                "Index of COS name. This same value is used
                to access the node and TG COS tables."
        ::= { wfAppnCosTgRowEntry 2 }

    wfAppnCosTgRowWgt OBJECT-TYPE
        SYNTAX	INTEGER
        ACCESS	read-only
        STATUS	mandatory
        DESCRIPTION
                "Weight to be associated with the nodes
                that fit the criteria specified by this tg-row."
        ::= { wfAppnCosTgRowEntry 3 }

    wfAppnCosTgRowEffCapMin OBJECT-TYPE
        SYNTAX	INTEGER(0..255)
        ACCESS	read-only
        STATUS	mandatory
        DESCRIPTION
                "Minimum acceptable speed for this Class of Service.
                The effective capacity is an integer value that indicates
                the actual kilo bits per second.
                It is derived from the link bandwidth and maximum load
                factor with the range of 0 thru 255
                DEVIATION: 6611 mib uses range of 0 thru 603,979,776."
        DEFVAL	{ 133 }
        ::= { wfAppnCosTgRowEntry 4 }

    wfAppnCosTgRowEffCapMax OBJECT-TYPE
        SYNTAX	INTEGER(0..255)
        ACCESS	read-only
        STATUS	mandatory
        DESCRIPTION
                "Maximum acceptable speed for this Class of Service.
                The effective capacity is an integer value that indicates
                the actual kilo bits per second.
                It is derived from the link bandwidth and maximum load
                factor with the range of 0 thru 255.
                DEVIATION: 6611 mib uses range of 0 thru 603,979,776."
        DEFVAL	{ 133 }
        ::= { wfAppnCosTgRowEntry 5 }

    wfAppnCosTgRowConnCostMin OBJECT-TYPE
        SYNTAX	INTEGER
        ACCESS	read-only
        STATUS	mandatory
        DESCRIPTION
                "Minimum acceptable cost per connect time
                for this Class of Service.
                Cost per connect time: a value representing
                the relative cost per unit of time to use
                the TG. Range is from 0, which means no cost,
                to 255."
        ::= { wfAppnCosTgRowEntry 6 }

    wfAppnCosTgRowConnCostMax OBJECT-TYPE
        SYNTAX	INTEGER
        ACCESS	read-only
        STATUS	mandatory
        DESCRIPTION
                "Maximum acceptable cost per connect time
                for this Class of Service.
                Cost per connect time: a value representing
                the relative cost per unit of time to use
                the TG. Range is from 0, which means no cost,
                to 255."
        ::= { wfAppnCosTgRowEntry 7 }

    wfAppnCosTgRowByteCostMin OBJECT-TYPE
        SYNTAX	INTEGER
        ACCESS	read-only
        STATUS	mandatory
        DESCRIPTION
                "Minimum acceptable cost per byte
                for this Class of Service."
        ::= { wfAppnCosTgRowEntry 8 }

    wfAppnCosTgRowByteCostMax OBJECT-TYPE
        SYNTAX	INTEGER
        ACCESS	read-only
        STATUS	mandatory
        DESCRIPTION
                "Maximum acceptable cost per byte
                for this Class of Service."
        ::= { wfAppnCosTgRowEntry 9 }

    wfAppnCosTgRowSecurityMin OBJECT-TYPE
        SYNTAX	INTEGER(0..255)
        ACCESS	read-only
        STATUS	mandatory
        DESCRIPTION
                "Minimum acceptable security
                for this Class of Service."
        ::= { wfAppnCosTgRowEntry 10 }

    wfAppnCosTgRowSecurityMax OBJECT-TYPE
        SYNTAX	INTEGER(0..255)
        ACCESS	read-only
        STATUS	mandatory
        DESCRIPTION
                "Maximum acceptable security
                for this Class of Service."
        ::= { wfAppnCosTgRowEntry 11 }

    wfAppnCosTgRowDelayMin OBJECT-TYPE
        SYNTAX  INTEGER {
                negligible(1),
                terrestrial(2),
                packet(3),
                long(4),
                maximum(5)                
                }
        ACCESS	read-write
        STATUS	mandatory
        DESCRIPTION
                "Minimum acceptable propagation delay for this class of service.
                Relative amount of time that it takes for a signal to travel
                the length of the logical link. 
                DEVIATION: 6611 MIB, uses units of microseconds."
        DEFVAL  { negligible }
        ::= { wfAppnCosTgRowEntry 12 }

    wfAppnCosTgRowDelayMax OBJECT-TYPE
        SYNTAX  INTEGER {
                negligible(1),
                terrestrial(2),
                packet(3),
                long(4),
                maximum(5)                
                }
        ACCESS	read-write
        STATUS	mandatory
        DESCRIPTION
                "Maximum acceptable propagation delay for this class of service.
                Relative amount of time that it takes for a signal to travel
                the length of the logical link.
                DEVIATION: 6611 MIB, uses units of microseconds."
        DEFVAL  { negligible }
        ::= { wfAppnCosTgRowEntry 13 }

    wfAppnCosTgRowUsr1Min OBJECT-TYPE
        SYNTAX	INTEGER
        ACCESS	read-only
        STATUS	mandatory
        DESCRIPTION
                "Minimum acceptable value for this
                user defined characteristic.
                Range of values is 0-255."
        ::= { wfAppnCosTgRowEntry 14 }

    wfAppnCosTgRowUsr1Max OBJECT-TYPE
        SYNTAX	INTEGER
        ACCESS	read-only
        STATUS	mandatory
        DESCRIPTION
                "Maximum acceptable value for this
                user defined characteristic.
                Range of values is 0-255."
        ::= { wfAppnCosTgRowEntry 15 }

    wfAppnCosTgRowUsr2Min OBJECT-TYPE
        SYNTAX	INTEGER
        ACCESS	read-only
        STATUS	mandatory
        DESCRIPTION
                "Minimum acceptable value for this
                user defined characteristic.
                Range of values is 0-255."
        ::= { wfAppnCosTgRowEntry 16 }

    wfAppnCosTgRowUsr2Max OBJECT-TYPE
        SYNTAX	INTEGER
        ACCESS	read-only
        STATUS	mandatory
        DESCRIPTION
                "Maximum acceptable value for this
                user defined characteristic.
                Range of values is 0-255."
        ::= { wfAppnCosTgRowEntry 17 }

    wfAppnCosTgRowUsr3Min OBJECT-TYPE
        SYNTAX	INTEGER
        ACCESS	read-only
        STATUS	mandatory
        DESCRIPTION
                "Minimum acceptable value for this
                user defined characteristic.
                Range of values is 0-255."
        ::= { wfAppnCosTgRowEntry 18 }

    wfAppnCosTgRowUsr3Max OBJECT-TYPE
        SYNTAX	INTEGER
        ACCESS	read-only
        STATUS	mandatory
        DESCRIPTION
                "Maximum acceptable value for this
                user defined characteristic.
                Range of values is 0-255."
        ::= { wfAppnCosTgRowEntry 19 }

    wfAppnTpPingTable OBJECT-TYPE
        SYNTAX	SEQUENCE OF WfAppnTpPingEntry
        ACCESS	not-accessible
        STATUS	mandatory
        DESCRIPTION
                "This table contains an entry for each instance of the APING application"
        ::= { wfAppnTps 1 }

    wfAppnTpPingEntry OBJECT-TYPE
        SYNTAX	WfAppnTpPingEntry
        ACCESS	not-accessible
        STATUS	mandatory
        DESCRIPTION
                "An entry in wfAppnTpPingTable."
        INDEX	{ wfAppnTpPingIndex }
        ::= { wfAppnTpPingTable 1 }

    WfAppnTpPingEntry ::= SEQUENCE {
    	    wfAppnTpPingDelete
    		INTEGER,
    	    wfAppnTpPingDisable
    		INTEGER,
    	    wfAppnTpPingIndex
    		INTEGER,
    	    wfAppnTpPingFqPluName
    		DisplayString,
    	    wfAppnTpPingDataLength
    		INTEGER,
    	    wfAppnTpPingConsecutiveSends
    		INTEGER,
    	    wfAppnTpPingEchoDisable
    		INTEGER,
    	    wfAppnTpPingIterations
    		INTEGER,
    	    wfAppnTpPingPartnerTpName
    		DisplayString,
    	    wfAppnTpPingMode
    		DisplayString,
    	    wfAppnTpPingState
    		INTEGER,
    	    wfAppnTpPingAllocTime
    		INTEGER,
    	    wfAppnTpPingMinTime
    		INTEGER,
    	    wfAppnTpPingMaxTime
    		INTEGER,
    	    wfAppnTpPingAvgTime
    		INTEGER,
    	    wfAppnTpPingPartnerVersion
    		DisplayString
        }

    wfAppnTpPingDelete OBJECT-TYPE
        SYNTAX	INTEGER {
    		    created(1),
    		    deleted(2)
    		}
        ACCESS	read-write
        STATUS	mandatory
        DESCRIPTION
                "Create/Delete parameter. Default is created.
                Users perform an SNMP SET operation on this
                object in order to create/delete a APING instance."
        DEFVAL	{ created }
        ::= { wfAppnTpPingEntry 1 }

    wfAppnTpPingDisable OBJECT-TYPE
        SYNTAX	INTEGER {
    		    enable(1),
    		    disable(2)
    		}
        ACCESS	read-write
        STATUS	mandatory
        DESCRIPTION
                "Enable/Disable parameter. Default is enabled.
                Users perform an SNMP SET operation on this
                object in order to enable/disable this APING instance."
        DEFVAL	{ enable }
        ::= { wfAppnTpPingEntry 2 }

    wfAppnTpPingIndex OBJECT-TYPE
        SYNTAX	INTEGER
        ACCESS	read-only
        STATUS	mandatory
        DESCRIPTION
                "This is the index of the Ping entry"
        ::= { wfAppnTpPingEntry 3 }

    wfAppnTpPingFqPluName OBJECT-TYPE
        SYNTAX	DisplayString
        ACCESS	read-write
        STATUS	mandatory
        DESCRIPTION
                "This is the Fully-Qualified name of the Partner LU running the APINGD TP"
        ::= { wfAppnTpPingEntry 4 }

    wfAppnTpPingDataLength OBJECT-TYPE
        SYNTAX	INTEGER
        ACCESS	read-write
        STATUS	mandatory
        DESCRIPTION
                "This is the length of the test data to be sent to the LU being PING-ed"
        DEFVAL	{ 100 }
        ::= { wfAppnTpPingEntry 5 }

    wfAppnTpPingConsecutiveSends OBJECT-TYPE
        SYNTAX	INTEGER
        ACCESS	read-write
        STATUS	mandatory
        DESCRIPTION
                "This specifies the number of consecutive sends that will be issued"
        DEFVAL	{ 1 }
        ::= { wfAppnTpPingEntry 6 }

    wfAppnTpPingEchoDisable OBJECT-TYPE
        SYNTAX	INTEGER {
    		    enable(1),
    		    disable(2)
    		}
        ACCESS	read-write
        STATUS	mandatory
        DESCRIPTION
                "This specifies whether the Target of the PING will be requested
                to echo the data"
        DEFVAL	{ enable }
        ::= { wfAppnTpPingEntry 7 }

    wfAppnTpPingIterations OBJECT-TYPE
        SYNTAX	INTEGER
        ACCESS	read-write
        STATUS	mandatory
        DESCRIPTION
                "This specifies the number of times the PING should be repeated"
        DEFVAL	{ 2 }
        ::= { wfAppnTpPingEntry 8 }

    wfAppnTpPingPartnerTpName OBJECT-TYPE
        SYNTAX	DisplayString
        ACCESS	read-write
        STATUS	mandatory
        DESCRIPTION
                "This specifies the partner TP name to ping. If no name is specified
                'APINGD' will be used"
        ::= { wfAppnTpPingEntry 9 }

    wfAppnTpPingMode OBJECT-TYPE
        SYNTAX	DisplayString
        ACCESS	read-write
        STATUS	mandatory
        DESCRIPTION
                "This specifies the mode to be used for this PING"
        ::= { wfAppnTpPingEntry 10 }

    wfAppnTpPingState OBJECT-TYPE
        SYNTAX	INTEGER {
    		    init(1),
    		    started(2),
    		    ok(3),
    		    failed(4)
    		}
        ACCESS	read-only
        STATUS	mandatory
        DESCRIPTION
                "This indicates the current state of the PING request"
        ::= { wfAppnTpPingEntry 11 }

    wfAppnTpPingAllocTime OBJECT-TYPE
        SYNTAX	INTEGER
        ACCESS	read-only
        STATUS	mandatory
        DESCRIPTION
                "This indicates the time (in milliseconds) it took to allocate the
                PING conversation"
        ::= { wfAppnTpPingEntry 12 }

    wfAppnTpPingMinTime OBJECT-TYPE
        SYNTAX	INTEGER
        ACCESS	read-only
        STATUS	mandatory
        DESCRIPTION
                "This indicates the minimum time (in milliseconds) it took to
                PING the partner"
        ::= { wfAppnTpPingEntry 13 }

    wfAppnTpPingMaxTime OBJECT-TYPE
        SYNTAX	INTEGER
        ACCESS	read-only
        STATUS	mandatory
        DESCRIPTION
                "This indicates the maximum time (in milliseconds) it took to
                PING the partner"
        ::= { wfAppnTpPingEntry 14 }

    wfAppnTpPingAvgTime OBJECT-TYPE
        SYNTAX	INTEGER
        ACCESS	read-only
        STATUS	mandatory
        DESCRIPTION
                "This indicates the average time (in milliseconds) it took to
                PING the partner"
        ::= { wfAppnTpPingEntry 15 }

    wfAppnTpPingPartnerVersion OBJECT-TYPE
        SYNTAX	DisplayString
        ACCESS	read-only
        STATUS	mandatory
        DESCRIPTION
                "This is the version string returned by the partner"
        ::= { wfAppnTpPingEntry 16 }

    wfAppnTpTunnelTable OBJECT-TYPE
        SYNTAX	SEQUENCE OF WfAppnTpTunnelEntry
        ACCESS	not-accessible
        STATUS	mandatory
        DESCRIPTION
                "This table contains entries for each APPN Tunnel"
        ::= { wfAppnTps 3 }

    wfAppnTpTunnelEntry OBJECT-TYPE
        SYNTAX	WfAppnTpTunnelEntry
        ACCESS	not-accessible
        STATUS	mandatory
        DESCRIPTION
                "An entry in wfAppnTpTunnelTable."
        INDEX	{ wfAppnTpTunnelCct }
        ::= { wfAppnTpTunnelTable 1 }

    WfAppnTpTunnelEntry ::= SEQUENCE {
    	    wfAppnTpTunnelDelete
    		INTEGER,
    	    wfAppnTpTunnelDisable
    		INTEGER,
    	    wfAppnTpTunnelState
    		INTEGER,
    	    wfAppnTpTunnelCct
    		INTEGER,
    	    wfAppnTpTunnelFqPluName
    		DisplayString,
    	    wfAppnTpTunnelModeName
    		DisplayString,
    	    wfAppnTpTunnelMedia
    		INTEGER,
    	    wfAppnTpTunnelMacAddress
    		OCTET STRING,
    	    wfAppnTpTunnelTxFrames
    		Counter,
    	    wfAppnTpTunnelRxFrames
    		Counter,
    	    wfAppnTpTunnelDropFrames
    		Counter
        }

    wfAppnTpTunnelDelete OBJECT-TYPE
        SYNTAX	INTEGER {
    		    created(1),
    		    deleted(2)
    		}
        ACCESS	read-write
        STATUS	mandatory
        DESCRIPTION
                "Create/Delete parameter. Default is created.
                Users perform an SNMP SET operation on this
                object in order to create/delete an APPN Tunnel
                instance."
        DEFVAL	{ created }
        ::= { wfAppnTpTunnelEntry 1 }

    wfAppnTpTunnelDisable OBJECT-TYPE
        SYNTAX	INTEGER {
    		    enable(1),
    		    disable(2)
    		}
        ACCESS	read-write
        STATUS	mandatory
        DESCRIPTION
                "Enable/Disable parameter. Default is enabled.
                Users perform an SNMP SET operation on this
                object in order to enable/disable this APPN Tunnel
                instance."
        DEFVAL	{ enable }
        ::= { wfAppnTpTunnelEntry 2 }

    wfAppnTpTunnelState OBJECT-TYPE
        SYNTAX	INTEGER {
    		    up(1),
    		    down(2),
    		    init(3),
    		    notpresent(4)
    		}
        ACCESS	read-only
        STATUS	mandatory
        DESCRIPTION
                "The current state of the Tunnel."
        DEFVAL	{ notpresent }
        ::= { wfAppnTpTunnelEntry 3 }

    wfAppnTpTunnelCct OBJECT-TYPE
        SYNTAX	INTEGER
        ACCESS	read-only
        STATUS	mandatory
        DESCRIPTION
                "This is the circuit number of the circuit running over this APPN Tunnel"
        ::= { wfAppnTpTunnelEntry 4 }

    wfAppnTpTunnelFqPluName OBJECT-TYPE
        SYNTAX	DisplayString
        ACCESS	read-write
        STATUS	mandatory
        DESCRIPTION
                "This specifies the Partner LU for this APPN Tunnel"
        ::= { wfAppnTpTunnelEntry 5 }

    wfAppnTpTunnelModeName OBJECT-TYPE
        SYNTAX	DisplayString
        ACCESS	read-write
        STATUS	mandatory
        DESCRIPTION
                "This specifies the Mode for this APPN Tunnel"
        ::= { wfAppnTpTunnelEntry 6 }

    wfAppnTpTunnelMedia OBJECT-TYPE
        SYNTAX	INTEGER {
    		    ring(5)
    		}
        ACCESS	read-write
        STATUS	mandatory
        DESCRIPTION
                "This specifies the media to be emulated by this tunnel"
        DEFVAL	{ ring }
        ::= { wfAppnTpTunnelEntry 7 }

    wfAppnTpTunnelMacAddress OBJECT-TYPE
        SYNTAX	OCTET STRING
        ACCESS	read-write
        STATUS	mandatory
        DESCRIPTION
                "This specifies the local MAC address to be used by this tunnel"
        ::= { wfAppnTpTunnelEntry 8 }

    wfAppnTpTunnelTxFrames OBJECT-TYPE
        SYNTAX	Counter
        ACCESS	read-only
        STATUS	mandatory
        DESCRIPTION
                "This indicates the number of frames transmitted over this APPN Tunnel"
        ::= { wfAppnTpTunnelEntry 9 }

    wfAppnTpTunnelRxFrames OBJECT-TYPE
        SYNTAX	Counter
        ACCESS	read-only
        STATUS	mandatory
        DESCRIPTION
                "This indicates the number of frames received over this APPN Tunnel"
        ::= { wfAppnTpTunnelEntry 10 }

    wfAppnTpTunnelDropFrames OBJECT-TYPE
        SYNTAX	Counter
        ACCESS	read-only
        STATUS	mandatory
        DESCRIPTION
                "This indicates the number of frames dropped by this APPN Tunnel"
        ::= { wfAppnTpTunnelEntry 11 }

    wfAppnDlurLuTable OBJECT-TYPE
        SYNTAX	SEQUENCE OF WfAppnDlurLuEntry
        ACCESS	not-accessible
        STATUS	mandatory
        DESCRIPTION
                "This table contains an entry for each LU currently being serviced by DLUR"
        ::= { wfAppnDlu 1 }

    wfAppnDlurLuEntry OBJECT-TYPE
        SYNTAX	WfAppnDlurLuEntry
        ACCESS	not-accessible
        STATUS	mandatory
        DESCRIPTION
                "An entry in wfAppnDlurLuTable."
        INDEX	{ wfAppnDlurLuName }
        ::= { wfAppnDlurLuTable 1 }

    WfAppnDlurLuEntry ::= SEQUENCE {
    	    wfAppnDlurLuName
    		DisplayString,
    	    wfAppnDlurLuPuName
    		DisplayString,
    	    wfAppnDlurLuDlusName
    		DisplayString,
    	    wfAppnDlurLuNauAddress
    		INTEGER,
    	    wfAppnDlurLuPluName
    		DisplayString,
    	    wfAppnDlurLuRscv
    		OCTET STRING,
    	    wfAppnDlurLuRscvText
    		DisplayString
        }

    wfAppnDlurLuName OBJECT-TYPE
        SYNTAX	DisplayString
        ACCESS	read-only
        STATUS	mandatory
        DESCRIPTION
                "This is the name of the LU"
        ::= { wfAppnDlurLuEntry 1 }

    wfAppnDlurLuPuName OBJECT-TYPE
        SYNTAX	DisplayString
        ACCESS	read-only
        STATUS	mandatory
        DESCRIPTION
                "This is the name of the PU associated with the LU"
        ::= { wfAppnDlurLuEntry 2 }

    wfAppnDlurLuDlusName OBJECT-TYPE
        SYNTAX	DisplayString
        ACCESS	read-only
        STATUS	mandatory
        DESCRIPTION
                "This is the name of the DLUS node supporting this LU"
        ::= { wfAppnDlurLuEntry 3 }

    wfAppnDlurLuNauAddress OBJECT-TYPE
        SYNTAX	INTEGER
        ACCESS	read-only
        STATUS	mandatory
        DESCRIPTION
                "This is the Network Addressable Unit address of this LU"
        ::= { wfAppnDlurLuEntry 4 }

    wfAppnDlurLuPluName OBJECT-TYPE
        SYNTAX	DisplayString
        ACCESS	read-only
        STATUS	mandatory
        DESCRIPTION
                "This is the name of the Partner LU"
        ::= { wfAppnDlurLuEntry 5 }

    wfAppnDlurLuRscv OBJECT-TYPE
        SYNTAX	OCTET STRING
        ACCESS	read-only
        STATUS	mandatory
        DESCRIPTION
                "This is the RSCV being used by this LU session"
        ::= { wfAppnDlurLuEntry 6 }

    wfAppnDlurLuRscvText OBJECT-TYPE
        SYNTAX	DisplayString
        ACCESS	read-only
        STATUS	mandatory
        DESCRIPTION
                "This is the RSCV (in a human-readable format) for this DLUR connection"
        ::= { wfAppnDlurLuEntry 7 }

    wfAppnDlurPuTable OBJECT-TYPE
        SYNTAX	SEQUENCE OF WfAppnDlurPuEntry
        ACCESS	not-accessible
        STATUS	mandatory
        DESCRIPTION
                "This table contains an entry for each PU currently being serviced by DLUR"
        ::= { wfAppnDlu 2 }

    wfAppnDlurPuEntry OBJECT-TYPE
        SYNTAX	WfAppnDlurPuEntry
        ACCESS	not-accessible
        STATUS	mandatory
        DESCRIPTION
                "An entry in wfAppnDlurPuTable."
        INDEX	{ wfAppnDlurPuName }
        ::= { wfAppnDlurPuTable 1 }

    WfAppnDlurPuEntry ::= SEQUENCE {
    	    wfAppnDlurPuName
    		DisplayString,
    	    wfAppnDlurPuId
    		OCTET STRING,
    	    wfAppnDlurPuDefinedDlusName
    		DisplayString,
    	    wfAppnDlurPuBackupDlusName
    		DisplayString,
    	    wfAppnDlurPuActiveDlusName
    		DisplayString,
    	    wfAppnDlurPuPcid
    		OCTET STRING,
    	    wfAppnDlurPuFqCpName
    		DisplayString
        }

    wfAppnDlurPuName OBJECT-TYPE
        SYNTAX	DisplayString
        ACCESS	read-only
        STATUS	mandatory
        DESCRIPTION
                "This is the name of the PU"
        ::= { wfAppnDlurPuEntry 1 }

    wfAppnDlurPuId OBJECT-TYPE
        SYNTAX	OCTET STRING
        ACCESS	read-only
        STATUS	mandatory
        DESCRIPTION
                "ID of this PU"
        ::= { wfAppnDlurPuEntry 2 }

    wfAppnDlurPuDefinedDlusName OBJECT-TYPE
        SYNTAX	DisplayString
        ACCESS	read-only
        STATUS	mandatory
        DESCRIPTION
                "This is the name of the primary DLUS node defined this PU"
        ::= { wfAppnDlurPuEntry 3 }

    wfAppnDlurPuBackupDlusName OBJECT-TYPE
        SYNTAX	DisplayString
        ACCESS	read-only
        STATUS	mandatory
        DESCRIPTION
                "This is the name of the backup DLUS node defined this PU"
        ::= { wfAppnDlurPuEntry 4 }

    wfAppnDlurPuActiveDlusName OBJECT-TYPE
        SYNTAX	DisplayString
        ACCESS	read-only
        STATUS	mandatory
        DESCRIPTION
                "This is the name of the DLUS node currently supporting this PU"
        ::= { wfAppnDlurPuEntry 5 }

    wfAppnDlurPuPcid OBJECT-TYPE
        SYNTAX	OCTET STRING
        ACCESS	read-only
        STATUS	mandatory
        DESCRIPTION
                "This is the PCID of the DLUR 'pipe' session"
        ::= { wfAppnDlurPuEntry 6 }

    wfAppnDlurPuFqCpName OBJECT-TYPE
        SYNTAX	DisplayString
        ACCESS	read-only
        STATUS	mandatory
        DESCRIPTION
                "This is the Fully-qualified CP name of the node assigning the
                PCID for the DLUR 'pipe' session"
        ::= { wfAppnDlurPuEntry 7 }

    wfAppnDlurDlusTable OBJECT-TYPE
        SYNTAX	SEQUENCE OF WfAppnDlurDlusEntry
        ACCESS	not-accessible
        STATUS	mandatory
        DESCRIPTION
                "This table contains an entry for each DLUS known to this DLUR"
        ::= { wfAppnDlu 3 }

    wfAppnDlurDlusEntry OBJECT-TYPE
        SYNTAX	WfAppnDlurDlusEntry
        ACCESS	not-accessible
        STATUS	mandatory
        DESCRIPTION
                "An entry in wfAppnDlurDlusTable."
        INDEX	{ wfAppnDlurDlusName }
        ::= { wfAppnDlurDlusTable 1 }

    WfAppnDlurDlusEntry ::= SEQUENCE {
    	    wfAppnDlurDlusName
    		DisplayString,
    	    wfAppnDlurDlusIsDefault
    		INTEGER,
    	    wfAppnDlurDlusIsBackupDefault
    		INTEGER,
    	    wfAppnDlurDlusPipeState
    		INTEGER,
    	    wfAppnDlurDlusActivePus
    		INTEGER,
    	    wfAppnDlurDlusSentReqactpus
    		Counter,
    	    wfAppnDlurDlusRcvReqactpuRsps
    		Counter,
    	    wfAppnDlurDlusRcvActpus
    		Counter,
    	    wfAppnDlurDlusSentActpuRsps
    		Counter,
    	    wfAppnDlurDlusSentReqdactpus
    		Counter,
    	    wfAppnDlurDlusRcvReqdactpuRsps
    		Counter,
    	    wfAppnDlurDlusRcvDactpus
    		Counter,
    	    wfAppnDlurDlusSentDactpuRsps
    		Counter,
    	    wfAppnDlurDlusRcvActlus
    		Counter,
    	    wfAppnDlurDlusSentActluRsps
    		Counter,
    	    wfAppnDlurDlusRcvDactlus
    		Counter,
    	    wfAppnDlurDlusSentDactluRsps
    		Counter,
    	    wfAppnDlurDlusRcvSscpPuMus
    		Counter,
    	    wfAppnDlurDlusSentSscpPuMus
    		Counter,
    	    wfAppnDlurDlusRcvSscpLuMus
    		Counter,
    	    wfAppnDlurDlusSentSscpLuMus
    		Counter
        }

    wfAppnDlurDlusName OBJECT-TYPE
        SYNTAX	DisplayString
        ACCESS	read-only
        STATUS	mandatory
        DESCRIPTION
                "This is the fully-qualified name of the DLUS node"
        ::= { wfAppnDlurDlusEntry 1 }

    wfAppnDlurDlusIsDefault OBJECT-TYPE
        SYNTAX	INTEGER {
    		    yes(1),
    		    no(2)
    		}
        ACCESS	read-only
        STATUS	mandatory
        DESCRIPTION
                "This indicates if the DLUS is the default DLUS"
        ::= { wfAppnDlurDlusEntry 2 }

    wfAppnDlurDlusIsBackupDefault OBJECT-TYPE
        SYNTAX	INTEGER {
    		    yes(1),
    		    no(2)
    		}
        ACCESS	read-only
        STATUS	mandatory
        DESCRIPTION
                "This indicates if the DLUS is the default backup DLUS"
        ::= { wfAppnDlurDlusEntry 3 }

    wfAppnDlurDlusPipeState OBJECT-TYPE
        SYNTAX	INTEGER {
    		    inactive(1),
    		    pendactive(2),
    		    active(3),
    		    pendinact(4)
    		}
        ACCESS	read-only
        STATUS	mandatory
        DESCRIPTION
                "This indicates the state of the DLUR-DLUS pipe"
        ::= { wfAppnDlurDlusEntry 4 }

    wfAppnDlurDlusActivePus OBJECT-TYPE
        SYNTAX	INTEGER
        ACCESS	read-only
        STATUS	mandatory
        DESCRIPTION
                "This indicates the number of PUs currently using this DLUR-DLUS pipe"
        ::= { wfAppnDlurDlusEntry 5 }

    wfAppnDlurDlusSentReqactpus OBJECT-TYPE
        SYNTAX	Counter
        ACCESS	read-only
        STATUS	mandatory
        DESCRIPTION
                "This indicates the number of REQACTPUs sent over this DLUR-DLUS pipe"
        ::= { wfAppnDlurDlusEntry 6 }

    wfAppnDlurDlusRcvReqactpuRsps OBJECT-TYPE
        SYNTAX	Counter
        ACCESS	read-only
        STATUS	mandatory
        DESCRIPTION
                "This indicates the number of REQACTPU responses received over this DLUR-DLUS pipe"
        ::= { wfAppnDlurDlusEntry 7 }

    wfAppnDlurDlusRcvActpus OBJECT-TYPE
        SYNTAX	Counter
        ACCESS	read-only
        STATUS	mandatory
        DESCRIPTION
                "This indicates the number of ACTPUs received over this DLUR-DLUS pipe"
        ::= { wfAppnDlurDlusEntry 8 }

    wfAppnDlurDlusSentActpuRsps OBJECT-TYPE
        SYNTAX	Counter
        ACCESS	read-only
        STATUS	mandatory
        DESCRIPTION
                "This indicates the number of ACTPU responses sent over this DLUR-DLUS pipe"
        ::= { wfAppnDlurDlusEntry 9 }

    wfAppnDlurDlusSentReqdactpus OBJECT-TYPE
        SYNTAX	Counter
        ACCESS	read-only
        STATUS	mandatory
        DESCRIPTION
                "This indicates the number of REQDACTPUs sent over this DLUR-DLUS pipe"
        ::= { wfAppnDlurDlusEntry 10 }

    wfAppnDlurDlusRcvReqdactpuRsps OBJECT-TYPE
        SYNTAX	Counter
        ACCESS	read-only
        STATUS	mandatory
        DESCRIPTION
                "This indicates the number of REQDACTPU responses received over this DLUR-DLUS pipe"
        ::= { wfAppnDlurDlusEntry 11 }

    wfAppnDlurDlusRcvDactpus OBJECT-TYPE
        SYNTAX	Counter
        ACCESS	read-only
        STATUS	mandatory
        DESCRIPTION
                "This indicates the number of DACTPUs received over this DLUR-DLUS pipe"
        ::= { wfAppnDlurDlusEntry 12 }

    wfAppnDlurDlusSentDactpuRsps OBJECT-TYPE
        SYNTAX	Counter
        ACCESS	read-only
        STATUS	mandatory
        DESCRIPTION
                "This indicates the number of DACTPU responses sent over this DLUR-DLUS pipe"
        ::= { wfAppnDlurDlusEntry 13 }

    wfAppnDlurDlusRcvActlus OBJECT-TYPE
        SYNTAX	Counter
        ACCESS	read-only
        STATUS	mandatory
        DESCRIPTION
                "This indicates the number of ACTLUs received over this DLUR-DLUS pipe"
        ::= { wfAppnDlurDlusEntry 14 }

    wfAppnDlurDlusSentActluRsps OBJECT-TYPE
        SYNTAX	Counter
        ACCESS	read-only
        STATUS	mandatory
        DESCRIPTION
                "This indicates the number of ACTLU responses sent over this DLUR-DLUS pipe"
        ::= { wfAppnDlurDlusEntry 15 }

    wfAppnDlurDlusRcvDactlus OBJECT-TYPE
        SYNTAX	Counter
        ACCESS	read-only
        STATUS	mandatory
        DESCRIPTION
                "This indicates the number of DACTLUs received over this DLUR-DLUS pipe"
        ::= { wfAppnDlurDlusEntry 16 }

    wfAppnDlurDlusSentDactluRsps OBJECT-TYPE
        SYNTAX	Counter
        ACCESS	read-only
        STATUS	mandatory
        DESCRIPTION
                "This indicates the number of DACTLU responses sent over this DLUR-DLUS pipe"
        ::= { wfAppnDlurDlusEntry 17 }

    wfAppnDlurDlusRcvSscpPuMus OBJECT-TYPE
        SYNTAX	Counter
        ACCESS	read-only
        STATUS	mandatory
        DESCRIPTION
                "This indicates the number of SSCP-PU MUs received over this DLUR-DLUS pipe"
        ::= { wfAppnDlurDlusEntry 18 }

    wfAppnDlurDlusSentSscpPuMus OBJECT-TYPE
        SYNTAX	Counter
        ACCESS	read-only
        STATUS	mandatory
        DESCRIPTION
                "This indicates the number of SSCP-PU MUs sent over this DLUR-DLUS pipe"
        ::= { wfAppnDlurDlusEntry 19 }

    wfAppnDlurDlusRcvSscpLuMus OBJECT-TYPE
        SYNTAX	Counter
        ACCESS	read-only
        STATUS	mandatory
        DESCRIPTION
                "This indicates the number of SSCP-LU MUs received over this DLUR-DLUS pipe"
        ::= { wfAppnDlurDlusEntry 20 }

    wfAppnDlurDlusSentSscpLuMus OBJECT-TYPE
        SYNTAX	Counter
        ACCESS	read-only
        STATUS	mandatory
        DESCRIPTION
                "This indicates the number of SSCP-LU MUs sent over this DLUR-DLUS pipe"
        ::= { wfAppnDlurDlusEntry 21 }

    wfAppnPathSwitch    OBJECT IDENTIFIER ::= { wfAppnGroup 8 }

    wfAppnPathSwitchDelete OBJECT-TYPE
        SYNTAX	INTEGER {
    		    created(1),
    		    deleted(2)
    		}
        ACCESS	read-write
        STATUS	mandatory
        DESCRIPTION
                "Create/Delete parameter. Default is created.
                Users perform an SNMP SET operation on this
                object in order to create/delete a path switch."
        DEFVAL	{ created }
        ::= { wfAppnPathSwitch 1 }

    wfAppnPathSwitchDisable OBJECT-TYPE
        SYNTAX	INTEGER {
    		    enable(1),
    		    disable(2)
    		}
        ACCESS	read-write
        STATUS	mandatory
        DESCRIPTION
                "Enable/Disable parameter. Default is enabled.
                Users perform an SNMP SET operation on this
                object in order to enable/disable this path switch."
        DEFVAL	{ enable }
        ::= { wfAppnPathSwitch 2 }

    wfAppnPathSwitchRtpConnName OBJECT-TYPE
        SYNTAX	DisplayString
        ACCESS	read-write
        STATUS	mandatory
        DESCRIPTION
                "This is the name of the RTP connection to path switch"
        ::= { wfAppnPathSwitch 3 }


    END  -- Wellfleet-APPN-MIB
