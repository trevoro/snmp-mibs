XYLAN-VLAN-MIB DEFINITIONS ::= BEGIN

	--  RCSID information

	--  $RCSfile: xylan-vlan.mib,v $
	--  $Revision: 1.84 $		$State: Exp $
	--  $Date: 1998/07/27 22:17:39 $
	--  $Author: lsl $


	--  xylan-vlan.mib
	--  Revision: 1.00
	--  Date: June 14, 1994

	--  Alcatel Internetworking, Inc.
	--  26801 W. Agoura Road
	--  Calabasas, CA 91301
	--  (818) 880-3500
	--  support@ind.alcatel.com

	--  This module provides authoritative definitions for Alcatel Internetworking, Inc.
	--  enterprise-specific virtual lan MIB.

	--  This module will be extended, as needed.


	--  Alcatel Internetworking, Inc. reserves the right to make changes in 
	--  specification and other information contained in this document 
	--  without prior notice.  The reader should consult Alcatel Internetworking,
	--  Inc. to determine whether any such changes have been made.
	--  Current MIBs are availible from the following URLs:
	--		ftp://ftp.ind.alcatel.com/pub/products/mibs
	--		http://www.ind.alcatel.com

	--  In no event shall Alcatel Internetworking, Inc. be liable for any incidental, 
	--  indirect, special, or consequential damages whatsoever (including 
	--  but not limited to lost profits) arising out of or related to this
	--  document or the information contained in it, even if Alcatel Internetworking,
	--  Inc. has been advised of, known, or should have known, the 
	--  possibility of such damages.

	--  Alcatel Internetworking, Inc. grants vendors, end-users, and other interested
	--  parties a non-exclusive license to use this Specification in connection
	--  with the management of Alcatel Internetworking, Inc. products.

	--  Copyright (C) 1994, Alcatel Internetworking, Inc. All Rights Reserved.
        --  History
        --  7/10/96 == plim added 1 more option to XylanVlanModes to support
        --             Frame-Relay Router mode

	IMPORTS
		Counter, TimeTicks, IpAddress
			FROM RFC1155-SMI
		OBJECT-TYPE
			FROM RFC-1212
		DisplayString 
			FROM RFC1213-MIB
		MacAddress, BridgeId, Timeout
			FROM BRIDGE-MIB
		XylanPortFuncCodes
			FROM XYLAN-PORT-MIB
		xylanVlanArch
			FROM XYLAN-BASE-MIB 
			;

	--  This MIB module uses the extended OBJECT-TYPE macro as defined in
	--  RFC 1212 (but known in the epilog files under RFC1213-SMI...)


	--  groups within the xylanVlanArch mib

	vLanInfo		OBJECT IDENTIFIER ::= { xylanVlanArch 1 }
	vIPRouterInfo	OBJECT IDENTIFIER ::= { xylanVlanArch 2 }
	vIPXRouterInfo	OBJECT IDENTIFIER ::= { xylanVlanArch 3 }
	vBrdgInfo		OBJECT IDENTIFIER ::= { xylanVlanArch 4 }
	vStpInfo		OBJECT IDENTIFIER ::= { xylanVlanArch 5 }
--  vRipConfig      OBJECT IDENTIFIER ::= { xylanVlanArch 6 }
    vRipInfo        OBJECT IDENTIFIER ::= { xylanVlanArch 7 }
    vSr             OBJECT IDENTIFIER ::= { xylanVlanArch 8 }
    vTrunking       OBJECT IDENTIFIER ::= { xylanVlanArch 9 }

	vAutoTracker    OBJECT IDENTIFIER ::= { xylanVlanArch 10 }
    atvIPRouterInfo OBJECT IDENTIFIER ::= { xylanVlanArch 11 }
    atvIPXRouterInfo OBJECT IDENTIFIER ::= { xylanVlanArch 12 }
    v80210          OBJECT IDENTIFIER ::= { xylanVlanArch 13 }
    vDBr            OBJECT IDENTIFIER ::= { xylanVlanArch 14 }
    v8021Q          OBJECT IDENTIFIER ::= { xylanVlanArch 15 }
    vDupMac         OBJECT IDENTIFIER ::= { xylanVlanArch 16 }
    vPmap	    OBJECT IDENTIFIER ::= { xylanVlanArch 17 }		


	--  various type codes.

	XylanVlanAdminStatCodes ::= INTEGER {
	    disable(1),
	    enable(2),
	    delete(3),
	    create(4),
	    modify(5)
	}

	XylanVlanOperStatCodes ::= INTEGER {
	    inactive(1),
	    active(2)
	}

	XylanVlanModes ::= INTEGER {
	    invalid(1),
	    other(2),
	    standard(3),
	    atmCIP(4),
	    frRouter(5)
	}

	NetNumber ::= OCTET STRING (SIZE (4))




	--  vLanInfo group.  This group contains the global Virtual LAN
	--  information data.
	--  Implementation of this group is mandatory.

	vLanCurrentNumber  OBJECT-TYPE
	    SYNTAX  INTEGER (1..65535)
	    ACCESS  read-write
	    STATUS  mandatory
	    DESCRIPTION
		 "The current instance of Virtual LAN which corresponds to
		  vLanNumber in object type vLanEntry.  All the Bridging,
		  Spanning Tree, and interface parameters refered thereafter
		  will be referenced from this instance only.  Default value
		  upon the OmniSwitch power up is 1.  It must be set to the
		  desired value before any access to the rest of the virtual
		  LAN system."
	    ::= { vLanInfo 1 }

	vLanTable  OBJECT-TYPE
	    SYNTAX  SEQUENCE OF VLanEntry
	    ACCESS  not-accessible
	    STATUS  mandatory
	    DESCRIPTION
		 "A list of Virtual LAN instances in this physical OmniSwitch."
	    ::= { vLanInfo 2 }

	vLanEntry  OBJECT-TYPE
	    SYNTAX  VLanEntry
	    ACCESS  not-accessible
	    STATUS  mandatory
	    DESCRIPTION
		 "A VLAN entry." 
	    INDEX { vLanNumber }
	    ::= { vLanTable 1 }

	VLanEntry ::= SEQUENCE {
	    vLanNumber
		INTEGER,
	    vLanBridgeAddress
		MacAddress,
	    vLanBridgeType
		INTEGER,
	    vLanDescription
		DisplayString,
	    vLanAdmStatus
		XylanVlanAdminStatCodes,
	    vLanOperStatus
		XylanVlanOperStatCodes,
	    vLanMode
		XylanVlanModes,
            vLanFloodOverride
                INTEGER,
	    vLanRouterAddress
		MacAddress,
            vLanMobileGroup
                INTEGER,
            vLanAuthGroup
                INTEGER,
            vLanAuthGroupProtocol
		OCTET STRING,
            vLanStpStatus
                INTEGER,
            vLanBrdgTpExtendedAgeingTime
                INTEGER,
            vLanPriority
                INTEGER
	    }

	vLanNumber  OBJECT-TYPE
	    SYNTAX  INTEGER (1..65535)
	    ACCESS  read-write
	    STATUS  mandatory
	    DESCRIPTION
		 "The VLAN number identifying this instance. Valid
		  range from 1 to 65535."
	    ::= { vLanEntry 1 }

	vLanBridgeAddress  OBJECT-TYPE
	    SYNTAX  MacAddress
	    ACCESS  read-only
	    STATUS  mandatory
	    DESCRIPTION
		"The MAC address used by the instance of VLAN which
		 specified in vLanCurrentNumber when it must
		 be referred to in a unique fashion.   It is
		 recommended that this be the numerically smallest
		 MAC address of all ports that belong to this
		 VLAN.  However it is only required to be unique.
		 When concatenated with vStpPriority a unique
		 BridgeIdentifier is formed which is used in the
		 Spanning Tree Protocol."
	    ::= { vLanEntry 2 }

	vLanBridgeType  OBJECT-TYPE
	    SYNTAX  INTEGER {
		unknown(1),
		other(2),
		transparent-only(3),
		sourceroute-only(4),
		srt(5),
		not-supported(6)
	    }
	    ACCESS  read-only
	    STATUS  deprecated
	    DESCRIPTION
		"Indicates what type of bridging this VLAN can
		 perform.  If a VLAN is actually performing a
		 certain type of bridging this will be indicated by
		 entries in the port table for the given type."
	    ::= { vLanEntry 3 }

	vLanDescription  OBJECT-TYPE
	    SYNTAX  DisplayString (SIZE (0..31))
	    ACCESS  read-write
	    STATUS  mandatory
	    DESCRIPTION
		 "Textual description of the VLAN instance."
	    ::= { vLanEntry 4 }

	vLanAdmStatus  OBJECT-TYPE
	    SYNTAX  XylanVlanAdminStatCodes
	    ACCESS  read-write
	    STATUS  mandatory
	    DESCRIPTION
		"The administrative status which can be set by
		 configuration. Disable(1) will disable ALL vports
		 that are connected to this VLAN, enable(2) will enable
		 ALL ports on this VLAN, delete(3) will dettach and
		 delete the ports/routers AND remove the VLAN."
	    ::= { vLanEntry 5 }

	vLanOperStatus  OBJECT-TYPE
	    SYNTAX  XylanVlanOperStatCodes
	    ACCESS  read-only
	    STATUS  mandatory
	    DESCRIPTION
		 "Provide operating status of a particular VLAN environment."
	    ::= { vLanEntry 6 }

	vLanMode  OBJECT-TYPE
	    SYNTAX  XylanVlanModes
	    ACCESS  read-write
	    STATUS  mandatory
	    DESCRIPTION
		"Provides special operating mode setup and status. Currently
		 this object is used to specify weather the VLAN supports
		 the standard or ATM CIP connections."
	    ::= { vLanEntry 7 }

        vLanFloodOverride  OBJECT-TYPE
            SYNTAX  INTEGER 
            ACCESS  read-write
            STATUS  mandatory
            DESCRIPTION
                 "Provides the flood limit value for all virtual ports
                  that belong to the specied VLAN.  The number is given
                  in bytes per second.  -1  and 0 have a special meaning.
                  -1 means use the default or configured flood limit 
                  for each virtual port that belongs to the specified
                  VLAN.  0 disables flood limiting on all virtual ports
                  that belong to the specifed VLAN."
            ::= { vLanEntry 8 }

        vLanRouterAddress  OBJECT-TYPE
            SYNTAX  MacAddress
            ACCESS  read-write
            STATUS  mandatory
            DESCRIPTION
                "The user-configured MAC address used by the
                 the VLAN's router port (IP / IPX). If this
                 value has not been configured, the value returned
                 is zero and this VLAN's router port will use
                 a factory provided default value.  The address
                 should be specified in canonical order."
            ::= { vLanEntry 9 }
 
        vLanMobileGroup  OBJECT-TYPE
            SYNTAX  INTEGER {
                       enabled (1),
                       disabled (2)
                    }
            ACCESS  read-write
            STATUS  mandatory
            DESCRIPTION
                 "If set to enabled, makes this a mobile group.
                  If set to disabled, makes this a non-mobile gropu."
            ::= { vLanEntry 10 }

	vLanAuthGroup  OBJECT-TYPE
	    SYNTAX  INTEGER {
                       enabled (1),
                       disabled (2)
                    }
            ACCESS  read-write
            STATUS  mandatory
            DESCRIPTION
                 "If set to enable, makes this a authenticated group.
                  If set to disable, makes this a non-authenticated group.
                  For it to be set to enable, the group should be a mobile
                  group."
            ::= { vLanEntry 11 }

	vLanAuthGroupProtocol  OBJECT-TYPE
	    SYNTAX  OCTET STRING
	    ACCESS  read-write
	    STATUS  mandatory
            DESCRIPTION
                 "If a NULL string is returned as the value,
                  this object is not applicable to that group.
                  The contents of the string can interpreted
                  based on the first byte. if the first byte is
                  1, the protocol is IP ( for all encaps ).
                  2, the protocol is IPX 
                  3, the protocol is DECNET
                  4, the protocol is APPLETALK
                  5, the protocol is specified as an Ether-Type value
                     with the next two bytes indicating the ether-type
                     value, for e.g banyan vines ether-type will be specified as
                     08 0B AD
                  6, the protocol is specified using dsap and ssap values
                     with the next two bytes giving the dsap and ssap value
                     respectively, for e.g for banyan vines llc encap,
                     it would look like 09 BC BC.
                  7, the protocol is specified using snap header with the
                     next 5 bytes indicating the snap header for that protocol.
                     For e.g if banyan vines snap has to be specified, it
                     would look like, 0A 00 00 00 80 C4.
                 FF, for all protocols."
            ::= { vLanEntry 12 }
	     
        vLanStpStatus  OBJECT-TYPE
            SYNTAX  INTEGER {
			      off(1),
			      on(2)
                            }
            ACCESS  read-write
            STATUS  mandatory
            DESCRIPTION
                "Indicates status of spanning tree for the current VLAN."
	    ::= { vLanEntry 13 }

        vLanBrdgTpExtendedAgeingTime  OBJECT-TYPE
	    SYNTAX  INTEGER (10..1000000)
	    ACCESS  read-write
	    STATUS  mandatory
	    DESCRIPTION
		"The AutoTracker extended ageing timer. This value indicates
              how long the switch will remember the mac address and its
              associated vlan information. The default value is 1200 secs.
              This means that the mac information will be remembered for
              (vLanBrdgTpExtendedAgeingTime - vBrdgTpAgingTime) seconds after the 
	      mac is aged out.  This value must be set to a value greater than 
	      or equal to vBrdgTpAgingTime." 
	    ::= { vLanEntry 14 }
        
        vLanPriority  OBJECT-TYPE
            SYNTAX  INTEGER
            ACCESS  read-write
            STATUS  mandatory
            DESCRIPTION
                 "This is the priority of the given VLAN. It can be any one 
                  level from 0 to 7 with 0 being the lowest and 7 being the 
                  highest"
            ::= { vLanEntry 15 }
 
	vLanNextFreeNumber  OBJECT-TYPE
	    SYNTAX  INTEGER (1..65535)
	    ACCESS  read-only
	    STATUS  mandatory
	    DESCRIPTION
		 "This is the next unused VLAN number. Typically this
		  will be used to create a new VLAN with the next
		  highest number."
	    ::= { vLanInfo 3 }



	--  vIPRouterInfo group.  This group contains the global
	--  Virtual IP Router information.

	vIPRouterTable  OBJECT-TYPE
	    SYNTAX  SEQUENCE OF VIPRouterEntry
	    ACCESS  not-accessible
	    STATUS  mandatory
	    DESCRIPTION
		"A list of Virtual Router instances in this
		 physical OmniSwitch."
	    ::= { vIPRouterInfo 1 }

	vIPRouterEntry  OBJECT-TYPE
	    SYNTAX  VIPRouterEntry
	    ACCESS  not-accessible
	    STATUS  mandatory
	    DESCRIPTION
		"A VLAN entry." 
	    INDEX { vIPRouterVLan }
	    ::= { vIPRouterTable 1 }

	VIPRouterEntry ::= SEQUENCE {
	    vIPRouterVLan
		INTEGER,
	    vIPRouterProtocol
		OCTET STRING,
	    vIPRouterNetAddress
		IpAddress,
	    vIPRouterSubNetMask
		IpAddress,
	    vIPRouterBcastAddress
		IpAddress,
	    vIPRouterDescription
		DisplayString,
	    vIPRouterAdmStatus
		XylanVlanAdminStatCodes,
	    vIPRouterOperStatus
		XylanVlanOperStatCodes,
            vIPRouterFramingType
                INTEGER,
            vIPRouterRipConfigMode
                INTEGER
	    }

	vIPRouterVLan  OBJECT-TYPE
	    SYNTAX  INTEGER (1..65535)
	    ACCESS  read-write
	    STATUS  mandatory
	    DESCRIPTION
		"VLAN ID for this vIPRouterEntry instance."
	    ::= { vIPRouterEntry 1 }

	vIPRouterProtocol  OBJECT-TYPE
	    SYNTAX  OCTET STRING (SIZE (2))
	    ACCESS  read-write
	    STATUS  mandatory
	    DESCRIPTION
		"The routing protocol(s) for this virtual router port.
		 Each IP router port can carry one or more routing protocols.
		 This will be represented by the logical ORing of each
		 protocol number.

		 Which are:

		 ipOther(1),
		 ipRip(2),
		 ipEgp(4),
		 ipGgp(8),
		 ipHello(16),
		 ipIs-is(32),
		 ipEs-is(64),
		 ipCiscoIgrp(128),
		 ipBbnSpfIgp(256),
		 ipOigp(512)"
	    ::= { vIPRouterEntry 2 }

	vIPRouterNetAddress  OBJECT-TYPE
	    SYNTAX  IpAddress
	    ACCESS  read-write
	    STATUS  mandatory
	    DESCRIPTION
		 "The IP network address for this virtual bridge
		  instance for the purpose of allowing access from
		  the external network management system."
	    ::= { vIPRouterEntry 3 }

	vIPRouterSubNetMask  OBJECT-TYPE
	    SYNTAX  IpAddress
	    ACCESS  read-write
	    STATUS  mandatory
	    DESCRIPTION
		 "The IP network subnet mask for this virtual bridge
		  instance for the purpose of allowing access from the
		  external network management system."
	    ::= { vIPRouterEntry 4 }

	vIPRouterBcastAddress  OBJECT-TYPE
	    SYNTAX  IpAddress
	    ACCESS  read-write
	    STATUS  mandatory
	    DESCRIPTION
		 "The IP broadcast address for this virtual bridge
		  instance for the purpose of allowing access from the
		  external network management system."
	    ::= { vIPRouterEntry 5 }

	vIPRouterDescription  OBJECT-TYPE
	    SYNTAX  DisplayString (SIZE (0..31))
	    ACCESS  read-write
	    STATUS  optional
	    DESCRIPTION
		"Textual description of the router instance."
	    ::= { vIPRouterEntry 6 }

	vIPRouterAdmStatus  OBJECT-TYPE
	    SYNTAX  XylanVlanAdminStatCodes
	    ACCESS  read-write
	    STATUS  mandatory
	    DESCRIPTION
		"The particular routing environment can be
		 enable(2) or disable(1) (or delete (3))
		 upon user's request."
	    ::= { vIPRouterEntry 7 }

	vIPRouterOperStatus  OBJECT-TYPE
	    SYNTAX  XylanVlanOperStatCodes
	    ACCESS  read-only
	    STATUS  mandatory
	    DESCRIPTION
		"Provide operating status of a particular
		 router envirnment."
	    ::= { vIPRouterEntry 8 }

        vIPRouterFramingType  OBJECT-TYPE
            SYNTAX INTEGER {
                       ethernet-2(1),
                       ethernet-802-3(2),
                       fddi(3),
                       token-ring(4),
                       token-ring-source-routed(5),
                       atm-1483(6)
                       }
            ACCESS  read-write
            STATUS  mandatory
            DESCRIPTION
                "Provides the ability to set the outbound frame type for IP
                 traffic.  The default frame type is Ethernet 2.  If the
                 frame type is incompatible with the transmitting media,
                 appropriate translation will be performed at egress."
	    ::= { vIPRouterEntry 9 }
 
        vIPRouterRipConfigMode  OBJECT-TYPE
            SYNTAX  INTEGER {
                        silent(1),
                        deaf(2),
                        active(3),
                        inactive(4)
                        }
            ACCESS  read-write
            STATUS  mandatory
            DESCRIPTION
                 "RIP's operational mode. 'silent' means that RIP listens
                  for routing updates but does not send them.  'deaf' means
                  that RIP sends routing updates but not listen to them.
                  'active' means that RIP both sends and receives routing
                  updates, and 'inactive' means that RIP is not operational
                  on the given virtual LAN. The default is 'simple'."
	    ::= { vIPRouterEntry 10 }

        -- vIPRouterRelayTable.  This table contains the parameters and
        -- status for UDP Relay services.

        -- UDP Relay service definitions.
                VIPRouterRelayServType ::= INTEGER {
                    vIPRouterRelayBootp(1),
                    vIPRouterRelayNBNS(2),
                    vIPRouterRelayNBDD(3),
                    vIPRouterRelayGen1(4),
                    vIPRouterRelayGen2(5),
                    vIPRouterRelayGen3(6),
                    vIPRouterRelayGen4(7),
                    vIPRouterRelayGen5(8)
                }
 
 
                vIPRouterRelayTable OBJECT-TYPE
                    SYNTAX  SEQUENCE OF VIPRouterRelayEntry
                    ACCESS  not-accessible
                    STATUS  mandatory
                    DESCRIPTION
                            " A list of UDP Relay Service instances."
                    ::= { vIPRouterInfo 2 }
 
                vIPRouterRelayEntry OBJECT-TYPE
                    SYNTAX  VIPRouterRelayEntry
                    ACCESS  not-accessible
                    STATUS  mandatory
                    DESCRIPTION
                           "A UDP Relay Service entry."
                    INDEX { vIPRouterRelayService }
                    ::= { vIPRouterRelayTable 1 }
 
 
                VIPRouterRelayEntry ::= SEQUENCE {
                    vIPRouterRelayService
                        VIPRouterRelayServType,
                    vIPRouterRelayMode
                        INTEGER,
                    vIPRouterRelayNextHop
                        IpAddress,
                    vIPRouterRelayParam1
                        INTEGER,
                    vIPRouterRelayParam2
                        INTEGER,
                    vIPRouterRelayDescription
                        DisplayString
                    }
 
                vIPRouterRelayService OBJECT-TYPE
                        SYNTAX VIPRouterRelayServType
                        ACCESS read-only
                        STATUS mandatory
                        DESCRIPTION
                             "This specifies the UDP Relay Service to be forwarded."
                ::= { vIPRouterRelayEntry 1 }

                vIPRouterRelayMode OBJECT-TYPE
                        SYNTAX INTEGER
                        ACCESS read-write
                        STATUS mandatory
                        DESCRIPTION
                                "This controls whether the internal UDP Relay service is enabled
                                or disabled.  When enabled, the service will forward packets
                                to a specified server (or specified broadcast address.) or
                                VLAN.  Note that for BOOTP/DHCP service,
                                unless the relay's next hop ip address (vIPRouterRelayForwAddr)
                                is set to a valid value, it will not possible to enable the relay.
                                For other services, a VLAN to forwared to (vIPRouterRelayForwVlan
                                in vIPRouterRelayForwTable) or a next hop ip address must be set.
                                The mode definitions are as follows:
                                1       - enabled
                                2       - configureRequest
                                3       - underConfiguration
                                4       - disabled

                                A manager will set the state to configureRequest(2)
                                before attempting to configure any other parameters
                                for a particular UPD Service.  The agent will then
                                set the state to underConfiguration(3).
                                When in the underConfiguration(3) state, a UDP
                                service is not completely configured and will
                                remain in this state until the management
                                station is finished configuring and sets the
                                state to either enabled(1) or disabled(4).
               
                                A manager is restricted to changing the state of an
                                entry in the following ways:
              
                                                        config    under
                                     To:         valid  Request   config    invalid
                                From:
                                valid             OK       NO        OK       OK 
                                configRequest    N/A      N/A       N/A      N/A 
                                underConfig       OK       NO        OK       OK 
                                invalid           NO       OK        NO       OK"
 
                ::= { vIPRouterRelayEntry 2 }
 
                vIPRouterRelayNextHop OBJECT-TYPE
                        SYNTAX  IpAddress
                        ACCESS read-write
                        STATUS mandatory
                        DESCRIPTION
                                "This sets the relay's forwarding address.  It
                                can either be set to a distinct IP address (e.g. the address
                                of a server), to an IP broadcast address or a VLAN."
                ::= { vIPRouterRelayEntry 3 }
 
                vIPRouterRelayParam1 OBJECT-TYPE
                        SYNTAX  INTEGER (-1..65535)
                        ACCESS read-write
                        STATUS mandatory
                        DESCRIPTION
                                "This sets the BOOTP/DHCP relay's maximum hops forwarding
                                limit.  If a BOOT/DHCP frame arrives with hopcount greater
                                than or equal to vIPRouterRelayParam1, it will be dropped.
                                For BOOTP/DHCP the legal range is 1..16.  For
                                Generic services, this sets the port number to be
                                forwarded.  The legal range is -1..65535 with -1 indicating
                                the unset state."
                ::= { vIPRouterRelayEntry 4 }
 
                vIPRouterRelayParam2 OBJECT-TYPE
                        SYNTAX  INTEGER (0..65535)
                        ACCESS read-write
                        STATUS mandatory
                        DESCRIPTION
                                "This sets the BOOTP/DHCP relay's forwarding delay and
                                is only used by the BOOTP/DHCP service.  For other services
                                it is ignored.  It is typically set as seconds, but the
                                value is totally client dependent.  The relay will not
                                forward frames until client frames have 'secs' field set
                                to at least the value of vIPRouterRelayParam2."
                ::= { vIPRouterRelayEntry 5 }
 
                vIPRouterRelayDescription OBJECT-TYPE
                        SYNTAX  DisplayString (SIZE (0..31))
                        ACCESS read-write
                        STATUS mandatory
                        DESCRIPTION
                                "This sets the service description for generic services.
                                 For other services, the description is fixed and may
                                 only be read."
                ::= { vIPRouterRelayEntry 6 }
 
 

	--  vIPXRouterInfo group.  This group contains the global
	--  Virtual IPX (novell) Router information.

	vIPXRouterTable  OBJECT-TYPE
	    SYNTAX  SEQUENCE OF VIPXRouterEntry
	    ACCESS  not-accessible
	    STATUS  mandatory
	    DESCRIPTION
		"A list of Virtual Router instances in this
		 physical OmniSwitch."
	    ::= { vIPXRouterInfo 1 }

	vIPXRouterEntry  OBJECT-TYPE
	    SYNTAX  VIPXRouterEntry
	    ACCESS  not-accessible
	    STATUS  mandatory
	    DESCRIPTION
		"A VLAN entry." 
	    INDEX { vIPXRouterVLan }
	    ::= { vIPXRouterTable 1 }

	VIPXRouterEntry ::= SEQUENCE {
	    vIPXRouterVLan
		INTEGER,
	    vIPXRouterProtocol
		INTEGER,
	    vIPXRouterNetAddress
		OCTET STRING,
	    vIPXRouterFramingType
		INTEGER,
	    vIPXRouterDescription
		DisplayString,
	    vIPXRouterAdmStatus
		XylanVlanAdminStatCodes,
	    vIPXRouterOperStatus
		XylanVlanOperStatCodes,
            vIPXSrcRteType
                INTEGER
	    }

	vIPXRouterVLan  OBJECT-TYPE
	    SYNTAX  INTEGER (1..65535)
	    ACCESS  read-write
	    STATUS  mandatory
	    DESCRIPTION
		"VLAN ID for this vIPXRouterEntry instance."
	    ::= { vIPXRouterEntry 1 }

	vIPXRouterProtocol  OBJECT-TYPE
	    SYNTAX  INTEGER
	    ACCESS  read-write
	    STATUS  mandatory
	    DESCRIPTION
		"The routing protocol(s) for this virtual router port.
		 Each IPX router port can carry one or more routing protocols.
		 This will be represented by the logical ORing of each
		 protocol number.

		 Which are:

		 ipxNone(1),
		 ipxRipOnly(2),
		 ipxRipAndSap(3),
		 ipxTriggered(4)"
	    ::= { vIPXRouterEntry 2 }

	vIPXRouterNetAddress  OBJECT-TYPE
	    SYNTAX  OCTET STRING (SIZE(4))
	    ACCESS  read-write
	    STATUS  mandatory
	    DESCRIPTION
		 "The IPX network address for this virtual bridge."
	    ::= { vIPXRouterEntry 3 }

        vIPXRouterFramingType  OBJECT-TYPE
            SYNTAX INTEGER {
                       ethernet-2(1),
                       ethernet-802-3-llc(2),
		       ethernet-802-3-snap(3),
		       ethernet-802-3-raw(4),
                       fddi-snap(5),
		       fddi-snap-sr(6),
		       fddi-llc(7),
		       fddi-llc-sr(8),
                       token-ring-snap(9),
		       token-ring-snap-sr(10),
		       token-ring-llc(11),
		       token-ring-llc-sr(12)
                       }
            ACCESS  read-write
            STATUS  mandatory
            DESCRIPTION
                "Provides the ability to set the outbound frame type for IPX
                 traffic.  The default frame type is 802.2 Novell Raw.  If the
                 frame type is incompatible with the transmitting media,
                 appropriate translation will be performed at egress."
	    ::= { vIPXRouterEntry 4 }
 
	vIPXRouterDescription  OBJECT-TYPE
	    SYNTAX  DisplayString (SIZE (0..31))
	    ACCESS  read-write
	    STATUS  optional
	    DESCRIPTION
		"Textual description of the router instance."
	    ::= { vIPXRouterEntry 5 }

	vIPXRouterAdmStatus  OBJECT-TYPE
	    SYNTAX  XylanVlanAdminStatCodes
	    ACCESS  read-write
	    STATUS  mandatory
	    DESCRIPTION
		"The particular routing environment can be
		 enabled(2) or disabled(1) upon user's request."
	    ::= { vIPXRouterEntry 6 }

	vIPXRouterOperStatus  OBJECT-TYPE
	    SYNTAX  XylanVlanOperStatCodes
	    ACCESS  read-only
	    STATUS  mandatory
	    DESCRIPTION
		"Provide operating status of a particular
		 router environment."
	    ::= { vIPXRouterEntry 7 }

	vIPXSrcRteType  OBJECT-TYPE
            SYNTAX INTEGER {
		are(1),
		ste(2),
		not-applicable(3)
		}
	    ACCESS  read-write
	    STATUS  mandatory
	    DESCRIPTION
		"Provide the ability to set the type of source routing
		 broadcasts between AllRoutesExplorer(0) and 
		SpanningTreeExplorer(1)."
	    ::= { vIPXRouterEntry 8 }


	--  the VLAN Transparent Bridging group
	--  Implementation of this group is mandatory for Xylan's products

	vBrdgTpLearnEntryDiscards  OBJECT-TYPE
	    SYNTAX  Counter
	    ACCESS  read-only
	    STATUS  mandatory
	    DESCRIPTION
		"The total number of Forwarding Database entries,
		 which have been or would have been learnt, but
		 have been discarded due to a lack of space to
		 store them in the Forwarding Database.  If this
		 counter is increasing, it indicates that the
		 Forwarding Database is regularly becoming full (a
		 condition which has unpleasant performance effects
		 on the subnetwork).  If this counter has a
		 significant value but is not presently increasing,
		 it indicates that the problem has been occurring
		 but is not persistent."
	    ::= {vBrdgInfo 1 }

	vBrdgTpAgingTime  OBJECT-TYPE
	    SYNTAX  INTEGER (10..1000000)
	    ACCESS  read-write
	    STATUS  mandatory
	    DESCRIPTION
		"The timeout period in seconds for aging out
		 dynamically learned forwarding information.
		 802.1D-1990 recommends a default of 300 seconds."
	    ::= {vBrdgInfo 2 }


	--  The Forwarding Database for Transparent VLAN Bridges

	vBrdgTpFdbTable OBJECT-TYPE
	    SYNTAX  SEQUENCE OF VBrdgTpFdbEntry
	    ACCESS  not-accessible
	    STATUS  mandatory
	    DESCRIPTION
		"A table that contains information about unicast
		 entries for which the bridge has forwarding and/or
		 filtering information.  This information is used
		 by the transparent bridging function within its VLAN
		 in determining how to propagate a received frame."
	    ::= { vBrdgInfo 3 }

	vBrdgTpFdbEntry OBJECT-TYPE
	    SYNTAX  VBrdgTpFdbEntry
	    ACCESS  not-accessible
	    STATUS  mandatory
	    DESCRIPTION
		"Information about a specific unicast MAC address
		 for which the VLAN bridge has some forwarding and/or
		 filtering information."
	    INDEX   { vBrdgTpFdbGroupId, vBrdgTpFdbAddress }
	    ::= { vBrdgTpFdbTable 1 }

	VBrdgTpFdbEntry ::=
	    SEQUENCE {
        vBrdgTpFdbGroupId
            INTEGER,
		vBrdgTpFdbAddress
		    MacAddress,
		vBrdgTpFdbRcvPortSlot
		    INTEGER,
		vBrdgTpFdbRcvPortIF
		    INTEGER,
		vBrdgTpFdbRcvPortFuncTyp
		    XylanPortFuncCodes,
		vBrdgTpFdbRcvPortFuncTypInst
		    INTEGER,
		vBrdgTpFdbRcvStatus
		    INTEGER,
		vBrdgTpFdbRcvVLANMembership
			INTEGER,
		vBrdgTpFdbDupStatus
		    INTEGER,
		vBrdgTpFdbLastSeenTime
		    Counter
		}

	vBrdgTpFdbGroupId OBJECT-TYPE
	    SYNTAX  INTEGER
	    ACCESS  read-only
	    STATUS  mandatory
	    DESCRIPTION
        "The GroupId for this bridge."
	    ::= { vBrdgTpFdbEntry 1 }

	vBrdgTpFdbAddress OBJECT-TYPE
	    SYNTAX  MacAddress
	    ACCESS  read-only
	    STATUS  mandatory
	    DESCRIPTION
		"A unicast MAC address for which the VLAN bridge has
		 forwarding and/or filtering information."
	    ::= { vBrdgTpFdbEntry 2 }

	vBrdgTpFdbRcvPortSlot OBJECT-TYPE
	    SYNTAX  INTEGER
	    ACCESS  read-only
	    STATUS  mandatory
	    DESCRIPTION
		"The slot number of the port that vBrdgTpFdbAddress is
		 received."
	    ::= { vBrdgTpFdbEntry 3 } 

	vBrdgTpFdbRcvPortIF OBJECT-TYPE
	    SYNTAX  INTEGER
	    ACCESS  read-only
	    STATUS  mandatory
	    DESCRIPTION
		"The on-board interface number of the port that
		 vBrdgTpFdbAddress is received."
	    ::= { vBrdgTpFdbEntry 4 } 

	vBrdgTpFdbRcvPortFuncTyp OBJECT-TYPE
	    SYNTAX  XylanPortFuncCodes
	    ACCESS  read-only
	    STATUS  mandatory
	    DESCRIPTION
		"The service type of the port that vBrdgTpFdbAddress
		 is received."
	    ::= { vBrdgTpFdbEntry 5 } 

	vBrdgTpFdbRcvPortFuncTypInst OBJECT-TYPE
	    SYNTAX  INTEGER
	    ACCESS  read-only
	    STATUS  mandatory
	    DESCRIPTION
		"The service type instance of the port that
		 vBrdgTpFdbAddress is received."
	    ::= { vBrdgTpFdbEntry 6 } 

	vBrdgTpFdbRcvStatus OBJECT-TYPE
	    SYNTAX  INTEGER {
			other(1),
			invalid(2),
			learned(3),
			self(4),
			mgmt(5)
			}
	    ACCESS  read-only
	    STATUS  mandatory
	    DESCRIPTION
		"The status of this entry.  Xylan does not support
		 other(1) and self(4).  The meanings of the
		 values are:
			invalid(2)	: this entry is no longer valid,
					  but has not yet been flushed
					  from the table.

			learned(3)	: this entry has been learned.

			mgmt(5)		: this entry is configured as a
					  static entry."

	    ::= { vBrdgTpFdbEntry 7 }

	vBrdgTpFdbRcvVLANMembership  OBJECT-TYPE
        SYNTAX  INTEGER
        ACCESS  read-only
        STATUS  mandatory
        DESCRIPTION
            "The Auto-Tracker VLAN membership for this device. Each bit
             that is set in this objects 32 bit value indicates that the
             device is part of the VLAN given by that bits position."
        ::= { vBrdgTpFdbEntry 8 }

	vBrdgTpFdbDupStatus OBJECT-TYPE
	    SYNTAX  INTEGER
	    ACCESS  read-only
	    STATUS  mandatory
	    DESCRIPTION
		"The variable indicates if vBrdgTpFdbAddress is a duplicate
		 Mac."
	    ::= { vBrdgTpFdbEntry 9 } 

	vBrdgTpFdbLastSeenTime OBJECT-TYPE
	    SYNTAX   Counter
	    ACCESS   read-only
            STATUS   mandatory
            DESCRIPTION
		"The time since, the specific unicast MAC address
	         for which the VLAN bridge has forwarding information
		 was last seen."
	    ::= { vBrdgTpFdbEntry 10 }

	
	--  The Static Database for Transparent VLAN Bridges.
	--  Unlike the Static address filtering in 802.1D,
	--  this group only allows the user to configure whether a
	--  MAC address should stay permanent in the database.
	--  If port information is set, will allow the MAC address
	--  to be set for that port and avoid flooding of that MAC.

	vBrdgStaticTable OBJECT-TYPE
	    SYNTAX  SEQUENCE OF VBrdgStaticEntry
	    ACCESS  not-accessible
	    STATUS  mandatory
	    DESCRIPTION
		"A table contains source addresses which can be
		 configured to stay permanent (not aging out) in
		 the Forwarding table."
	    ::= { vBrdgInfo 4 }

	vBrdgStaticEntry OBJECT-TYPE
	    SYNTAX  VBrdgStaticEntry
	    ACCESS  not-accessible
	    STATUS  mandatory
	    DESCRIPTION
		"Information about a specific unicast MAC address
		 for which the VLAN bridge has VLAN information."
	    INDEX   { vBrdgStaticAddress }
	    ::= { vBrdgStaticTable 1 }

	VBrdgStaticEntry ::=
	    SEQUENCE {
		vBrdgStaticAddress
		    MacAddress,
		vBrdgStaticPortSlot
		    INTEGER,
		vBrdgStaticPortIF
		    INTEGER,
		vBrdgStaticPortFuncTyp
		    XylanPortFuncCodes,
		vBrdgStaticPortFuncTypInst
		    INTEGER,
		vBrdgStaticStatus
		    INTEGER
		}

	vBrdgStaticAddress OBJECT-TYPE
	    SYNTAX  MacAddress
	    ACCESS  read-write
	    STATUS  mandatory
	    DESCRIPTION
		"The MAC address which the static status applies."
	    ::= { vBrdgStaticEntry 1 }

	vBrdgStaticPortSlot OBJECT-TYPE
	    SYNTAX  INTEGER
	    ACCESS  read-write
	    STATUS  mandatory
	    DESCRIPTION
		"The slot number of the port that vBrdgStaticAddress
		 applies.  Entering this entry allows the MAC address
		 to set in this port.  If this entry is provided,
		 vBrdgStaticPortIF, vBrdgStaticPortFuncTyp and
		 vBrdgStaticPortFuncTypInst must also be set."
	    ::= { vBrdgStaticEntry 2 }

	vBrdgStaticPortIF OBJECT-TYPE
	    SYNTAX  INTEGER
	    ACCESS  read-write
	    STATUS  mandatory
	    DESCRIPTION
		"The on-board interface of the port that vBrdgStaticAddress
		 applies.  Entering this entry allows the MAC address
		 to set in this port.  If this entry is set,
		 vBrdgStaticPortSlot, vBrdgStaticPortFuncTyp and
		 vBrdgStaticPortFuncTypInst must also be set."
	    ::= { vBrdgStaticEntry 3 }

	vBrdgStaticPortFuncTyp OBJECT-TYPE
	    SYNTAX  XylanPortFuncCodes
	    ACCESS  read-write
	    STATUS  mandatory
	    DESCRIPTION
		"The service type of the port that vBrdgStaticAddress
		 applies.  Entering this entry allows the MAC address
		 to set in this port.  If this entry is set,
		 vBrdgStaticPortSlot, vBrdgStaticPortIF and
		 vBrdgStaticPortFuncTypInst must also be set."
	    ::= { vBrdgStaticEntry 4 }

	vBrdgStaticPortFuncTypInst OBJECT-TYPE
	    SYNTAX  INTEGER
	    ACCESS  read-write
	    STATUS  mandatory
	    DESCRIPTION
		"The service type instance of the port that
		 vBrdgStaticAddress applies.  Entering this entry
		 allows the MAC address to set in this port.  If this
		 entry is set, vBrdgStaticPortSlot, vBrdgStaticPortIF
		 and vBrdgStaticPortFuncTyp must also be set."
	    ::= { vBrdgStaticEntry 5 }

	vBrdgStaticStatus OBJECT-TYPE
	    SYNTAX  INTEGER {
			other(1),
			invalid(2),
			permanent(3),
			deleteOnReset(4),
			deleteOnTimeout(5)
			}
	    ACCESS  read-write
	    STATUS  mandatory
	    DESCRIPTION
		"This object indicates the status of this entry.
		 Xylan does not support other(1).
		 The default value is permenent(3).

			invalid(2) - writing this value to the
				     object removes the entry.
			permanent(3) - this entry will never age
				       out and remain even after
				       next reset.
			deleteOnReset(4) - this entry will not age
				 	   out until reset.
			deleteOnTimeout(5) - write this value to the
					     entry will cause it to
					     age out."
	    ::= { vBrdgStaticEntry 6 }


   vBrdgTpATVLANAgeingTime  OBJECT-TYPE
	    SYNTAX  INTEGER (10..1000000)
	    ACCESS  read-write
	    STATUS  mandatory
	    DESCRIPTION
		"The AutoTracker extended ageing timer. This value indicates
         how long the switch will remember the mac address and its
         associated vlan information. The default value is 1200 secs.
         This means that the mac information will be remembered for
         (vBrdgTpATVLANAgeingTime - vBrdgTpAgingTime) seconds after the 
	 mac is aged out.  This value must be set to a value greater than 
	 or equal to vBrdgTpAgingTime." 
	    ::= {vBrdgInfo 5 }


	--  the Spanning Tree group
	--  Large percentage of this group is lifted from rfc1493
	--  Implementation of this group is manatory for XyLan products.

	vStpProtocolSpecification OBJECT-TYPE
	    SYNTAX  INTEGER {
			unknown(1),
			decLb100(2),
			ieee8021d(3)
			}
	    ACCESS  read-only
	    STATUS  mandatory
	    DESCRIPTION
		"The version of the Spanning Tree Protocol implemented
		 for the Xylan products.  The IEE 802.1d implementation
		 is the only version supported.  If future versions of
		 the IEEE Spanning Tree Protocol are released that are
		 incompatible with the current version a new value
		 will be defined."
	    ::= { vStpInfo 1 }

	vStpPriority OBJECT-TYPE
	    SYNTAX  INTEGER (0..65535)
	    ACCESS  read-write
	    STATUS  mandatory
	    DESCRIPTION
		"The value of the write-able portion of the Bridge
		 ID, i.e., the first two octets of the (8 octet
		 long) Bridge ID.  The other (last) 6 octets of the
		 Bridge ID are given by the value of vLanBridgeAddress."
	    ::= { vStpInfo 2 }

	vStpBridgeAddress OBJECT-TYPE
	    SYNTAX  BridgeId
	    ACCESS  read-only
	    STATUS  mandatory
	    DESCRIPTION
		"The bridge identifier of this VLAN of the spanning
		 tree as determined by the Spanning Tree Protocol
		 as executed by this VLAN."
	    ::= { vStpInfo 3 }


	vStpTimeSinceTopologyChange OBJECT-TYPE
	    SYNTAX  TimeTicks
	    ACCESS  read-only
	    STATUS  mandatory
	    DESCRIPTION
		"The time (in hundredths of a second) since the
		 last time a topology change was detected by the
		 VLAN bridge entity."
	    ::= { vStpInfo 4 }

	vStpTopChanges OBJECT-TYPE
	    SYNTAX  Counter
	    ACCESS  read-only
	    STATUS  mandatory
	    DESCRIPTION
		"The total number of topology changes detected by
		 this VLAN bridge since the management entity was last
		 reset or initialized."
	    ::= { vStpInfo 5 }

	vStpDesignatedRoot OBJECT-TYPE
	    SYNTAX  BridgeId
	    ACCESS  read-only
	    STATUS  mandatory
	    DESCRIPTION
		"The bridge identifier of the root of the spanning
		 tree as determined by the Spanning Tree Protocol
		 as executed by this VLAN.  This value is used as
		 the Root Identifier parameter in all Configuration
		 Bridge PDUs originated by this node."
	    ::= { vStpInfo 6 }

	vStpRootCost OBJECT-TYPE
	    SYNTAX  INTEGER
	    ACCESS  read-only
	    STATUS  mandatory
	    DESCRIPTION
		"The cost of the path to the root as seen from
		 this VLAN bridge."
	    ::= { vStpInfo 7 }

	vStpRootPortSlot OBJECT-TYPE
	    SYNTAX  INTEGER
	    ACCESS  read-only
	    STATUS  mandatory
	    DESCRIPTION
		"The slot number of the port which offers the
		 lowest cost path from this VLAN bridge to the root
		 bridge."
	    ::= { vStpInfo 8 }

	vStpRootPortIF OBJECT-TYPE
	    SYNTAX  INTEGER
	    ACCESS  read-only
	    STATUS  mandatory
	    DESCRIPTION
		"The on-board interface of the port which offers the
		 lowest cost path from this VLAN bridge to the root
		 bridge."
	    ::= { vStpInfo 9 }

	vStpRootPortFuncTyp OBJECT-TYPE
	    SYNTAX  XylanPortFuncCodes
	    ACCESS  read-only
	    STATUS  mandatory
	    DESCRIPTION
		"The service type of the port which offers the
		 lowest cost path from this VLAN bridge to the root
		 bridge."
	    ::= { vStpInfo 10 }

	vStpRootPortFuncTypInst OBJECT-TYPE
	    SYNTAX  INTEGER
	    ACCESS  read-only
	    STATUS  mandatory
	    DESCRIPTION
		"The service type instance of the port which offers the
		 lowest cost path from this VLAN bridge to the root
		 bridge."
	    ::= { vStpInfo 11 }

	vStpMaxAge OBJECT-TYPE
	    SYNTAX  Timeout
	    ACCESS  read-only
	    STATUS  mandatory
	    DESCRIPTION
		"The maximum age of Spanning Tree Protocol
		 information learned from the network on any port
		 before it is discarded, in units of hundredths of
		 a second.  This is the actual value that this
		 bridge is currently using."
	    ::= { vStpInfo 12 }

	vStpHelloTime OBJECT-TYPE
	    SYNTAX  Timeout
	    ACCESS  read-only
	    STATUS  mandatory
	    DESCRIPTION
		"The amount of time between the transmission of
		 Configuration bridge PDUs by this VLAN on any port
		 when it is the root of the spanning tree or trying
		 to become so, in units of hundredths of a second.
		 This is the actual value that this VLAN is
		 currently using."
	    ::= { vStpInfo 13 }

	vStpHoldTime OBJECT-TYPE
	    SYNTAX  INTEGER
	    ACCESS  read-only
	    STATUS  mandatory
	    DESCRIPTION
		"This time value determines the interval length
		 during which no more than two Configuration bridge
		 PDUs shall be transmitted by this VLAN, in units
		 of hundredths of a second."
	    ::= { vStpInfo 14 }

	vStpForwardDelay OBJECT-TYPE
	    SYNTAX  INTEGER
	    ACCESS  read-only
	    STATUS  mandatory
	    DESCRIPTION
		"This time value, measured in units of hundredths
		 of a second, controls how fast a port changes its
		 spanning state when moving towards the Forwarding
		 state.  The value determines how long the port
		 stays in each of the Listening and Learning
		 states, which precede the Forwarding state.  This
		 value is also used, when a topology change has
		 been detected and is underway, to age all dynamic
		 entries in the Forwarding Database.  [Note that
		 this value is the one that this bridge is
		 currently using, in contrast to
		 vStpBridgeForwardDelay which is the value that
		 this VLAN and all others would start using
		 if/when this bridge were to become the root.]"
	    ::= { vStpInfo 15 }

	vStpBridgeMaxAge OBJECT-TYPE
	    SYNTAX  Timeout (600..4000)
	    ACCESS  read-write
	    STATUS  mandatory
	    DESCRIPTION
		"The value that all bridges use for MaxAge when
		 this VLAN is acting as the root.  Note that
		 802.1D-1990 specifies that the range for this
		 parameter is related to the value of
		 vStpBridgeHelloTime. The granularity of this
		 timer is specified by 802.1D-1990 to be 1 second.
		 An agent may return a badValue error if a set is
		 attempted to a value which is not a whole number
		 of seconds."
	    ::= { vStpInfo 16 }

	vStpBridgeHelloTime OBJECT-TYPE
	    SYNTAX  Timeout (100..1000)
	    ACCESS  read-write
	    STATUS  mandatory
	    DESCRIPTION
		"The value that all VLANs use for HelloTime when
		 this bridge is acting as the root.  The
		 granularity of this timer is specified by 802.1D-
		 1990 to be 1 second.  An agent may return a
		 badValue error if a set is attempted to a value
		 which is not a whole number of seconds."
	    ::= { vStpInfo 17 }

	vStpBridgeForwardDelay OBJECT-TYPE
	    SYNTAX  Timeout (400..3000)
	    ACCESS  read-write
	    STATUS  mandatory
	    DESCRIPTION
		"The value that all VLANs use for ForwardDelay
		 when this VLAN is acting as the root.  Note that
		 802.1D-1990 specifies that the range for this
		 parameter is related to the value of
		 vStpBridgeMaxAge.  The granularity of this
		 timer is specified by 802.1D-1990 to be 1 second.
		 An agent may return a badValue error if a set is
		 attempted to a value which is not a whole number
		 of seconds."
	    ::= { vStpInfo 18 }

	--  The Spanning Tree Port Table for Xylan's VLAN implementation

	vStpPortTable OBJECT-TYPE
	    SYNTAX  SEQUENCE OF VStpPortEntry
	    ACCESS  not-accessible
	    STATUS  mandatory
	    DESCRIPTION
		"A table that contains port-specific information
		 for the Spanning Tree Protocol."
	    ::= { vStpInfo 19 }

	vStpPortEntry OBJECT-TYPE
	    SYNTAX  VStpPortEntry
	    ACCESS  not-accessible
	    STATUS  mandatory
	    DESCRIPTION
		"A list of information maintained by every port
		 about the Spanning Tree Protocol state for that port."
	    INDEX   { vStpPortSlot, vStpPortIF, vStpPortFuncTyp,
		      vStpPortFuncTypInst }
	    ::= { vStpPortTable 1 }

	VStpPortEntry ::=
	    SEQUENCE {
		vStpPortSlot
		    INTEGER,
		vStpPortIF
		    INTEGER,
		vStpPortFuncTyp
		    INTEGER,
		vStpPortFuncTypInst
		    INTEGER,
		vStpPortPriority
		    INTEGER,
		vStpPortState
		    INTEGER,
		vStpPortEnable
		    INTEGER,
		vStpPortPathCost
		    INTEGER,
		vStpPortDesignatedRoot
		    BridgeId,
		vStpPortDesignatedCost
		    INTEGER,
		vStpPortDesignatedBridge
		    BridgeId,
		vStpPortDesignatedPtPrio
		    INTEGER,
		vStpPortDesignatedPtSlot
		    INTEGER,
		vStpPortDesignatedPtIF
		    INTEGER,
		vStpPortDesignatedPtFuncTyp
		    XylanPortFuncCodes,
		vStpPortDesignatedPtFuncTypInst
		    INTEGER,
		vStpPortForwardTransitions
		    INTEGER
	    }

	vStpPortSlot OBJECT-TYPE
	    SYNTAX  INTEGER
	    ACCESS  read-only
	    STATUS  mandatory
	    DESCRIPTION
		"The slot number of the port for which this entry
		 contains Spanning Tree Protocol management
		 information."
	    ::= { vStpPortEntry 1 }

	vStpPortIF OBJECT-TYPE
	    SYNTAX  INTEGER
	    ACCESS  read-only
	    STATUS  mandatory
	    DESCRIPTION
		"The on-board interface number of the port for which
		 this entry contains Spanning Tree Protocol management
		 information."
	    ::= { vStpPortEntry 2 }

	vStpPortFuncTyp OBJECT-TYPE
	    SYNTAX  INTEGER
	    ACCESS  read-only
	    STATUS  mandatory
	    DESCRIPTION
		"The service type of the port for which this entry
		 contains Spanning Tree Protocol management
		 information."
	    ::= { vStpPortEntry 3 }

	vStpPortFuncTypInst OBJECT-TYPE
	    SYNTAX  INTEGER
	    ACCESS  read-only
	    STATUS  mandatory
	    DESCRIPTION
		"The service type instance of the port for which this
		 entry contains Spanning Tree Protocol management
		 information."
	    ::= { vStpPortEntry 4 }

	vStpPortPriority OBJECT-TYPE
	    SYNTAX  INTEGER
	    ACCESS  read-write
	    STATUS  mandatory
	    DESCRIPTION
		"The priority of this port which used originally as
		 part of the port ID specified in 802.1D."
	    ::= { vStpPortEntry 5 }

	vStpPortState OBJECT-TYPE
	    SYNTAX  INTEGER {
			disabled(1),
			blocking(2),
			listening(3),
			learning(4),
			forwarding(5)
			}
	    ACCESS  read-only
	    STATUS  mandatory
	    DESCRIPTION
		"The port's current state as defined by
		 application of the Spanning Tree Protocol.  This
		 state controls what action a port takes on
		 reception of a frame.  For ports which are disabled
		 (see vStpPortEnable), this object will have a value
                 of disabled(1).  Xylan does not support the broken(6)
		 state as defined in RFC1493."
	    ::= { vStpPortEntry 6 }

	vStpPortEnable OBJECT-TYPE
	    SYNTAX  INTEGER {
			enabled(1),
			disabled(2)
			}
	    ACCESS  read-write
	    STATUS  mandatory
	    DESCRIPTION
		"The enabled/disabled status of the port."
	    ::= { vStpPortEntry 7 }

	vStpPortPathCost OBJECT-TYPE
	    SYNTAX  INTEGER (1..65535)
	    ACCESS  read-write
	    STATUS  mandatory
	    DESCRIPTION
		"The contribution of this port to the path cost of
		 paths towards the spanning tree root which include
		 this port.  802.1D-1990 recommends that the
		 default value of this parameter be in inverse
		 proportion to the speed of the attached LAN."
	    ::= { vStpPortEntry 8 }

	vStpPortDesignatedRoot OBJECT-TYPE
	    SYNTAX  BridgeId
	    ACCESS  read-only
	    STATUS  mandatory
	    DESCRIPTION
		"The unique Bridge Identifier of the Bridge
		 recorded as the Root in the Configuration BPDUs
		 transmitted by the Designated Bridge for the
		 segment to which the port is attached."
	    ::= { vStpPortEntry 9 }

	vStpPortDesignatedCost OBJECT-TYPE
	    SYNTAX  INTEGER
	    ACCESS  read-only
	    STATUS  mandatory
	    DESCRIPTION
		"The path cost of the Designated Port of the
		 segment connected to this port.  This value is
		 compared to the Root Path Cost field in received
		 bridge PDUs."
	    ::= { vStpPortEntry 10 }

	vStpPortDesignatedBridge OBJECT-TYPE
	    SYNTAX  BridgeId
	    ACCESS  read-only
	    STATUS  mandatory
	    DESCRIPTION
		"The Bridge Identifier of the bridge which this
		 port considers to be the Designated Bridge for
		 this port's segment."
	    ::= { vStpPortEntry 11 }

	vStpPortDesignatedPtPrio OBJECT-TYPE
	    SYNTAX  INTEGER
	    ACCESS  read-only
	    STATUS  mandatory
	    DESCRIPTION
		"The priority portion of the port ID on the Designated
		 Bridge for this port's segment."
	    ::= { vStpPortEntry 12 }

	vStpPortDesignatedPtSlot OBJECT-TYPE
	    SYNTAX  INTEGER
	    ACCESS  read-only
	    STATUS  mandatory
	    DESCRIPTION
		"The slot of the port on the Designated
		 Bridge for this port's segment."
	    ::= { vStpPortEntry 13 }

	vStpPortDesignatedPtIF OBJECT-TYPE
	    SYNTAX  INTEGER
	    ACCESS  read-only
	    STATUS  mandatory
	    DESCRIPTION
		"The on-board interface number of the port on the
		 Designated Bridge for this port's segment."
	    ::= { vStpPortEntry 14 }

	vStpPortDesignatedPtFuncTyp OBJECT-TYPE
	    SYNTAX  XylanPortFuncCodes
	    ACCESS  read-only
	    STATUS  mandatory
	    DESCRIPTION
		"The service type of the port on the Designated
		 Bridge for this port's segment."
	    ::= { vStpPortEntry 15 }

	vStpPortDesignatedPtFuncTypInst OBJECT-TYPE
	    SYNTAX  INTEGER
	    ACCESS  read-only
	    STATUS  mandatory
	    DESCRIPTION
		"The service type instance of the port on the Designated
		 Bridge for this port's segment."
	    ::= { vStpPortEntry 16 }

	vStpPortForwardTransitions OBJECT-TYPE
	    SYNTAX  INTEGER
	    ACCESS  read-only
	    STATUS  mandatory
	    DESCRIPTION
		"The number of times this port has transitioned
		 from the Learning state to the Forwarding state."
	    ::= { vStpPortEntry 17 }

        vStpLanMode  OBJECT-TYPE
            SYNTAX  INTEGER {
                ieee-stap(1),
                ibm-stap(2)
            }   
            ACCESS  read-write
            STATUS  mandatory
            DESCRIPTION
                "Indicates which type of spanning tree (IEEE or IBM)
                 is to be used for the current VLAN."
	    ::= { vStpInfo 20 }

        vStpStatus  OBJECT-TYPE
            SYNTAX  XylanVlanOperStatCodes
            ACCESS  read-write
            STATUS  mandatory
            DESCRIPTION
                "Indicates status of spanning tree for the current VLAN."
	    ::= { vStpInfo 21 }

        vRipInfoTable  OBJECT-TYPE
            SYNTAX  SEQUENCE OF VRipInfoEntry
            ACCESS  not-accessible
            STATUS  mandatory
            DESCRIPTION
                 "A list of Virtual LAN instances for RIP statistics."
            ::= { vRipInfo 1 }
            
        vRipInfoEntry  OBJECT-TYPE
            SYNTAX  VRipInfoEntry
            ACCESS  not-accessible
            STATUS  mandatory
            DESCRIPTION
                 "A VLAN entry for RIP statistics."
            INDEX { vRipInfovLanNumber }
            ::= { vRipInfoTable 1 }
 
        VRipInfoEntry ::= SEQUENCE {
            vRipInfovLanNumber
                INTEGER,
            vRipInPkts
                Counter,
            vRipOutPkts
                Counter,
            vRipBadSize
                Counter,
            vRipBadVersion
                Counter,
            vRipNonZero
                Counter,
            vRipBadFamily
                Counter,
            vRipBadMetric
                Counter,
            vRipBadAddr
                Counter,
            vRipBadCommand
                Counter,
            vRipTransmitsFailed
                Counter
            }
          
        vRipInfovLanNumber  OBJECT-TYPE
            SYNTAX  INTEGER (1..65535)
            ACCESS  read-only
            STATUS  mandatory
            DESCRIPTION
                 "The VLAN number identifying this instance. Valid
                  range from 1 to 65535."
            ::= { vRipInfoEntry 1 }

        vRipInPkts  OBJECT-TYPE
            SYNTAX  Counter
            ACCESS  read-only
            STATUS  mandatory
            DESCRIPTION
                 "The number of RIP routing updates and requests received
                  on this virtual LAN."
            ::= { vRipInfoEntry 2 }

        vRipOutPkts  OBJECT-TYPE
            SYNTAX  Counter
            ACCESS  read-only
            STATUS  mandatory
            DESCRIPTION
                 "The number of RIP routing updates and requests sent on
                  this virtual LAN."
            ::= { vRipInfoEntry 3 }
 
        vRipBadSize  OBJECT-TYPE
            SYNTAX  Counter
            ACCESS  read-only
            STATUS  mandatory
            DESCRIPTION
                 "The number of RIP packets received on this virtual LAN
                  whose size was incorrect."
            ::= { vRipInfoEntry 4 }
 
        vRipBadVersion  OBJECT-TYPE
            SYNTAX  Counter
            ACCESS  read-only
            STATUS  mandatory
            DESCRIPTION
                 "The number of RIP packets received on this virtual LAN
                  whose version number was incorrect."
            ::= { vRipInfoEntry 5 }

        vRipNonZero  OBJECT-TYPE
            SYNTAX  Counter
            ACCESS  read-only
            STATUS  mandatory
            DESCRIPTION
                 "The number of RIP packets received on this virtual LAN
                  which contained a non-zero value in one of the 'must be
                  zero' fields."
            ::= { vRipInfoEntry 6 }
 
        vRipBadFamily  OBJECT-TYPE
            SYNTAX  Counter
            ACCESS  read-only
            STATUS  mandatory
            DESCRIPTION
                 "The number of RIP packets received on this virtual LAN
                  which contained a bad value for the family type."
            ::= { vRipInfoEntry 7 }
 
        vRipBadMetric  OBJECT-TYPE
            SYNTAX  Counter
            ACCESS  read-only
            STATUS  mandatory
            DESCRIPTION
                 "The number of RIP packets received on this virtual LAN
                  which contained a bad value for a route's metric."
            ::= { vRipInfoEntry 8 }

        vRipBadAddr  OBJECT-TYPE
            SYNTAX  Counter
            ACCESS  read-only
            STATUS  mandatory
            DESCRIPTION
                 "The number of RIP packets received on this virtual LAN
                  whose host portion of the source IP address is bad."
            ::= { vRipInfoEntry 9 }
 
        vRipBadCommand  OBJECT-TYPE
            SYNTAX  Counter
            ACCESS  read-only
            STATUS  mandatory
            DESCRIPTION
                 "The number of RIP packets received on this virtual LAN
                  whose command type was neither a request nor a response."
            ::= { vRipInfoEntry 10 }
 
        vRipTransmitsFailed  OBJECT-TYPE
            SYNTAX  Counter
            ACCESS  read-only
            STATUS  mandatory
            DESCRIPTION
                 "The number of RIP routing updaates or requests that the
                  OmniSwitch was unable to transmit."
            ::= { vRipInfoEntry 13 }
 

          -- the vSr group

          vSrTable OBJECT-TYPE
              SYNTAX  SEQUENCE OF VSrPortEntry
              ACCESS  not-accessible
              STATUS  mandatory
              DESCRIPTION
                      "A table that contains information about every
                      virtual port that is associated with this source route
                      switch."
              ::= { vSr 1 }
              
          vSrSapFilterEnable OBJECT-TYPE -- sapfilter support
              SYNTAX INTEGER {
                  on  (1),
                  off (2),
                  turnOffAndClearAll (3)
              }
              ACCESS  read-write
              STATUS  mandatory
              DESCRIPTION
                  "A scalar value to enable or disable the SAP filtering
                  feature in this source route switch."
              ::= { vSr 2 }

          vSrPortEntry OBJECT-TYPE
              SYNTAX  VSrPortEntry
              ACCESS  not-accessible
              STATUS  mandatory
              DESCRIPTION
                      "A list of information for each virtual port of a source
                      route switch."
              INDEX { vSrSlot, vSrInterface, vSrFuncType, vSrInstance }
              ::= { vSrTable 1 }

          VSrPortEntry ::=
              SEQUENCE {
                  vSrSlot
                      INTEGER,
                  vSrInterface
                      INTEGER,
                  vSrFuncType
                      INTEGER,
                  vSrInstance
                      INTEGER,
                  vSrHopCount
                      INTEGER,
                  vSrLocalSegment
                      INTEGER,
                  vSrBridgeNum
                      INTEGER,
                  vSrVirtualRing 
                      INTEGER,
                  vSrLargestFrame
                      INTEGER,
                  vSrSTESpanMode
                      INTEGER,
                  vSrSpecInFrames
                      Counter,
                  vSrSpecOutFrames
                      Counter,
                  vSrApeInFrames
                      Counter,
                  vSrApeOutFrames
                      Counter,
                  vSrSteInFrames
                      Counter,
                  vSrSteOutFrames
                      Counter,
                  vSrInvalidRif 
                      Counter,
                  vSrDuplicateSegmentDiscards
                      Counter,
                  vSrHopCountExceededDiscards
                      Counter,
                  vSrDupLanIdOrTreeErrors
                      Counter,
                  vSrLanIdMismatches
                      Counter,
                  vSrBridgeLfMode
                      INTEGER,
                  vSrPortType
                      INTEGER,
                  vSrAREblock
                      INTEGER,
                  vSrHopCountIn
                      INTEGER,

                  -- sapfilter support
                  vSrSapDenyFilter1 
                      INTEGER, --OCTET STRING,
                  vSrSapDenyFilter2
                      INTEGER, --OCTET STRING,
                  vSrSapPermitFilter1
                      INTEGER, --OCTET STRING,
                  vSrSapPermitFilter2
                      INTEGER --OCTET STRING,
              }

          vSrSlot OBJECT-TYPE
              SYNTAX  INTEGER (1..9)
              ACCESS  read-only
              STATUS  mandatory
              DESCRIPTION
                      "The physical slot number of the port for which this entry
                      contains Source Route management information."
              ::= { vSrPortEntry 1 }

          vSrInterface OBJECT-TYPE
              SYNTAX  INTEGER (1..32)
              ACCESS  read-only
              STATUS  mandatory
              DESCRIPTION
                      "The on-board interface number of the port for which 
                       this entry contains Source Route management information."
              ::= { vSrPortEntry 2 }

          vSrFuncType OBJECT-TYPE
              SYNTAX  INTEGER (1..9)
              ACCESS  read-only
              STATUS  mandatory
              DESCRIPTION
                      "The service type of the port for which this entry
                      contains Source Route management information."
              ::= { vSrPortEntry 3 }

          vSrInstance OBJECT-TYPE
              SYNTAX  INTEGER (1..254)
              ACCESS  read-only
              STATUS  mandatory
              DESCRIPTION
                      " The service type instance of the port for which this
                       entry contains Source Route management information."
              ::= { vSrPortEntry 4 }

          vSrHopCount OBJECT-TYPE
              SYNTAX  INTEGER
              ACCESS  read-write
              STATUS  mandatory
              DESCRIPTION
                      "The maximum number of routing descriptors allowed
                      in an All Paths or Spanning Tree Explorer frames."
              ::= { vSrPortEntry 5 }

          vSrLocalSegment OBJECT-TYPE
              SYNTAX  INTEGER
              ACCESS  read-write
              STATUS  mandatory
              DESCRIPTION
                      "The segment number that uniquely identifies the
                      segment to which this virtual port is connected. Current
                      source routing protocols limit this value to the
                      range: 0 through 4095. (The value 0 is used by
                      some management applications for special test
                      cases.) A value of 65535 signifies that no segment
                      number is assigned to this virtual port."
              ::= { vSrPortEntry 6 }

          vSrBridgeNum OBJECT-TYPE
              SYNTAX  INTEGER
              ACCESS  read-write
              STATUS  mandatory
              DESCRIPTION
                      "A bridge number uniquely identifies a bridge when
                      more than one bridge is used to span the same two
                      segments.  Current source routing protocols limit
                      this value to the range: 0 through 15. A value of
                      65535 signifies that no bridge number is assigned
                      to this bridge."
              ::= { vSrPortEntry 7 }

         vSrVirtualRing OBJECT-TYPE
              SYNTAX  INTEGER
              ACCESS  read-write
              STATUS  mandatory
              DESCRIPTION
                      "This is to indicate whether the ring that this
                       virtual port is connected to is virtual or physical
                            1 = virtual
                            2 = physical."
              ::= { vSrPortEntry 8 }

          -- It would be nice if we could use ifMtu as the size of the
          -- largest frame, but we can't because ifMtu is defined to be
          -- the size that the (inter-)network layer can use which can
          -- differ from the MAC layer (especially if several layers of
          -- encapsulation are used).

          vSrLargestFrame OBJECT-TYPE
              SYNTAX  INTEGER
              ACCESS  read-write
              STATUS  mandatory
              DESCRIPTION
                      "The maximum size of the INFO field (LLC and
                      above) that this virtual port can send/receive.  It does
                      not include any MAC level (framing) octets.  The
                      value of this object is used by this bridge to
                      determine whether a modification of the
                      LargestFrame (LF, see [14]) field of the Routing
                      Control field of the Routing Information Field is
                      necessary.

                      64 valid values are defined by the IEEE 802.5M SRT
                      Addendum: 516, 635, 754, 873, 993, 1112, 1231,
                      1350, 1470, 1542, 1615, 1688, 1761, 1833, 1906,
                      1979, 2052, 2345, 2638, 2932, 3225, 3518, 3812,
                      4105, 4399, 4865, 5331, 5798, 6264, 6730, 7197,
                      7663, 8130, 8539, 8949, 9358, 9768, 10178, 10587,
                      10997, 11407, 12199, 12992, 13785, 14578, 15370,
                      16163, 16956, 17749, 20730, 23711, 26693, 29674,
                      32655, 35637, 38618, 41600, 44591, 47583, 50575,
                      53567, 56559, 59551, and 65535.

                      An illegal value will not be accepted by the
                      bridge."
              ::= { vSrPortEntry 9 }

          vSrSTESpanMode OBJECT-TYPE
              SYNTAX  INTEGER {
                          auto-span(1),
                          disabled(2),
                          forced(3)
                      }
              ACCESS  read-write
              STATUS  mandatory
              DESCRIPTION
                      "Determines how this virtual port behaves when presented
                      with a Spanning Tree Explorer frame.  The value
                      'disabled(2)' indicates that the virtual port will not
                      accept or send Spanning Tree Explorer packets; any
                      STE packets received will be silently discarded.
                      The value 'forced(3)' indicates the virtual port will
                      always accept and propagate Spanning Tree Explorer
                      frames.  This allows a manually configured
                      Spanning Tree for this class of packet to be
                      configured.  Note that unlike transparent
                      bridging, this is not catastrophic to the network
                      if there are loops.  The value 'auto-span(1)' can
                      only be returned by a bridge that both implements
                      the Spanning Tree Protocol and has use of the
                      protocol enabled on this virtual port. The behavior of the
                      virtual port for Spanning Tree Explorer frames is
                      determined by the state of vStpPortState.  If
                      the virtual port is in the 'forwarding' state, the frame
                      will be accepted or propagated.  Otherwise, it
                      will be silently discarded."
              ::= { vSrPortEntry 10 }

          vSrSpecInFrames OBJECT-TYPE
              SYNTAX  Counter
              ACCESS  read-only
              STATUS  mandatory
              DESCRIPTION
                      "The number of Specifically Routed frames, also
                      referred to as Source Routed Frames, that have
                      been received from this virtual port's segment."
              ::= { vSrPortEntry 11 }

          vSrSpecOutFrames OBJECT-TYPE
              SYNTAX  Counter
              ACCESS  read-only
              STATUS  mandatory
              DESCRIPTION
                      "The number of Specifically Routed frames, also
                      referred to as Source Routed Frames, that this
                      virtual port has transmitted on its segment."
              ::= { vSrPortEntry 12 }

          vSrApeInFrames OBJECT-TYPE
              SYNTAX  Counter
              ACCESS  read-only
              STATUS  mandatory
              DESCRIPTION
                      "The number of All Paths Explorer frames, also
                      referred to as All Routes Explorer frames, that
                      have been received by this virtual port from its segment."
              ::= { vSrPortEntry 13 }

          vSrApeOutFrames OBJECT-TYPE
              SYNTAX  Counter
              ACCESS  read-only
              STATUS  mandatory
              DESCRIPTION
                      "The number of all Paths Explorer Frames, also
                      referred to as All Routes Explorer frames, that
                      have been transmitted by this virtual port on its
                      segment."
              ::= { vSrPortEntry 14 }

          vSrSteInFrames OBJECT-TYPE
              SYNTAX  Counter
              ACCESS  read-only
              STATUS  mandatory
              DESCRIPTION
                      "The number of spanning tree explorer frames that
                      have been received by this virtual port from its segment."
              ::= { vSrPortEntry 15 }

          vSrSteOutFrames OBJECT-TYPE
              SYNTAX  Counter
              ACCESS  read-only
              STATUS  mandatory
              DESCRIPTION
                      "The number of spanning tree explorer frames that
                      have been transmitted by this virtual port on its
                      segment."
              ::= { vSrPortEntry 16 }

          vSrInvalidRif OBJECT-TYPE
              SYNTAX  Counter
              ACCESS  read-only
              STATUS  mandatory
              DESCRIPTION
                      "The number of explorer frames that have been
                      discarded by this virtual port because the routing
                      Information field contained an invalid value."
              ::= { vSrPortEntry 17 }

          vSrDuplicateSegmentDiscards OBJECT-TYPE
              SYNTAX  Counter
              ACCESS  read-only
              STATUS  mandatory
              DESCRIPTION
                      "The number of frames that have been discarded by
                      this virtual port because the routing descriptor field
                      contained a duplicate segment identifier."
              ::= { vSrPortEntry 18 }

          vSrHopCountExceededDiscards OBJECT-TYPE
              SYNTAX  Counter
              ACCESS  read-only
              STATUS  mandatory
              DESCRIPTION
                      "The number of explorer frames that have been
                      discarded by this virtual port because the Routing
                      Information Field has exceeded the maximum route
                      descriptor length."
              ::= { vSrPortEntry 19 }

          vSrDupLanIdOrTreeErrors OBJECT-TYPE
              SYNTAX  Counter
              ACCESS  read-only
              STATUS  mandatory
              DESCRIPTION
                      "The number of duplicate LAN IDs or Tree errors.
                      This helps in detection of problems in networks
                      containing older IBM Source Routing Bridges."
              ::= { vSrPortEntry 20 }

          vSrLanIdMismatches OBJECT-TYPE
              SYNTAX  Counter
              ACCESS  read-only
              STATUS  mandatory
              DESCRIPTION
                      "The number of ARE and STE frames that were
                      discarded because the last LAN ID in the routing
                      information field did not equal the LAN-in ID.
                      This error can occur in implementations which do
                      only a LAN-in ID and Bridge Number check instead
                      of a LAN-in ID, Bridge Number, and LAN-out ID
                      check before they forward broadcast frames."
              ::= { vSrPortEntry 21 }

          vSrBridgeLfMode OBJECT-TYPE
              SYNTAX  INTEGER {
                          mode3(1),
                          mode6(2)
                      }
              ACCESS  read-only
              STATUS  mandatory
              DESCRIPTION
                      "Indicates whether the bridge operates using older
                      3 bit length negotiation fields or the newer 6 bit
                      length field in its RIF."
              ::= { vSrPortEntry 22 }

          vSrPortType OBJECT-TYPE
              SYNTAX  INTEGER 
              ACCESS  read-write
              STATUS  mandatory
              DESCRIPTION
                      "Indicates whether this port is a SRT or SR only
                        SRT = 1
                        SR  = 2  "
              ::= { vSrPortEntry 23 }

          vSrAREblock OBJECT-TYPE
              SYNTAX  INTEGER 
              ACCESS  read-write
              STATUS  mandatory
              DESCRIPTION
                      "Indicates whether this port would treat ARE frames
                       exactly like STE frames which would be blocked if
                       the Spanning Tree mode is blocking.
                       1 - this port would not block ARE.
                       2 - this port would block ARE. "
              ::= { vSrPortEntry 24 }

          vSrHopCountIn OBJECT-TYPE
              SYNTAX  INTEGER
              ACCESS  read-write
              STATUS  mandatory
              DESCRIPTION
                      "The maximum number of routing descriptors allowed
                      in an inbound All Paths or Spanning Tree Explorer frames."
              ::= { vSrPortEntry 25 }

          vSrSapDenyFilter1 OBJECT-TYPE
              SYNTAX  INTEGER 
              ACCESS  read-write
              STATUS  mandatory
              DESCRIPTION
                      "Packets with this SAP value are to be discarded."
              ::= { vSrPortEntry 26 }
          vSrSapDenyFilter2 OBJECT-TYPE
              SYNTAX  INTEGER 
              ACCESS  read-write
              STATUS  mandatory
              DESCRIPTION
                      "Packets with this SAP value are to be discarded."
              ::= { vSrPortEntry 27 }
          vSrSapPermitFilter1 OBJECT-TYPE
              SYNTAX  INTEGER 
              ACCESS  read-write
              STATUS  mandatory
              DESCRIPTION
                      "Packets without this SAP value are to be discarded."
              ::= { vSrPortEntry 28 }
          vSrSapPermitFilter2 OBJECT-TYPE
              SYNTAX  INTEGER 
              ACCESS  read-write
              STATUS  mandatory
              DESCRIPTION
                      "Packets without this SAP value are to be discarded."
              ::= { vSrPortEntry 29 }

          -- the vTrunking group

        vTrunkingServicesTable  OBJECT-TYPE
            SYNTAX  SEQUENCE OF VTrunkingServicesEntry
            ACCESS  not-accessible
            STATUS  mandatory
            DESCRIPTION
                 "A list of commands to add or remove Virtual LANs from
                  a trunking service."
            ::= { vTrunking 1 }
 
        vTrunkingServicesEntry  OBJECT-TYPE
            SYNTAX  VTrunkingServicesEntry
            ACCESS  not-accessible
            STATUS  mandatory
            DESCRIPTION
                 "A trunking services entry."
            INDEX { vTrunkingServicesSlot, vTrunkingServicesStation }
            ::= { vTrunkingServicesTable 1 }
 
        VTrunkingServicesEntry ::= SEQUENCE {
            vTrunkingServicesSlot
                INTEGER,
            vTrunkingServicesStation
                INTEGER,
            vTrunkingServicesDescription
		DisplayString,
            vTrunkingServicesBridgeID
                INTEGER
            }
 
        vTrunkingServicesSlot OBJECT-TYPE
            SYNTAX  INTEGER
            ACCESS  read-only
            STATUS  mandatory
            DESCRIPTION
                 "The slot number (1-based) of the physical port providing
                  the trunking service."
            ::= { vTrunkingServicesEntry 1 }
 
        vTrunkingServicesStation OBJECT-TYPE
            SYNTAX  INTEGER
            ACCESS  read-only
            STATUS  mandatory
            DESCRIPTION
                 "The station number (1-based) within the physical port
                  providing the trunking service."
            ::= { vTrunkingServicesEntry 2 }
  
        vTrunkingServicesDescription OBJECT-TYPE
            SYNTAX  DisplayString 
            ACCESS  read-write
            STATUS  mandatory
            DESCRIPTION
                 "A description of the trunking service being provided."
            ::= { vTrunkingServicesEntry 3 }
 
        vTrunkingServicesBridgeID OBJECT-TYPE
            SYNTAX  INTEGER (0..65535)
            ACCESS  read-only
            STATUS  mandatory
            DESCRIPTION
                 "The VLAN ID of the Virtual Bridge port for the given
                  trunking service. A value of 0 means that the Virtual
                  Bridge port does not exist."
            ::= { vTrunkingServicesEntry 4 }
 
        vTrunkingVlanTable  OBJECT-TYPE
            SYNTAX  SEQUENCE OF VTrunkingVlanEntry
            ACCESS  not-accessible
            STATUS  mandatory
            DESCRIPTION
                 "A list of commands to add or remove Virtual LANs from
                  a trunking service."
            ::= { vTrunking 2 }

        vTrunkingVlanEntry  OBJECT-TYPE
            SYNTAX  VTrunkingVlanEntry
            ACCESS  not-accessible
            STATUS  mandatory
            DESCRIPTION
                 "A trunking Virtual LAN entry."
            INDEX { vTrunkingSlot, vTrunkingStation, vTrunkingLanNumber }
            ::= { vTrunkingVlanTable 1 }

        VTrunkingVlanEntry ::= SEQUENCE {
            vTrunkingSlot
                INTEGER,
            vTrunkingStation
                INTEGER,
            vTrunkingLanNumber
                INTEGER,
            vTrunkingCommand
                INTEGER
            }

	vTrunkingSlot OBJECT-TYPE
	    SYNTAX  INTEGER 
	    ACCESS  read-only
	    STATUS  mandatory
	    DESCRIPTION
		 "The slot number (1-based) of the physical port providing 
		  the trunking service."
	    ::= { vTrunkingVlanEntry 1 }

	vTrunkingStation OBJECT-TYPE
	    SYNTAX  INTEGER 
	    ACCESS  read-only
	    STATUS  mandatory
	    DESCRIPTION
		 "The station number (1-based) within the physical port
		  providing the trunking service."
	    ::= { vTrunkingVlanEntry 2 }

	vTrunkingLanNumber OBJECT-TYPE
	    SYNTAX  INTEGER (1..65535)
	    ACCESS  read-only
	    STATUS  mandatory
	    DESCRIPTION
		 "The VLAN ID to be added to or removed from the given
	          trunking service."
	    ::= { vTrunkingVlanEntry 3 }

	vTrunkingCommand OBJECT-TYPE
	    SYNTAX  INTEGER {
                        add(1),
                        remove(2)
            }
	    ACCESS  read-write
	    STATUS  mandatory
	    DESCRIPTION
		 "The command to either add or remove the specified VLAN ID
		  from the given trunking service."
	    ::= { vTrunkingVlanEntry 4 }

	-- Auto-Tracker Objects

	atportRuleTable OBJECT-TYPE
		SYNTAX		SEQUENCE OF AtportRuleEntry
		ACCESS		not-accessible
		STATUS		mandatory
		DESCRIPTION
			"This table is used to configure a Port Rule for a VLAN.
			 The VLAN has to be created before any rule can be configured
			 for it."
		::= { vAutoTracker 1 }

	atportRuleEntry OBJECT-TYPE
		SYNTAX		AtportRuleEntry
		ACCESS		not-accessible
		STATUS		mandatory
		DESCRIPTION
			"An entry in the atportRuleTable. Each entry in this table 
			 identifies exactly one port that is part of the VLAN 
			 definition. Hence all the entries of this table with the same 
			 GroupId and VLANId collectively define one VLAN which is based 
			 on a Port Rule. 
			 A specific port can be included in definition of more than one 
			 vlan as long as those two vlans are part of the same VLAN group.
			 That is to say, a port can belong to more than one vlan but can 
			 be part of atmost one VLAN group."
		INDEX { atportRuleGroupId, atportRuleVLANId, 
				atportRuleIdx, atportRulePortId }
		::= { atportRuleTable 1 }

	AtportRuleEntry ::= SEQUENCE {
		atportRuleGroupId
			INTEGER,
		atportRuleVLANId
			INTEGER,
		atportRuleIdx
			INTEGER,
		atportRulePortId
			OCTET STRING,
		atportRulePortState
			INTEGER
	}

	atportRuleGroupId OBJECT-TYPE
		SYNTAX		INTEGER (1..32)
		ACCESS		read-write
		STATUS		mandatory
		DESCRIPTION	
			"This object indicates the VLAN Group in which the VLAN 
			 defined by this rule is." 
		::= { atportRuleEntry 1 }

	atportRuleVLANId OBJECT-TYPE
		SYNTAX		INTEGER (2..32)
		ACCESS		read-write
		STATUS		mandatory
		DESCRIPTION	
			"This object is the VLAN defined by this port-rule."
		::= { atportRuleEntry 2 }

	atportRuleIdx OBJECT-TYPE
		SYNTAX		INTEGER (0..32)
		ACCESS		read-write
		STATUS		mandatory
		DESCRIPTION
			"This object indicates the exact port-rule for this VLAN. 
			 There can be more than one port-rule defined for this VLAN. 
			 This object identifies the port rule of which the port is part of. 
			 When creating a VLAN using this table, this value should be set to 
			 0 to indicate that this is a new port rule. If the port rule 
			 needs to be modified, then this object will be the port rule
			 to modify."
		::= { atportRuleEntry 3 }

	atportRulePortId OBJECT-TYPE
		SYNTAX		OCTET STRING (SIZE (4))
		ACCESS		read-write
		STATUS		mandatory
		DESCRIPTION	
			"This object defines the Virtual port that is part of this 
			 PORT rule. The first octet gives the slot number on which
			 the port resides, the second being the physical interface,
			 third octet being the service and the fourth being the
			 instance of the service."
		::= { atportRuleEntry 4 }

	atportRulePortState OBJECT-TYPE
		SYNTAX		INTEGER {
						enabled (1),
						disabled (2),
						delete(3)
					}
		ACCESS		read-write
		STATUS		mandatory
		DESCRIPTION
			"This object indicates whether this perticular rule is being used 
			 as part this VLANs definition. When set to disabled, this rule is 
			 not used as part of this vlans definition."
		::= { atportRuleEntry 5 }

	-- The MAC Rule Table

	atMacRuleTable OBJECT-TYPE
		SYNTAX		SEQUENCE OF AtMacRuleEntry
		ACCESS		not-accessible
		STATUS		mandatory
		DESCRIPTION
			"This table is used to configure an Auto-Tracker VLAN based on a 
			 MAC Rule.  Note the a VLAN created by using this table will not 
			 be enabled until the atVLANAdminStatus in the atVLANControlTable 
			 is not set to enabled."	
		::= { vAutoTracker 2 }

	atMacRuleEntry OBJECT-TYPE
		SYNTAX		AtMacRuleEntry
		ACCESS		not-accessible
		STATUS		mandatory
		DESCRIPTION
			"An entry in the atMacRuleTable. Each entry in this table 
			 identifies exactly one MAC address. All entries in this 
			 table with the same GroupId and VLANId collectively define a VLAN."
		INDEX { atMacRuleGroupId, atMacRuleVLANId, 
			  	atMacRuleIndex, atMacRuleMacAddress }
		::= { atMacRuleTable 1 }

	AtMacRuleEntry ::= SEQUENCE {
		atMacRuleGroupId
			INTEGER,
		atMacRuleVLANId
			INTEGER,
		atMacRuleIndex
			INTEGER,
		atMacRuleMacAddress
			MacAddress,
		atMacRuleMacAddressState
			INTEGER
	}

	atMacRuleGroupId OBJECT-TYPE
		SYNTAX		INTEGER (1..32)
		ACCESS		read-write
		STATUS		mandatory
		DESCRIPTION	
			"This object indicates the VLAN Group in which the VLAN defined
			 by this rule is."
		::= { atMacRuleEntry 1 }

	atMacRuleVLANId OBJECT-TYPE
		SYNTAX		INTEGER (2..32)
		ACCESS		read-write
		STATUS		mandatory
		DESCRIPTION	
			"This object is the VLAN Id for this MAC-rule based vlan."
		::= { atMacRuleEntry 2 }

	atMacRuleIndex OBJECT-TYPE
		SYNTAX		INTEGER (0..32)
		ACCESS		read-write
		STATUS		mandatory
		DESCRIPTION
			"The rule of which this MAC address list is part of. 
			 When creating a VLAN, this object must be set to 0."
		::= { atMacRuleEntry 3 }

	atMacRuleMacAddress OBJECT-TYPE
		SYNTAX		MacAddress
		ACCESS		read-write
		STATUS		mandatory
		DESCRIPTION	
			"This object gives the value of the MAC address that is part of
			 the MAC rule definition."
		::= { atMacRuleEntry 4 }

	atMacRuleMacAddressState OBJECT-TYPE
		SYNTAX		INTEGER {
						enabled (1),
						disabled (2),
						delete(3)
					}
		ACCESS		read-write
		STATUS		mandatory
		DESCRIPTION
			"This object indicates whether this perticular rule is being used 
			 as part this VLANs definition. When set to disabled, this rule is 
			 not used as part of this vlans definition."
		::= { atMacRuleEntry 5 }

	-- The Protocol Rule Table

	atProtoRuleTable OBJECT-TYPE
		SYNTAX		SEQUENCE OF AtProtoRuleEntry
		ACCESS		not-accessible
		STATUS		mandatory
		DESCRIPTION
			"This table is used to configure an Auto-Tracker VLAN based on 
			 Protocol Rule. Note that any VLAN created using this table will 
			 not be enabled until the atVLANAdminStatus in the 
			 atVLANControlTable is not set to enabled."
		::= { vAutoTracker 3 }

	atProtoRuleEntry OBJECT-TYPE
		SYNTAX		AtProtoRuleEntry
		ACCESS		not-accessible
		STATUS		mandatory
		DESCRIPTION
			"An entry in the atProtoRuleTable. "
		INDEX { atProtoRuleGroupId, atProtoRuleVLANId, atProtoRuleIndex }
		::= { atProtoRuleTable 1 }

	AtProtoRuleEntry ::= SEQUENCE {
		atProtoRuleGroupId
			INTEGER,
		atProtoRuleVLANId
			INTEGER,
		atProtoRuleIndex
			INTEGER,
		atProtoRule
			OCTET STRING,
		atProtoRuleStatus
			INTEGER
	}

	atProtoRuleGroupId OBJECT-TYPE
		SYNTAX		INTEGER (1..32)
		ACCESS		read-write
		STATUS		mandatory
		DESCRIPTION	
			"This object indicates the VLAN Group in which the VLAN defined
			 by this rule is defined."
		::= { atProtoRuleEntry 1 }

	atProtoRuleVLANId OBJECT-TYPE
		SYNTAX		INTEGER (2..32)
		ACCESS		read-write
		STATUS		mandatory
		DESCRIPTION	
			"This object is the VLAN Id defined by this Protocol-rule."
		::= { atProtoRuleEntry 2 }

	atProtoRuleIndex OBJECT-TYPE
		SYNTAX		INTEGER(0..32)
		ACCESS		read-write
		STATUS		mandatory
		DESCRIPTION
			"This object specifies the exact protocol rule for this VLAN. 
			 On creating a VLAN based on protocol rule, this object must be 
			 set to 0."
		::= { atProtoRuleEntry 3 }	

	atProtoRule OBJECT-TYPE
		SYNTAX		OCTET STRING (SIZE (5))
		ACCESS		read-write
		STATUS		mandatory
		DESCRIPTION	
			"This object is an octet string of length 5 bytes. 
			 This object specifies the protocol type that defines this vlan. 
			 The values for the different protocols are:
				IP         - first byte = 1,
				IPX        - first byte = 2,
				AppleTalk  - first byte = 3,
				DECNet     - first byte = 4,
				Note that, in case of IP, ARP is included as IP and need not 
				be specified explicitly. 
				Similarly when AppleTalk is chosen both DDP and AARP
				are included.

			 If any other protocol is used, it can be defined either by using
				Ether-type - first byte = 5 specifying its ether-type, 
							 second and third byte = ether-type value in hex.

				DSAP and SSAP - first byte = 6 specifying that its SAP type
							 second byte = DSAP, third byte = SSAP in hex.

				SNAP Type - first byte = 7 specifying its SNAP
							 second through sixth byte = snap value in hex."
		::= { atProtoRuleEntry 4 }

	atProtoRuleStatus OBJECT-TYPE
		SYNTAX		INTEGER {
						enabled (1),
						disabled (2),
						delete(3)
					}
		ACCESS		read-write
		STATUS		mandatory
		DESCRIPTION
			"This object indicates whether this perticular rule is being used 
			 as part this VLANs definition. When set to disabled, this rule is 
			 not used as part of this vlans definition."
		::= { atProtoRuleEntry 5 }

	-- The Network Address Rule Table

	atNetRuleTable OBJECT-TYPE
		SYNTAX		SEQUENCE OF AtNetRuleEntry
		ACCESS		not-accessible
		STATUS		mandatory
		DESCRIPTION
			"This table is used to configure an Auto-Tracker VLAN based on 
			 Net Addr Rule. Note that any VLAN created using this table will 
			 not be enabled until the atVLANAdminStatus in the 
			 atVLANControlTable is not set to enabled."
		::= { vAutoTracker 4 }

	atNetRuleEntry OBJECT-TYPE
		SYNTAX		AtNetRuleEntry
		ACCESS		not-accessible
		STATUS		mandatory
		DESCRIPTION
			"An entry in the atNetRuleTable. A VLAN can be defined using 
			 exaclty one address only except in the case of IPX where it 
			 could either be a Network number or the encapsulation."
		INDEX { atNetRuleGroupId, atNetRuleVLANId, atNetRuleIndex }
		::= { atNetRuleTable 1 }

	AtNetRuleEntry ::= SEQUENCE {
		atNetRuleGroupId
			INTEGER,
		atNetRuleVLANId
			INTEGER,
		atNetRuleIndex
			INTEGER,
		atNetRuleProtocolId
			INTEGER,
		atNetRuleNetAddr
			OCTET STRING,
		atNetRuleStatus
			INTEGER
	}

	atNetRuleGroupId OBJECT-TYPE
		SYNTAX		INTEGER (1..32)
		ACCESS		read-write
		STATUS		mandatory
		DESCRIPTION	
			"This object indicates the VLAN Group in which this VLAN is 
			 defined."
		::= { atNetRuleEntry 1 }

	atNetRuleVLANId OBJECT-TYPE
		SYNTAX		INTEGER (2..32)
		ACCESS		read-write
		STATUS		mandatory
		DESCRIPTION	
			"This object is the VLAN Id for this NetAddr-rule based vlan."
		::= { atNetRuleEntry 2 }

	atNetRuleIndex OBJECT-TYPE
		SYNTAX		INTEGER (0..32)
		ACCESS		read-write
		STATUS		mandatory
		DESCRIPTION
			"This object specifies the exact Network Address rule for this VLAN.
			 When creating a VLAN using the Network Address rule, this object 
			 must be set to 0."
		::= { atNetRuleEntry 3 }

	atNetRuleProtocolId OBJECT-TYPE
		SYNTAX		INTEGER {
						ip (1),
						ipx (2),
						dec (3)
					}
		ACCESS		read-write
		STATUS		mandatory
		DESCRIPTION	
			"This object indicates which protocols Network Address is used to 
			 define this VLAN." 
		::= { atNetRuleEntry 4 }

	atNetRuleNetAddr OBJECT-TYPE
		SYNTAX		OCTET STRING
		ACCESS		read-write
		STATUS		mandatory
		DESCRIPTION
			"This object gives the network address that defines this vlan. 
			 If the protocol is IP, this object contains the four bytes of IP 
			 address followed by four bytes of IP Subnet Mask. 

			 If the protocol is IPX, this object contains the four bytes of 
			 Network Number followed by one byte of encapsulation type used 
			 on that network. The values for the encapsulation types are:
				byte 5 = 1  - IPX 802.3 encapsulation
				byte 5 = 2  - IPX Ethernet2 encapsulation
				byte 5 = 3  - IPX LLC encapsulation
				byte 5 = 4  - IPX SNAP encapsulation 

			If the protocol is DECNet, this object contains the one byte of 
			DEC area."
		::= { atNetRuleEntry 5 }
	
	atNetRuleStatus OBJECT-TYPE
		SYNTAX		INTEGER {
						enabled (1),
						disabled (2),
						delete(3)
					}
		ACCESS		read-write
		STATUS		mandatory
		DESCRIPTION
			"This object indicates whether this perticular rule is being used 
			 as part this VLANs definition. When set to disabled, this rule is 
			 not used as part of this vlans definition."
		::= { atNetRuleEntry 6 }

	-- The User defined rule table.

	atUserRuleTable OBJECT-TYPE
		SYNTAX		SEQUENCE OF AtUserRuleEntry
		ACCESS		not-accessible
		STATUS		mandatory
		DESCRIPTION
			"This table is used to configure an Auto-Tracker VLAN based on a 
			 User Defined Rule.Note that any VLAN created using this table 
			 will not be enabled until the atVLANAdminStatus in the 
			 atVLANControlTable is not set to enabled."
		::= { vAutoTracker 5 }

	atUserRuleEntry OBJECT-TYPE
		SYNTAX		AtUserRuleEntry
		ACCESS		not-accessible
		STATUS		mandatory
		DESCRIPTION
			"An entry in the atUserRuleTable. A VLAN can be defined by more 
			 than one rule. In that case, the device will belong to that VLAN 
			 if it matches atleast one of the rules defined for that VLAN."
		INDEX { atUserRuleGroupId, atUserRuleVLANId, atUserRuleIndex }
		::= { atUserRuleTable 1 }

	AtUserRuleEntry ::= SEQUENCE {
		atUserRuleGroupId
			INTEGER,
		atUserRuleVLANId
			INTEGER,
		atUserRuleIndex
			INTEGER,
		atUserRuleOffset
			INTEGER,
		atUserRuleValue
			OCTET STRING,
		atUserRuleMask
			OCTET STRING,
		atUserRuleStatus
			INTEGER
	}

	atUserRuleGroupId OBJECT-TYPE
		SYNTAX		INTEGER (1..32)
		ACCESS		read-write
		STATUS		mandatory
		DESCRIPTION	
			"This object indicates the VLAN Group in which this VLAN is 
			 defined."
		::= { atUserRuleEntry 1 }

	atUserRuleVLANId OBJECT-TYPE
		SYNTAX		INTEGER (2..32)
		ACCESS		read-write
		STATUS		mandatory
		DESCRIPTION	
			"This object is the VLAN Id for this User-rule based vlan."
		::= { atUserRuleEntry 2 }

	atUserRuleIndex OBJECT-TYPE
		SYNTAX		INTEGER (0..32)
		ACCESS		read-write
		STATUS		mandatory
		DESCRIPTION
			"This object indicates the exact User defined rule for this VLAN.
			 When creating a VLAN using the user defined rules, this object must
			 be set to 0."
		::= { atUserRuleEntry 3 }
	
	atUserRuleOffset OBJECT-TYPE
		SYNTAX		INTEGER (0..64)
		ACCESS		read-write
		STATUS		mandatory
		DESCRIPTION	
			"This object defines the offset into a frame where the pattern to 
			 match is located. This offset is relative to the start of the MAC 
			 header."
		::= { atUserRuleEntry 4 }

	atUserRuleValue OBJECT-TYPE
		SYNTAX		OCTET STRING ( SIZE (8))
		ACCESS		read-write
		STATUS		mandatory
		DESCRIPTION
			"This object defines the value of the pattern to match in a frame. 
			 The maximum length of this value can be 8 octets and the 
			 associated mask should have the same length as this object."
		::= { atUserRuleEntry 5 }

	atUserRuleMask OBJECT-TYPE
		SYNTAX		OCTET STRING (SIZE(8))
		ACCESS		read-write
		STATUS		mandatory
		DESCRIPTION	
			"This object defines the mask for the pattern to match. The Mask 
			 can be upto 8 bytes long but has to be of the same length as the 
			 Value."
		::= { atUserRuleEntry 6 }

	atUserRuleStatus OBJECT-TYPE
		SYNTAX		INTEGER {
						enabled (1),
						disabled (2),
						delete(3)
					}
		ACCESS		read-write
		STATUS		mandatory
		DESCRIPTION
			"This object indicates whether this perticular rule is being used 
			 as part this VLANs definition. When set to disabled, this rule is 
			 not used as part of this vlans definition."
		::= { atUserRuleEntry 7 }

	-- The Auto-Tracker VLAN Rule Summary Table

	atVLANRuleSumTable OBJECT-TYPE
		SYNTAX		SEQUENCE OF AtVLANRuleSumEntry
		ACCESS		not-accessible
		STATUS		mandatory
		DESCRIPTION
			"This table provides the summary of vlan rule configuration."
		::= { vAutoTracker 6 }

	atVLANRuleSumEntry OBJECT-TYPE
		SYNTAX		AtVLANRuleSumEntry
		ACCESS		not-accessible
		STATUS		mandatory
		DESCRIPTION
			"An entry in the vlan summary table."
		INDEX { atVLANRuleSumGroupId, atVLANRuleSumVLANId, atVLANRuleIndex }
		::= { atVLANRuleSumTable 1 }

	AtVLANRuleSumEntry ::= SEQUENCE {
		atVLANRuleSumGroupId
			INTEGER,
		atVLANRuleSumVLANId
			INTEGER,
		atVLANRuleIndex
			INTEGER,
		atVLANRuleSubIndex
			INTEGER,
		atVLANRuleType
			INTEGER
	}

	atVLANRuleSumGroupId OBJECT-TYPE
		SYNTAX		INTEGER (1..32)
		ACCESS		read-only
		STATUS		mandatory
		DESCRIPTION
			"The group to which the VLAN belongs."
		::= { atVLANRuleSumEntry 1 }

	atVLANRuleSumVLANId OBJECT-TYPE
		SYNTAX		INTEGER(1..32)
		ACCESS		read-only
		STATUS		mandatory
		DESCRIPTION
			"The VLAN Id for this rule is defined."
		::= { atVLANRuleSumEntry 2 }

	atVLANRuleIndex OBJECT-TYPE
		SYNTAX		INTEGER
		ACCESS		read-only
		STATUS		mandatory
		DESCRIPTION
			"The exact rule identifier for this rule."
		::= { atVLANRuleSumEntry 3 }

	atVLANRuleSubIndex OBJECT-TYPE
		SYNTAX		INTEGER
		ACCESS		read-only
		STATUS		mandatory
		DESCRIPTION
			"In case a VLAN is defined using multiple instances of the same 
			 type of rule, this object identifies the exact instance of that 
			 type of rule. This object could then be used along with the group 
			 and vlanid to get the complete definition of this rule from the 
			 appropriate rule table."
		::= { atVLANRuleSumEntry 4 }

	atVLANRuleType OBJECT-TYPE
		SYNTAX		INTEGER {
						port-rule (1),
						mac-rule (2),
						protocol-rule (3),
						network-rule (4),
						user-defined-rule (5),
						mcast-rule (6),
						binding-rule (7),
						dhcp-port-rule (8),
						dhcp-mac-rule (9)
					}
		ACCESS		read-only
		STATUS		mandatory
		DESCRIPTION
			"The type of rule. This object can then be used to decide which 
			 table to lookup for the complete definition of the rule."
		::= { atVLANRuleSumEntry 5 }

	-- The Auto-Tracker VLAN Control Table.

	atVLANControlTable OBJECT-TYPE
		SYNTAX		SEQUENCE OF AtVLANControlEntry
		ACCESS		not-accessible
		STATUS		mandatory
		DESCRIPTION
			"This table gives the control information about all Auto-Tracker 
			 VLANs."
		::= { vAutoTracker 7 }

	atVLANControlEntry OBJECT-TYPE
		SYNTAX		AtVLANControlEntry
		ACCESS		not-accessible
		STATUS		mandatory
		DESCRIPTION
			"An entry in the control table."
		INDEX { atVLANGroupId, atVLANId }
		::= { atVLANControlTable 1 }

	AtVLANControlEntry ::= SEQUENCE {
		atVLANGroupId
			INTEGER,
		atVLANId
			INTEGER,
		atVLANDesc
			DisplayString,
		atVLANAdminStatus
			INTEGER,
		atVLANOperStatus
			INTEGER
	}

	atVLANGroupId OBJECT-TYPE
		SYNTAX		INTEGER
		ACCESS		read-write
		STATUS		mandatory
		DESCRIPTION
			"This is the VLAN group to which the VLAN belongs."
		::= { atVLANControlEntry 1 }

	atVLANId OBJECT-TYPE
		SYNTAX		INTEGER
		ACCESS		read-write
		STATUS		mandatory
		DESCRIPTION
			"The VLAN id for this VLAN."
		::= { atVLANControlEntry 2 }

	atVLANDesc OBJECT-TYPE
		SYNTAX		DisplayString (SIZE(0..31))
		ACCESS		read-write
		STATUS		mandatory
		DESCRIPTION
			"The description for this vlan."
		::= { atVLANControlEntry 3 }

	atVLANAdminStatus OBJECT-TYPE
		SYNTAX		INTEGER {
						enabled (1),
						disabled (2),
						delete(3)
					}
		ACCESS		read-write
		STATUS		mandatory
		DESCRIPTION
			"The Admin status of the VLAN. If set to disabled, any rules 
			 configured for this vlan will no longer be used and their status 
			 will be changed to disabled."
		::= { atVLANControlEntry 4 }

	atVLANOperStatus OBJECT-TYPE
		SYNTAX		INTEGER {
						active (1),
						inactive (2)
					}
		ACCESS		read-only
		STATUS		mandatory
		DESCRIPTION
			"The operation status of this vlan. If there any devices learnt by 
			 this system on this vlan, the operation status of the vlan is 
			 said to be active."
		::= { atVLANControlEntry 5 }

	atDefaultVlan  OBJECT-TYPE
        SYNTAX     INTEGER {
                         on (1),
                         off (2)
                   }
        ACCESS     read-write
        STATUS     mandatory
        DESCRIPTION
           "When set to on, it allows devices to be assigned to the default
            vlan, else if it set to off, such devices are not assigned to
            any vlan, thereby preventing them from communicating to other
            devices."
        ::= { vAutoTracker 8 }
   


	-- Multicast VLAN Objects

	atmcportRuleTable OBJECT-TYPE
		SYNTAX		SEQUENCE OF AtmcportRuleEntry
		ACCESS		not-accessible
		STATUS		mandatory
		DESCRIPTION
			"This table is used to configure a Port Rule for a VLAN.
			 The VLAN has to be created before any rule can be configured
			 for it."
		::= { vAutoTracker 9 }

	atmcportRuleEntry OBJECT-TYPE
		SYNTAX		AtmcportRuleEntry
		ACCESS		not-accessible
		STATUS		mandatory
		DESCRIPTION
			"An entry in the atportRuleTable. Each entry in this table 
			 identifies exactly one port that is part of the VLAN 
			 definition. Hence all the entries of this table with the same 
			 GroupId and VLANId collectively define one VLAN which is based 
			 on a Port Rule. 
			 A specific port can be included in definition of more than one 
			 vlan as long as those two vlans are part of the same VLAN group.
			 That is to say, a port can belong to more than one vlan but can 
			 be part of atmost one VLAN group."
		INDEX { atmcportRuleGroupId, atmcportRuleVLANId, 
				atmcportRuleIdx, atmcportRulePortId }
		::= { atmcportRuleTable 1 }

	AtmcportRuleEntry ::= SEQUENCE {
		atmcportRuleGroupId
			INTEGER,
		atmcportRuleVLANId
			INTEGER,
		atmcportRuleIdx
			INTEGER,
		atmcportRulePortId
			OCTET STRING,
		atmcportRulePortState
			INTEGER
	}

	atmcportRuleGroupId OBJECT-TYPE
		SYNTAX		INTEGER (1..32)
		ACCESS		read-write
		STATUS		mandatory
		DESCRIPTION	
			"This object indicates the VLAN Group in which the VLAN 
			 defined by this rule is." 
		::= { atmcportRuleEntry 1 }

	atmcportRuleVLANId OBJECT-TYPE
		SYNTAX		INTEGER (2..32)
		ACCESS		read-write
		STATUS		mandatory
		DESCRIPTION	
			"This object is the VLAN defined by this port-rule."
		::= { atmcportRuleEntry 2 }

	atmcportRuleIdx OBJECT-TYPE
		SYNTAX		INTEGER (0..32)
		ACCESS		read-write
		STATUS		mandatory
		DESCRIPTION
			"This object indicates the exact port-rule for this VLAN. 
			 There can be more than one port-rule defined for this VLAN. 
			 This object identifies the port rule of which the port is part of. 
			 When creating a VLAN using this table, this value should be set to 
			 0 to indicate that this is a new port rule. If the port rule 
			 needs to be modified, then this object will be the port rule
			 to modify."
		::= { atmcportRuleEntry 3 }

	atmcportRulePortId OBJECT-TYPE
		SYNTAX		OCTET STRING (SIZE (4))
		ACCESS		read-write
		STATUS		mandatory
		DESCRIPTION	
			"This object defines the Virtual port that is part of this 
			 PORT rule. The first octet gives the slot number on which
			 the port resides, the second being the physical interface,
			 third octet being the service and the fourth being the
			 instance of the service."
		::= { atmcportRuleEntry 4 }

	atmcportRulePortState OBJECT-TYPE
		SYNTAX		INTEGER {
						enabled (1),
						disabled (2)
					}
		ACCESS		read-write
		STATUS		mandatory
		DESCRIPTION
			"This object determines whether the port is being added or 
			 deleted from this port rule definition."
		::= { atmcportRuleEntry 5 }

	-- The MAC Rule Table

	atmcMacRuleTable OBJECT-TYPE
		SYNTAX		SEQUENCE OF AtmcMacRuleEntry
		ACCESS		not-accessible
		STATUS		mandatory
		DESCRIPTION
			"This table is used to configure an Auto-Tracker VLAN based on a 
			 MAC Rule.  Note the a VLAN created by using this table will not 
			 be enabled until the atVLANAdminStatus in the atVLANControlTable 
			 is not set to enabled."	
		::= { vAutoTracker 10 }

	atmcMacRuleEntry OBJECT-TYPE
		SYNTAX		AtmcMacRuleEntry
		ACCESS		not-accessible
		STATUS		mandatory
		DESCRIPTION
			"An entry in the atmcMacRuleTable. Each entry in this table 
			 identifies exactly one MAC address. All entries in this 
			 table with the same GroupId and VLANId collectively define a VLAN."
		INDEX { atmcMacRuleGroupId, atmcMacRuleVLANId, 
			  	atmcMacRuleIndex, atmcMacRuleMacAddress }
		::= { atmcMacRuleTable 1 }

	AtmcMacRuleEntry ::= SEQUENCE {
		atmcMacRuleGroupId
			INTEGER,
		atmcMacRuleVLANId
			INTEGER,
		atmcMacRuleIndex
			INTEGER,
		atmcMacRuleMacAddress
			MacAddress,
		atmcMacRuleMacAddressState
			INTEGER
	}

	atmcMacRuleGroupId OBJECT-TYPE
		SYNTAX		INTEGER (1..32)
		ACCESS		read-write
		STATUS		mandatory
		DESCRIPTION	
			"This object indicates the VLAN Group in which the VLAN defined
			 by this rule is."
		::= { atmcMacRuleEntry 1 }

	atmcMacRuleVLANId OBJECT-TYPE
		SYNTAX		INTEGER (2..32)
		ACCESS		read-write
		STATUS		mandatory
		DESCRIPTION	
			"This object is the VLAN Id for this MAC-rule based vlan."
		::= { atmcMacRuleEntry 2 }

	atmcMacRuleIndex OBJECT-TYPE
		SYNTAX		INTEGER (0..32)
		ACCESS		read-write
		STATUS		mandatory
		DESCRIPTION
			"The rule of which this MAC address list is part of. 
			 When creating a VLAN, this object must be set to 0."
		::= { atmcMacRuleEntry 3 }

	atmcMacRuleMacAddress OBJECT-TYPE
		SYNTAX		MacAddress
		ACCESS		read-write
		STATUS		mandatory
		DESCRIPTION	
			"This object gives the value of the MAC address that is part of
			 the MAC rule definition."
		::= { atmcMacRuleEntry 4 }

	atmcMacRuleMacAddressState OBJECT-TYPE
		SYNTAX		INTEGER {
						enabled (1),
						disabled (2)
					}
		ACCESS		read-write
		STATUS		mandatory
		DESCRIPTION
			"This object determines if the MAC address is included in the 
			 VLAN definition. If the object is set to disabled, the MAC 
			 address is removed from the VLAN definition."
		::= { atmcMacRuleEntry 5 }

    -- The Auto-Tracker MCAST Rule Table

    atMcastRuleTable  OBJECT-TYPE
        SYNTAX      SEQUENCE OF AtMcastRuleEntry
        ACCESS      not-accessible
        STATUS      mandatory
        DESCRIPTION
            "This table is used to configure MCAST Rules for a VLAN."
        ::= { vAutoTracker 11 }

    atMcastRuleEntry  OBJECT-TYPE
        SYNTAX      AtMcastRuleEntry
        ACCESS      not-accessible
        STATUS      mandatory
        DESCRIPTION
            "An entry in the MCAST Rule table."
        INDEX { atMcastRuleGroupId, atMcastRuleVLANId, atMcastRuleIndex,
				atMcastRuleMacAddress }
        ::= { atMcastRuleTable 1 }

    AtMcastRuleEntry ::= SEQUENCE {
        atMcastRuleGroupId
             INTEGER,
        atMcastRuleVLANId
             INTEGER,
        atMcastRuleIndex
             INTEGER,
        atMcastRuleMacAddress
             MacAddress,
        atMcastRuleMacAddressState 
             INTEGER
    }

    atMcastRuleGroupId  OBJECT-TYPE
        SYNTAX      INTEGER (1..65535)
        ACCESS      read-write
        STATUS      mandatory
        DESCRIPTION
            "The group in which this rule is defined."
        ::= { atMcastRuleEntry 1 }

    atMcastRuleVLANId   OBJECT-TYPE
        SYNTAX      INTEGER (2..32)
        ACCESS      read-write
        STATUS      mandatory
        DESCRIPTION
            "The VLAN for which this rule is defined."
        ::= { atMcastRuleEntry 2 }

    atMcastRuleIndex  OBJECT-TYPE
        SYNTAX      INTEGER (1..32)
        ACCESS      read-write
        STATUS      mandatory
        DESCRIPTION
            "The rule index ( a vlan can have multiple rules defined ) which
             exactly identifies this rule."
        ::= { atMcastRuleEntry 3 }

    atMcastRuleMacAddress  OBJECT-TYPE
        SYNTAX      MacAddress
        ACCESS      read-write
        STATUS      mandatory
        DESCRIPTION
            "The Multicast MAC Address that makes up this rule."
        ::= { atMcastRuleEntry 4 }

    atMcastRuleMacAddressState  OBJECT-TYPE
        SYNTAX      INTEGER {
                       enable (1),
                       disable (2),
                       delete (3)
                    }
        ACCESS      read-write
        STATUS      mandatory
        DESCRIPTION
            "The admin-state of this multicast mac address."
        ::= { atMcastRuleEntry 5 }

	-- The Auto-Tracker VLAN Rule Summary Table

	atmcVLANRuleSumTable OBJECT-TYPE
		SYNTAX		SEQUENCE OF AtmcVLANRuleSumEntry
		ACCESS		not-accessible
		STATUS		mandatory
		DESCRIPTION
			"This table provides the summary of vlan rule configuration."
		::= { vAutoTracker 12 }

	atmcVLANRuleSumEntry OBJECT-TYPE
		SYNTAX		AtmcVLANRuleSumEntry
		ACCESS		not-accessible
		STATUS		mandatory
		DESCRIPTION
			"An entry in the vlan summary table."
		INDEX { atmcVLANRuleSumGroupId, atmcVLANRuleSumVLANId, atmcVLANRuleIndex }
		::= { atmcVLANRuleSumTable 1 }

	AtmcVLANRuleSumEntry ::= SEQUENCE {
		atmcVLANRuleSumGroupId
			INTEGER,
		atmcVLANRuleSumVLANId
			INTEGER,
		atmcVLANRuleIndex
			INTEGER,
		atmcVLANRuleSubIndex
			INTEGER,
		atmcVLANRuleType
			INTEGER
	}

	atmcVLANRuleSumGroupId OBJECT-TYPE
		SYNTAX		INTEGER (1..32)
		ACCESS		read-only
		STATUS		mandatory
		DESCRIPTION
			"The group to which the VLAN belongs."
		::= { atmcVLANRuleSumEntry 1 }

	atmcVLANRuleSumVLANId OBJECT-TYPE
		SYNTAX		INTEGER(1..32)
		ACCESS		read-only
		STATUS		mandatory
		DESCRIPTION
			"The VLAN Id for this rule is defined."
		::= { atmcVLANRuleSumEntry 2 }

	atmcVLANRuleIndex OBJECT-TYPE
		SYNTAX		INTEGER
		ACCESS		read-only
		STATUS		mandatory
		DESCRIPTION
			"The exact rule identifier for this rule."
		::= { atmcVLANRuleSumEntry 3 }

	atmcVLANRuleSubIndex OBJECT-TYPE
		SYNTAX		INTEGER
		ACCESS		read-only
		STATUS		mandatory
		DESCRIPTION
			"In case a VLAN is defined using multiple instances of the same 
			 type of rule, this object identifies the exact instance of that 
			 type of rule. This object could then be used along with the group 
			 and vlanid to get the complete definition of this rule from the 
			 appropriate rule table."
		::= { atmcVLANRuleSumEntry 4 }

	atmcVLANRuleType OBJECT-TYPE
		SYNTAX		INTEGER {
						port-rule (1),
						mac-rule (2),
						mcast-rule (3)
					}
		ACCESS		read-only
		STATUS		mandatory
		DESCRIPTION
			"The type of rule. This object can then be used to decide which 
			 table to lookup for the complete definition of the rule."
		::= { atmcVLANRuleSumEntry 5 }

	-- The Auto-Tracker VLAN Control Table.

	atmcVLANControlTable OBJECT-TYPE
		SYNTAX		SEQUENCE OF AtmcVLANControlEntry
		ACCESS		not-accessible
		STATUS		mandatory
		DESCRIPTION
			"This table gives the control information about all Auto-Tracker 
			 VLANs."
		::= { vAutoTracker 13 }

	atmcVLANControlEntry OBJECT-TYPE
		SYNTAX		AtmcVLANControlEntry
		ACCESS		not-accessible
		STATUS		mandatory
		DESCRIPTION
			"An entry in the control table."
		INDEX { atmcVLANGroupId, atmcVLANId }
		::= { atmcVLANControlTable 1 }

	AtmcVLANControlEntry ::= SEQUENCE {
		atmcVLANGroupId
			INTEGER,
		atmcVLANId
			INTEGER,
		atmcVLANDesc
			DisplayString,
		atmcVLANAdminStatus
			INTEGER,
		atmcVLANOperStatus
			INTEGER
	}

	atmcVLANGroupId OBJECT-TYPE
		SYNTAX		INTEGER
		ACCESS		read-write
		STATUS		mandatory
		DESCRIPTION
			"This is the VLAN group to which the VLAN belongs."
		::= { atmcVLANControlEntry 1 }

	atmcVLANId OBJECT-TYPE
		SYNTAX		INTEGER
		ACCESS		read-write
		STATUS		mandatory
		DESCRIPTION
			"The VLAN id for this VLAN."
		::= { atmcVLANControlEntry 2 }

	atmcVLANDesc OBJECT-TYPE
		SYNTAX		DisplayString (SIZE(0..31))
		ACCESS		read-write
		STATUS		mandatory
		DESCRIPTION
			"The description for this vlan."
		::= { atmcVLANControlEntry 3 }

	atmcVLANAdminStatus OBJECT-TYPE
		SYNTAX		INTEGER {
						enabled (1),
						disabled (2),
						delete(3)
					}
		ACCESS		read-write
		STATUS		mandatory
		DESCRIPTION
			"The Admin status of the VLAN. If set to disabled, any rules 
			 configured for this vlan will no longer be used and their status 
			 will be changed to disabled."
		::= { atmcVLANControlEntry 4 }

	atmcVLANOperStatus OBJECT-TYPE
		SYNTAX		INTEGER {
						active (1),
						inactive (2)
					}
		ACCESS		read-only
		STATUS		mandatory
		DESCRIPTION
			"The operation status of this vlan. If there any devices learnt by 
			 this system on this vlan, the operation status of the vlan is 
			 said to be active."
		::= { atmcVLANControlEntry 5 }

	
    gmAutoServiceTable  OBJECT-TYPE
       SYNTAX  SEQUENCE OF GmAutoServiceEntry
       ACCESS  not-accessible
       STATUS  mandatory
       DESCRIPTION
       "Table of Auto-Activated Services"
       ::= { vAutoTracker 14 }

    gmAutoServiceEntry  OBJECT-TYPE
       SYNTAX  GmAutoServiceEntry
       ACCESS  not-accessible
       STATUS  mandatory
       DESCRIPTION
       "an entry in the table"
       INDEX { gmAutoServiceGroupId, gmAutoServicePrimarySlot,
               gmAutoServicePrimaryPort, gmAutoServiceIndex }
       ::= { gmAutoServiceTable 1 }

    GmAutoServiceEntry ::= SEQUENCE {
       gmAutoServiceGroupId
       INTEGER,
       gmAutoServicePrimarySlot
       INTEGER,
       gmAutoServicePrimaryPort
       INTEGER,
       gmAutoServiceIndex
       INTEGER,
       gmAutoServiceType
       INTEGER,
       gmAutoServiceName
       DisplayString,
       gmAutoServiceSecondarySlot
       INTEGER,
       gmAutoServiceSecondaryPort
       INTEGER,
       gmAutoServiceAdminState
       INTEGER,
       gmAutoServiceOperState
       INTEGER,
       gmAutoServiceActiveSlot
       INTEGER,
       gmAutoServiceActivePort
       INTEGER,
       gmAutoServiceNumber
       INTEGER,
       gmAutoServiceTranslations
       INTEGER
   }

   gmAutoServiceGroupId  OBJECT-TYPE
       SYNTAX  INTEGER
       ACCESS  read-write
       STATUS  mandatory
       DESCRIPTION
       "Group for which this service is configured"
       ::= { gmAutoServiceEntry 1 }

   gmAutoServicePrimarySlot  OBJECT-TYPE
       SYNTAX  INTEGER
       ACCESS  read-write
       STATUS  mandatory
       DESCRIPTION
       "Primary slot on which this service will be activated."
       ::= { gmAutoServiceEntry 2 }

   gmAutoServicePrimaryPort  OBJECT-TYPE
       SYNTAX  INTEGER
       ACCESS  read-write
       STATUS  mandatory
       DESCRIPTION
       "Primary port on which this service will be activated."
       ::= { gmAutoServiceEntry 3 }

   gmAutoServiceIndex  OBJECT-TYPE
       SYNTAX  INTEGER
       ACCESS  read-write
       STATUS  mandatory
       DESCRIPTION
       "Service index associated with this service"
       ::= { gmAutoServiceEntry 4 }

   gmAutoServiceType  OBJECT-TYPE
       SYNTAX  INTEGER {
					eth-lane (1),
					token-ring-lane (2)
               }
       ACCESS  read-write
       STATUS  mandatory
       DESCRIPTION
       "Type of this service - currently only lane is supported and
        this object should have a value of 1."
       ::= { gmAutoServiceEntry 5 }

   gmAutoServiceName  OBJECT-TYPE
       SYNTAX  DisplayString
       ACCESS  read-write
       STATUS  mandatory
       DESCRIPTION
       "The name of the service. In case of LANE, this is the elan name."
       ::= { gmAutoServiceEntry 6 }

   gmAutoServiceSecondarySlot  OBJECT-TYPE
       SYNTAX  INTEGER
       ACCESS  read-write
       STATUS  mandatory
       DESCRIPTION
       "Secondary slot on which this service will be activated."
       ::= { gmAutoServiceEntry 7 }

   gmAutoServiceSecondaryPort  OBJECT-TYPE
       SYNTAX  INTEGER
       ACCESS  read-write
       STATUS  mandatory
       DESCRIPTION
       "Secondary port on which this service will be activated."
       ::= { gmAutoServiceEntry 8 }

   gmAutoServiceAdminState  OBJECT-TYPE
       SYNTAX  INTEGER {
					enable (1),
					disable (2),
					delete (3)
				}
       ACCESS  read-write
       STATUS  mandatory
       DESCRIPTION
       "The admin state of this service"
       ::= { gmAutoServiceEntry 9 }

   gmAutoServiceOperState  OBJECT-TYPE
       SYNTAX  INTEGER {
					active (1),
					inactive (2)
				}
       ACCESS  read-write
       STATUS  mandatory
       DESCRIPTION
	   "Operational state of this service."
       ::= { gmAutoServiceEntry 10 }

   gmAutoServiceActiveSlot  OBJECT-TYPE
       SYNTAX  INTEGER
       ACCESS  read-only
       STATUS  mandatory
       DESCRIPTION
       "Slot on the which the service is currently active."
       ::= { gmAutoServiceEntry 11 }

   gmAutoServiceActivePort  OBJECT-TYPE
       SYNTAX  INTEGER
       ACCESS  read-only
       STATUS  mandatory
       DESCRIPTION
       "Physical Port on the which the service is currently active."
       ::= { gmAutoServiceEntry 12 }

   gmAutoServiceNumber  OBJECT-TYPE
       SYNTAX  INTEGER
       ACCESS  read-only
       STATUS  mandatory
       DESCRIPTION
       "Service number assigned by the switch when this service is activated."
       ::= { gmAutoServiceEntry 13 }

   gmAutoServiceTranslations  OBJECT-TYPE
       SYNTAX  INTEGER {
                  enabled (1),
                  disabled (2)
               }
       ACCESS  read-write
       STATUS  mandatory
       DESCRIPTION
       "This parameter controls whether frame translations will be
        exercised for this lane service once activated."
       ::= { gmAutoServiceEntry 14 }
       


	-- The Bind Rule Table

	atBindRuleTable  OBJECT-TYPE
		SYNTAX  SEQUENCE OF AtBindRuleEntry
		ACCESS	not-accessible
		STATUS	mandatory
		DESCRIPTION
		"The Binding Rule table."
		::= { vAutoTracker 16 }

	atBindRuleEntry  OBJECT-TYPE
		SYNTAX	AtBindRuleEntry
		ACCESS	not-accessible
		STATUS  mandatory
		DESCRIPTION
		"An entry in the Binding Rule Table."
		INDEX { atBindRuleGroupId, atBindRuleVlanId, atBindRuleIndex }
		::= { atBindRuleTable 1 }

	AtBindRuleEntry ::= SEQUENCE {
		atBindRuleGroupId
			INTEGER,
		atBindRuleVlanId
			INTEGER,
		atBindRuleIndex
			INTEGER,
		atBindRulePortId
			OCTET STRING, 
		atBindRuleIPAddress
			IpAddress,
		atBindRuleMacAddress
			MacAddress,
		atBindRuleProtocol
			OCTET STRING,
		atBindRuleBindParameter
			INTEGER,
		atBindRuleStatus
			INTEGER
	}

	atBindRuleGroupId  OBJECT-TYPE
		SYNTAX  INTEGER
		ACCESS	read-write
		STATUS  mandatory
		DESCRIPTION
		"The group id of the vlan for which this rule is configured."
		::=  { atBindRuleEntry 1 }

	atBindRuleVlanId  OBJECT-TYPE
		SYNTAX  INTEGER
		ACCESS  read-write
		STATUS  mandatory
		DESCRIPTION
		"The vlan id for which this rule is configured."
		::= { atBindRuleEntry 2 }

	atBindRuleIndex  OBJECT-TYPE
		SYNTAX  INTEGER
		ACCESS  read-write
		STATUS  mandatory
		DESCRIPTION
		"The index which uniquely identifies this rule for this vlan."
		::= { atBindRuleEntry 3 }

	atBindRulePortId  OBJECT-TYPE
		SYNTAX  OCTET STRING  (SIZE(4))
		ACCESS  read-write
		STATUS  mandatory
		DESCRIPTION
		"The port ( slot/intf/srvc/inst) for which this binding is configured."
		::= { atBindRuleEntry 4 }

	atBindRuleIPAddress  OBJECT-TYPE
		SYNTAX  IpAddress
		ACCESS  read-write
		STATUS  mandatory
		DESCRIPTION
		"The IP address for which this binding is configured."
		::= { atBindRuleEntry 5 }

	atBindRuleMacAddress  OBJECT-TYPE
		SYNTAX  MacAddress
		ACCESS  read-write
		STATUS	mandatory
		DESCRIPTION
		"The mac address for which this binding is configured."
		::= { atBindRuleEntry 6 }

	atBindRuleProtocol  OBJECT-TYPE
		SYNTAX	OCTET STRING
		ACCESS	read-write
		STATUS	mandatory
		DESCRIPTION
		"The protocol for which this binding is configured."
		::= { atBindRuleEntry 7 }

	atBindRuleBindParameter  OBJECT-TYPE
		SYNTAX  INTEGER {
					port-ip-mac (7),
					port-protocol (9),
					port-mac-protocol (13),
                                        ip-mac (6),
                                        ip-port (3),
                                        mac-port (5)
				}	
		ACCESS	read-write
		STATUS	mandatory
		DESCRIPTION
		"The parameters to bind together."
		::= { atBindRuleEntry 8 }	
		
	atBindRuleStatus  OBJECT-TYPE
		SYNTAX  INTEGER {
					enable (1),
					disable (2),
					delete (3)
				}
		ACCESS  read-write
		STATUS  mandatory
		DESCRIPTION
		"The admin status for this rule."
		::= { atBindRuleEntry 9 }


	-- The Group Mobility Group list table

	gmGroupListTable  OBJECT-TYPE
		SYNTAX  SEQUENCE OF GmGroupListEntry
		ACCESS	not-accessible
		STATUS	mandatory
		DESCRIPTION
		"This table lists the groups on a port."
		::= { vAutoTracker 17 }

	gmGroupListEntry  OBJECT-TYPE
		SYNTAX  GmGroupListEntry
		ACCESS  not-accessible
		STATUS	mandatory
		DESCRIPTION
		"An entry in the Group List table."
		INDEX { gmGroupListPortSlot, gmGroupListPortInterface, gmGroupListGroupId }
		::= { gmGroupListTable 1 }

	GmGroupListEntry ::= SEQUENCE {
		gmGroupListPortSlot
			INTEGER,
		gmGroupListPortInterface
			INTEGER,
		gmGroupListGroupId
			INTEGER
	}

	gmGroupListPortSlot  OBJECT-TYPE
		SYNTAX	INTEGER
		ACCESS	read-only
		STATUS	mandatory
		DESCRIPTION
		"The slot id of the port for which the group list is requested."
		::= { gmGroupListEntry 1 }

	gmGroupListPortInterface  OBJECT-TYPE
		SYNTAX	INTEGER
		ACCESS	read-only
		STATUS	mandatory
		DESCRIPTION
		"The physical port number for which the group list is requested."
		::= { gmGroupListEntry 2 }

	gmGroupListGroupId  OBJECT-TYPE
		SYNTAX	INTEGER
		ACCESS	read-only
		STATUS	mandatory
		DESCRIPTION
		"One of the Groups to which the port belongs."
		::= { gmGroupListEntry 3 }


	atDHCPportRuleTable OBJECT-TYPE
		SYNTAX		SEQUENCE OF AtDHCPportRuleEntry
		ACCESS		not-accessible
		STATUS		mandatory
		DESCRIPTION
			"This table is used to configure a Port Rule for a VLAN.
			 The VLAN has to be created before any rule can be configured
			 for it."
		::= { vAutoTracker 18 }

	-- DHCP PORT Rules

	atDHCPportRuleEntry OBJECT-TYPE
		SYNTAX		AtDHCPportRuleEntry
		ACCESS		not-accessible
		STATUS		mandatory
		DESCRIPTION
			"An entry in the atDHCPportRuleTable. Each entry in this table 
			 identifies exactly one port that is part of the VLAN 
			 definition. Hence all the entries of this table with the same 
			 GroupId and VLANId collectively define one VLAN which is based 
			 on a Port Rule. 
			 A specific port can be included in definition of more than one 
			 vlan as long as those two vlans are part of the same VLAN group.
			 That is to say, a port can belong to more than one vlan but can 
			 be part of atmost one VLAN group."
		INDEX { atDHCPportRuleGroupId, atDHCPportRuleVLANId, 
				atDHCPportRuleIdx, atDHCPportRulePortId }
		::= { atDHCPportRuleTable 1 }

	AtDHCPportRuleEntry ::= SEQUENCE {
		atDHCPportRuleGroupId
			INTEGER,
		atDHCPportRuleVLANId
			INTEGER,
		atDHCPportRuleIdx
			INTEGER,
		atDHCPportRulePortId
			OCTET STRING,
		atDHCPportRulePortState
			INTEGER
	}

	atDHCPportRuleGroupId OBJECT-TYPE
		SYNTAX		INTEGER (1..32)
		ACCESS		read-write
		STATUS		mandatory
		DESCRIPTION	
			"This object indicates the VLAN Group in which the VLAN 
			 defined by this rule is." 
		::= { atDHCPportRuleEntry 1 }

	atDHCPportRuleVLANId OBJECT-TYPE
		SYNTAX		INTEGER (1..32)
		ACCESS		read-write
		STATUS		mandatory
		DESCRIPTION	
			"This object is the VLAN defined by this port-rule."
		::= { atDHCPportRuleEntry 2 }

	atDHCPportRuleIdx OBJECT-TYPE
		SYNTAX		INTEGER (0..32)
		ACCESS		read-write
		STATUS		mandatory
		DESCRIPTION
			"This object indicates the exact port-rule for this VLAN. 
			 There can be more than one port-rule defined for this VLAN. 
			 This object identifies the port rule of which the port is part of. 
			 When creating a VLAN using this table, this value should be set to 
			 0 to indicate that this is a new port rule. If the port rule 
			 needs to be modified, then this object will be the port rule
			 to modify."
		::= { atDHCPportRuleEntry 3 }

	atDHCPportRulePortId OBJECT-TYPE
		SYNTAX		OCTET STRING (SIZE (4))
		ACCESS		read-write
		STATUS		mandatory
		DESCRIPTION	
			"This object defines the Virtual port that is part of this 
			 PORT rule. The first octet gives the slot number on which
			 the port resides, the second being the physical interface,
			 third octet being the service and the fourth being the
			 instance of the service."
		::= { atDHCPportRuleEntry 4 }

	atDHCPportRulePortState OBJECT-TYPE
		SYNTAX		INTEGER {
						enabled (1),
						disabled (2)
					}
		ACCESS		read-write
		STATUS		mandatory
		DESCRIPTION
			"This object determines whether the port is being added or 
			 deleted from this port rule definition."
		::= { atDHCPportRuleEntry 5 }

	-- The DHCP MAC Rule Table

	atDHCPMacRuleTable OBJECT-TYPE
		SYNTAX		SEQUENCE OF AtDHCPMacRuleEntry
		ACCESS		not-accessible
		STATUS		mandatory
		DESCRIPTION
			"This table is used to configure an Auto-Tracker VLAN based on a 
			 MAC Rule.  Note the a VLAN created by using this table will not 
			 be enabled until the atVLANAdminStatus in the atVLANControlTable 
			 is not set to enabled."	
		::= { vAutoTracker 19 }

	atDHCPMacRuleEntry OBJECT-TYPE
		SYNTAX		AtDHCPMacRuleEntry
		ACCESS		not-accessible
		STATUS		mandatory
		DESCRIPTION
			"An entry in the atDHCPMacRuleTable. Each entry in this table 
			 identifies exactly one MAC address. All entries in this 
			 table with the same GroupId and VLANId collectively define a VLAN."
		INDEX { atDHCPMacRuleGroupId, atDHCPMacRuleVLANId, 
			  	atDHCPMacRuleIndex, atDHCPMacRuleMacAddress }
		::= { atDHCPMacRuleTable 1 }

	AtDHCPMacRuleEntry ::= SEQUENCE {
		atDHCPMacRuleGroupId
			INTEGER,
		atDHCPMacRuleVLANId
			INTEGER,
		atDHCPMacRuleIndex
			INTEGER,
		atDHCPMacRuleMacAddress
			MacAddress,
		atDHCPMacRuleMacAddressState
			INTEGER
	}

	atDHCPMacRuleGroupId OBJECT-TYPE
		SYNTAX		INTEGER (1..32)
		ACCESS		read-write
		STATUS		mandatory
		DESCRIPTION	
			"This object indicates the VLAN Group in which the VLAN defined
			 by this rule is."
		::= { atDHCPMacRuleEntry 1 }

	atDHCPMacRuleVLANId OBJECT-TYPE
		SYNTAX		INTEGER (1..32)
		ACCESS		read-write
		STATUS		mandatory
		DESCRIPTION	
			"This object is the VLAN Id for this MAC-rule based vlan."
		::= { atDHCPMacRuleEntry 2 }

	atDHCPMacRuleIndex OBJECT-TYPE
		SYNTAX		INTEGER (0..32)
		ACCESS		read-write
		STATUS		mandatory
		DESCRIPTION
			"The rule of which this MAC address list is part of. 
			 When creating a VLAN, this object must be set to 0."
		::= { atDHCPMacRuleEntry 3 }

	atDHCPMacRuleMacAddress OBJECT-TYPE
		SYNTAX		MacAddress
		ACCESS		read-write
		STATUS		mandatory
		DESCRIPTION	
			"This object gives the value of the MAC address that is part of
			 the MAC rule definition."
		::= { atDHCPMacRuleEntry 4 }

	atDHCPMacRuleMacAddressState OBJECT-TYPE
		SYNTAX		INTEGER {
						enabled (1),
						disabled (2)
					}
		ACCESS		read-write
		STATUS		mandatory
		DESCRIPTION
			"This object determines if the MAC address is included in the 
			 VLAN definition. If the object is set to disabled, the MAC 
			 address is removed from the VLAN definition."
		::= { atDHCPMacRuleEntry 5 }


	groupMobilityStatus  OBJECT-TYPE
		SYNTAX		INTEGER {
						enable (1),
						disable (2)
					}
		ACCESS		read-write
		STATUS		mandatory
		DESCRIPTION
			"This object can used to configure the global status of
			 group-mobility feature on the switch." 
		::= { vAutoTracker 20 }

	gmMoveToDefGroup		OBJECT-TYPE
		SYNTAX		INTEGER {
						on (1),
						off (2)
					}
		ACCESS		read-write
		STATUS		mandatory
		DESCRIPTION
			"When this object is set on, the switch will remove the port
			 of out of a mobile group when the last device in that group
			 learnt on that port ages out due to inactivity. When it is
			 set to off, the port will remain in such a group, even if
			 all macs leant on that port in that group age out."
		::= { vAutoTracker 21 }

	gmDefGroup		OBJECT-TYPE
		SYNTAX		INTEGER {
						on (1),
						off (2)
					}
		ACCESS		read-write
		STATUS		mandatory
		DESCRIPTION
			"When this object is set to on, the switch will assign the port's
			 default group id to all such devices which are learned and
			 do not match any policies for mobile groups. If it is set to off,
			 such devices will get assigned to no groups
			 and the traffic they send will be discarded by the switch."
		::= { vAutoTracker 22 }


	--gmMoveFromDefGroup	OBJECT-TYPE
	--	SYNTAX		INTEGER {
	--					on (1),
	--					off (2)
	--				}
	--	ACCESS		read-write
	--	STATUS		mandatory
	--	DESCRIPTION
	--		"When this object is set to on, the switch will move the
	--		 port to the new group when the first device matching a rule
	--		 for a mobile group is learnt on that port, i.e. the priamry group
	--		 for that port will change when the first device that matches a rule
	--		 is learned on that port. If it is set to off, it will simply 
	--		 add the matched group to the port leaving the primary group
	--		 unchanged."
	--	::= { vAutoTracker 23 }

		
		
	-- The Auto-Tracker IP Router Info table



	atvIPRouterTable  OBJECT-TYPE
	    SYNTAX  SEQUENCE OF AtVIPRouterEntry
	    ACCESS  not-accessible
	    STATUS  mandatory
	    DESCRIPTION
		"A list of Virtual Router instances in this
		 physical OmniSwitch."
	    ::= { atvIPRouterInfo 1 }

	atvIPRouterEntry  OBJECT-TYPE
	    SYNTAX  AtVIPRouterEntry
	    ACCESS  not-accessible
	    STATUS  mandatory
	    DESCRIPTION
		"A VLAN entry." 
	    INDEX { atvIPRouterVLanGroup, atvIPRouterVLan }
	    ::= { atvIPRouterTable 1 }

	AtVIPRouterEntry ::= SEQUENCE {
		atvIPRouterVLanGroup
		INTEGER,
	    atvIPRouterVLan
		INTEGER,
	    atvIPRouterProtocol
		OCTET STRING,
	    atvIPRouterNetAddress
		IpAddress,
	    atvIPRouterSubNetMask
		IpAddress,
	    atvIPRouterBcastAddress
		IpAddress,
	    atvIPRouterDescription
		DisplayString,
	    atvIPRouterAdmStatus
		XylanVlanAdminStatCodes,
	    atvIPRouterOperStatus
		XylanVlanOperStatCodes,
		atvIPRouterFramingType
		INTEGER,
		atvIPRouterRipConfigMode
		INTEGER,
            atvIPRouterRelayServicesFwd
                INTEGER
	    }

	atvIPRouterVLanGroup  OBJECT-TYPE
	    SYNTAX  INTEGER (1..65535)
	    ACCESS  read-write
	    STATUS  mandatory
	    DESCRIPTION
		"VLAN Group ID for this atvIPRouterEntry instance."
	    ::= { atvIPRouterEntry 1 }

	atvIPRouterVLan  OBJECT-TYPE
		SYNTAX	INTEGER (1..32)
		ACCESS	read-write
		STATUS	mandatory
		DESCRIPTION
		"Auto Tracker VLAN Id for this router port instance."
		::= { atvIPRouterEntry 2 }

	atvIPRouterProtocol  OBJECT-TYPE
	    SYNTAX  OCTET STRING (SIZE (2))
	    ACCESS  read-write
	    STATUS  mandatory
	    DESCRIPTION
		"The routing protocol(s) for this virtual router port.
		 Each IP router port can carry one or more routing protocols.
		 This will be represented by the logical ORing of each
		 protocol number.

		 Which are:

		 ipOther(1),
		 ipRip(2),
		 ipEgp(4),
		 ipGgp(8),
		 ipHello(16),
		 ipIs-is(32),
		 ipEs-is(64),
		 ipCiscoIgrp(128),
		 ipBbnSpfIgp(256),
		 ipOigp(512)"
	    ::= { atvIPRouterEntry 3 }

	atvIPRouterNetAddress  OBJECT-TYPE
	    SYNTAX  IpAddress
	    ACCESS  read-write
	    STATUS  mandatory
	    DESCRIPTION
		 "The IP network address for this virtual bridge
		  instance for the purpose of allowing access from
		  the external network management system."
	    ::= { atvIPRouterEntry 4 }

	atvIPRouterSubNetMask  OBJECT-TYPE
	    SYNTAX  IpAddress
	    ACCESS  read-write
	    STATUS  mandatory
	    DESCRIPTION
		 "The IP network subnet mask for this virtual bridge
		  instance for the purpose of allowing access from the
		  external network management system."
	    ::= { atvIPRouterEntry 5 }

	atvIPRouterBcastAddress  OBJECT-TYPE
	    SYNTAX  IpAddress
	    ACCESS  read-write
	    STATUS  mandatory
	    DESCRIPTION
		 "The IP broadcast address for this virtual bridge
		  instance for the purpose of allowing access from the
		  external network management system."
	    ::= { atvIPRouterEntry 6 }

	atvIPRouterDescription  OBJECT-TYPE
	    SYNTAX  DisplayString (SIZE (0..31))
	    ACCESS  read-write
	    STATUS  optional
	    DESCRIPTION
		"Textual description of the router instance."
	    ::= { atvIPRouterEntry 7 }

	atvIPRouterAdmStatus  OBJECT-TYPE
	    SYNTAX  XylanVlanAdminStatCodes
	    ACCESS  read-write
	    STATUS  mandatory
	    DESCRIPTION
		"The particular routing environment can be
		 enable(2) or disable(1) (or delete (3))
		 upon user's request."
	    ::= { atvIPRouterEntry 8 }

	atvIPRouterOperStatus  OBJECT-TYPE
	    SYNTAX  XylanVlanOperStatCodes
	    ACCESS  read-only
	    STATUS  mandatory
	    DESCRIPTION
		"Provide operating status of a particular
		 router envirnment."
	    ::= { atvIPRouterEntry 9 }

	atvIPRouterFramingType  OBJECT-TYPE
		SYNTAX INTEGER {
                       ethernet-2(1),
                       ethernet-802-3(2),
                       fddi(3),
                       token-ring(4),
                       token-ring-source-routed(5)
                       }
		ACCESS  read-write
		STATUS  mandatory
		DESCRIPTION
		"Provides the ability to set the outbound frame type for IP
		traffic.  The default frame type is Ethernet 2.  If the
		frame type is incompatible with the transmitting media,
		appropriate translation will be performed at egress."
	    ::= { atvIPRouterEntry 10 }
 
	atvIPRouterRipConfigMode  OBJECT-TYPE
		SYNTAX  INTEGER {
                        silent(1),
                        deaf(2),
                        active(3),
                        inactive(4)
                        }
		ACCESS  read-write
		STATUS  mandatory
		DESCRIPTION
                 "RIP's operational mode. 'silent' means that RIP listens
                  for routing updates but does not send them.  'deaf' means
                  that RIP sends routing updates but not listen to them.
                  'active' means that RIP both sends and receives routing
                  updates, and 'inactive' means that RIP is not operational
                  on the given virtual LAN. The default is 'simple'."
	    ::= { atvIPRouterEntry 11 }

        atvIPRouterRelayServicesFwd  OBJECT-TYPE
                SYNTAX  INTEGER ( 0..65535 )
                ACCESS  read-write
                STATUS  mandatory
                DESCRIPTION
                        "Each of the 8 least significant bits are assigned
                        to a UDP Relay service as follows:
                        01H  - bootp  (Not currently allowed)
                        02H  - NBNS
                        04H  - NBDD
                        08H  - Gen1
                        10H  - Gen2
                        20H  - Gen3
                        40H  - Gen4
                        80H  - Gen5
                        A set bit indicates that packets are being forwarded
                        to this vlan for the service corresponding to the
                        bit.

                        Use bit 15 to indicate that a UDP Relay Service should
                        be unset and packets should not be forwarded to this
                        vlan.
                        8001H - bootp (Not currently allowed)
                        8002H - NBNS
                        8004H - NBDD
                        8008H - Gen1
                        8010H - Gen2
                        8020H - Gen3
                        8040H - Gen4
                        8080H - Gen5"
            ::= { atvIPRouterEntry 12 }

 
	  --AutoTracker vIPXRouterInfo group.  This group contains the global
	  --Virtual IPX (novell) Router information.

	atvIPXRouterTable  OBJECT-TYPE
	    SYNTAX  SEQUENCE OF AtVIPXRouterEntry
	    ACCESS  not-accessible
	    STATUS  mandatory
	    DESCRIPTION
		"A list of Virtual Router instances in this
		 physical OmniSwitch."
	    ::= { atvIPXRouterInfo 1 }

	atvIPXRouterEntry  OBJECT-TYPE
	    SYNTAX  AtVIPXRouterEntry
	    ACCESS  not-accessible
	    STATUS  mandatory
	    DESCRIPTION
		"A VLAN entry." 
	    INDEX { atvIPXRouterVLanGroup, atvIPXRouterVLan }
	    ::= { atvIPXRouterTable 1 }

	AtVIPXRouterEntry ::= SEQUENCE {
	    atvIPXRouterVLanGroup
		INTEGER,
	    atvIPXRouterVLan
		INTEGER,
	    atvIPXRouterProtocol
		INTEGER,
	    atvIPXRouterNetAddress
		NetNumber,
	    atvIPXRouterFramingType
		INTEGER,
	    atvIPXRouterDescription
		DisplayString,
	    atvIPXRouterAdmStatus
		XylanVlanAdminStatCodes,
	    atvIPXRouterOperStatus
		XylanVlanOperStatCodes,
        atvIPXSrcRteType
        INTEGER
	    }

	atvIPXRouterVLanGroup  OBJECT-TYPE
	    SYNTAX  INTEGER (1..65535)
	    ACCESS  read-write
	    STATUS  mandatory
	    DESCRIPTION
		"VLAN Group ID for this vIPXRouterEntry instance."
	    ::= { atvIPXRouterEntry 1 }

	atvIPXRouterVLan  OBJECT-TYPE
	    SYNTAX  INTEGER (1..32)
	    ACCESS  read-write
	    STATUS  mandatory
	    DESCRIPTION
		"VLAN ID for this vIPXRouterEntry instance."
	    ::= { atvIPXRouterEntry 2 }

	
	atvIPXRouterProtocol  OBJECT-TYPE
	    SYNTAX  INTEGER
	    ACCESS  read-write
	    STATUS  mandatory
	    DESCRIPTION
		"The routing protocol(s) for this virtual router port.
		 Each IPX router port can carry one or more routing protocols.
		 This will be represented by the logical ORing of each
		 protocol number.

		 Which are:

		 ipxOther(1),
		 ipxRip(2),
		 ipxSap(4)"
	    ::= { atvIPXRouterEntry 3 }

	atvIPXRouterNetAddress  OBJECT-TYPE
		SYNTAX	NetNumber
	    ACCESS  read-write
	    STATUS  mandatory
	    DESCRIPTION
		 "The IPX network address for this virtual bridge."
	    ::= { atvIPXRouterEntry 4 }

	atvIPXRouterFramingType  OBJECT-TYPE
	    SYNTAX  INTEGER {
                ethernet-2(1),
                ethernet-802-3-llc(2),
                ethernet-802-3-snap(3),
                ethernet-802-3-raw(4),
                fddi-snap(5),
                fddi-snap-sr(6),
                fddi-llc(7),
                fddi-llc-sr(8),
                token-ring-snap(9),
                token-ring-snap-sr(10),
                token-ring-llc(11),
                token-ring-llc-sr(12)
                }

	    ACCESS  read-write
	    STATUS  mandatory
	    DESCRIPTION
                "Provides the ability to set the outbound frame type for IPX
                 traffic.  The default frame type is 802.2 Novell Raw.  If the
                 frame type is incompatible with the transmitting media,
                 appropriate translation will be performed at egress."   
	    ::= { atvIPXRouterEntry 5 }

	atvIPXRouterDescription  OBJECT-TYPE
	    SYNTAX  DisplayString (SIZE (0..31))
	    ACCESS  read-write
	    STATUS  optional
	    DESCRIPTION
		"Textual description of the router instance."
	    ::= { atvIPXRouterEntry 6 }

	atvIPXRouterAdmStatus  OBJECT-TYPE
	    SYNTAX  XylanVlanAdminStatCodes
	    ACCESS  read-write
	    STATUS  mandatory
	    DESCRIPTION
		"The particular routing environment can be
		 enabled(2) or disabled(1) upon user's request."
	    ::= { atvIPXRouterEntry 7 }

	atvIPXRouterOperStatus  OBJECT-TYPE
	    SYNTAX  XylanVlanOperStatCodes
	    ACCESS  read-only
	    STATUS  mandatory
	    DESCRIPTION
		"Provide operating status of a particular
		 router envirnment."
	    ::= { atvIPXRouterEntry 8 }

    atvIPXSrcRteType  OBJECT-TYPE
        SYNTAX INTEGER {
               are(1),
               ste(2),
               not-applicable(3)
               }
        ACCESS  read-write
        STATUS  mandatory
        DESCRIPTION
        "Provide the ability to set the type of source routing
         broadcasts between AllRoutesExplorer(0) and
        SpanningTreeExplorer(1)."
        ::= { atvIPXRouterEntry 9 }
	-- Auto-Tracker Objects

          -- the v80210 group

        v80210ServicesTable  OBJECT-TYPE
            SYNTAX  SEQUENCE OF V80210ServicesEntry
            ACCESS  not-accessible
            STATUS  mandatory
            DESCRIPTION
                 "A list of commands to add or remove Virtual LANs from
                  a 80210 service."
            ::= { v80210 1 }
 
        v80210ServicesEntry  OBJECT-TYPE
            SYNTAX  V80210ServicesEntry
            ACCESS  not-accessible
            STATUS  mandatory
            DESCRIPTION
                 "A 80210 services entry."
            INDEX { v80210ServicesSlot, v80210ServicesStation }
            ::= { v80210ServicesTable 1 }
 
        V80210ServicesEntry ::= SEQUENCE {
            v80210ServicesSlot
                INTEGER,
            v80210ServicesStation
                INTEGER,
            v80210ServicesDescription
		DisplayString,
            v80210ServicesBridgeID
                INTEGER
            }
 
        v80210ServicesSlot OBJECT-TYPE
            SYNTAX  INTEGER
            ACCESS  read-only
            STATUS  mandatory
            DESCRIPTION
                 "The slot number (1-based) of the physical port providing
                  the 80210 service."
            ::= { v80210ServicesEntry 1 }
 
        v80210ServicesStation OBJECT-TYPE
            SYNTAX  INTEGER
            ACCESS  read-only
            STATUS  mandatory
            DESCRIPTION
                 "The station number (1-based) within the physical port
                  providing the 80210 service."
            ::= { v80210ServicesEntry 2 }
  
        v80210ServicesDescription OBJECT-TYPE
            SYNTAX  DisplayString 
            ACCESS  read-write
            STATUS  mandatory
            DESCRIPTION
                 "A description of the 80210 service being provided."
            ::= { v80210ServicesEntry 3 }
 
        v80210ServicesBridgeID OBJECT-TYPE
            SYNTAX  INTEGER (0..65535)
            ACCESS  read-only
            STATUS  mandatory
            DESCRIPTION
                 "The VLAN ID of the Virtual Bridge port for the given
                  80210 service. A value of 0 means that the Virtual
                  Bridge port does not exist."
            ::= { v80210ServicesEntry 4 }
 
        v80210VlanTable  OBJECT-TYPE
            SYNTAX  SEQUENCE OF V80210VlanEntry
            ACCESS  not-accessible
            STATUS  mandatory
            DESCRIPTION
                 "A list of commands to add or remove Virtual LANs from
                  a 80210 service."
            ::= { v80210 2 }

        v80210VlanEntry  OBJECT-TYPE
            SYNTAX  V80210VlanEntry
            ACCESS  not-accessible
            STATUS  mandatory
            DESCRIPTION
                 "A 80210trunking Virtual LAN entry."
            INDEX { v80210Slot, v80210Station, v80210LanNumber }
            ::= { v80210VlanTable 1 }

        V80210VlanEntry ::= SEQUENCE {
            v80210Slot
                INTEGER,
            v80210Station
                INTEGER,
            v80210LanNumber
                INTEGER,
            v80210Command
                INTEGER
            }

	v80210Slot OBJECT-TYPE
	    SYNTAX  INTEGER 
	    ACCESS  read-only
	    STATUS  mandatory
	    DESCRIPTION
		 "The slot number (1-based) of the physical port providing 
		  the 80210 service."
	    ::= { v80210VlanEntry 1 }

	v80210Station OBJECT-TYPE
	    SYNTAX  INTEGER 
	    ACCESS  read-only
	    STATUS  mandatory
	    DESCRIPTION
		 "The station number (1-based) within the physical port
		  providing the 80210 service."
	    ::= { v80210VlanEntry 2 }

	v80210LanNumber OBJECT-TYPE
	    SYNTAX  INTEGER (1..65535)
	    ACCESS  read-only
	    STATUS  mandatory
	    DESCRIPTION
		 "The VLAN ID to be added to or removed from the given
	          80210 service."
	    ::= { v80210VlanEntry 3 }

	v80210Command OBJECT-TYPE
	    SYNTAX  INTEGER {
                        add(1),
                        remove(2)
            }
	    ACCESS  read-write
	    STATUS  mandatory
	    DESCRIPTION
		 "The command to either add or remove the specified VLAN ID
		  from the given 80210 service."
	    ::= { v80210VlanEntry 4 }

          -- the vDBr group

        vDBrServicesTable  OBJECT-TYPE
            SYNTAX  SEQUENCE OF VDBrServicesEntry
            ACCESS  not-accessible
            STATUS  mandatory
            DESCRIPTION
                 "A list of commands to add or remove Virtual LANs from
                  an DBr service."
            ::= { vDBr 1 }
 
        vDBrServicesEntry  OBJECT-TYPE
            SYNTAX  VDBrServicesEntry
            ACCESS  not-accessible
            STATUS  mandatory
            DESCRIPTION
                 "An DBr services entry."
            INDEX { vDBrServicesSlot, vDBrServicesStation }
            ::= { vDBrServicesTable 1 }
 
        VDBrServicesEntry ::= SEQUENCE {
            vDBrServicesSlot
                INTEGER,
            vDBrServicesStation
                INTEGER,
            vDBrServicesDescription
		DisplayString,
            vDBrServicesBridgeID
                INTEGER
            }
 
        vDBrServicesSlot OBJECT-TYPE
            SYNTAX  INTEGER
            ACCESS  read-only
            STATUS  mandatory
            DESCRIPTION
                 "The slot number (1-based) of the physical port providing
                  the DBr service."
            ::= { vDBrServicesEntry 1 }
 
        vDBrServicesStation OBJECT-TYPE
            SYNTAX  INTEGER
            ACCESS  read-only
            STATUS  mandatory
            DESCRIPTION
                 "The station number (1-based) within the physical port
                  providing the DBr service."
            ::= { vDBrServicesEntry 2 }
  
        vDBrServicesDescription OBJECT-TYPE
            SYNTAX  DisplayString 
            ACCESS  read-write
            STATUS  mandatory
            DESCRIPTION
                 "A description of the DBr service being provided."
            ::= { vDBrServicesEntry 3 }
 
        vDBrServicesBridgeID OBJECT-TYPE
            SYNTAX  INTEGER (0..65535)
            ACCESS  read-only
            STATUS  mandatory
            DESCRIPTION
                 "The VLAN ID of the Virtual Bridge port for the given
                  DBr service. A value of 0 means that the Virtual
                  Bridge port does not exist."
            ::= { vDBrServicesEntry 4 }
 
        vDBrVlanTable  OBJECT-TYPE
            SYNTAX  SEQUENCE OF VDBrVlanEntry
            ACCESS  not-accessible
            STATUS  mandatory
            DESCRIPTION
                 "A list of commands to add or remove Virtual LANs from
                  the DBr service."
            ::= { vDBr 2 }

        vDBrVlanEntry  OBJECT-TYPE
            SYNTAX  VDBrVlanEntry
            ACCESS  not-accessible
            STATUS  mandatory
            DESCRIPTION
                 "An DBr trunking Virtual LAN entry."
            INDEX { vDBrSlot, vDBrStation, vDBrLanNumber }
            ::= { vDBrVlanTable 1 }

        VDBrVlanEntry ::= SEQUENCE {
            vDBrSlot
                INTEGER,
            vDBrStation
                INTEGER,
            vDBrLanNumber
                INTEGER,
            vDBrCommand
                INTEGER
            }

	vDBrSlot OBJECT-TYPE
	    SYNTAX  INTEGER 
	    ACCESS  read-only
	    STATUS  mandatory
	    DESCRIPTION
		 "The slot number (1-based) of the physical port providing 
		  the DBr service."
	    ::= { vDBrVlanEntry 1 }

	vDBrStation OBJECT-TYPE
	    SYNTAX  INTEGER 
	    ACCESS  read-only
	    STATUS  mandatory
	    DESCRIPTION
		 "The station number (1-based) within the physical port
		  providing the DBr service."
	    ::= { vDBrVlanEntry 2 }

	vDBrLanNumber OBJECT-TYPE
	    SYNTAX  INTEGER (1..65535)
	    ACCESS  read-only
	    STATUS  mandatory
	    DESCRIPTION
		 "The VLAN ID to be added to or removed from the given
	          DBr service."
	    ::= { vDBrVlanEntry 3 }

	vDBrCommand OBJECT-TYPE
	    SYNTAX  INTEGER {
                        add(1),
                        remove(2)
            }
	    ACCESS  read-write
	    STATUS  mandatory
	    DESCRIPTION
		 "The command to either add or remove the specified VLAN ID
		  from the given DBr service."
	    ::= { vDBrVlanEntry 4 }

          -- the vDupMac group
 
          vDupMacMac OBJECT-TYPE
	      SYNTAX  MacAddress
              ACCESS  read-only
              STATUS  mandatory
              DESCRIPTION
                    "The router port's MAC address for which the last duplicate MAC address was detected ."
              ::= { vDupMac 1 }

          vDupMacSlot OBJECT-TYPE
              SYNTAX  INTEGER
              ACCESS  read-only
              STATUS  mandatory
              DESCRIPTION
                    "The slot number (1-based) where duplicate MAC address was last received."
              ::= { vDupMac 2 }

          vDupMacIntf OBJECT-TYPE
              SYNTAX  INTEGER
              ACCESS  read-only
              STATUS  mandatory
              DESCRIPTION
                    "The interface number (1-based) where duplicate MAC address was last received."
              ::= { vDupMac 3 }

          vDupMacTime OBJECT-TYPE
              SYNTAX  INTEGER
              ACCESS  read-only
              STATUS  mandatory
              DESCRIPTION
                    "The time in seconds that the duplicate MAC address was detected."
              ::= { vDupMac 4 }

	
	-- the 8021q group

	qGroupTable	OBJECT-TYPE
		SYNTAX	SEQUENCE OF QGroupEntry
		ACCESS	not-accessible
		STATUS	mandatory
		DESCRIPTION
		"This table lists the 802.1q groups on a port."
		::=	{ v8021Q 1 }
	
	qGroupEntry OBJECT-TYPE
		SYNTAX	QGroupEntry
		ACCESS	not-accessible
		STATUS	mandatory
		DESCRIPTION
		"An entry in 802.1q group table."
		INDEX { qGroupSlot, qGroupPort, qGroupGroupId }
		::= { qGroupTable 1 }

	QGroupEntry ::= SEQUENCE {
		qGroupSlot
			INTEGER,
		qGroupPort
			INTEGER,
		qGroupGroupId
			INTEGER,
		qGroupMode
			INTEGER,
		qGroupDescription
			DisplayString,
		qGroupTag
			INTEGER,
		qGroupPriority
			INTEGER,		
		qGroupAdminStatus
			INTEGER,
		qGroupTxPkts
			Counter,
		qGroupRxPkts
			Counter,
		qGroupTxOctets
			Counter,
		qGroupRxOctets
			Counter
		}

	qGroupSlot	OBJECT-TYPE
		SYNTAX	INTEGER
		ACCESS	read-write
		STATUS	mandatory
		DESCRIPTION
		"The slot id of the required port."
		::= { qGroupEntry 1 }

	qGroupPort	OBJECT-TYPE
		SYNTAX	INTEGER
		ACCESS	read-write
		STATUS	mandatory
		DESCRIPTION
		"The physical port number."
		::= { qGroupEntry 2 }

	qGroupGroupId OBJECT-TYPE
		SYNTAX	INTEGER
		ACCESS	read-write
		STATUS	mandatory
		DESCRIPTION
		"Group Id on the particular port."
		::= { qGroupEntry 3 }

	qGroupMode OBJECT-TYPE
		SYNTAX	INTEGER {
				gstsxylan(1),
				gstsieee(2),
				msts(3),
				ssts(4)
			}
		ACCESS	read-write
		STATUS	mandatory
		DESCRIPTION
		"gstsxylan(1) indicates spanning tree support on a gigabit port by proprietary mode and gstsieee(2) indicates spanning tree on a gigabit port by IEEE mode, msts(3) indicates multiple spanning tree support on a 10/100 Mammoth Ethernet port, and ssts(4) indicates single spanning tree support on a 10/100 Mammoth Ethernet port."
		::= { qGroupEntry 4 }

	qGroupDescription OBJECT-TYPE
		SYNTAX DisplayString ( SIZE (0..31) )
		ACCESS read-write
		STATUS	mandatory	
		DESCRIPTION
		"Textual description of multiple spanning tree."
		::= { qGroupEntry 5 }
	

	qGroupTag OBJECT-TYPE
		SYNTAX INTEGER 
		ACCESS read-write
		STATUS	mandatory	
		DESCRIPTION
		"Tag used for support multiple spanning tree."
		::= { qGroupEntry 6 }


	qGroupPriority OBJECT-TYPE
		SYNTAX INTEGER 
		ACCESS read-write
		STATUS	mandatory	
		DESCRIPTION
		"Priority used for support multiple spanning tree."
		::= { qGroupEntry 7 }


	qGroupAdminStatus OBJECT-TYPE
		SYNTAX	INTEGER {
				delete(0),
				create(1)
				}
		ACCESS	read-write
		STATUS	mandatory
		DESCRIPTION
		"Value of 0 indicates the service should be deleted, value of 1 indicates the service should be created."
		::= { qGroupEntry 8 }

	qGroupTxPkts	OBJECT-TYPE
		SYNTAX	Counter
		ACCESS	read-only
		STATUS	mandatory
		DESCRIPTION
		"Gives the number of transmitteded packets."
		::= { qGroupEntry 9 }

	qGroupRxPkts	OBJECT-TYPE
		SYNTAX	Counter
		ACCESS	read-only
		STATUS	mandatory
		DESCRIPTION
		"Gives the number of received packets."
		::= { qGroupEntry 10 }

	qGroupTxOctets	OBJECT-TYPE
		SYNTAX	Counter
		ACCESS	read-only
		STATUS	mandatory
		DESCRIPTION
		"Gives the number of transmitted bytes."
		::= { qGroupEntry 11 }

	qGroupRxOctets	OBJECT-TYPE
		SYNTAX	Counter
		ACCESS	read-only
		STATUS	mandatory
		DESCRIPTION
		"Gives the number of received bytes."
		::= { qGroupEntry 12 }
	
	-- end 8021q group 

	-- port mapping

	-- vPmapIngressTable	OBJECT IDENTIFIER::= { vPmap 1 }
	-- vPmapEgressTable	OBJECT IDENTIFIER::= { vPmap 2 }	
	-- vPmapConfigTable 	OBJECT IDENTIFIER::= { vPmap 3 }
	-- vPmapNextId		OBJECT IDENTIFIER::= { vPmap 4 }

	-- The vPmapIngressTable

	vPmapIngressTable	OBJECT-TYPE
		SYNTAX  SEQUENCE OF PmapIngressEntry
		ACCESS  not-accessible
		STATUS	mandatory
		DESCRIPTION
			"A list of Port Mapping	Ingress port table instance on this physical OmniSwitch or OSR."
		::= { vPmap 1 }

	vPmapIngressEntry	OBJECT-TYPE
		SYNTAX  PmapIngressEntry
		ACCESS  not-accessible
		STATUS	mandatory
		DESCRIPTION
			"A Port Mapping Ingress Port entry."
		INDEX { pMapIngressId, pMapIngressSlot, pMapIngressPort, pMapIngressSrvc, pMapIngressInst }
		::= { vPmapIngressTable 1 }

	PmapIngressEntry ::= SEQUENCE {
		pMapIngressId
			INTEGER,
		pMapIngressSlot
			INTEGER,
		pMapIngressPort
			INTEGER,
		pMapIngressSrvc
			INTEGER,
		pMapIngressInst
			INTEGER,
		pMapIngressAdminStatus
			INTEGER
		}


	pMapIngressId	OBJECT-TYPE
		SYNTAX	INTEGER(1..128)
		ACCESS  read-write
		STATUS  mandatory
		DESCRIPTION
			"A unique number that identifies this Port Mapping on the OmniSwitch or OSR."
		::= { vPmapIngressEntry 1 }

	
	pMapIngressSlot	OBJECT-TYPE
		SYNTAX	INTEGER(1..11)
		ACCESS  read-write
		STATUS  mandatory
		DESCRIPTION
			"A physical slot number on which the Port Mapping Ingress Port is configured."
		::= { vPmapIngressEntry 2 }


	pMapIngressPort	OBJECT-TYPE
		SYNTAX	INTEGER(1..32)
		ACCESS  read-write
		STATUS  mandatory
		DESCRIPTION
			"A physical port number that is associated with the Port Mapping Ingress Port."
		::= { vPmapIngressEntry 3 }


	pMapIngressSrvc	OBJECT-TYPE
		SYNTAX	INTEGER
		ACCESS  read-write
		STATUS  mandatory
		DESCRIPTION
			"A service type that is associated with this Port Mapping Ingress Port."
		::= { vPmapIngressEntry 4 }

	pMapIngressInst	OBJECT-TYPE
		SYNTAX	INTEGER
		ACCESS  read-write
		STATUS  mandatory
		DESCRIPTION
			"A Instance that is associated with this Port Mapping Ingress Port."
		::= { vPmapIngressEntry 5 }

	pMapIngressAdminStatus	OBJECT-TYPE
		SYNTAX	INTEGER {
				add (1),
				delete (2)
				}
		ACCESS  read-write
		STATUS  mandatory
		DESCRIPTION
			"This object indicates whether to add(1) to or delete(2) from the Port Mapping Ingress List."
		::= { vPmapIngressEntry 6 }


	-- The vPmapEgressTable

	vPmapEgressTable	OBJECT-TYPE
		SYNTAX  SEQUENCE OF PmapEgressEntry
		ACCESS  not-accessible
		STATUS	mandatory
		DESCRIPTION
			"A list of Port Mapping	Egress port table instance on this physical OmniSwitch or OSR."
		::= { vPmap 2 }

	vPmapEgressEntry	OBJECT-TYPE
		SYNTAX  PmapEgressEntry
		ACCESS  not-accessible
		STATUS	mandatory
		DESCRIPTION
			"A Port Mapping Egress Port entry."
		INDEX { pMapEgressId, pMapEgressSlot, pMapEgressPort, pMapEgressSrvc, pMapEgressInst }
		::= { vPmapEgressTable 1 }

	PmapEgressEntry ::= SEQUENCE {
		pMapEgressId
			INTEGER,
		pMapEgressSlot
			INTEGER,
		pMapEgressPort
			INTEGER,
		pMapEgressSrvc
			INTEGER,
		pMapEgressInst
			INTEGER,
		pMapEgressAdminStatus
			INTEGER
		}


	pMapEgressId	OBJECT-TYPE
		SYNTAX	INTEGER(1..254)
		ACCESS  read-write
		STATUS  mandatory
		DESCRIPTION
			"A unique number that identifies this Port Mapping on the physical OmniSwitch or OSR."
		::= { vPmapEgressEntry 1 }

	
	pMapEgressSlot	OBJECT-TYPE
		SYNTAX	INTEGER(1..11)
		ACCESS  read-write
		STATUS  mandatory
		DESCRIPTION
			"A physical slot number on whitch the Port Mapping Egress Port is configured."
		::= { vPmapEgressEntry 2 }


	pMapEgressPort	OBJECT-TYPE
		SYNTAX	INTEGER(1..32)
		ACCESS  read-write
		STATUS  mandatory
		DESCRIPTION
			"A physical port number that is associated with the Port Mapping Egress Port."
		::= { vPmapEgressEntry 3 }


	pMapEgressSrvc	OBJECT-TYPE
		SYNTAX	INTEGER
		ACCESS  read-write
		STATUS  mandatory
		DESCRIPTION
			"A service type that is associated with this Port Mapping Egress Port."
		::= { vPmapEgressEntry 4 }

	pMapEgressInst	OBJECT-TYPE
		SYNTAX	INTEGER
		ACCESS  read-write
		STATUS  mandatory
		DESCRIPTION
			"A Instance that is associated with this Port Mapping Egress Port."
		::= { vPmapEgressEntry 5 }

	pMapEgressAdminStatus	OBJECT-TYPE
		SYNTAX	INTEGER {
				add (1),
				delete (2)
				}
		ACCESS  read-write
		STATUS  mandatory
		DESCRIPTION
			"This object indicates whether to add(1) to or delete(2) from the Port Mapping Egress Port."
		::= { vPmapEgressEntry 6 }
	

	-- The vPmapConfigTable 
		
	vPmapConfigTable	OBJECT-TYPE		
		SYNTAX  SEQUENCE OF PmapConfigEntry
		ACCESS  not-accessible
		STATUS	mandatory
		DESCRIPTION
			"A list of Port Mapping	config table instance on this physical OmniSwitch or OSR."
		::= { vPmap 3 }
		
	 	
	 vPmapConfigEntry	OBJECT-TYPE	
		SYNTAX  PmapConfigEntry
		ACCESS  not-accessible
		STATUS	mandatory
		DESCRIPTION
			"A Port Mapping configuration table entry."
		INDEX { pMapConfigId }
		::= { vPmapConfigTable 1 }

	PmapConfigEntry ::= SEQUENCE {
		pMapConfigId
			INTEGER,
		pMapConfigStatus
			INTEGER
		}

	pMapConfigId	OBJECT-TYPE
		SYNTAX	INTEGER(1..128)
		ACCESS  read-only
		STATUS  mandatory
		DESCRIPTION
			"A unique number that identifies this Port Mapping with the physical OmniSwitch or OSR."
		::= { vPmapConfigEntry 1 }
	
	pMapConfigStatus	OBJECT-TYPE
		SYNTAX	INTEGER {
				set (1),
				delete (2)
				}
		ACCESS  read-write
		STATUS  mandatory
		DESCRIPTION
			"This object indicates whether to set (1) or delete (2) the port mapping configeration.."
		::= { vPmapConfigEntry 2 }

	
	vPmapNextId	OBJECT-TYPE
		SYNTAX  INTEGER (1..128)
		ACCESS  read-only
		STATUS	mandatory
		DESCRIPTION
			"The unique number that identifiers the next Port Mapping Table."
		::= { vPmap 4 }

	END
