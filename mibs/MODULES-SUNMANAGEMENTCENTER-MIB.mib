--
--
--
MODULES-SUNMANAGEMENTCENTER-MIB DEFINITIONS ::= BEGIN

  IMPORTS
	enterprises, NOTIFICATION-TYPE, OBJECT-TYPE, MODULE-IDENTITY
		FROM SNMPv2-SMI;

sun             OBJECT IDENTIFIER ::= { enterprises 42 }
prod            OBJECT IDENTIFIER ::= { sun 2 }
sunsymon        OBJECT IDENTIFIER ::= { prod 12 }
agent           OBJECT IDENTIFIER ::= { sunsymon 2 }
base            OBJECT IDENTIFIER ::= { agent 1 }
modules		OBJECT IDENTIFIER ::= { agent 2 }
info		OBJECT IDENTIFIER ::= { base 2 }

--
system		OBJECT IDENTIFIER ::= { info 1 }

--
hardware		OBJECT IDENTIFIER ::= { modules 1 }
operatingSystem		OBJECT IDENTIFIER ::= { modules 2 }
localApplication	OBJECT IDENTIFIER ::= { modules 3 }
remoteSystem		OBJECT IDENTIFIER ::= { modules 4 }
serverSupport		OBJECT IDENTIFIER ::= { modules 5 }
dr			OBJECT IDENTIFIER ::= { modules 10 }
healthMonitor		OBJECT IDENTIFIER ::= { modules 11 }
kernelReader		OBJECT IDENTIFIER ::= { modules 12 }
processDetails		OBJECT IDENTIFIER ::= { modules 13 }
mib2Proxy		OBJECT IDENTIFIER ::= { modules 14 }
dtable			OBJECT IDENTIFIER ::= { modules 15 }
kernelReaderSimple	OBJECT IDENTIFIER ::= { modules 16 }
hdreg			OBJECT IDENTIFIER ::= { modules 17 }
a5x00			OBJECT IDENTIFIER ::= { modules 18 }
t300			OBJECT IDENTIFIER ::= { modules 19 }
processTable		OBJECT IDENTIFIER ::= { modules 20 }
datalogRegistry		OBJECT IDENTIFIER ::= { modules 21 }
dirmon			OBJECT IDENTIFIER ::= { modules 22 }
filemon			OBJECT IDENTIFIER ::= { modules 23 }
fscan			OBJECT IDENTIFIER ::= { modules 24 }
hpJetdirect		OBJECT IDENTIFIER ::= { modules 25 }
nfsmon			OBJECT IDENTIFIER ::= { modules 27 }
nfsstat			OBJECT IDENTIFIER ::= { modules 28 }
printSpool		OBJECT IDENTIFIER ::= { modules 29 }
agentStats		OBJECT IDENTIFIER ::= { modules 30 }
domainControl		OBJECT IDENTIFIER ::= { modules 31 }
topologyLicense		OBJECT IDENTIFIER ::= { modules 32 }
topology		OBJECT IDENTIFIER ::= { modules 33 }
cfgserver		OBJECT IDENTIFIER ::= { modules 34 }
eventmgr		OBJECT IDENTIFIER ::= { modules 35 }
toolAdhocs		OBJECT IDENTIFIER ::= { modules 36 }
printSpoolv3		OBJECT IDENTIFIER ::= { modules 37 }
discovery		OBJECT IDENTIFIER ::= { modules 38 }
ipv6			OBJECT IDENTIFIER ::= { modules 39 }
agent-update		OBJECT IDENTIFIER ::= { modules 40 }
altpath			OBJECT IDENTIFIER ::= { modules 45 }
metadataManager		OBJECT IDENTIFIER ::= { modules 46 }
logview			OBJECT IDENTIFIER ::= { modules 47 }
mcp			OBJECT IDENTIFIER ::= { modules 48 }
builder			OBJECT IDENTIFIER ::= { modules 49 }
dr-serengeti		OBJECT IDENTIFIER ::= { modules 51 }
em			OBJECT IDENTIFIER ::= { modules 52 }
crashdump		OBJECT IDENTIFIER ::= { modules 53 }
filewch			OBJECT IDENTIFIER ::= { modules 54 }
patchmgt		OBJECT IDENTIFIER ::= { modules 55 }
scriptLauncher		OBJECT IDENTIFIER ::= { modules 56 }
scriptRepository	OBJECT IDENTIFIER ::= { modules 57 }
httpST			OBJECT IDENTIFIER ::= { modules 58 }
ftpST			OBJECT IDENTIFIER ::= { modules 59 }
telnetST		OBJECT IDENTIFIER ::= { modules 60 }
dnsST			OBJECT IDENTIFIER ::= { modules 61 }
nisST			OBJECT IDENTIFIER ::= { modules 62 }
ldapST			OBJECT IDENTIFIER ::= { modules 63 }
smtpST			OBJECT IDENTIFIER ::= { modules 64 }
imapST			OBJECT IDENTIFIER ::= { modules 65 }
popST			OBJECT IDENTIFIER ::= { modules 66 }
calendarST		OBJECT IDENTIFIER ::= { modules 67 }
httpSE			OBJECT IDENTIFIER ::= { modules 68 }
ftpSE			OBJECT IDENTIFIER ::= { modules 69 }
telnetSE		OBJECT IDENTIFIER ::= { modules 70 }
dnsSE			OBJECT IDENTIFIER ::= { modules 71 }
nisSE			OBJECT IDENTIFIER ::= { modules 72 }
ldapSE			OBJECT IDENTIFIER ::= { modules 73 }
smtpSE			OBJECT IDENTIFIER ::= { modules 74 }
imapSE			OBJECT IDENTIFIER ::= { modules 75 }
popSE			OBJECT IDENTIFIER ::= { modules 76 }
calendarSE		OBJECT IDENTIFIER ::= { modules 77 }
edot			OBJECT IDENTIFIER ::= { modules 78 }
pkgchk			OBJECT IDENTIFIER ::= { modules 81 }
patchadmin		OBJECT IDENTIFIER ::= { modules 82 }
perftool		OBJECT IDENTIFIER ::= { modules 88 }
ichange			OBJECT IDENTIFIER ::= { modules 89 }
v880-dr			OBJECT IDENTIFIER ::= { modules 90 }
serengeti-platadmin	OBJECT IDENTIFIER ::= { modules 100 }
serengeti-rules		OBJECT IDENTIFIER ::= { modules 101 }
cod			OBJECT IDENTIFIER ::= { modules 200 }


--
--
config		OBJECT IDENTIFIER ::= { hardware 1 }
reader4u	OBJECT IDENTIFIER ::= { config 1 }
reader4udt	OBJECT IDENTIFIER ::= { config 2 }
reader4uwg	OBJECT IDENTIFIER ::= { config 3 }
reader4u1P	OBJECT IDENTIFIER ::= { config 4 }
reader4u1D	OBJECT IDENTIFIER ::= { config 5 }
reader4unt	OBJECT IDENTIFIER ::= { config 6 }
readerSerengeti OBJECT IDENTIFIER ::= { config 7 }
reader4uvh	OBJECT IDENTIFIER ::= { config 8 }
readerECP	OBJECT IDENTIFIER ::= { config 9 }
readerELP	OBJECT IDENTIFIER ::= { config 10 }


END
