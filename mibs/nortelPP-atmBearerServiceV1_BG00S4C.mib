Nortel-Magellan-Passport-AtmBearerServiceMIB
DEFINITIONS ::= BEGIN



IMPORTS

      OBJECT-TYPE
   FROM RFC-1212

      passportMIBs
   FROM Nortel-Magellan-Passport-UsefulDefinitionsMIB

      DisplayString,
      StorageType,
      RowStatus
   FROM Nortel-Magellan-Passport-StandardTextualConventionsMIB

      NonReplicated,
      Link
   FROM Nortel-Magellan-Passport-TextualConventionsMIB

      atmIfVccIndex,
      atmIfVptIndex,
      atmIfVcc,
      atmIfVpcIndex,
      atmIfVpc,
      atmIfVptVccIndex,
      atmIfIndex,
      atmIfVptVcc
   FROM Nortel-Magellan-Passport-AtmCoreMIB;




-- LAST-UPDATED   "9808030000Z"
-- ORGANIZATION   "Nortel"
-- CONTACT-INFO   "
--         Nortel Magellan Network Management
--         
--         Postal: P.O. Box 5080, Station F 
--                 Ottawa, Ontario 
--                 Canada  K2C 3T1
--         
--         Email:  nm_plm@nt.com"
-- DESCRIPTION
--    "The module describing the Nortel Magellan Passport
--     AtmBearerService Enterprise MIB."

atmBearerServiceMIB OBJECT IDENTIFIER ::= { passportMIBs 64 }










-- AtmIf/n Vcc/vpi.vci Nrp
-- This component is used to establish a single hop of a nailed-up 
-- ATM Bearer Service (ABS) connection. By linking together two 
-- Nrps within a module, the associated connections are configured to 
-- relay ATM cells to one another. The Nrp component requires 
-- exclusive use of its parent Vcc or Vpc and cannot co-exist with other 
-- ATM service components (such as Nep, Test, and Loop).

atmIfVpcNrp OBJECT IDENTIFIER ::= { atmIfVpc 4 }



atmIfVpcNrpRowStatusTable OBJECT-TYPE
   SYNTAX     SEQUENCE OF AtmIfVpcNrpRowStatusEntry
   ACCESS     not-accessible
   STATUS     mandatory
   DESCRIPTION
     "This entry controls the addition and deletion of 
      atmIfVpcNrp components."
::= { atmIfVpcNrp 1 }

atmIfVpcNrpRowStatusEntry OBJECT-TYPE
   SYNTAX     AtmIfVpcNrpRowStatusEntry
   ACCESS     not-accessible
   STATUS     mandatory
   DESCRIPTION
     "A single entry in the table represents a single 
      atmIfVpcNrp component."
   INDEX {
      atmIfIndex,
      atmIfVpcIndex,
      atmIfVpcNrpIndex }
::= { atmIfVpcNrpRowStatusTable 1 }

AtmIfVpcNrpRowStatusEntry ::= SEQUENCE {
   atmIfVpcNrpRowStatus
      RowStatus,
   atmIfVpcNrpComponentName
      DisplayString,
   atmIfVpcNrpStorageType
      StorageType,
   atmIfVpcNrpIndex
      NonReplicated }

atmIfVpcNrpRowStatus OBJECT-TYPE
   SYNTAX     RowStatus 
   ACCESS     read-write
   STATUS     mandatory
   DESCRIPTION
     "This variable is used as the basis for SNMP naming of
      atmIfVpcNrp components.
      These components can be added and deleted."
::= { atmIfVpcNrpRowStatusEntry 1 }

atmIfVpcNrpComponentName OBJECT-TYPE
   SYNTAX     DisplayString 
   ACCESS     read-only
   STATUS     mandatory
   DESCRIPTION
     "This variable provides the component's string name for
      use with the ASCII Console Interface"
::= { atmIfVpcNrpRowStatusEntry 2 }

atmIfVpcNrpStorageType OBJECT-TYPE
   SYNTAX     StorageType 
   ACCESS     read-only
   STATUS     mandatory
   DESCRIPTION
     "This variable represents the storage type value for the
      atmIfVpcNrp tables."
::= { atmIfVpcNrpRowStatusEntry 4 }

atmIfVpcNrpIndex OBJECT-TYPE
   SYNTAX     NonReplicated 
   ACCESS     not-accessible
   STATUS     mandatory
   DESCRIPTION
     "This variable represents the index for the atmIfVpcNrp tables."
::= { atmIfVpcNrpRowStatusEntry 10 }

atmIfVpcNrpProvTable OBJECT-TYPE
   SYNTAX     SEQUENCE OF AtmIfVpcNrpProvEntry
   ACCESS     not-accessible
   STATUS     mandatory
   DESCRIPTION
     "This group contains the provisionable attributes for the Nrp 
      component."
::= { atmIfVpcNrp 100 }

atmIfVpcNrpProvEntry OBJECT-TYPE
   SYNTAX     AtmIfVpcNrpProvEntry
   ACCESS     not-accessible
   STATUS     mandatory
   DESCRIPTION
     "An entry in the atmIfVpcNrpProvTable."
   INDEX {
      atmIfIndex,
      atmIfVpcIndex,
      atmIfVpcNrpIndex }
::= { atmIfVpcNrpProvTable 1 }

AtmIfVpcNrpProvEntry ::= SEQUENCE {
   atmIfVpcNrpNextHop
      Link,
   atmIfVpcNrpConnectionPointType
      INTEGER,
   atmIfVpcNrpOamSegmentBoundary
      INTEGER,
   atmIfVpcNrpTxAal5PartialPacketDiscard
      INTEGER,
   atmIfVpcNrpRxAal5PartialPacketDiscard
      INTEGER,
   atmIfVpcNrpBandwidthElastic
      INTEGER,
   atmIfVpcNrpOverrideHoldingPriority
      INTEGER }

atmIfVpcNrpNextHop OBJECT-TYPE
   SYNTAX     Link 
   ACCESS     read-write
   STATUS     mandatory
   DESCRIPTION
     "This attribute specifies the Nrp component with which this Nrp is 
      associated. A sample value is AtmIf/31 Vcc/0.32 Nrp."
::= { atmIfVpcNrpProvEntry 10 }

atmIfVpcNrpConnectionPointType OBJECT-TYPE
   SYNTAX     INTEGER  {
                 segmentEndPoint(1),
                 connectingPoint(2),
                 autoConfigure(4) }
   ACCESS     read-write
   STATUS     obsolete
   DESCRIPTION
     "This attribute specifies the connection point type desired for a Nrp 
      component. The actual connection point type value is visible in the 
      parent component's connectionPointType attribute. 
      
      The desired connection point type can be specified directly as a 
      segmentEndPoint or connectingPoint. If autoConfigure is 
      specified, the switch will select the connection point type based on 
      the type attribute of the associated AtmIf, choosing 
      segmentEndPoint for a UNI-type ATM interface and 
      connectingPoint for a PPI-type ATM interface.
      
      It is obsoleted. The value is mapped into oamSegmentBoundary 
      attribute. segmentEndPoint is mapped into yes. connectingPoint is 
      mapped into no. autoConfigure is mapped into sameAsInterface."
   DEFVAL     { autoConfigure }
::= { atmIfVpcNrpProvEntry 20 }

atmIfVpcNrpOamSegmentBoundary OBJECT-TYPE
   SYNTAX     INTEGER  {
                 no(0),
                 yes(1),
                 sameAsInterface(2) }
   ACCESS     read-write
   STATUS     mandatory
   DESCRIPTION
     "This attribute specifies the OAM segment boundary desired for a 
      Nrp component. It affects the connection point type value visible in 
      the parent component's connectionPointType attribute. 
      
      The desired OAM segment boundary can be specified directly as 
      yes, no or sameAsInterface. If sameAsInterface is specified, the 
      OAM segment boundary is same as the oamSegmentBoundary 
      attribute of the associated AtmIf and the switch will set the 
      connectionPointType, choosing segmentEndPoint for a segment-
      boundary ATM interface and connectingPoint for a non-segment-
      boundary ATM interface."
   DEFVAL     { sameAsInterface }
::= { atmIfVpcNrpProvEntry 30 }

atmIfVpcNrpTxAal5PartialPacketDiscard OBJECT-TYPE
   SYNTAX     INTEGER  {
                 disabled(0),
                 enabled(1) }
   ACCESS     read-write
   STATUS     obsolete
   DESCRIPTION
     "This attribute is obsolete in P4.2 and has been migrated under Vcd 
      (Vpd) component. 
      
      This attribute specifies whether the AAL5 Partial Packet Discard 
      (PPD) feature has been enabled or disabled on the Nrp in the 
      transmit direction. This feature allows the NRP to discard the 
      remainder of a cell-forwarded AAL5 frame if a cell of this frame 
      has been discarded due to congestion. This increases the 'goodput' 
      of the link, since cells which are only going to be discarded by the 
      AAL5 reassembly are not transmitted.
      
      When this attribute is set to enabled, the PPD feature is applied in 
      the transmit direction. It should only be enabled for connections 
      whose end points are performing AAL5 segmentation and 
      reassembly. When this attribute is set to disabled, the PPD feature is 
      not applied to traffic for this connection in the transmit direction. 
      Note that specifying enabled for a non-AAL5 connection will cause 
      all traffic to be discarded once congestion is encountered."
   DEFVAL     { disabled }
::= { atmIfVpcNrpProvEntry 31 }

atmIfVpcNrpRxAal5PartialPacketDiscard OBJECT-TYPE
   SYNTAX     INTEGER  {
                 disabled(0),
                 enabled(1),
                 sameAsTx(2) }
   ACCESS     read-write
   STATUS     obsolete
   DESCRIPTION
     "This attribute is obsolete in P4.2 and has been migrated under Vcd 
      (Vpd) component.
      
      This attribute specifies whether the AAL5 Partial Packet Discard 
      (PPD) feature has been enabled or disabled on the Nrp in the 
      receive direction. This feature allows the NRP to discard the 
      remainder of a cell-forwarded AAL5 frame if a cell of this frame 
      has been discarded due to congestion or usage parameter control 
      (UPC). This increases the 'goodput' of the link, since cells which 
      are only going to be discarded by the AAL5 reassembly are not 
      transmitted.
      
      When this attribute is set to enabled, the PPD feature is applied in 
      the receive direction. It should only be enabled for connections 
      whose end points are performing AAL5 segmentation and 
      reassembly. When this attribute is set to disabled, the PPD feature is 
      not applied to traffic for this connection in the receive direction. 
      When this attribute is set to sameAsTx, the PPD feature for traffic 
      in the receive direction will be configured the same way as it is in 
      the transmit direction. 
      Note that specifying enabled for a non-AAL5 connection will cause 
      all traffic to be discarded once congestion is encountered."
   DEFVAL     { sameAsTx }
::= { atmIfVpcNrpProvEntry 32 }

atmIfVpcNrpBandwidthElastic OBJECT-TYPE
   SYNTAX     INTEGER  {
                 no(0),
                 yes(1) }
   ACCESS     read-write
   STATUS     mandatory
   DESCRIPTION
     "This attribute is only of importance for connections which are 
      carried on a link with a variable bandwidth. For example, the 
      bandwidth may be reduced in the event that one or more physical 
      links in the IMA group fail, such that the originally requested 
      bandwidth cannot be maintained. This attribute shows whether the 
      application running on this connection can continue to operate if the 
      bandwidth is reduced. If the bandwidth is reduced, the amount by 
      which it is reduced will be displayed in the bandwidthReduction 
      attribute. 
      
      A value of yes, indicates that this connection is elastic, and the 
      bandwidth may be reduced but the connection will not be released. 
      Currently, this attribute should only be set to yes for situations 
      where this Nrp is functioning as a loopback on one side of an IMA 
      link. There are no other situations where this setting is valid.
      
      A value of no indicates that the bandwidth for this connection will 
      not be reduced in the event of link bandwidth reduction. However, 
      this connection may be released based on its holdingPriority."
   DEFVAL     { no }
::= { atmIfVpcNrpProvEntry 33 }

atmIfVpcNrpOverrideHoldingPriority OBJECT-TYPE
   SYNTAX     INTEGER  {
                 n0(0),
                 n1(1),
                 n2(2),
                 n3(3),
                 n4(4),
                 noOverride(6) }
   ACCESS     read-write
   STATUS     mandatory
   DESCRIPTION
     "This attribute specifies the holding priority of this connection. 
      Holding priority is used when there is an IMA group where some 
      physical links have failed. Holding priority determines the order in 
      which connections are released. 4 is the lowest holding priority and 
      is released first. 0 is a higher priority and is released last. The value 
      specified in this attribute will override whatever holdingPriority that 
      has been provisioned at the Vcd (or Vpd). If the value is left at the 
      default of noOverride, the holdingPriority provisioned at the Vcd 
      (or Vpd) will be used."
   DEFVAL     { noOverride }
::= { atmIfVpcNrpProvEntry 34 }


-- AtmIf/n Vcc/vpi.vci Nrp
-- This component is used to establish a single hop of a nailed-up 
-- ATM Bearer Service (ABS) connection. By linking together two 
-- Nrps within a module, the associated connections are configured to 
-- relay ATM cells to one another. The Nrp component requires 
-- exclusive use of its parent Vcc or Vpc and cannot co-exist with other 
-- ATM service components (such as Nep, Test, and Loop).

atmIfVccNrp OBJECT IDENTIFIER ::= { atmIfVcc 4 }



atmIfVccNrpRowStatusTable OBJECT-TYPE
   SYNTAX     SEQUENCE OF AtmIfVccNrpRowStatusEntry
   ACCESS     not-accessible
   STATUS     mandatory
   DESCRIPTION
     "This entry controls the addition and deletion of 
      atmIfVccNrp components."
::= { atmIfVccNrp 1 }

atmIfVccNrpRowStatusEntry OBJECT-TYPE
   SYNTAX     AtmIfVccNrpRowStatusEntry
   ACCESS     not-accessible
   STATUS     mandatory
   DESCRIPTION
     "A single entry in the table represents a single 
      atmIfVccNrp component."
   INDEX {
      atmIfIndex,
      atmIfVccIndex,
      atmIfVccNrpIndex }
::= { atmIfVccNrpRowStatusTable 1 }

AtmIfVccNrpRowStatusEntry ::= SEQUENCE {
   atmIfVccNrpRowStatus
      RowStatus,
   atmIfVccNrpComponentName
      DisplayString,
   atmIfVccNrpStorageType
      StorageType,
   atmIfVccNrpIndex
      NonReplicated }

atmIfVccNrpRowStatus OBJECT-TYPE
   SYNTAX     RowStatus 
   ACCESS     read-write
   STATUS     mandatory
   DESCRIPTION
     "This variable is used as the basis for SNMP naming of
      atmIfVccNrp components.
      These components can be added and deleted."
::= { atmIfVccNrpRowStatusEntry 1 }

atmIfVccNrpComponentName OBJECT-TYPE
   SYNTAX     DisplayString 
   ACCESS     read-only
   STATUS     mandatory
   DESCRIPTION
     "This variable provides the component's string name for
      use with the ASCII Console Interface"
::= { atmIfVccNrpRowStatusEntry 2 }

atmIfVccNrpStorageType OBJECT-TYPE
   SYNTAX     StorageType 
   ACCESS     read-only
   STATUS     mandatory
   DESCRIPTION
     "This variable represents the storage type value for the
      atmIfVccNrp tables."
::= { atmIfVccNrpRowStatusEntry 4 }

atmIfVccNrpIndex OBJECT-TYPE
   SYNTAX     NonReplicated 
   ACCESS     not-accessible
   STATUS     mandatory
   DESCRIPTION
     "This variable represents the index for the atmIfVccNrp tables."
::= { atmIfVccNrpRowStatusEntry 10 }

atmIfVccNrpProvTable OBJECT-TYPE
   SYNTAX     SEQUENCE OF AtmIfVccNrpProvEntry
   ACCESS     not-accessible
   STATUS     mandatory
   DESCRIPTION
     "This group contains the provisionable attributes for the Nrp 
      component."
::= { atmIfVccNrp 100 }

atmIfVccNrpProvEntry OBJECT-TYPE
   SYNTAX     AtmIfVccNrpProvEntry
   ACCESS     not-accessible
   STATUS     mandatory
   DESCRIPTION
     "An entry in the atmIfVccNrpProvTable."
   INDEX {
      atmIfIndex,
      atmIfVccIndex,
      atmIfVccNrpIndex }
::= { atmIfVccNrpProvTable 1 }

AtmIfVccNrpProvEntry ::= SEQUENCE {
   atmIfVccNrpNextHop
      Link,
   atmIfVccNrpConnectionPointType
      INTEGER,
   atmIfVccNrpOamSegmentBoundary
      INTEGER,
   atmIfVccNrpTxAal5PartialPacketDiscard
      INTEGER,
   atmIfVccNrpRxAal5PartialPacketDiscard
      INTEGER,
   atmIfVccNrpBandwidthElastic
      INTEGER,
   atmIfVccNrpOverrideHoldingPriority
      INTEGER }

atmIfVccNrpNextHop OBJECT-TYPE
   SYNTAX     Link 
   ACCESS     read-write
   STATUS     mandatory
   DESCRIPTION
     "This attribute specifies the Nrp component with which this Nrp is 
      associated. A sample value is AtmIf/31 Vcc/0.32 Nrp."
::= { atmIfVccNrpProvEntry 10 }

atmIfVccNrpConnectionPointType OBJECT-TYPE
   SYNTAX     INTEGER  {
                 segmentEndPoint(1),
                 connectingPoint(2),
                 autoConfigure(4) }
   ACCESS     read-write
   STATUS     obsolete
   DESCRIPTION
     "This attribute specifies the connection point type desired for a Nrp 
      component. The actual connection point type value is visible in the 
      parent component's connectionPointType attribute. 
      
      The desired connection point type can be specified directly as a 
      segmentEndPoint or connectingPoint. If autoConfigure is 
      specified, the switch will select the connection point type based on 
      the type attribute of the associated AtmIf, choosing 
      segmentEndPoint for a UNI-type ATM interface and 
      connectingPoint for a PPI-type ATM interface.
      
      It is obsoleted. The value is mapped into oamSegmentBoundary 
      attribute. segmentEndPoint is mapped into yes. connectingPoint is 
      mapped into no. autoConfigure is mapped into sameAsInterface."
   DEFVAL     { autoConfigure }
::= { atmIfVccNrpProvEntry 20 }

atmIfVccNrpOamSegmentBoundary OBJECT-TYPE
   SYNTAX     INTEGER  {
                 no(0),
                 yes(1),
                 sameAsInterface(2) }
   ACCESS     read-write
   STATUS     mandatory
   DESCRIPTION
     "This attribute specifies the OAM segment boundary desired for a 
      Nrp component. It affects the connection point type value visible in 
      the parent component's connectionPointType attribute. 
      
      The desired OAM segment boundary can be specified directly as 
      yes, no or sameAsInterface. If sameAsInterface is specified, the 
      OAM segment boundary is same as the oamSegmentBoundary 
      attribute of the associated AtmIf and the switch will set the 
      connectionPointType, choosing segmentEndPoint for a segment-
      boundary ATM interface and connectingPoint for a non-segment-
      boundary ATM interface."
   DEFVAL     { sameAsInterface }
::= { atmIfVccNrpProvEntry 30 }

atmIfVccNrpTxAal5PartialPacketDiscard OBJECT-TYPE
   SYNTAX     INTEGER  {
                 disabled(0),
                 enabled(1) }
   ACCESS     read-write
   STATUS     obsolete
   DESCRIPTION
     "This attribute is obsolete in P4.2 and has been migrated under Vcd 
      (Vpd) component. 
      
      This attribute specifies whether the AAL5 Partial Packet Discard 
      (PPD) feature has been enabled or disabled on the Nrp in the 
      transmit direction. This feature allows the NRP to discard the 
      remainder of a cell-forwarded AAL5 frame if a cell of this frame 
      has been discarded due to congestion. This increases the 'goodput' 
      of the link, since cells which are only going to be discarded by the 
      AAL5 reassembly are not transmitted.
      
      When this attribute is set to enabled, the PPD feature is applied in 
      the transmit direction. It should only be enabled for connections 
      whose end points are performing AAL5 segmentation and 
      reassembly. When this attribute is set to disabled, the PPD feature is 
      not applied to traffic for this connection in the transmit direction. 
      Note that specifying enabled for a non-AAL5 connection will cause 
      all traffic to be discarded once congestion is encountered."
   DEFVAL     { disabled }
::= { atmIfVccNrpProvEntry 31 }

atmIfVccNrpRxAal5PartialPacketDiscard OBJECT-TYPE
   SYNTAX     INTEGER  {
                 disabled(0),
                 enabled(1),
                 sameAsTx(2) }
   ACCESS     read-write
   STATUS     obsolete
   DESCRIPTION
     "This attribute is obsolete in P4.2 and has been migrated under Vcd 
      (Vpd) component.
      
      This attribute specifies whether the AAL5 Partial Packet Discard 
      (PPD) feature has been enabled or disabled on the Nrp in the 
      receive direction. This feature allows the NRP to discard the 
      remainder of a cell-forwarded AAL5 frame if a cell of this frame 
      has been discarded due to congestion or usage parameter control 
      (UPC). This increases the 'goodput' of the link, since cells which 
      are only going to be discarded by the AAL5 reassembly are not 
      transmitted.
      
      When this attribute is set to enabled, the PPD feature is applied in 
      the receive direction. It should only be enabled for connections 
      whose end points are performing AAL5 segmentation and 
      reassembly. When this attribute is set to disabled, the PPD feature is 
      not applied to traffic for this connection in the receive direction. 
      When this attribute is set to sameAsTx, the PPD feature for traffic 
      in the receive direction will be configured the same way as it is in 
      the transmit direction. 
      Note that specifying enabled for a non-AAL5 connection will cause 
      all traffic to be discarded once congestion is encountered."
   DEFVAL     { sameAsTx }
::= { atmIfVccNrpProvEntry 32 }

atmIfVccNrpBandwidthElastic OBJECT-TYPE
   SYNTAX     INTEGER  {
                 no(0),
                 yes(1) }
   ACCESS     read-write
   STATUS     mandatory
   DESCRIPTION
     "This attribute is only of importance for connections which are 
      carried on a link with a variable bandwidth. For example, the 
      bandwidth may be reduced in the event that one or more physical 
      links in the IMA group fail, such that the originally requested 
      bandwidth cannot be maintained. This attribute shows whether the 
      application running on this connection can continue to operate if the 
      bandwidth is reduced. If the bandwidth is reduced, the amount by 
      which it is reduced will be displayed in the bandwidthReduction 
      attribute. 
      
      A value of yes, indicates that this connection is elastic, and the 
      bandwidth may be reduced but the connection will not be released. 
      Currently, this attribute should only be set to yes for situations 
      where this Nrp is functioning as a loopback on one side of an IMA 
      link. There are no other situations where this setting is valid.
      
      A value of no indicates that the bandwidth for this connection will 
      not be reduced in the event of link bandwidth reduction. However, 
      this connection may be released based on its holdingPriority."
   DEFVAL     { no }
::= { atmIfVccNrpProvEntry 33 }

atmIfVccNrpOverrideHoldingPriority OBJECT-TYPE
   SYNTAX     INTEGER  {
                 n0(0),
                 n1(1),
                 n2(2),
                 n3(3),
                 n4(4),
                 noOverride(6) }
   ACCESS     read-write
   STATUS     mandatory
   DESCRIPTION
     "This attribute specifies the holding priority of this connection. 
      Holding priority is used when there is an IMA group where some 
      physical links have failed. Holding priority determines the order in 
      which connections are released. 4 is the lowest holding priority and 
      is released first. 0 is a higher priority and is released last. The value 
      specified in this attribute will override whatever holdingPriority that 
      has been provisioned at the Vcd (or Vpd). If the value is left at the 
      default of noOverride, the holdingPriority provisioned at the Vcd 
      (or Vpd) will be used."
   DEFVAL     { noOverride }
::= { atmIfVccNrpProvEntry 34 }


-- AtmIf/n Vcc/vpi.vci Nrp
-- This component is used to establish a single hop of a nailed-up 
-- ATM Bearer Service (ABS) connection. By linking together two 
-- Nrps within a module, the associated connections are configured to 
-- relay ATM cells to one another. The Nrp component requires 
-- exclusive use of its parent Vcc or Vpc and cannot co-exist with other 
-- ATM service components (such as Nep, Test, and Loop).

atmIfVptVccNrp OBJECT IDENTIFIER ::= { atmIfVptVcc 4 }



atmIfVptVccNrpRowStatusTable OBJECT-TYPE
   SYNTAX     SEQUENCE OF AtmIfVptVccNrpRowStatusEntry
   ACCESS     not-accessible
   STATUS     mandatory
   DESCRIPTION
     "This entry controls the addition and deletion of 
      atmIfVptVccNrp components."
::= { atmIfVptVccNrp 1 }

atmIfVptVccNrpRowStatusEntry OBJECT-TYPE
   SYNTAX     AtmIfVptVccNrpRowStatusEntry
   ACCESS     not-accessible
   STATUS     mandatory
   DESCRIPTION
     "A single entry in the table represents a single 
      atmIfVptVccNrp component."
   INDEX {
      atmIfIndex,
      atmIfVptIndex,
      atmIfVptVccIndex,
      atmIfVptVccNrpIndex }
::= { atmIfVptVccNrpRowStatusTable 1 }

AtmIfVptVccNrpRowStatusEntry ::= SEQUENCE {
   atmIfVptVccNrpRowStatus
      RowStatus,
   atmIfVptVccNrpComponentName
      DisplayString,
   atmIfVptVccNrpStorageType
      StorageType,
   atmIfVptVccNrpIndex
      NonReplicated }

atmIfVptVccNrpRowStatus OBJECT-TYPE
   SYNTAX     RowStatus 
   ACCESS     read-write
   STATUS     mandatory
   DESCRIPTION
     "This variable is used as the basis for SNMP naming of
      atmIfVptVccNrp components.
      These components can be added and deleted."
::= { atmIfVptVccNrpRowStatusEntry 1 }

atmIfVptVccNrpComponentName OBJECT-TYPE
   SYNTAX     DisplayString 
   ACCESS     read-only
   STATUS     mandatory
   DESCRIPTION
     "This variable provides the component's string name for
      use with the ASCII Console Interface"
::= { atmIfVptVccNrpRowStatusEntry 2 }

atmIfVptVccNrpStorageType OBJECT-TYPE
   SYNTAX     StorageType 
   ACCESS     read-only
   STATUS     mandatory
   DESCRIPTION
     "This variable represents the storage type value for the
      atmIfVptVccNrp tables."
::= { atmIfVptVccNrpRowStatusEntry 4 }

atmIfVptVccNrpIndex OBJECT-TYPE
   SYNTAX     NonReplicated 
   ACCESS     not-accessible
   STATUS     mandatory
   DESCRIPTION
     "This variable represents the index for the atmIfVptVccNrp tables."
::= { atmIfVptVccNrpRowStatusEntry 10 }

atmIfVptVccNrpProvTable OBJECT-TYPE
   SYNTAX     SEQUENCE OF AtmIfVptVccNrpProvEntry
   ACCESS     not-accessible
   STATUS     mandatory
   DESCRIPTION
     "This group contains the provisionable attributes for the Nrp 
      component."
::= { atmIfVptVccNrp 100 }

atmIfVptVccNrpProvEntry OBJECT-TYPE
   SYNTAX     AtmIfVptVccNrpProvEntry
   ACCESS     not-accessible
   STATUS     mandatory
   DESCRIPTION
     "An entry in the atmIfVptVccNrpProvTable."
   INDEX {
      atmIfIndex,
      atmIfVptIndex,
      atmIfVptVccIndex,
      atmIfVptVccNrpIndex }
::= { atmIfVptVccNrpProvTable 1 }

AtmIfVptVccNrpProvEntry ::= SEQUENCE {
   atmIfVptVccNrpNextHop
      Link,
   atmIfVptVccNrpConnectionPointType
      INTEGER,
   atmIfVptVccNrpOamSegmentBoundary
      INTEGER,
   atmIfVptVccNrpTxAal5PartialPacketDiscard
      INTEGER,
   atmIfVptVccNrpRxAal5PartialPacketDiscard
      INTEGER,
   atmIfVptVccNrpBandwidthElastic
      INTEGER,
   atmIfVptVccNrpOverrideHoldingPriority
      INTEGER }

atmIfVptVccNrpNextHop OBJECT-TYPE
   SYNTAX     Link 
   ACCESS     read-write
   STATUS     mandatory
   DESCRIPTION
     "This attribute specifies the Nrp component with which this Nrp is 
      associated. A sample value is AtmIf/31 Vcc/0.32 Nrp."
::= { atmIfVptVccNrpProvEntry 10 }

atmIfVptVccNrpConnectionPointType OBJECT-TYPE
   SYNTAX     INTEGER  {
                 segmentEndPoint(1),
                 connectingPoint(2),
                 autoConfigure(4) }
   ACCESS     read-write
   STATUS     obsolete
   DESCRIPTION
     "This attribute specifies the connection point type desired for a Nrp 
      component. The actual connection point type value is visible in the 
      parent component's connectionPointType attribute. 
      
      The desired connection point type can be specified directly as a 
      segmentEndPoint or connectingPoint. If autoConfigure is 
      specified, the switch will select the connection point type based on 
      the type attribute of the associated AtmIf, choosing 
      segmentEndPoint for a UNI-type ATM interface and 
      connectingPoint for a PPI-type ATM interface.
      
      It is obsoleted. The value is mapped into oamSegmentBoundary 
      attribute. segmentEndPoint is mapped into yes. connectingPoint is 
      mapped into no. autoConfigure is mapped into sameAsInterface."
   DEFVAL     { autoConfigure }
::= { atmIfVptVccNrpProvEntry 20 }

atmIfVptVccNrpOamSegmentBoundary OBJECT-TYPE
   SYNTAX     INTEGER  {
                 no(0),
                 yes(1),
                 sameAsInterface(2) }
   ACCESS     read-write
   STATUS     mandatory
   DESCRIPTION
     "This attribute specifies the OAM segment boundary desired for a 
      Nrp component. It affects the connection point type value visible in 
      the parent component's connectionPointType attribute. 
      
      The desired OAM segment boundary can be specified directly as 
      yes, no or sameAsInterface. If sameAsInterface is specified, the 
      OAM segment boundary is same as the oamSegmentBoundary 
      attribute of the associated AtmIf and the switch will set the 
      connectionPointType, choosing segmentEndPoint for a segment-
      boundary ATM interface and connectingPoint for a non-segment-
      boundary ATM interface."
   DEFVAL     { sameAsInterface }
::= { atmIfVptVccNrpProvEntry 30 }

atmIfVptVccNrpTxAal5PartialPacketDiscard OBJECT-TYPE
   SYNTAX     INTEGER  {
                 disabled(0),
                 enabled(1) }
   ACCESS     read-write
   STATUS     obsolete
   DESCRIPTION
     "This attribute is obsolete in P4.2 and has been migrated under Vcd 
      (Vpd) component. 
      
      This attribute specifies whether the AAL5 Partial Packet Discard 
      (PPD) feature has been enabled or disabled on the Nrp in the 
      transmit direction. This feature allows the NRP to discard the 
      remainder of a cell-forwarded AAL5 frame if a cell of this frame 
      has been discarded due to congestion. This increases the 'goodput' 
      of the link, since cells which are only going to be discarded by the 
      AAL5 reassembly are not transmitted.
      
      When this attribute is set to enabled, the PPD feature is applied in 
      the transmit direction. It should only be enabled for connections 
      whose end points are performing AAL5 segmentation and 
      reassembly. When this attribute is set to disabled, the PPD feature is 
      not applied to traffic for this connection in the transmit direction. 
      Note that specifying enabled for a non-AAL5 connection will cause 
      all traffic to be discarded once congestion is encountered."
   DEFVAL     { disabled }
::= { atmIfVptVccNrpProvEntry 31 }

atmIfVptVccNrpRxAal5PartialPacketDiscard OBJECT-TYPE
   SYNTAX     INTEGER  {
                 disabled(0),
                 enabled(1),
                 sameAsTx(2) }
   ACCESS     read-write
   STATUS     obsolete
   DESCRIPTION
     "This attribute is obsolete in P4.2 and has been migrated under Vcd 
      (Vpd) component.
      
      This attribute specifies whether the AAL5 Partial Packet Discard 
      (PPD) feature has been enabled or disabled on the Nrp in the 
      receive direction. This feature allows the NRP to discard the 
      remainder of a cell-forwarded AAL5 frame if a cell of this frame 
      has been discarded due to congestion or usage parameter control 
      (UPC). This increases the 'goodput' of the link, since cells which 
      are only going to be discarded by the AAL5 reassembly are not 
      transmitted.
      
      When this attribute is set to enabled, the PPD feature is applied in 
      the receive direction. It should only be enabled for connections 
      whose end points are performing AAL5 segmentation and 
      reassembly. When this attribute is set to disabled, the PPD feature is 
      not applied to traffic for this connection in the receive direction. 
      When this attribute is set to sameAsTx, the PPD feature for traffic 
      in the receive direction will be configured the same way as it is in 
      the transmit direction. 
      Note that specifying enabled for a non-AAL5 connection will cause 
      all traffic to be discarded once congestion is encountered."
   DEFVAL     { sameAsTx }
::= { atmIfVptVccNrpProvEntry 32 }

atmIfVptVccNrpBandwidthElastic OBJECT-TYPE
   SYNTAX     INTEGER  {
                 no(0),
                 yes(1) }
   ACCESS     read-write
   STATUS     mandatory
   DESCRIPTION
     "This attribute is only of importance for connections which are 
      carried on a link with a variable bandwidth. For example, the 
      bandwidth may be reduced in the event that one or more physical 
      links in the IMA group fail, such that the originally requested 
      bandwidth cannot be maintained. This attribute shows whether the 
      application running on this connection can continue to operate if the 
      bandwidth is reduced. If the bandwidth is reduced, the amount by 
      which it is reduced will be displayed in the bandwidthReduction 
      attribute. 
      
      A value of yes, indicates that this connection is elastic, and the 
      bandwidth may be reduced but the connection will not be released. 
      Currently, this attribute should only be set to yes for situations 
      where this Nrp is functioning as a loopback on one side of an IMA 
      link. There are no other situations where this setting is valid.
      
      A value of no indicates that the bandwidth for this connection will 
      not be reduced in the event of link bandwidth reduction. However, 
      this connection may be released based on its holdingPriority."
   DEFVAL     { no }
::= { atmIfVptVccNrpProvEntry 33 }

atmIfVptVccNrpOverrideHoldingPriority OBJECT-TYPE
   SYNTAX     INTEGER  {
                 n0(0),
                 n1(1),
                 n2(2),
                 n3(3),
                 n4(4),
                 noOverride(6) }
   ACCESS     read-write
   STATUS     mandatory
   DESCRIPTION
     "This attribute specifies the holding priority of this connection. 
      Holding priority is used when there is an IMA group where some 
      physical links have failed. Holding priority determines the order in 
      which connections are released. 4 is the lowest holding priority and 
      is released first. 0 is a higher priority and is released last. The value 
      specified in this attribute will override whatever holdingPriority that 
      has been provisioned at the Vcd (or Vpd). If the value is left at the 
      default of noOverride, the holdingPriority provisioned at the Vcd 
      (or Vpd) will be used."
   DEFVAL     { noOverride }
::= { atmIfVptVccNrpProvEntry 34 }




-- 
-- Version and Compliance statements
-- 



-- Object-Group Statement:
-- A list of all current accessible leaf objects.

-- OBJECTS { atmIfVptVccNrpNextHop,
--           atmIfVpcNrpOamSegmentBoundary,
--           atmIfVccNrpStorageType,
--           atmIfVccNrpRowStatus,
--           atmIfVpcNrpComponentName,
--           atmIfVccNrpNextHop,
--           atmIfVccNrpOamSegmentBoundary,
--           atmIfVpcNrpStorageType,
--           atmIfVpcNrpRowStatus,
--           atmIfVptVccNrpComponentName,
--           atmIfVpcNrpNextHop,
--           atmIfVptVccNrpBandwidthElastic,
--           atmIfVccNrpBandwidthElastic,
--           atmIfVptVccNrpStorageType,
--           atmIfVpcNrpBandwidthElastic,
--           atmIfVccNrpComponentName,
--           atmIfVptVccNrpRowStatus,
--           atmIfVccNrpOverrideHoldingPriority,
--           atmIfVptVccNrpOamSegmentBoundary,
--           atmIfVpcNrpOverrideHoldingPriority,
--           atmIfVptVccNrpOverrideHoldingPriority }
-- STATUS  mandatory
-- DESCRIPTION
--   "A list of all current accessible leaf objects."

atmBearerServiceGroup OBJECT IDENTIFIER ::= { atmBearerServiceMIB 1 }
atmBearerServiceGroupBE OBJECT IDENTIFIER ::= { atmBearerServiceGroup 5 }
atmBearerServiceGroupBE00 OBJECT IDENTIFIER ::= { atmBearerServiceGroupBE 1 }
atmBearerServiceGroupBE00A OBJECT IDENTIFIER ::= { atmBearerServiceGroupBE00 2 }



-- Agent-Capabilities Statement:

-- PRODUCT-RELEASE "Passport Release 7.0 AtmBearerService."
-- STATUS          mandatory
-- DESCRIPTION     "AtmBearerService MIB: MIB Version BE00A,
--                  Software Version BG00S4C."
-- SUPPORTS        Nortel-Magellan-Passport-AtmBearerServiceMIB
--    INCLUDES     { atmBearerServiceGroupBE00A }

atmBearerServiceCapabilities OBJECT IDENTIFIER ::= { atmBearerServiceMIB 3 }
atmBearerServiceCapabilitiesBE OBJECT IDENTIFIER ::= { atmBearerServiceCapabilities 5 }
atmBearerServiceCapabilitiesBE00 OBJECT IDENTIFIER ::= { atmBearerServiceCapabilitiesBE 1 }
atmBearerServiceCapabilitiesBE00A OBJECT IDENTIFIER ::= { atmBearerServiceCapabilitiesBE00 2 }





END
