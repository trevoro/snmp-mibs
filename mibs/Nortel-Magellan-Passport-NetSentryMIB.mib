Nortel-Magellan-Passport-NetSentryMIB
DEFINITIONS ::= BEGIN



IMPORTS

      OBJECT-TYPE
   FROM RFC-1212

      passportMIBs
   FROM Nortel-Magellan-Passport-UsefulDefinitionsMIB

      Counter32,
      DisplayString,
      StorageType,
      RowStatus,
      Integer32
   FROM Nortel-Magellan-Passport-StandardTextualConventionsMIB

      AsciiString,
      NonReplicated,
      AsciiStringIndex
   FROM Nortel-Magellan-Passport-TextualConventionsMIB

      vrIndex,
      vr
   FROM Nortel-Magellan-Passport-VirtualRouterMIB;




-- LAST-UPDATED   "9702280000Z"
-- ORGANIZATION   "Nortel"
-- CONTACT-INFO   "
--         Nortel Magellan Network Management
--         
--         Postal: P.O. Box 5080, Station F 
--                 Ottawa, Ontario 
--                 Canada  K2C 3T1
--         
--         Email:  nm_plm@nt.com"
-- DESCRIPTION
--    "The module describing the Nortel Magellan Passport
--     NetSentry Enterprise MIB."

netSentryMIB OBJECT IDENTIFIER ::= { passportMIBs 31 }










-- Vr/<string> NetSentry
-- This is the top-level component for NetSentry. It exists to hold global 
-- NetSentry data, and the subcomponents.

vrNs OBJECT IDENTIFIER ::= { vr 4 }



vrNsRowStatusTable OBJECT-TYPE
   SYNTAX     SEQUENCE OF VrNsRowStatusEntry
   ACCESS     not-accessible
   STATUS     mandatory
   DESCRIPTION
     "This entry controls the addition and deletion of 
      vrNs components."
::= { vrNs 1 }

vrNsRowStatusEntry OBJECT-TYPE
   SYNTAX     VrNsRowStatusEntry
   ACCESS     not-accessible
   STATUS     mandatory
   DESCRIPTION
     "A single entry in the table represents a single 
      vrNs component."
   INDEX {
      vrIndex,
      vrNsIndex }
::= { vrNsRowStatusTable 1 }

VrNsRowStatusEntry ::= SEQUENCE {
   vrNsRowStatus
      RowStatus,
   vrNsComponentName
      DisplayString,
   vrNsStorageType
      StorageType,
   vrNsIndex
      NonReplicated }

vrNsRowStatus OBJECT-TYPE
   SYNTAX     RowStatus 
   ACCESS     read-write
   STATUS     mandatory
   DESCRIPTION
     "This variable is used as the basis for SNMP naming of
      vrNs components.
      These components can be added and deleted."
::= { vrNsRowStatusEntry 1 }

vrNsComponentName OBJECT-TYPE
   SYNTAX     DisplayString 
   ACCESS     read-only
   STATUS     mandatory
   DESCRIPTION
     "This variable provides the component's string name for
      use with the ASCII Console Interface"
::= { vrNsRowStatusEntry 2 }

vrNsStorageType OBJECT-TYPE
   SYNTAX     StorageType 
   ACCESS     read-only
   STATUS     mandatory
   DESCRIPTION
     "This variable represents the storage type value for the
      vrNs tables."
::= { vrNsRowStatusEntry 4 }

vrNsIndex OBJECT-TYPE
   SYNTAX     NonReplicated 
   ACCESS     not-accessible
   STATUS     mandatory
   DESCRIPTION
     "This variable represents the index for the vrNs tables."
::= { vrNsRowStatusEntry 10 }

vrNsProvTable OBJECT-TYPE
   SYNTAX     SEQUENCE OF VrNsProvEntry
   ACCESS     not-accessible
   STATUS     mandatory
   DESCRIPTION
     "This contains the global NetSentry control flags."
::= { vrNs 100 }

vrNsProvEntry OBJECT-TYPE
   SYNTAX     VrNsProvEntry
   ACCESS     not-accessible
   STATUS     mandatory
   DESCRIPTION
     "An entry in the vrNsProvTable."
   INDEX {
      vrIndex,
      vrNsIndex }
::= { vrNsProvTable 1 }

VrNsProvEntry ::= SEQUENCE {
   vrNsDropConditions
      OCTET STRING }

vrNsDropConditions OBJECT-TYPE
   SYNTAX     OCTET STRING (SIZE (1))
   ACCESS     read-write
   STATUS     mandatory
   DESCRIPTION
     "This attribute controls under what circumstances NetSentry drops 
      packets. It is possible for NetSentry to drop packets when:
      There is no memory to contain statistics for this packet (statsNoMem), it 
      is for whatever reason impossible to clone, copy, or log a copy of the 
      packet via the clone_to copy_to or log_to actions respectively 
      (cantCloneTo, cantCopyTo and cantLogTo), and if the packet encounters 
      a filter which is provisioned at a filter point within a protocol 
      component, but not defined in any of the files defined by File 
      components within NetSentry (this is a Null filter).

      Description of bits:
      statsNoMem(0)
      cantCloneTo(1)
      cantLogTo(2)
      cantCopyTo(3)
      cantMacCloneTo(4)
      nullFilter(5)"
::= { vrNsProvEntry 1 }

vrNsStatsTable OBJECT-TYPE
   SYNTAX     SEQUENCE OF VrNsStatsEntry
   ACCESS     not-accessible
   STATUS     mandatory
   DESCRIPTION
     "This contains the global NetSentry (in particular, non-protocol specific) 
      statistics."
::= { vrNs 101 }

vrNsStatsEntry OBJECT-TYPE
   SYNTAX     VrNsStatsEntry
   ACCESS     not-accessible
   STATUS     mandatory
   DESCRIPTION
     "An entry in the vrNsStatsTable."
   INDEX {
      vrIndex,
      vrNsIndex }
::= { vrNsStatsTable 1 }

VrNsStatsEntry ::= SEQUENCE {
   vrNsPacketsProcessed
      Counter32,
   vrNsPacketsFailed
      Counter32,
   vrNsStatsNoMem
      Counter32,
   vrNsHsaOkayFailed
      Counter32,
   vrNsDepthExceeded
      Counter32,
   vrNsDroppedStatsNoMem
      Counter32,
   vrNsDroppedCantCloneTo
      Counter32,
   vrNsDroppedCantLogTo
      Counter32,
   vrNsDroppedCantCopyTo
      Counter32,
   vrNsDroppedNullFilter
      Counter32 }

vrNsPacketsProcessed OBJECT-TYPE
   SYNTAX     Counter32 
   ACCESS     read-only
   STATUS     mandatory
   DESCRIPTION
     "This attribute counts the total number of packets processed through 
      NetSentry. This counter will wrap around to zero when it exceeds its 
      maximum value, 4294967295."
::= { vrNsStatsEntry 1 }

vrNsPacketsFailed OBJECT-TYPE
   SYNTAX     Counter32 
   ACCESS     read-only
   STATUS     mandatory
   DESCRIPTION
     "This attribute counts the total number of packets processed through 
      NetSentry which ended with a fail disposition. This counter will wrap 
      around to zero when it exceeds its maximum value, 4294967295."
::= { vrNsStatsEntry 2 }

vrNsStatsNoMem OBJECT-TYPE
   SYNTAX     Counter32 
   ACCESS     read-only
   STATUS     mandatory
   DESCRIPTION
     "This attribute counts the total number of packets processed through 
      NetSentry for which statistic should have been gathered, but for which 
      statistics were not gathered due to a failure to allocate memory. Such 
      packets may or may not be dropped according to the values provisioned 
      in dropConditions under the NetSentry component. If this attribute is 
      being incremented, the system is suffering from memory shortfalls, and 
      some operator action is advised. Perhaps memory allocations should be 
      re-provisioned, NetSentry statistics gathering should be reduced, or 
      NetSentry statistics tables should be cleared to temporarily free memory. 
      This counter will wrap around to zero when it exceeds its maximum 
      value, 4294967295."
::= { vrNsStatsEntry 3 }

vrNsHsaOkayFailed OBJECT-TYPE
   SYNTAX     Counter32 
   ACCESS     read-only
   STATUS     mandatory
   DESCRIPTION
     "This attribute counts the total number of packets processed through 
      NetSentry which encountered, and did not match, an hsa_okay pattern. 
      Such packets are likely to be generated from misconfigured hosts. Some 
      operator action to track down these hosts is advised. This counter will 
      wrap around to zero should it ever exceed its maximum value, 
      4294967295."
::= { vrNsStatsEntry 4 }

vrNsDepthExceeded OBJECT-TYPE
   SYNTAX     Counter32 
   ACCESS     read-only
   STATUS     mandatory
   DESCRIPTION
     "This attribute counts the total number of times a NetSentry filter was 
      executed which referenced too many layers of indirect filters. If this 
      count is non-zero, the filter definitions the unit is using are incorrect, and 
      some operator action to track down the erroneous filter definitions is 
      advised. Filters will not be behaving correctly if this counter is 
      increasing, and security could be compromised. This count should 
      always be zero, and it will wrap around to zero should it ever exceed its 
      maximum value of 4294967295."
::= { vrNsStatsEntry 5 }

vrNsDroppedStatsNoMem OBJECT-TYPE
   SYNTAX     Counter32 
   ACCESS     read-only
   STATUS     mandatory
   DESCRIPTION
     "This counts the total number of packets that were actually dropped due 
      to an inability to allocate memory to hold statistics for the packet. Such 
      a packet must have had a NetSentry statistics gathering action applied to 
      it, in order for the attempt to gather statistics to be made, and the 
      dropConditions attribute must include the statsNoMem value."
::= { vrNsStatsEntry 6 }

vrNsDroppedCantCloneTo OBJECT-TYPE
   SYNTAX     Counter32 
   ACCESS     read-only
   STATUS     mandatory
   DESCRIPTION
     "This counts the total number of packets that were dropped due to the 
      failure of a clone_to action applied to the packet. This counter will only 
      increment if the dropConditions attribute includes the cantCloneTo 
      value."
::= { vrNsStatsEntry 7 }

vrNsDroppedCantLogTo OBJECT-TYPE
   SYNTAX     Counter32 
   ACCESS     read-only
   STATUS     mandatory
   DESCRIPTION
     "This counts the total number of packets that 
      were dropped due to the failure of a log_to 
      action applied to the packet. This counter 
      will only increment if the dropConditions 
      attribute includes the cantLogTo value."
::= { vrNsStatsEntry 8 }

vrNsDroppedCantCopyTo OBJECT-TYPE
   SYNTAX     Counter32 
   ACCESS     read-only
   STATUS     mandatory
   DESCRIPTION
     "This counts the total number of packets that 
      were dropped due to the failure of a copy_to 
      action applied to the packet. This counter 
      will only increment if the dropConditions 
      attribute includes the cantCopyTo value."
::= { vrNsStatsEntry 9 }

vrNsDroppedNullFilter OBJECT-TYPE
   SYNTAX     Counter32 
   ACCESS     read-only
   STATUS     mandatory
   DESCRIPTION
     "This counts the total number of packets that 
      were dropped because the packet passed through a filter point into which 
      was provisioned a filter which was never defined in a file loaded into 
      NetSentry. Such filter points have atached to the the so-call Null Filter, 
      which will either succeed or fail all packets passing through it, 
      depending on whether or not the dropConditions attribute includes the 
      nullFilter value."
::= { vrNsStatsEntry 10 }


-- Vr/<string> NetSentry File/<filename>
-- This component's instance value is a single filename to be compiled. 
-- The file must reside in
-- /provisioning/netsentry/prov
-- in order to be compiled at provisioning activate time, but in
-- /provisioning/netsentry/oper
-- to be recompiled with the ReLoad verb. This is to provide the same sort 
-- of protections that the provisioning system gives with its activate-
-- confirm-commit sequence.

vrNsFile OBJECT IDENTIFIER ::= { vrNs 2 }



vrNsFileRowStatusTable OBJECT-TYPE
   SYNTAX     SEQUENCE OF VrNsFileRowStatusEntry
   ACCESS     not-accessible
   STATUS     mandatory
   DESCRIPTION
     "This entry controls the addition and deletion of 
      vrNsFile components."
::= { vrNsFile 1 }

vrNsFileRowStatusEntry OBJECT-TYPE
   SYNTAX     VrNsFileRowStatusEntry
   ACCESS     not-accessible
   STATUS     mandatory
   DESCRIPTION
     "A single entry in the table represents a single 
      vrNsFile component."
   INDEX {
      vrIndex,
      vrNsIndex,
      vrNsFileIndex }
::= { vrNsFileRowStatusTable 1 }

VrNsFileRowStatusEntry ::= SEQUENCE {
   vrNsFileRowStatus
      RowStatus,
   vrNsFileComponentName
      DisplayString,
   vrNsFileStorageType
      StorageType,
   vrNsFileIndex
      AsciiStringIndex }

vrNsFileRowStatus OBJECT-TYPE
   SYNTAX     RowStatus 
   ACCESS     read-write
   STATUS     mandatory
   DESCRIPTION
     "This variable is used as the basis for SNMP naming of
      vrNsFile components.
      These components can be added and deleted."
::= { vrNsFileRowStatusEntry 1 }

vrNsFileComponentName OBJECT-TYPE
   SYNTAX     DisplayString 
   ACCESS     read-only
   STATUS     mandatory
   DESCRIPTION
     "This variable provides the component's string name for
      use with the ASCII Console Interface"
::= { vrNsFileRowStatusEntry 2 }

vrNsFileStorageType OBJECT-TYPE
   SYNTAX     StorageType 
   ACCESS     read-only
   STATUS     mandatory
   DESCRIPTION
     "This variable represents the storage type value for the
      vrNsFile tables."
::= { vrNsFileRowStatusEntry 4 }

vrNsFileIndex OBJECT-TYPE
   SYNTAX     AsciiStringIndex (SIZE (1..64))
   ACCESS     not-accessible
   STATUS     mandatory
   DESCRIPTION
     "This variable represents the index for the vrNsFile tables."
::= { vrNsFileRowStatusEntry 10 }

vrNsFileOperTable OBJECT-TYPE
   SYNTAX     SEQUENCE OF VrNsFileOperEntry
   ACCESS     not-accessible
   STATUS     mandatory
   DESCRIPTION
     "This holds hold a single compiler error message."
::= { vrNsFile 10 }

vrNsFileOperEntry OBJECT-TYPE
   SYNTAX     VrNsFileOperEntry
   ACCESS     not-accessible
   STATUS     mandatory
   DESCRIPTION
     "An entry in the vrNsFileOperTable."
   INDEX {
      vrIndex,
      vrNsIndex,
      vrNsFileIndex }
::= { vrNsFileOperTable 1 }

VrNsFileOperEntry ::= SEQUENCE {
   vrNsFileCompilerErrorMsg
      AsciiString }

vrNsFileCompilerErrorMsg OBJECT-TYPE
   SYNTAX     AsciiString (SIZE (1..80))
   ACCESS     read-only
   STATUS     mandatory
   DESCRIPTION
     "This attribute contains a single string holding the compiler error which 
      caused the compile to fail. In the event that the file is recompiled (using 
      the RELoad verb), the value of this will change, to reflect the new error, 
      if any was encountered, or no error, if the compile was successful."
   DEFVAL     { '4e6f204572726f72'H }  -- "No Error"
::= { vrNsFileOperEntry 1 }


-- Vr/<string> NetSentry Engine/n
-- The existence of this component represents the presence of NetSentry on 
-- a particular Logical Processor. Each Engine component must correspond 
-- to a matching Lp component. If NetSentry filtering is needed on some 
-- Lp, a corresponding Engine must be provisioned.

vrNsEngine OBJECT IDENTIFIER ::= { vrNs 3 }



vrNsEngineRowStatusTable OBJECT-TYPE
   SYNTAX     SEQUENCE OF VrNsEngineRowStatusEntry
   ACCESS     not-accessible
   STATUS     mandatory
   DESCRIPTION
     "This entry controls the addition and deletion of 
      vrNsEngine components."
::= { vrNsEngine 1 }

vrNsEngineRowStatusEntry OBJECT-TYPE
   SYNTAX     VrNsEngineRowStatusEntry
   ACCESS     not-accessible
   STATUS     mandatory
   DESCRIPTION
     "A single entry in the table represents a single 
      vrNsEngine component."
   INDEX {
      vrIndex,
      vrNsIndex,
      vrNsEngineIndex }
::= { vrNsEngineRowStatusTable 1 }

VrNsEngineRowStatusEntry ::= SEQUENCE {
   vrNsEngineRowStatus
      RowStatus,
   vrNsEngineComponentName
      DisplayString,
   vrNsEngineStorageType
      StorageType,
   vrNsEngineIndex
      Integer32 }

vrNsEngineRowStatus OBJECT-TYPE
   SYNTAX     RowStatus 
   ACCESS     read-write
   STATUS     mandatory
   DESCRIPTION
     "This variable is used as the basis for SNMP naming of
      vrNsEngine components.
      These components can be added and deleted."
::= { vrNsEngineRowStatusEntry 1 }

vrNsEngineComponentName OBJECT-TYPE
   SYNTAX     DisplayString 
   ACCESS     read-only
   STATUS     mandatory
   DESCRIPTION
     "This variable provides the component's string name for
      use with the ASCII Console Interface"
::= { vrNsEngineRowStatusEntry 2 }

vrNsEngineStorageType OBJECT-TYPE
   SYNTAX     StorageType 
   ACCESS     read-only
   STATUS     mandatory
   DESCRIPTION
     "This variable represents the storage type value for the
      vrNsEngine tables."
::= { vrNsEngineRowStatusEntry 4 }

vrNsEngineIndex OBJECT-TYPE
   SYNTAX     Integer32 (0..15)
   ACCESS     not-accessible
   STATUS     mandatory
   DESCRIPTION
     "This variable represents the index for the vrNsEngine tables."
::= { vrNsEngineRowStatusEntry 10 }


-- Vr/<string> NetSentry IPStats
-- This component holds all the statistics gathered for the IP protocol. If 
-- IPStatistics is provisioned, NetSentry statistics gathering actions will 
-- gather statistics for all IP packets to which they apply.

vrNsIPStats OBJECT IDENTIFIER ::= { vrNs 4 }



vrNsIPStatsRowStatusTable OBJECT-TYPE
   SYNTAX     SEQUENCE OF VrNsIPStatsRowStatusEntry
   ACCESS     not-accessible
   STATUS     mandatory
   DESCRIPTION
     "This entry controls the addition and deletion of 
      vrNsIPStats components."
::= { vrNsIPStats 1 }

vrNsIPStatsRowStatusEntry OBJECT-TYPE
   SYNTAX     VrNsIPStatsRowStatusEntry
   ACCESS     not-accessible
   STATUS     mandatory
   DESCRIPTION
     "A single entry in the table represents a single 
      vrNsIPStats component."
   INDEX {
      vrIndex,
      vrNsIndex,
      vrNsIPStatsIndex }
::= { vrNsIPStatsRowStatusTable 1 }

VrNsIPStatsRowStatusEntry ::= SEQUENCE {
   vrNsIPStatsRowStatus
      RowStatus,
   vrNsIPStatsComponentName
      DisplayString,
   vrNsIPStatsStorageType
      StorageType,
   vrNsIPStatsIndex
      NonReplicated }

vrNsIPStatsRowStatus OBJECT-TYPE
   SYNTAX     RowStatus 
   ACCESS     read-write
   STATUS     mandatory
   DESCRIPTION
     "This variable is used as the basis for SNMP naming of
      vrNsIPStats components.
      These components can be added and deleted."
::= { vrNsIPStatsRowStatusEntry 1 }

vrNsIPStatsComponentName OBJECT-TYPE
   SYNTAX     DisplayString 
   ACCESS     read-only
   STATUS     mandatory
   DESCRIPTION
     "This variable provides the component's string name for
      use with the ASCII Console Interface"
::= { vrNsIPStatsRowStatusEntry 2 }

vrNsIPStatsStorageType OBJECT-TYPE
   SYNTAX     StorageType 
   ACCESS     read-only
   STATUS     mandatory
   DESCRIPTION
     "This variable represents the storage type value for the
      vrNsIPStats tables."
::= { vrNsIPStatsRowStatusEntry 4 }

vrNsIPStatsIndex OBJECT-TYPE
   SYNTAX     NonReplicated 
   ACCESS     not-accessible
   STATUS     mandatory
   DESCRIPTION
     "This variable represents the index for the vrNsIPStats tables."
::= { vrNsIPStatsRowStatusEntry 10 }

-- 
-- *** THIS SUBTREE CURRENTLY NOT IMPLEMENTED ***
-- 

-- Vr/<string> NetSentry IPStats AddrStat/128.12.3.7,-
-- This component holds statistics for a source address, a destination 
-- address, or a source address/destination address pair. This component 
-- may reside in one of a variety of by-protocol tables, each with a double 
-- index for rows. One index is the source address, one is the destination 
-- address. One of the indices may be a "-", which indicates that the other 
-- index is the relevent one. That is, a statistic referred to with source 
-- address "128.12.3.7" and destination address "-" is a statistic for packets 
-- originating from 128.12.3.7 alone.

vrNsIPStatsAddrStat OBJECT IDENTIFIER ::= { vrNsIPStats 2 }



vrNsIPStatsAddrStatRowStatusTable OBJECT-TYPE
   SYNTAX     SEQUENCE OF VrNsIPStatsAddrStatRowStatusEntry
   ACCESS     not-accessible
   STATUS     mandatory
   DESCRIPTION
     "*** THIS TABLE CURRENTLY NOT IMPLEMENTED ***

      This entry controls the addition and deletion of 
      vrNsIPStatsAddrStat components."
::= { vrNsIPStatsAddrStat 1 }

vrNsIPStatsAddrStatRowStatusEntry OBJECT-TYPE
   SYNTAX     VrNsIPStatsAddrStatRowStatusEntry
   ACCESS     not-accessible
   STATUS     mandatory
   DESCRIPTION
     "A single entry in the table represents a single 
      vrNsIPStatsAddrStat component."
   INDEX {
      vrIndex,
      vrNsIndex,
      vrNsIPStatsIndex,
      vrNsIPStatsAddrStatSourceAddressIndex,
      vrNsIPStatsAddrStatDestinationAddressIndex }
::= { vrNsIPStatsAddrStatRowStatusTable 1 }

VrNsIPStatsAddrStatRowStatusEntry ::= SEQUENCE {
   vrNsIPStatsAddrStatRowStatus
      RowStatus,
   vrNsIPStatsAddrStatComponentName
      DisplayString,
   vrNsIPStatsAddrStatStorageType
      StorageType,
   vrNsIPStatsAddrStatSourceAddressIndex
      AsciiStringIndex,
   vrNsIPStatsAddrStatDestinationAddressIndex
      AsciiStringIndex }

vrNsIPStatsAddrStatRowStatus OBJECT-TYPE
   SYNTAX     RowStatus 
   ACCESS     read-only
   STATUS     mandatory
   DESCRIPTION
     "This variable is used as the basis for SNMP naming of
      vrNsIPStatsAddrStat components.
      These components cannot be added nor deleted."
::= { vrNsIPStatsAddrStatRowStatusEntry 1 }

vrNsIPStatsAddrStatComponentName OBJECT-TYPE
   SYNTAX     DisplayString 
   ACCESS     read-only
   STATUS     mandatory
   DESCRIPTION
     "This variable provides the component's string name for
      use with the ASCII Console Interface"
::= { vrNsIPStatsAddrStatRowStatusEntry 2 }

vrNsIPStatsAddrStatStorageType OBJECT-TYPE
   SYNTAX     StorageType 
   ACCESS     read-only
   STATUS     mandatory
   DESCRIPTION
     "This variable represents the storage type value for the
      vrNsIPStatsAddrStat tables."
::= { vrNsIPStatsAddrStatRowStatusEntry 4 }

vrNsIPStatsAddrStatSourceAddressIndex OBJECT-TYPE
   SYNTAX     AsciiStringIndex (SIZE (1..32))
   ACCESS     not-accessible
   STATUS     mandatory
   DESCRIPTION
     "This variable represents an index for the vrNsIPStatsAddrStat tables."
::= { vrNsIPStatsAddrStatRowStatusEntry 10 }

vrNsIPStatsAddrStatDestinationAddressIndex OBJECT-TYPE
   SYNTAX     AsciiStringIndex (SIZE (1..32))
   ACCESS     not-accessible
   STATUS     mandatory
   DESCRIPTION
     "This variable represents an index for the vrNsIPStatsAddrStat tables."
::= { vrNsIPStatsAddrStatRowStatusEntry 11 }

vrNsIPStatsAddrStatStatsTable OBJECT-TYPE
   SYNTAX     SEQUENCE OF VrNsIPStatsAddrStatStatsEntry
   ACCESS     not-accessible
   STATUS     mandatory
   DESCRIPTION
     "*** THIS TABLE CURRENTLY NOT IMPLEMENTED ***

      This is the basic statistic used throughout NetSentry by-protocol 
      statistics gathering. It contains counters for total packets, total octets in 
      packets, and two user counters, counter_1 and counter_2."
::= { vrNsIPStatsAddrStat 10 }

vrNsIPStatsAddrStatStatsEntry OBJECT-TYPE
   SYNTAX     VrNsIPStatsAddrStatStatsEntry
   ACCESS     not-accessible
   STATUS     mandatory
   DESCRIPTION
     "An entry in the vrNsIPStatsAddrStatStatsTable."
   INDEX {
      vrIndex,
      vrNsIndex,
      vrNsIPStatsIndex,
      vrNsIPStatsAddrStatSourceAddressIndex,
      vrNsIPStatsAddrStatDestinationAddressIndex }
::= { vrNsIPStatsAddrStatStatsTable 1 }

VrNsIPStatsAddrStatStatsEntry ::= SEQUENCE {
   vrNsIPStatsAddrStatPacketCount
      Counter32,
   vrNsIPStatsAddrStatByteCount
      Counter32,
   vrNsIPStatsAddrStatCounter1
      Counter32,
   vrNsIPStatsAddrStatCounter2
      Counter32 }

vrNsIPStatsAddrStatPacketCount OBJECT-TYPE
   SYNTAX     Counter32 
   ACCESS     read-only
   STATUS     mandatory
   DESCRIPTION
     "This is the number of packets which caused the enclosing Statistics 
      group to to be incremented. This counter will wrap around to zero when 
      it exceeds its maximum value, 4294967295."
::= { vrNsIPStatsAddrStatStatsEntry 1 }

vrNsIPStatsAddrStatByteCount OBJECT-TYPE
   SYNTAX     Counter32 
   ACCESS     read-only
   STATUS     mandatory
   DESCRIPTION
     "This is the number of bytes in all the packets which caused the enclosing 
      Statistics group to be incremented. This counter will wrap around to 
      zero when it exceeds its maximum value, 4294967295."
::= { vrNsIPStatsAddrStatStatsEntry 2 }

vrNsIPStatsAddrStatCounter1 OBJECT-TYPE
   SYNTAX     Counter32 
   ACCESS     read-only
   STATUS     mandatory
   DESCRIPTION
     "This is the number of times a packet caused a counter_1 action to be 
      applied with reference to the enclosing Statistics group. This counter 
      will wrap around to zero when it exceeds its maximum value, 
      4294967295."
::= { vrNsIPStatsAddrStatStatsEntry 3 }

vrNsIPStatsAddrStatCounter2 OBJECT-TYPE
   SYNTAX     Counter32 
   ACCESS     read-only
   STATUS     mandatory
   DESCRIPTION
     "This is the number of times a packet caused a counter_2 action to be 
      applied with reference to the enclosing Statistics group. This counter 
      will wrap around to zero when it exceeds its maximum value, 
      4294967295."
::= { vrNsIPStatsAddrStatStatsEntry 4 }


-- Vr/<string> NetSentry IPXStats
-- This component holds all the statistics gathered for the IPX protocol. If 
-- IPXStatistics is provisioned, NetSentry statistics gathering actions will 
-- gather statistics for all IPX packets to which they apply.

vrNsIPXStats OBJECT IDENTIFIER ::= { vrNs 5 }



vrNsIPXStatsRowStatusTable OBJECT-TYPE
   SYNTAX     SEQUENCE OF VrNsIPXStatsRowStatusEntry
   ACCESS     not-accessible
   STATUS     mandatory
   DESCRIPTION
     "This entry controls the addition and deletion of 
      vrNsIPXStats components."
::= { vrNsIPXStats 1 }

vrNsIPXStatsRowStatusEntry OBJECT-TYPE
   SYNTAX     VrNsIPXStatsRowStatusEntry
   ACCESS     not-accessible
   STATUS     mandatory
   DESCRIPTION
     "A single entry in the table represents a single 
      vrNsIPXStats component."
   INDEX {
      vrIndex,
      vrNsIndex,
      vrNsIPXStatsIndex }
::= { vrNsIPXStatsRowStatusTable 1 }

VrNsIPXStatsRowStatusEntry ::= SEQUENCE {
   vrNsIPXStatsRowStatus
      RowStatus,
   vrNsIPXStatsComponentName
      DisplayString,
   vrNsIPXStatsStorageType
      StorageType,
   vrNsIPXStatsIndex
      NonReplicated }

vrNsIPXStatsRowStatus OBJECT-TYPE
   SYNTAX     RowStatus 
   ACCESS     read-write
   STATUS     mandatory
   DESCRIPTION
     "This variable is used as the basis for SNMP naming of
      vrNsIPXStats components.
      These components can be added and deleted."
::= { vrNsIPXStatsRowStatusEntry 1 }

vrNsIPXStatsComponentName OBJECT-TYPE
   SYNTAX     DisplayString 
   ACCESS     read-only
   STATUS     mandatory
   DESCRIPTION
     "This variable provides the component's string name for
      use with the ASCII Console Interface"
::= { vrNsIPXStatsRowStatusEntry 2 }

vrNsIPXStatsStorageType OBJECT-TYPE
   SYNTAX     StorageType 
   ACCESS     read-only
   STATUS     mandatory
   DESCRIPTION
     "This variable represents the storage type value for the
      vrNsIPXStats tables."
::= { vrNsIPXStatsRowStatusEntry 4 }

vrNsIPXStatsIndex OBJECT-TYPE
   SYNTAX     NonReplicated 
   ACCESS     not-accessible
   STATUS     mandatory
   DESCRIPTION
     "This variable represents the index for the vrNsIPXStats tables."
::= { vrNsIPXStatsRowStatusEntry 10 }

-- 
-- *** THIS SUBTREE CURRENTLY NOT IMPLEMENTED ***
-- 

-- Vr/<string> NetSentry IPStats AddrStat/128.12.3.7,-
-- This component holds statistics for a source address, a destination 
-- address, or a source address/destination address pair. This component 
-- may reside in one of a variety of by-protocol tables, each with a double 
-- index for rows. One index is the source address, one is the destination 
-- address. One of the indices may be a "-", which indicates that the other 
-- index is the relevent one. That is, a statistic referred to with source 
-- address "128.12.3.7" and destination address "-" is a statistic for packets 
-- originating from 128.12.3.7 alone.

vrNsIPXStatsAddrStat OBJECT IDENTIFIER ::= { vrNsIPXStats 2 }



vrNsIPXStatsAddrStatRowStatusTable OBJECT-TYPE
   SYNTAX     SEQUENCE OF VrNsIPXStatsAddrStatRowStatusEntry
   ACCESS     not-accessible
   STATUS     mandatory
   DESCRIPTION
     "*** THIS TABLE CURRENTLY NOT IMPLEMENTED ***

      This entry controls the addition and deletion of 
      vrNsIPXStatsAddrStat components."
::= { vrNsIPXStatsAddrStat 1 }

vrNsIPXStatsAddrStatRowStatusEntry OBJECT-TYPE
   SYNTAX     VrNsIPXStatsAddrStatRowStatusEntry
   ACCESS     not-accessible
   STATUS     mandatory
   DESCRIPTION
     "A single entry in the table represents a single 
      vrNsIPXStatsAddrStat component."
   INDEX {
      vrIndex,
      vrNsIndex,
      vrNsIPXStatsIndex,
      vrNsIPXStatsAddrStatSourceAddressIndex,
      vrNsIPXStatsAddrStatDestinationAddressIndex }
::= { vrNsIPXStatsAddrStatRowStatusTable 1 }

VrNsIPXStatsAddrStatRowStatusEntry ::= SEQUENCE {
   vrNsIPXStatsAddrStatRowStatus
      RowStatus,
   vrNsIPXStatsAddrStatComponentName
      DisplayString,
   vrNsIPXStatsAddrStatStorageType
      StorageType,
   vrNsIPXStatsAddrStatSourceAddressIndex
      AsciiStringIndex,
   vrNsIPXStatsAddrStatDestinationAddressIndex
      AsciiStringIndex }

vrNsIPXStatsAddrStatRowStatus OBJECT-TYPE
   SYNTAX     RowStatus 
   ACCESS     read-only
   STATUS     mandatory
   DESCRIPTION
     "This variable is used as the basis for SNMP naming of
      vrNsIPXStatsAddrStat components.
      These components cannot be added nor deleted."
::= { vrNsIPXStatsAddrStatRowStatusEntry 1 }

vrNsIPXStatsAddrStatComponentName OBJECT-TYPE
   SYNTAX     DisplayString 
   ACCESS     read-only
   STATUS     mandatory
   DESCRIPTION
     "This variable provides the component's string name for
      use with the ASCII Console Interface"
::= { vrNsIPXStatsAddrStatRowStatusEntry 2 }

vrNsIPXStatsAddrStatStorageType OBJECT-TYPE
   SYNTAX     StorageType 
   ACCESS     read-only
   STATUS     mandatory
   DESCRIPTION
     "This variable represents the storage type value for the
      vrNsIPXStatsAddrStat tables."
::= { vrNsIPXStatsAddrStatRowStatusEntry 4 }

vrNsIPXStatsAddrStatSourceAddressIndex OBJECT-TYPE
   SYNTAX     AsciiStringIndex (SIZE (1..32))
   ACCESS     not-accessible
   STATUS     mandatory
   DESCRIPTION
     "This variable represents an index for the vrNsIPXStatsAddrStat tables."
::= { vrNsIPXStatsAddrStatRowStatusEntry 10 }

vrNsIPXStatsAddrStatDestinationAddressIndex OBJECT-TYPE
   SYNTAX     AsciiStringIndex (SIZE (1..32))
   ACCESS     not-accessible
   STATUS     mandatory
   DESCRIPTION
     "This variable represents an index for the vrNsIPXStatsAddrStat tables."
::= { vrNsIPXStatsAddrStatRowStatusEntry 11 }

vrNsIPXStatsAddrStatStatsTable OBJECT-TYPE
   SYNTAX     SEQUENCE OF VrNsIPXStatsAddrStatStatsEntry
   ACCESS     not-accessible
   STATUS     mandatory
   DESCRIPTION
     "*** THIS TABLE CURRENTLY NOT IMPLEMENTED ***

      This is the basic statistic used throughout NetSentry by-protocol 
      statistics gathering. It contains counters for total packets, total octets in 
      packets, and two user counters, counter_1 and counter_2."
::= { vrNsIPXStatsAddrStat 10 }

vrNsIPXStatsAddrStatStatsEntry OBJECT-TYPE
   SYNTAX     VrNsIPXStatsAddrStatStatsEntry
   ACCESS     not-accessible
   STATUS     mandatory
   DESCRIPTION
     "An entry in the vrNsIPXStatsAddrStatStatsTable."
   INDEX {
      vrIndex,
      vrNsIndex,
      vrNsIPXStatsIndex,
      vrNsIPXStatsAddrStatSourceAddressIndex,
      vrNsIPXStatsAddrStatDestinationAddressIndex }
::= { vrNsIPXStatsAddrStatStatsTable 1 }

VrNsIPXStatsAddrStatStatsEntry ::= SEQUENCE {
   vrNsIPXStatsAddrStatPacketCount
      Counter32,
   vrNsIPXStatsAddrStatByteCount
      Counter32,
   vrNsIPXStatsAddrStatCounter1
      Counter32,
   vrNsIPXStatsAddrStatCounter2
      Counter32 }

vrNsIPXStatsAddrStatPacketCount OBJECT-TYPE
   SYNTAX     Counter32 
   ACCESS     read-only
   STATUS     mandatory
   DESCRIPTION
     "This is the number of packets which caused the enclosing Statistics 
      group to to be incremented. This counter will wrap around to zero when 
      it exceeds its maximum value, 4294967295."
::= { vrNsIPXStatsAddrStatStatsEntry 1 }

vrNsIPXStatsAddrStatByteCount OBJECT-TYPE
   SYNTAX     Counter32 
   ACCESS     read-only
   STATUS     mandatory
   DESCRIPTION
     "This is the number of bytes in all the packets which caused the enclosing 
      Statistics group to be incremented. This counter will wrap around to 
      zero when it exceeds its maximum value, 4294967295."
::= { vrNsIPXStatsAddrStatStatsEntry 2 }

vrNsIPXStatsAddrStatCounter1 OBJECT-TYPE
   SYNTAX     Counter32 
   ACCESS     read-only
   STATUS     mandatory
   DESCRIPTION
     "This is the number of times a packet caused a counter_1 action to be 
      applied with reference to the enclosing Statistics group. This counter 
      will wrap around to zero when it exceeds its maximum value, 
      4294967295."
::= { vrNsIPXStatsAddrStatStatsEntry 3 }

vrNsIPXStatsAddrStatCounter2 OBJECT-TYPE
   SYNTAX     Counter32 
   ACCESS     read-only
   STATUS     mandatory
   DESCRIPTION
     "This is the number of times a packet caused a counter_2 action to be 
      applied with reference to the enclosing Statistics group. This counter 
      will wrap around to zero when it exceeds its maximum value, 
      4294967295."
::= { vrNsIPXStatsAddrStatStatsEntry 4 }


-- Vr/<string> NetSentry ATStats
-- This component holds all the statistics gathered for the AppleTalk 
-- protocol. If AppleTalkStatistics is provisioned, NetSentry statistics 
-- gathering actions will gather statistics for AppleTalk packets to which 
-- they apply.

vrNsATStats OBJECT IDENTIFIER ::= { vrNs 6 }



vrNsATStatsRowStatusTable OBJECT-TYPE
   SYNTAX     SEQUENCE OF VrNsATStatsRowStatusEntry
   ACCESS     not-accessible
   STATUS     mandatory
   DESCRIPTION
     "This entry controls the addition and deletion of 
      vrNsATStats components."
::= { vrNsATStats 1 }

vrNsATStatsRowStatusEntry OBJECT-TYPE
   SYNTAX     VrNsATStatsRowStatusEntry
   ACCESS     not-accessible
   STATUS     mandatory
   DESCRIPTION
     "A single entry in the table represents a single 
      vrNsATStats component."
   INDEX {
      vrIndex,
      vrNsIndex,
      vrNsATStatsIndex }
::= { vrNsATStatsRowStatusTable 1 }

VrNsATStatsRowStatusEntry ::= SEQUENCE {
   vrNsATStatsRowStatus
      RowStatus,
   vrNsATStatsComponentName
      DisplayString,
   vrNsATStatsStorageType
      StorageType,
   vrNsATStatsIndex
      NonReplicated }

vrNsATStatsRowStatus OBJECT-TYPE
   SYNTAX     RowStatus 
   ACCESS     read-write
   STATUS     mandatory
   DESCRIPTION
     "This variable is used as the basis for SNMP naming of
      vrNsATStats components.
      These components can be added and deleted."
::= { vrNsATStatsRowStatusEntry 1 }

vrNsATStatsComponentName OBJECT-TYPE
   SYNTAX     DisplayString 
   ACCESS     read-only
   STATUS     mandatory
   DESCRIPTION
     "This variable provides the component's string name for
      use with the ASCII Console Interface"
::= { vrNsATStatsRowStatusEntry 2 }

vrNsATStatsStorageType OBJECT-TYPE
   SYNTAX     StorageType 
   ACCESS     read-only
   STATUS     mandatory
   DESCRIPTION
     "This variable represents the storage type value for the
      vrNsATStats tables."
::= { vrNsATStatsRowStatusEntry 4 }

vrNsATStatsIndex OBJECT-TYPE
   SYNTAX     NonReplicated 
   ACCESS     not-accessible
   STATUS     mandatory
   DESCRIPTION
     "This variable represents the index for the vrNsATStats tables."
::= { vrNsATStatsRowStatusEntry 10 }

-- 
-- *** THIS SUBTREE CURRENTLY NOT IMPLEMENTED ***
-- 

-- Vr/<string> NetSentry IPStats AddrStat/128.12.3.7,-
-- This component holds statistics for a source address, a destination 
-- address, or a source address/destination address pair. This component 
-- may reside in one of a variety of by-protocol tables, each with a double 
-- index for rows. One index is the source address, one is the destination 
-- address. One of the indices may be a "-", which indicates that the other 
-- index is the relevent one. That is, a statistic referred to with source 
-- address "128.12.3.7" and destination address "-" is a statistic for packets 
-- originating from 128.12.3.7 alone.

vrNsATStatsAddrStat OBJECT IDENTIFIER ::= { vrNsATStats 2 }



vrNsATStatsAddrStatRowStatusTable OBJECT-TYPE
   SYNTAX     SEQUENCE OF VrNsATStatsAddrStatRowStatusEntry
   ACCESS     not-accessible
   STATUS     mandatory
   DESCRIPTION
     "*** THIS TABLE CURRENTLY NOT IMPLEMENTED ***

      This entry controls the addition and deletion of 
      vrNsATStatsAddrStat components."
::= { vrNsATStatsAddrStat 1 }

vrNsATStatsAddrStatRowStatusEntry OBJECT-TYPE
   SYNTAX     VrNsATStatsAddrStatRowStatusEntry
   ACCESS     not-accessible
   STATUS     mandatory
   DESCRIPTION
     "A single entry in the table represents a single 
      vrNsATStatsAddrStat component."
   INDEX {
      vrIndex,
      vrNsIndex,
      vrNsATStatsIndex,
      vrNsATStatsAddrStatSourceAddressIndex,
      vrNsATStatsAddrStatDestinationAddressIndex }
::= { vrNsATStatsAddrStatRowStatusTable 1 }

VrNsATStatsAddrStatRowStatusEntry ::= SEQUENCE {
   vrNsATStatsAddrStatRowStatus
      RowStatus,
   vrNsATStatsAddrStatComponentName
      DisplayString,
   vrNsATStatsAddrStatStorageType
      StorageType,
   vrNsATStatsAddrStatSourceAddressIndex
      AsciiStringIndex,
   vrNsATStatsAddrStatDestinationAddressIndex
      AsciiStringIndex }

vrNsATStatsAddrStatRowStatus OBJECT-TYPE
   SYNTAX     RowStatus 
   ACCESS     read-only
   STATUS     mandatory
   DESCRIPTION
     "This variable is used as the basis for SNMP naming of
      vrNsATStatsAddrStat components.
      These components cannot be added nor deleted."
::= { vrNsATStatsAddrStatRowStatusEntry 1 }

vrNsATStatsAddrStatComponentName OBJECT-TYPE
   SYNTAX     DisplayString 
   ACCESS     read-only
   STATUS     mandatory
   DESCRIPTION
     "This variable provides the component's string name for
      use with the ASCII Console Interface"
::= { vrNsATStatsAddrStatRowStatusEntry 2 }

vrNsATStatsAddrStatStorageType OBJECT-TYPE
   SYNTAX     StorageType 
   ACCESS     read-only
   STATUS     mandatory
   DESCRIPTION
     "This variable represents the storage type value for the
      vrNsATStatsAddrStat tables."
::= { vrNsATStatsAddrStatRowStatusEntry 4 }

vrNsATStatsAddrStatSourceAddressIndex OBJECT-TYPE
   SYNTAX     AsciiStringIndex (SIZE (1..32))
   ACCESS     not-accessible
   STATUS     mandatory
   DESCRIPTION
     "This variable represents an index for the vrNsATStatsAddrStat tables."
::= { vrNsATStatsAddrStatRowStatusEntry 10 }

vrNsATStatsAddrStatDestinationAddressIndex OBJECT-TYPE
   SYNTAX     AsciiStringIndex (SIZE (1..32))
   ACCESS     not-accessible
   STATUS     mandatory
   DESCRIPTION
     "This variable represents an index for the vrNsATStatsAddrStat tables."
::= { vrNsATStatsAddrStatRowStatusEntry 11 }

vrNsATStatsAddrStatStatsTable OBJECT-TYPE
   SYNTAX     SEQUENCE OF VrNsATStatsAddrStatStatsEntry
   ACCESS     not-accessible
   STATUS     mandatory
   DESCRIPTION
     "*** THIS TABLE CURRENTLY NOT IMPLEMENTED ***

      This is the basic statistic used throughout NetSentry by-protocol 
      statistics gathering. It contains counters for total packets, total octets in 
      packets, and two user counters, counter_1 and counter_2."
::= { vrNsATStatsAddrStat 10 }

vrNsATStatsAddrStatStatsEntry OBJECT-TYPE
   SYNTAX     VrNsATStatsAddrStatStatsEntry
   ACCESS     not-accessible
   STATUS     mandatory
   DESCRIPTION
     "An entry in the vrNsATStatsAddrStatStatsTable."
   INDEX {
      vrIndex,
      vrNsIndex,
      vrNsATStatsIndex,
      vrNsATStatsAddrStatSourceAddressIndex,
      vrNsATStatsAddrStatDestinationAddressIndex }
::= { vrNsATStatsAddrStatStatsTable 1 }

VrNsATStatsAddrStatStatsEntry ::= SEQUENCE {
   vrNsATStatsAddrStatPacketCount
      Counter32,
   vrNsATStatsAddrStatByteCount
      Counter32,
   vrNsATStatsAddrStatCounter1
      Counter32,
   vrNsATStatsAddrStatCounter2
      Counter32 }

vrNsATStatsAddrStatPacketCount OBJECT-TYPE
   SYNTAX     Counter32 
   ACCESS     read-only
   STATUS     mandatory
   DESCRIPTION
     "This is the number of packets which caused the enclosing Statistics 
      group to to be incremented. This counter will wrap around to zero when 
      it exceeds its maximum value, 4294967295."
::= { vrNsATStatsAddrStatStatsEntry 1 }

vrNsATStatsAddrStatByteCount OBJECT-TYPE
   SYNTAX     Counter32 
   ACCESS     read-only
   STATUS     mandatory
   DESCRIPTION
     "This is the number of bytes in all the packets which caused the enclosing 
      Statistics group to be incremented. This counter will wrap around to 
      zero when it exceeds its maximum value, 4294967295."
::= { vrNsATStatsAddrStatStatsEntry 2 }

vrNsATStatsAddrStatCounter1 OBJECT-TYPE
   SYNTAX     Counter32 
   ACCESS     read-only
   STATUS     mandatory
   DESCRIPTION
     "This is the number of times a packet caused a counter_1 action to be 
      applied with reference to the enclosing Statistics group. This counter 
      will wrap around to zero when it exceeds its maximum value, 
      4294967295."
::= { vrNsATStatsAddrStatStatsEntry 3 }

vrNsATStatsAddrStatCounter2 OBJECT-TYPE
   SYNTAX     Counter32 
   ACCESS     read-only
   STATUS     mandatory
   DESCRIPTION
     "This is the number of times a packet caused a counter_2 action to be 
      applied with reference to the enclosing Statistics group. This counter 
      will wrap around to zero when it exceeds its maximum value, 
      4294967295."
::= { vrNsATStatsAddrStatStatsEntry 4 }


-- Vr/<string> NetSentry DNStats
-- This component holds all the statistics gathered for the DECnet 
-- protocol. If DECnetStatistics is provisioned, NetSentry statistics 
-- gathering actions will gather statistics for DECnet packets to which they 
-- apply.

vrNsDNStats OBJECT IDENTIFIER ::= { vrNs 7 }



vrNsDNStatsRowStatusTable OBJECT-TYPE
   SYNTAX     SEQUENCE OF VrNsDNStatsRowStatusEntry
   ACCESS     not-accessible
   STATUS     mandatory
   DESCRIPTION
     "This entry controls the addition and deletion of 
      vrNsDNStats components."
::= { vrNsDNStats 1 }

vrNsDNStatsRowStatusEntry OBJECT-TYPE
   SYNTAX     VrNsDNStatsRowStatusEntry
   ACCESS     not-accessible
   STATUS     mandatory
   DESCRIPTION
     "A single entry in the table represents a single 
      vrNsDNStats component."
   INDEX {
      vrIndex,
      vrNsIndex,
      vrNsDNStatsIndex }
::= { vrNsDNStatsRowStatusTable 1 }

VrNsDNStatsRowStatusEntry ::= SEQUENCE {
   vrNsDNStatsRowStatus
      RowStatus,
   vrNsDNStatsComponentName
      DisplayString,
   vrNsDNStatsStorageType
      StorageType,
   vrNsDNStatsIndex
      NonReplicated }

vrNsDNStatsRowStatus OBJECT-TYPE
   SYNTAX     RowStatus 
   ACCESS     read-write
   STATUS     mandatory
   DESCRIPTION
     "This variable is used as the basis for SNMP naming of
      vrNsDNStats components.
      These components can be added and deleted."
::= { vrNsDNStatsRowStatusEntry 1 }

vrNsDNStatsComponentName OBJECT-TYPE
   SYNTAX     DisplayString 
   ACCESS     read-only
   STATUS     mandatory
   DESCRIPTION
     "This variable provides the component's string name for
      use with the ASCII Console Interface"
::= { vrNsDNStatsRowStatusEntry 2 }

vrNsDNStatsStorageType OBJECT-TYPE
   SYNTAX     StorageType 
   ACCESS     read-only
   STATUS     mandatory
   DESCRIPTION
     "This variable represents the storage type value for the
      vrNsDNStats tables."
::= { vrNsDNStatsRowStatusEntry 4 }

vrNsDNStatsIndex OBJECT-TYPE
   SYNTAX     NonReplicated 
   ACCESS     not-accessible
   STATUS     mandatory
   DESCRIPTION
     "This variable represents the index for the vrNsDNStats tables."
::= { vrNsDNStatsRowStatusEntry 10 }

-- 
-- *** THIS SUBTREE CURRENTLY NOT IMPLEMENTED ***
-- 

-- Vr/<string> NetSentry IPStats AddrStat/128.12.3.7,-
-- This component holds statistics for a source address, a destination 
-- address, or a source address/destination address pair. This component 
-- may reside in one of a variety of by-protocol tables, each with a double 
-- index for rows. One index is the source address, one is the destination 
-- address. One of the indices may be a "-", which indicates that the other 
-- index is the relevent one. That is, a statistic referred to with source 
-- address "128.12.3.7" and destination address "-" is a statistic for packets 
-- originating from 128.12.3.7 alone.

vrNsDNStatsAddrStat OBJECT IDENTIFIER ::= { vrNsDNStats 2 }



vrNsDNStatsAddrStatRowStatusTable OBJECT-TYPE
   SYNTAX     SEQUENCE OF VrNsDNStatsAddrStatRowStatusEntry
   ACCESS     not-accessible
   STATUS     mandatory
   DESCRIPTION
     "*** THIS TABLE CURRENTLY NOT IMPLEMENTED ***

      This entry controls the addition and deletion of 
      vrNsDNStatsAddrStat components."
::= { vrNsDNStatsAddrStat 1 }

vrNsDNStatsAddrStatRowStatusEntry OBJECT-TYPE
   SYNTAX     VrNsDNStatsAddrStatRowStatusEntry
   ACCESS     not-accessible
   STATUS     mandatory
   DESCRIPTION
     "A single entry in the table represents a single 
      vrNsDNStatsAddrStat component."
   INDEX {
      vrIndex,
      vrNsIndex,
      vrNsDNStatsIndex,
      vrNsDNStatsAddrStatSourceAddressIndex,
      vrNsDNStatsAddrStatDestinationAddressIndex }
::= { vrNsDNStatsAddrStatRowStatusTable 1 }

VrNsDNStatsAddrStatRowStatusEntry ::= SEQUENCE {
   vrNsDNStatsAddrStatRowStatus
      RowStatus,
   vrNsDNStatsAddrStatComponentName
      DisplayString,
   vrNsDNStatsAddrStatStorageType
      StorageType,
   vrNsDNStatsAddrStatSourceAddressIndex
      AsciiStringIndex,
   vrNsDNStatsAddrStatDestinationAddressIndex
      AsciiStringIndex }

vrNsDNStatsAddrStatRowStatus OBJECT-TYPE
   SYNTAX     RowStatus 
   ACCESS     read-only
   STATUS     mandatory
   DESCRIPTION
     "This variable is used as the basis for SNMP naming of
      vrNsDNStatsAddrStat components.
      These components cannot be added nor deleted."
::= { vrNsDNStatsAddrStatRowStatusEntry 1 }

vrNsDNStatsAddrStatComponentName OBJECT-TYPE
   SYNTAX     DisplayString 
   ACCESS     read-only
   STATUS     mandatory
   DESCRIPTION
     "This variable provides the component's string name for
      use with the ASCII Console Interface"
::= { vrNsDNStatsAddrStatRowStatusEntry 2 }

vrNsDNStatsAddrStatStorageType OBJECT-TYPE
   SYNTAX     StorageType 
   ACCESS     read-only
   STATUS     mandatory
   DESCRIPTION
     "This variable represents the storage type value for the
      vrNsDNStatsAddrStat tables."
::= { vrNsDNStatsAddrStatRowStatusEntry 4 }

vrNsDNStatsAddrStatSourceAddressIndex OBJECT-TYPE
   SYNTAX     AsciiStringIndex (SIZE (1..32))
   ACCESS     not-accessible
   STATUS     mandatory
   DESCRIPTION
     "This variable represents an index for the vrNsDNStatsAddrStat tables."
::= { vrNsDNStatsAddrStatRowStatusEntry 10 }

vrNsDNStatsAddrStatDestinationAddressIndex OBJECT-TYPE
   SYNTAX     AsciiStringIndex (SIZE (1..32))
   ACCESS     not-accessible
   STATUS     mandatory
   DESCRIPTION
     "This variable represents an index for the vrNsDNStatsAddrStat tables."
::= { vrNsDNStatsAddrStatRowStatusEntry 11 }

vrNsDNStatsAddrStatStatsTable OBJECT-TYPE
   SYNTAX     SEQUENCE OF VrNsDNStatsAddrStatStatsEntry
   ACCESS     not-accessible
   STATUS     mandatory
   DESCRIPTION
     "*** THIS TABLE CURRENTLY NOT IMPLEMENTED ***

      This is the basic statistic used throughout NetSentry by-protocol 
      statistics gathering. It contains counters for total packets, total octets in 
      packets, and two user counters, counter_1 and counter_2."
::= { vrNsDNStatsAddrStat 10 }

vrNsDNStatsAddrStatStatsEntry OBJECT-TYPE
   SYNTAX     VrNsDNStatsAddrStatStatsEntry
   ACCESS     not-accessible
   STATUS     mandatory
   DESCRIPTION
     "An entry in the vrNsDNStatsAddrStatStatsTable."
   INDEX {
      vrIndex,
      vrNsIndex,
      vrNsDNStatsIndex,
      vrNsDNStatsAddrStatSourceAddressIndex,
      vrNsDNStatsAddrStatDestinationAddressIndex }
::= { vrNsDNStatsAddrStatStatsTable 1 }

VrNsDNStatsAddrStatStatsEntry ::= SEQUENCE {
   vrNsDNStatsAddrStatPacketCount
      Counter32,
   vrNsDNStatsAddrStatByteCount
      Counter32,
   vrNsDNStatsAddrStatCounter1
      Counter32,
   vrNsDNStatsAddrStatCounter2
      Counter32 }

vrNsDNStatsAddrStatPacketCount OBJECT-TYPE
   SYNTAX     Counter32 
   ACCESS     read-only
   STATUS     mandatory
   DESCRIPTION
     "This is the number of packets which caused the enclosing Statistics 
      group to to be incremented. This counter will wrap around to zero when 
      it exceeds its maximum value, 4294967295."
::= { vrNsDNStatsAddrStatStatsEntry 1 }

vrNsDNStatsAddrStatByteCount OBJECT-TYPE
   SYNTAX     Counter32 
   ACCESS     read-only
   STATUS     mandatory
   DESCRIPTION
     "This is the number of bytes in all the packets which caused the enclosing 
      Statistics group to be incremented. This counter will wrap around to 
      zero when it exceeds its maximum value, 4294967295."
::= { vrNsDNStatsAddrStatStatsEntry 2 }

vrNsDNStatsAddrStatCounter1 OBJECT-TYPE
   SYNTAX     Counter32 
   ACCESS     read-only
   STATUS     mandatory
   DESCRIPTION
     "This is the number of times a packet caused a counter_1 action to be 
      applied with reference to the enclosing Statistics group. This counter 
      will wrap around to zero when it exceeds its maximum value, 
      4294967295."
::= { vrNsDNStatsAddrStatStatsEntry 3 }

vrNsDNStatsAddrStatCounter2 OBJECT-TYPE
   SYNTAX     Counter32 
   ACCESS     read-only
   STATUS     mandatory
   DESCRIPTION
     "This is the number of times a packet caused a counter_2 action to be 
      applied with reference to the enclosing Statistics group. This counter 
      will wrap around to zero when it exceeds its maximum value, 
      4294967295."
::= { vrNsDNStatsAddrStatStatsEntry 4 }


-- Vr/<string> NetSentry BrStats
-- This component holds all the statistics gathered for Bridged packets. If 
-- BridgingStatistics is provisioned, NetSentry statistics gathering actions 
-- will gather statistics for Bridged packets to which they apply.

vrNsBrStats OBJECT IDENTIFIER ::= { vrNs 8 }



vrNsBrStatsRowStatusTable OBJECT-TYPE
   SYNTAX     SEQUENCE OF VrNsBrStatsRowStatusEntry
   ACCESS     not-accessible
   STATUS     mandatory
   DESCRIPTION
     "This entry controls the addition and deletion of 
      vrNsBrStats components."
::= { vrNsBrStats 1 }

vrNsBrStatsRowStatusEntry OBJECT-TYPE
   SYNTAX     VrNsBrStatsRowStatusEntry
   ACCESS     not-accessible
   STATUS     mandatory
   DESCRIPTION
     "A single entry in the table represents a single 
      vrNsBrStats component."
   INDEX {
      vrIndex,
      vrNsIndex,
      vrNsBrStatsIndex }
::= { vrNsBrStatsRowStatusTable 1 }

VrNsBrStatsRowStatusEntry ::= SEQUENCE {
   vrNsBrStatsRowStatus
      RowStatus,
   vrNsBrStatsComponentName
      DisplayString,
   vrNsBrStatsStorageType
      StorageType,
   vrNsBrStatsIndex
      NonReplicated }

vrNsBrStatsRowStatus OBJECT-TYPE
   SYNTAX     RowStatus 
   ACCESS     read-write
   STATUS     mandatory
   DESCRIPTION
     "This variable is used as the basis for SNMP naming of
      vrNsBrStats components.
      These components can be added and deleted."
::= { vrNsBrStatsRowStatusEntry 1 }

vrNsBrStatsComponentName OBJECT-TYPE
   SYNTAX     DisplayString 
   ACCESS     read-only
   STATUS     mandatory
   DESCRIPTION
     "This variable provides the component's string name for
      use with the ASCII Console Interface"
::= { vrNsBrStatsRowStatusEntry 2 }

vrNsBrStatsStorageType OBJECT-TYPE
   SYNTAX     StorageType 
   ACCESS     read-only
   STATUS     mandatory
   DESCRIPTION
     "This variable represents the storage type value for the
      vrNsBrStats tables."
::= { vrNsBrStatsRowStatusEntry 4 }

vrNsBrStatsIndex OBJECT-TYPE
   SYNTAX     NonReplicated 
   ACCESS     not-accessible
   STATUS     mandatory
   DESCRIPTION
     "This variable represents the index for the vrNsBrStats tables."
::= { vrNsBrStatsRowStatusEntry 10 }

-- 
-- *** THIS SUBTREE CURRENTLY NOT IMPLEMENTED ***
-- 

-- Vr/<string> NetSentry IPStats AddrStat/128.12.3.7,-
-- This component holds statistics for a source address, a destination 
-- address, or a source address/destination address pair. This component 
-- may reside in one of a variety of by-protocol tables, each with a double 
-- index for rows. One index is the source address, one is the destination 
-- address. One of the indices may be a "-", which indicates that the other 
-- index is the relevent one. That is, a statistic referred to with source 
-- address "128.12.3.7" and destination address "-" is a statistic for packets 
-- originating from 128.12.3.7 alone.

vrNsBrStatsAddrStat OBJECT IDENTIFIER ::= { vrNsBrStats 2 }



vrNsBrStatsAddrStatRowStatusTable OBJECT-TYPE
   SYNTAX     SEQUENCE OF VrNsBrStatsAddrStatRowStatusEntry
   ACCESS     not-accessible
   STATUS     mandatory
   DESCRIPTION
     "*** THIS TABLE CURRENTLY NOT IMPLEMENTED ***

      This entry controls the addition and deletion of 
      vrNsBrStatsAddrStat components."
::= { vrNsBrStatsAddrStat 1 }

vrNsBrStatsAddrStatRowStatusEntry OBJECT-TYPE
   SYNTAX     VrNsBrStatsAddrStatRowStatusEntry
   ACCESS     not-accessible
   STATUS     mandatory
   DESCRIPTION
     "A single entry in the table represents a single 
      vrNsBrStatsAddrStat component."
   INDEX {
      vrIndex,
      vrNsIndex,
      vrNsBrStatsIndex,
      vrNsBrStatsAddrStatSourceAddressIndex,
      vrNsBrStatsAddrStatDestinationAddressIndex }
::= { vrNsBrStatsAddrStatRowStatusTable 1 }

VrNsBrStatsAddrStatRowStatusEntry ::= SEQUENCE {
   vrNsBrStatsAddrStatRowStatus
      RowStatus,
   vrNsBrStatsAddrStatComponentName
      DisplayString,
   vrNsBrStatsAddrStatStorageType
      StorageType,
   vrNsBrStatsAddrStatSourceAddressIndex
      AsciiStringIndex,
   vrNsBrStatsAddrStatDestinationAddressIndex
      AsciiStringIndex }

vrNsBrStatsAddrStatRowStatus OBJECT-TYPE
   SYNTAX     RowStatus 
   ACCESS     read-only
   STATUS     mandatory
   DESCRIPTION
     "This variable is used as the basis for SNMP naming of
      vrNsBrStatsAddrStat components.
      These components cannot be added nor deleted."
::= { vrNsBrStatsAddrStatRowStatusEntry 1 }

vrNsBrStatsAddrStatComponentName OBJECT-TYPE
   SYNTAX     DisplayString 
   ACCESS     read-only
   STATUS     mandatory
   DESCRIPTION
     "This variable provides the component's string name for
      use with the ASCII Console Interface"
::= { vrNsBrStatsAddrStatRowStatusEntry 2 }

vrNsBrStatsAddrStatStorageType OBJECT-TYPE
   SYNTAX     StorageType 
   ACCESS     read-only
   STATUS     mandatory
   DESCRIPTION
     "This variable represents the storage type value for the
      vrNsBrStatsAddrStat tables."
::= { vrNsBrStatsAddrStatRowStatusEntry 4 }

vrNsBrStatsAddrStatSourceAddressIndex OBJECT-TYPE
   SYNTAX     AsciiStringIndex (SIZE (1..32))
   ACCESS     not-accessible
   STATUS     mandatory
   DESCRIPTION
     "This variable represents an index for the vrNsBrStatsAddrStat tables."
::= { vrNsBrStatsAddrStatRowStatusEntry 10 }

vrNsBrStatsAddrStatDestinationAddressIndex OBJECT-TYPE
   SYNTAX     AsciiStringIndex (SIZE (1..32))
   ACCESS     not-accessible
   STATUS     mandatory
   DESCRIPTION
     "This variable represents an index for the vrNsBrStatsAddrStat tables."
::= { vrNsBrStatsAddrStatRowStatusEntry 11 }

vrNsBrStatsAddrStatStatsTable OBJECT-TYPE
   SYNTAX     SEQUENCE OF VrNsBrStatsAddrStatStatsEntry
   ACCESS     not-accessible
   STATUS     mandatory
   DESCRIPTION
     "*** THIS TABLE CURRENTLY NOT IMPLEMENTED ***

      This is the basic statistic used throughout NetSentry by-protocol 
      statistics gathering. It contains counters for total packets, total octets in 
      packets, and two user counters, counter_1 and counter_2."
::= { vrNsBrStatsAddrStat 10 }

vrNsBrStatsAddrStatStatsEntry OBJECT-TYPE
   SYNTAX     VrNsBrStatsAddrStatStatsEntry
   ACCESS     not-accessible
   STATUS     mandatory
   DESCRIPTION
     "An entry in the vrNsBrStatsAddrStatStatsTable."
   INDEX {
      vrIndex,
      vrNsIndex,
      vrNsBrStatsIndex,
      vrNsBrStatsAddrStatSourceAddressIndex,
      vrNsBrStatsAddrStatDestinationAddressIndex }
::= { vrNsBrStatsAddrStatStatsTable 1 }

VrNsBrStatsAddrStatStatsEntry ::= SEQUENCE {
   vrNsBrStatsAddrStatPacketCount
      Counter32,
   vrNsBrStatsAddrStatByteCount
      Counter32,
   vrNsBrStatsAddrStatCounter1
      Counter32,
   vrNsBrStatsAddrStatCounter2
      Counter32 }

vrNsBrStatsAddrStatPacketCount OBJECT-TYPE
   SYNTAX     Counter32 
   ACCESS     read-only
   STATUS     mandatory
   DESCRIPTION
     "This is the number of packets which caused the enclosing Statistics 
      group to to be incremented. This counter will wrap around to zero when 
      it exceeds its maximum value, 4294967295."
::= { vrNsBrStatsAddrStatStatsEntry 1 }

vrNsBrStatsAddrStatByteCount OBJECT-TYPE
   SYNTAX     Counter32 
   ACCESS     read-only
   STATUS     mandatory
   DESCRIPTION
     "This is the number of bytes in all the packets which caused the enclosing 
      Statistics group to be incremented. This counter will wrap around to 
      zero when it exceeds its maximum value, 4294967295."
::= { vrNsBrStatsAddrStatStatsEntry 2 }

vrNsBrStatsAddrStatCounter1 OBJECT-TYPE
   SYNTAX     Counter32 
   ACCESS     read-only
   STATUS     mandatory
   DESCRIPTION
     "This is the number of times a packet caused a counter_1 action to be 
      applied with reference to the enclosing Statistics group. This counter 
      will wrap around to zero when it exceeds its maximum value, 
      4294967295."
::= { vrNsBrStatsAddrStatStatsEntry 3 }

vrNsBrStatsAddrStatCounter2 OBJECT-TYPE
   SYNTAX     Counter32 
   ACCESS     read-only
   STATUS     mandatory
   DESCRIPTION
     "This is the number of times a packet caused a counter_2 action to be 
      applied with reference to the enclosing Statistics group. This counter 
      will wrap around to zero when it exceeds its maximum value, 
      4294967295."
::= { vrNsBrStatsAddrStatStatsEntry 4 }

-- 
-- *** THIS SUBTREE CURRENTLY NOT IMPLEMENTED ***
-- 

-- Vr/<string> NetSentry Filter/not_tcp,Filter
-- Each instance of this component names a single NetSentry Filter or other 
-- NetSentry data object.

vrNsFilter OBJECT IDENTIFIER ::= { vrNs 9 }



vrNsFilterRowStatusTable OBJECT-TYPE
   SYNTAX     SEQUENCE OF VrNsFilterRowStatusEntry
   ACCESS     not-accessible
   STATUS     mandatory
   DESCRIPTION
     "*** THIS TABLE CURRENTLY NOT IMPLEMENTED ***

      This entry controls the addition and deletion of 
      vrNsFilter components."
::= { vrNsFilter 1 }

vrNsFilterRowStatusEntry OBJECT-TYPE
   SYNTAX     VrNsFilterRowStatusEntry
   ACCESS     not-accessible
   STATUS     mandatory
   DESCRIPTION
     "A single entry in the table represents a single 
      vrNsFilter component."
   INDEX {
      vrIndex,
      vrNsIndex,
      vrNsFilterNameIndex,
      vrNsFilterKindIndex }
::= { vrNsFilterRowStatusTable 1 }

VrNsFilterRowStatusEntry ::= SEQUENCE {
   vrNsFilterRowStatus
      RowStatus,
   vrNsFilterComponentName
      DisplayString,
   vrNsFilterStorageType
      StorageType,
   vrNsFilterNameIndex
      AsciiStringIndex,
   vrNsFilterKindIndex
      INTEGER }

vrNsFilterRowStatus OBJECT-TYPE
   SYNTAX     RowStatus 
   ACCESS     read-only
   STATUS     mandatory
   DESCRIPTION
     "This variable is used as the basis for SNMP naming of
      vrNsFilter components.
      These components cannot be added nor deleted."
::= { vrNsFilterRowStatusEntry 1 }

vrNsFilterComponentName OBJECT-TYPE
   SYNTAX     DisplayString 
   ACCESS     read-only
   STATUS     mandatory
   DESCRIPTION
     "This variable provides the component's string name for
      use with the ASCII Console Interface"
::= { vrNsFilterRowStatusEntry 2 }

vrNsFilterStorageType OBJECT-TYPE
   SYNTAX     StorageType 
   ACCESS     read-only
   STATUS     mandatory
   DESCRIPTION
     "This variable represents the storage type value for the
      vrNsFilter tables."
::= { vrNsFilterRowStatusEntry 4 }

vrNsFilterNameIndex OBJECT-TYPE
   SYNTAX     AsciiStringIndex (SIZE (1..32))
   ACCESS     not-accessible
   STATUS     mandatory
   DESCRIPTION
     "This variable represents an index for the vrNsFilter tables."
::= { vrNsFilterRowStatusEntry 10 }

vrNsFilterKindIndex OBJECT-TYPE
   SYNTAX     INTEGER  {
                 filter(0),
                 pafSet(1),
                 compartment(2),
                 aesoData(3),
                 nleso(4),
                 aeso(5),
                 accreditTable(6),
                 setData(7),
                 metaFilter(8) }
   ACCESS     not-accessible
   STATUS     mandatory
   DESCRIPTION
     "This variable represents an index for the vrNsFilter tables."
::= { vrNsFilterRowStatusEntry 11 }

vrNsFilterStatsTable OBJECT-TYPE
   SYNTAX     SEQUENCE OF VrNsFilterStatsEntry
   ACCESS     not-accessible
   STATUS     mandatory
   DESCRIPTION
     "*** THIS TABLE CURRENTLY NOT IMPLEMENTED ***

      This group contains the various counters associated with a particular 
      filter definition. A packet being processed through a NetSentry filter will 
      encounter zero or more dispositions according to which elements of the 
      filter have patterns which match the packet. This group counts, for the 
      enclosing Filter, how many packets encountered each sort of disposition 
      while being processed through the filter."
::= { vrNsFilter 10 }

vrNsFilterStatsEntry OBJECT-TYPE
   SYNTAX     VrNsFilterStatsEntry
   ACCESS     not-accessible
   STATUS     mandatory
   DESCRIPTION
     "An entry in the vrNsFilterStatsTable."
   INDEX {
      vrIndex,
      vrNsIndex,
      vrNsFilterNameIndex,
      vrNsFilterKindIndex }
::= { vrNsFilterStatsTable 1 }

VrNsFilterStatsEntry ::= SEQUENCE {
   vrNsFilterPacketsSucceeded
      Counter32,
   vrNsFilterBytesSucceeded
      Counter32,
   vrNsFilterPacketsFailed
      Counter32,
   vrNsFilterBytesFailed
      Counter32,
   vrNsFilterPacketsBreaked
      Counter32,
   vrNsFilterBytesBreaked
      Counter32,
   vrNsFilterPacketsContinued
      Counter32,
   vrNsFilterBytesContinued
      Counter32 }

vrNsFilterPacketsSucceeded OBJECT-TYPE
   SYNTAX     Counter32 
   ACCESS     read-only
   STATUS     mandatory
   DESCRIPTION
     "This counter contains the number of packets which passed through 
      NetSentry, which happen to have been matched against an element of the 
      enclosing Filter component which had a succeed disposition."
::= { vrNsFilterStatsEntry 1 }

vrNsFilterBytesSucceeded OBJECT-TYPE
   SYNTAX     Counter32 
   ACCESS     read-only
   STATUS     mandatory
   DESCRIPTION
     "This counter counts the number of bytes in the packets counted in the 
      packetsSucceeded."
::= { vrNsFilterStatsEntry 2 }

vrNsFilterPacketsFailed OBJECT-TYPE
   SYNTAX     Counter32 
   ACCESS     read-only
   STATUS     mandatory
   DESCRIPTION
     "This counter contains the number of packets which passed through 
      NetSentry, which happen to have been matched against an element of the 
      enclosing Filter which had a fail disposition."
::= { vrNsFilterStatsEntry 3 }

vrNsFilterBytesFailed OBJECT-TYPE
   SYNTAX     Counter32 
   ACCESS     read-only
   STATUS     mandatory
   DESCRIPTION
     "This counter counts the number of bytes in the packets counted in the 
      packetsFailed counter."
::= { vrNsFilterStatsEntry 4 }

vrNsFilterPacketsBreaked OBJECT-TYPE
   SYNTAX     Counter32 
   ACCESS     read-only
   STATUS     mandatory
   DESCRIPTION
     "This counter contains the number of packets which passed through 
      NetSentry, which happen to have been matched against an element of the 
      enclosing Filter which had a break disposition."
::= { vrNsFilterStatsEntry 5 }

vrNsFilterBytesBreaked OBJECT-TYPE
   SYNTAX     Counter32 
   ACCESS     read-only
   STATUS     mandatory
   DESCRIPTION
     "This counter counts the number of bytes in the packets counted in the 
      packetsBreaked counter."
::= { vrNsFilterStatsEntry 6 }

vrNsFilterPacketsContinued OBJECT-TYPE
   SYNTAX     Counter32 
   ACCESS     read-only
   STATUS     mandatory
   DESCRIPTION
     "This counter contains the number of packets which passed through 
      NetSentry, which happen to have been matched against at least one 
      element of the enclosing Filter which had a continue disposition. Such a 
      packet may also have been counted in one of the packetsSucceeded 
      packetsFailed or packetsBreaked counters, since a continue disposition 
      does not exit a NetSentry filter unless it is the disposition in the last 
      element of the filter."
::= { vrNsFilterStatsEntry 7 }

vrNsFilterBytesContinued OBJECT-TYPE
   SYNTAX     Counter32 
   ACCESS     read-only
   STATUS     mandatory
   DESCRIPTION
     "This counter counts the number of bytes in the packets counted in the 
      packetsContinued counter."
::= { vrNsFilterStatsEntry 8 }




-- 
-- Version and Compliance statements
-- 



-- Object-Group Statement:
-- A list of all current accessible leaf objects.

-- OBJECTS { vrNsATStatsAddrStatCounter1,
--           vrNsPacketsFailed,
--           vrNsBrStatsAddrStatByteCount,
--           vrNsBrStatsStorageType,
--           vrNsBrStatsAddrStatRowStatus,
--           vrNsDNStatsAddrStatCounter1,
--           vrNsBrStatsAddrStatPacketCount,
--           vrNsFilterBytesContinued,
--           vrNsFilterBytesSucceeded,
--           vrNsFilterRowStatus,
--           vrNsFileCompilerErrorMsg,
--           vrNsBrStatsAddrStatStorageType,
--           vrNsBrStatsAddrStatCounter1,
--           vrNsATStatsRowStatus,
--           vrNsFilterPacketsSucceeded,
--           vrNsBrStatsRowStatus,
--           vrNsDropConditions,
--           vrNsIPXStatsAddrStatByteCount,
--           vrNsEngineStorageType,
--           vrNsFilterBytesFailed,
--           vrNsStorageType,
--           vrNsIPXStatsAddrStatRowStatus,
--           vrNsFilterBytesBreaked,
--           vrNsHsaOkayFailed,
--           vrNsIPStatsAddrStatByteCount,
--           vrNsIPStatsStorageType,
--           vrNsIPXStatsAddrStatStorageType,
--           vrNsDNStatsAddrStatByteCount,
--           vrNsATStatsComponentName,
--           vrNsDNStatsStorageType,
--           vrNsIPXStatsStorageType,
--           vrNsATStatsAddrStatByteCount,
--           vrNsDNStatsAddrStatPacketCount,
--           vrNsIPStatsAddrStatStorageType,
--           vrNsIPStatsAddrStatCounter1,
--           vrNsFilterComponentName,
--           vrNsATStatsAddrStatComponentName,
--           vrNsDroppedStatsNoMem,
--           vrNsDroppedCantCloneTo,
--           vrNsIPXStatsRowStatus,
--           vrNsDroppedCantCopyTo,
--           vrNsFileStorageType,
--           vrNsRowStatus,
--           vrNsDNStatsAddrStatStorageType,
--           vrNsStatsNoMem,
--           vrNsIPStatsRowStatus,
--           vrNsBrStatsAddrStatComponentName,
--           vrNsPacketsProcessed,
--           vrNsIPXStatsAddrStatPacketCount,
--           vrNsDNStatsRowStatus,
--           vrNsDepthExceeded,
--           vrNsBrStatsComponentName,
--           vrNsIPStatsAddrStatRowStatus,
--           vrNsIPStatsAddrStatPacketCount,
--           vrNsFilterPacketsFailed,
--           vrNsEngineComponentName,
--           vrNsComponentName,
--           vrNsDroppedCantLogTo,
--           vrNsEngineRowStatus,
--           vrNsBrStatsAddrStatCounter2,
--           vrNsFileRowStatus,
--           vrNsIPXStatsAddrStatComponentName,
--           vrNsDNStatsComponentName,
--           vrNsATStatsAddrStatRowStatus,
--           vrNsFilterPacketsBreaked,
--           vrNsDroppedNullFilter,
--           vrNsIPXStatsAddrStatCounter2,
--           vrNsIPStatsAddrStatComponentName,
--           vrNsATStatsAddrStatCounter2,
--           vrNsFilterStorageType,
--           vrNsDNStatsAddrStatComponentName,
--           vrNsIPStatsAddrStatCounter2,
--           vrNsATStatsStorageType,
--           vrNsDNStatsAddrStatRowStatus,
--           vrNsIPStatsComponentName,
--           vrNsDNStatsAddrStatCounter2,
--           vrNsATStatsAddrStatPacketCount,
--           vrNsFileComponentName,
--           vrNsIPXStatsComponentName,
--           vrNsFilterPacketsContinued,
--           vrNsIPXStatsAddrStatCounter1,
--           vrNsATStatsAddrStatStorageType }
-- STATUS  mandatory
-- DESCRIPTION
--   "A list of all current accessible leaf objects."

netSentryGroup OBJECT IDENTIFIER ::= { netSentryMIB 1 }
netSentryGroupBD OBJECT IDENTIFIER ::= { netSentryGroup 4 }
netSentryGroupBD00 OBJECT IDENTIFIER ::= { netSentryGroupBD 1 }
netSentryGroupBD00A OBJECT IDENTIFIER ::= { netSentryGroupBD00 2 }



-- Agent-Capabilities Statement:

-- PRODUCT-RELEASE "Passport Release 7.0 NetSentry."
-- STATUS          mandatory
-- DESCRIPTION     "NetSentry MIB: MIB Version BD00A,
--                  Software Version BG00S4C."
-- SUPPORTS        Nortel-Magellan-Passport-NetSentryMIB
--    INCLUDES     { netSentryGroupBD00A }

netSentryCapabilities OBJECT IDENTIFIER ::= { netSentryMIB 3 }
netSentryCapabilitiesBD OBJECT IDENTIFIER ::= { netSentryCapabilities 4 }
netSentryCapabilitiesBD00 OBJECT IDENTIFIER ::= { netSentryCapabilitiesBD 1 }
netSentryCapabilitiesBD00A OBJECT IDENTIFIER ::= { netSentryCapabilitiesBD00 2 }





END
