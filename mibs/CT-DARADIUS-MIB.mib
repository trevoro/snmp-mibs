CT-DARADIUS-MIB DEFINITIONS ::= BEGIN

--  ct-daradius-mib
--  Revision: 01.00.00
--  Date: June 25, 1999
--  		
--  Cabletron Systems, Inc.
--  35 Industrial Way, P.O. Box 5005
--  Rochester, NH 03867-0505
--  (603) 332-9400
--  support@ctron.com

--  This module provides authoritative definitions for Cabletron's
--  enterprise specific DA RADIUS MIB.
--
--  This module will be extended, as required.
--

--  Cabletron Systems reserves the right to make changes in
--  specification and other information contained in this document
--  without prior notice.  The reader should consult Cabletron Systems
--  to determine whether any such changes have been made.
--
--  In no event shall Cabletron Systems be liable for any incidental,
--  indirect, special, or consequential damages whatsoever (including
--  but not limited to lost profits) arising out of or related to this
--  document or the information contained in it, even if Cabletron
--  Systems has been advised of, known, or should have known, the
--  possibility of such damages.
--
--  Cabletron grants vendors, end-users, and other interested parties
--  a non-exclusive license to use this Specification in connection
--  with the management of Cabletron products.

--  Copyright (c)1999 Cabletron Systems
        
IMPORTS
   OBJECT-TYPE
      FROM RFC-1212
   IpAddress
	FROM RFC1155-SMI
   DisplayString
      FROM RFC1213-MIB
   cabletron
      FROM CTRON-OIDS;
            
ctSSA           OBJECT IDENTIFIER ::= { cabletron 4497 }
 
daRadius              OBJECT IDENTIFIER ::= { ctSSA 24 }

daRadiusConfig        OBJECT IDENTIFIER ::= { daRadius 1 }

daRadiusGeneralConfig OBJECT IDENTIFIER ::= { daRadiusConfig 1 }

daRadiusStats         OBJECT IDENTIFIER ::= { daRadius 2 }

daRadiusGeneralStats  OBJECT IDENTIFIER ::= { daRadiusStats 1 }


-- RADIUS Client General Configuration

daRadiusgcEnabled OBJECT-TYPE
   SYNTAX  INTEGER { enabled(1), 
                     disabled(2) }
   ACCESS  read-write
   STATUS  mandatory
   DESCRIPTION  
          "Administrative status for the RADIUS client."
   ::= { daRadiusGeneralConfig 1 }
       
daRadiusgcAuthNumRetries OBJECT-TYPE
   SYNTAX  INTEGER
   ACCESS  read-write
   STATUS  mandatory
   DESCRIPTION
          "Number of times the RADIUS client will issue a request to a
           RADIUS Authentication Server if the server does not respond."
   ::= { daRadiusGeneralConfig 2 }
        
daRadiusgcAuthSecsBtwnRetries OBJECT-TYPE
   SYNTAX  INTEGER
   ACCESS  read-write
   STATUS  mandatory
   DESCRIPTION
          "Number of seconds a RADIUS Authentication Server has to
           respond to a request before the RADIUS client gives up waiting."
   ::= { daRadiusGeneralConfig 3 }

daRadiusgcAcctNumRetries OBJECT-TYPE
   SYNTAX  INTEGER
   ACCESS  read-write
   STATUS  mandatory
   DESCRIPTION
          "Number of times the RADIUS client will issue a request to a
           RADIUS Accounting Server attempting to solicit a response."
   ::= { daRadiusGeneralConfig 4 }
        
gcAcctSecsBtwnRetries  OBJECT-TYPE
   SYNTAX  INTEGER
   ACCESS  read-write
   STATUS  mandatory
   DESCRIPTION
          "Number of seconds a RADIUS Accounting Server has to
           respond to a request before the RADIUS client gives up waiting."
   ::= { daRadiusGeneralConfig 5 }
   

-- RADIUS Server Configuration Table

daRadiusServerCfgTable OBJECT-TYPE
   SYNTAX  SEQUENCE OF DaRadiusServerCfgEntry
   ACCESS  not-accessible
   STATUS  mandatory
   DESCRIPTION
          "This table contains RADIUS server configurations used by the
           RADIUS client."
   ::= { daRadiusConfig 2 }
   
daRadiusServerCfgEntry OBJECT-TYPE
   SYNTAX  DaRadiusServerCfgEntry
   ACCESS  not-accessible
   STATUS  mandatory
   DESCRIPTION
          "Each entry contains configuration information for
           a RADIUS server."
   INDEX { scIndex }
   ::= { daRadiusServerCfgTable 1 }
           
DaRadiusServerCfgEntry ::=
   SEQUENCE {
      scIndex        INTEGER,
      scStatus       INTEGER,
      scIpAddress    IpAddress,
      scSharedSecret DisplayString,
      scUdpPort      INTEGER
   }
   
scIndex OBJECT-TYPE
   SYNTAX  INTEGER { primaryAuthentication(1), 
                     secondaryAuthentication(2),
                     primaryAccounting(3),
                     secondaryAccounting(4) }
   ACCESS  read-only
   STATUS  mandatory
   DESCRIPTION
          "Type of RADIUS server."
   ::= { daRadiusServerCfgEntry 1 }
   
scStatus OBJECT-TYPE
   SYNTAX  INTEGER { enabled(1),
                     disabled(2) }
   ACCESS  read-write
   STATUS  mandatory
   DESCRIPTION
          "RADIUS client administrative status for the RADIUS server, 
           indicating if the server is enabled to be used by the 
           RADIUS client."
   ::= { daRadiusServerCfgEntry 2 }
   
scIpAddress OBJECT-TYPE
   SYNTAX  IpAddress
   ACCESS  read-write
   STATUS  mandatory
   DESCRIPTION
          "RADIUS server IP address."
   ::= {daRadiusServerCfgEntry 3 }
   
scSharedSecret OBJECT-TYPE
   SYNTAX  DisplayString
   ACCESS  read-write
   STATUS  mandatory
   DESCRIPTION
          "Shared secret used to authentication transactions between
           the RADIUS client and the RADIUS server."
   ::= {daRadiusServerCfgEntry 4 }
   
scUdpPort OBJECT-TYPE
   SYNTAX  INTEGER
   ACCESS  read-write
   STATUS  mandatory
   DESCRIPTION
          "RADIUS server UDP port."
   ::= {daRadiusServerCfgEntry 5 }
   

-- RADIUS Client General Statistics

gsInDiscards OBJECT-TYPE
   SYNTAX  INTEGER
   ACCESS  read-only
   STATUS  mandatory
   DESCRIPTION
          "The number of packets received from RADIUS servers which were
           chosen to be discarded even though no errors had been detected.
           The packets were chosen to be discarded before the source
           RADIUS server was identified.  One possible reason for discarding 
           a packet could be because the packet was received after the 
           RADIUS client gave up waiting for it."
   ::= { daRadiusGeneralStats 1 }
   
gsInErrors OBJECT-TYPE
   SYNTAX  INTEGER
   ACCESS  read-only
   STATUS  mandatory
   DESCRIPTION
          "The number of packets received from RADIUS servers that
           contained errors preventing them from being processed.
           The packets were found to contain errors before the
           source RADIUS server was identified."
   ::= { daRadiusGeneralStats 2 }
               

-- RADIUS Server Statistics Table

daRadiusServerStatsTable OBJECT-TYPE
   SYNTAX  SEQUENCE OF DaRadiusServerStatsEntry
   ACCESS  not-accessible
   STATUS  mandatory
   DESCRIPTION
          "This table contains RADIUS server statistics tallied by the
           RADIUS client."
   ::= { daRadiusStats 2 }
   
daRadiusServerStatsEntry OBJECT-TYPE
   SYNTAX  DaRadiusServerStatsEntry
   ACCESS  not-accessible
   STATUS  mandatory
   DESCRIPTION
          "Each entry contains RADIUS server statistics tallied by the
           RADIUS client."
   INDEX { ssIndex }
   ::= { daRadiusServerStatsTable 1 }
   
DaRadiusServerStatsEntry ::=
   SEQUENCE {
      ssIndex            INTEGER,
      ssInPkts           INTEGER,
      ssInDiscards       INTEGER,
      ssInErrors         INTEGER,
      ssOutPkts          INTEGER,
      ssOutErrors        INTEGER,
      ssResponseTimeouts INTEGER
   }           

ssIndex OBJECT-TYPE
   SYNTAX  INTEGER { primaryAuthentication(1), 
                     secondaryAuthentication(2),
                     primaryAccounting(3),
                     secondaryAccounting(4) }
   ACCESS  read-only
   STATUS  mandatory
   DESCRIPTION
          "Type of RADIUS server."
   ::= { daRadiusServerStatsEntry 1 }

ssInPkts OBJECT-TYPE
   SYNTAX  INTEGER
   ACCESS  read-only
   STATUS  mandatory
   DESCRIPTION
          "The number of packets received from the RADIUS server that
           were successfully handled by the RADIUS client."
   ::= { daRadiusServerStatsEntry 2 }
   
ssInDiscards OBJECT-TYPE           
   SYNTAX  INTEGER
   ACCESS  read-only
   STATUS  mandatory
   DESCRIPTION
          "The number of packets received from the RADIUS server which were
           chosen to be discarded even though no errors had been detected.
           One possible reason for discarding a packet could be because the 
           RADIUS code field of the packet was not recognized."
   ::= { daRadiusServerStatsEntry 3 }
   
ssInErrors OBJECT-TYPE
   SYNTAX  INTEGER           
   ACCESS  read-only
   STATUS  mandatory
   DESCRIPTION
          "The number of packets received from the RADIUS server that
           contained errors preventing them from being processed."
   ::= { daRadiusServerStatsEntry 4 }

ssOutPkts OBJECT-TYPE
   SYNTAX  INTEGER
   ACCESS  read-only
   STATUS  mandatory
   DESCRIPTION
          "The number of packets transmitted to the RADIUS server."
   ::= { daRadiusServerStatsEntry 5 }

ssOutErrors OBJECT-TYPE
   SYNTAX  INTEGER
   ACCESS  read-only
   STATUS  mandatory
   DESCRIPTION
          "The number of packets the RADIUS client was unable
           to transmit to the RADIUS server due to transmission
           errors."
   ::= { daRadiusServerStatsEntry 6 }
   
ssResponseTimeouts OBJECT-TYPE
   SYNTAX  INTEGER
   ACCESS  read-only
   STATUS  mandatory
   DESCRIPTION
          "The number of times the RADIUS client did not receive
           a response from the RADIUS server within the expected time."
   ::= { daRadiusServerStatsEntry 7 } 

END
