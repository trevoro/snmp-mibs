Rogue-Engineering-Inc-Sentinel-Remote-IO-with-SNMP
-- ******************************************************
--Rogue Engineering Inc., SNMP  MIB
--Prefix for private enterprises:  1.3.6.1.4.1  
--Rogue Engineering Inc. private enterprize number:  28459
--
--This MIB is for the Sentinel Remote I/O with SNMP product
--Version supported: Firmware 228-02
--Last Updated: June 4, 2008
--
--The following objects are implemented in the MIB-II System Group
--
--1.3.6.1.2.1.1.1   sysDescr
--1.3.6.1.2.1.1.2   sysObjectID
--1.3.6.1.2.1.1.3   sysUpTime
--1.3.6.1.2.1.1.4   sysContact
--1.3.6.1.2.1.1.5   sysName
--1.3.6.1.2.1.1.6   sysLocation
--1.3.6.1.2.1.1.7   sysServices
--
--
--
-- ************************************************************

DEFINITIONS ::= BEGIN

IMPORTS  
    enterprises
        FROM RFC1155-SMI
    MODULE-IDENTITY, OBJECT-TYPE, NOTIFICATION-TYPE, Integer32 
        FROM SNMPv2-SMI
    MODULE-COMPLIANCE, OBJECT-GROUP
        FROM SNMPv2-CONF
    SnmpAdminString
        FROM SNMP-FRAMEWORK-MIB;

rogueSentinelv2 MODULE-IDENTITY
    LAST-UPDATED "200806041700Z"
    ORGANIZATION "Rogue Engineering Inc."
    CONTACT-INFO
        "    Tim Kirk
             Rogue Engineering Inc.
             3860 S. Jason St.
             Englewood, CO 80110
             
             Tel: 303-734-0706
             Fax: 303-734-0517
             Internet: http://www.rogue-engr.com
             Email:    tkirk@rogue-engr.com"
    DESCRIPTION 
        "This MIB is for the Sentinel Remote I/O with SNMP"
    REVISION "200806041700Z"
    DESCRIPTION
        "Supports Firmware 228-02"
    ::= { rogueRIOS 2 }                                         -- 28459.228.2


-- Rogue Engineering Inc. MIBs
rogueEngr      OBJECT IDENTIFIER ::= { enterprises 28459 }     -- 1.3.6.1.4.1.28459

-- Items under the rogueEngr tree are product-specific
-- The RIOS product is ID 228
rogueRIOS   OBJECT IDENTIFIER ::= { rogueEngr 228 }            -- 28459.228


-- Major object categories for Remote I/O with SNMP product
regMap          OBJECT IDENTIFIER ::= { rogueSentinelv2 1 }     -- 28459.228.2.1
trapMap         OBJECT IDENTIFIER ::= { rogueSentinelv2 2 }     -- 28459.228.2.2
history         OBJECT IDENTIFIER ::= { rogueSentinelv2 3 }     -- 28459.228.2.3


-- ******************************************************
--
-- READ/WRITE REGISTER DEFINITIONS (corresponds to the Modbus Register map)
-- 
-- ******************************************************

regFirmwareVersion OBJECT-TYPE
    SYNTAX  Integer32
    MAX-ACCESS  read-only
    STATUS  current
    DESCRIPTION
        "Firmware Version"
    ::= { regMap 3 }


regFirmwareRevision OBJECT-TYPE
    SYNTAX  Integer32
    MAX-ACCESS  read-only
    STATUS  current
    DESCRIPTION
        "Firmware Revision"
    ::= { regMap 4 }


regSerialBaud OBJECT-TYPE
    SYNTAX  Integer32
    MAX-ACCESS  read-write
    STATUS  current
    DESCRIPTION
        "Baud Rate 0=9600,1=19200,2=57600"
    ::= { regMap 99 }


regSNMPManagerIP1 OBJECT-TYPE
    SYNTAX  Integer32
    MAX-ACCESS  read-write
    STATUS  current
    DESCRIPTION
        "SNMP Manager IP Address (Destination for Traps) (1 of 4)"
    ::= { regMap 100 }


regSNMPManagerIP2 OBJECT-TYPE
    SYNTAX  Integer32
    MAX-ACCESS  read-write
    STATUS  current
    DESCRIPTION
        "SNMP Manager IP Address (Destination for Traps) (2 of 4)"
    ::= { regMap 101 }


regSNMPManagerIP3 OBJECT-TYPE
    SYNTAX  Integer32
    MAX-ACCESS  read-write
    STATUS  current
    DESCRIPTION
        "SNMP Manager IP Address (Destination for Traps) (3 of 4)"
    ::= { regMap 102 }


regSNMPManagerIP4 OBJECT-TYPE
    SYNTAX  Integer32
    MAX-ACCESS  read-write
    STATUS  current
    DESCRIPTION
        "SNMP Manager IP Address (Destination for Traps) (4 of 4)"
    ::= { regMap 103 }


regMODBUSAddress OBJECT-TYPE
    SYNTAX  Integer32
    MAX-ACCESS  read-write
    STATUS  current
    DESCRIPTION
        "MODBUS Address"
    ::= { regMap 104 }


regMACAddress1 OBJECT-TYPE
    SYNTAX  Integer32
    MAX-ACCESS  read-write
    STATUS  current
    DESCRIPTION
        "MAC Address (1 of 6)"
    ::= { regMap 105 }


regMACAddress2 OBJECT-TYPE
    SYNTAX  Integer32
    MAX-ACCESS  read-write
    STATUS  current
    DESCRIPTION
        "MAC Address (2 of 6)"
    ::= { regMap 106 }


regMACAddress3 OBJECT-TYPE
    SYNTAX  Integer32
    MAX-ACCESS  read-write
    STATUS  current
    DESCRIPTION
        "MAC Address (3 of 6)"
    ::= { regMap 107 }


regMACAddress4 OBJECT-TYPE
    SYNTAX  Integer32
    MAX-ACCESS  read-write
    STATUS  current
    DESCRIPTION
        "MAC Address (4 of 6)"
    ::= { regMap 108 }


regMACAddress5 OBJECT-TYPE
    SYNTAX  Integer32
    MAX-ACCESS  read-write
    STATUS  current
    DESCRIPTION
        "MAC Address (5 of 6)"
    ::= { regMap 109 }


regMACAddress6 OBJECT-TYPE
    SYNTAX  Integer32
    MAX-ACCESS  read-write
    STATUS  current
    DESCRIPTION
        "MAC Address (6 of 6)"
    ::= { regMap 110 }


regIPAddress1 OBJECT-TYPE
    SYNTAX  Integer32
    MAX-ACCESS  read-write
    STATUS  current
    DESCRIPTION
        "IP Address (1 of 4)"
    ::= { regMap 111 }


regIPAddress2 OBJECT-TYPE
    SYNTAX  Integer32
    MAX-ACCESS  read-write
    STATUS  current
    DESCRIPTION
        "IP Address (2 of 4)"
    ::= { regMap 112 }


regIPAddress3 OBJECT-TYPE
    SYNTAX  Integer32
    MAX-ACCESS  read-write
    STATUS  current
    DESCRIPTION
        "IP Address (3 of 4)"
    ::= { regMap 113 }


regIPAddress4 OBJECT-TYPE
    SYNTAX  Integer32
    MAX-ACCESS  read-write
    STATUS  current
    DESCRIPTION
        "IP Address (4 of 4)"
    ::= { regMap 114 }


regGatewayIPAddress1 OBJECT-TYPE
    SYNTAX  Integer32
    MAX-ACCESS  read-write
    STATUS  current
    DESCRIPTION
        "Gateway IP Address (1 of 4)"
    ::= { regMap 115 }


regGatewayIPAddress2 OBJECT-TYPE
    SYNTAX  Integer32
    MAX-ACCESS  read-write
    STATUS  current
    DESCRIPTION
        "Gateway IP Address (2 of 4)"
    ::= { regMap 116 }


regGatewayIPAddress3 OBJECT-TYPE
    SYNTAX  Integer32
    MAX-ACCESS  read-write
    STATUS  current
    DESCRIPTION
        "Gateway IP Address (3 of 4)"
    ::= { regMap 117 }


regGatewayIPAddress4 OBJECT-TYPE
    SYNTAX  Integer32
    MAX-ACCESS  read-write
    STATUS  current
    DESCRIPTION
        "Gateway IP Address (4 of 4)"
    ::= { regMap 118 }


regSubnetMask1 OBJECT-TYPE
    SYNTAX  Integer32
    MAX-ACCESS  read-write
    STATUS  current
    DESCRIPTION
        "Subnet Mask (1 of 4)"
    ::= { regMap 119 }


regSubnetMask2 OBJECT-TYPE
    SYNTAX  Integer32
    MAX-ACCESS  read-write
    STATUS  current
    DESCRIPTION
        "Subnet Mask (2 of 4)"
    ::= { regMap 120 }


regSubnetMask3 OBJECT-TYPE
    SYNTAX  Integer32
    MAX-ACCESS  read-write
    STATUS  current
    DESCRIPTION
        "Subnet Mask (3 of 4)"
    ::= { regMap 121 }


regSubnetMask4 OBJECT-TYPE
    SYNTAX  Integer32
    MAX-ACCESS  read-write
    STATUS  current
    DESCRIPTION
        "Subnet Mask (4 of 4)"
    ::= { regMap 122 }


regControllerName1 OBJECT-TYPE
    SYNTAX  Integer32
    MAX-ACCESS  read-write
    STATUS  current
    DESCRIPTION
        "Controller Name or Description (1 of 55)"
    ::= { regMap 208 }


regControllerName2 OBJECT-TYPE
    SYNTAX  Integer32
    MAX-ACCESS  read-write
    STATUS  current
    DESCRIPTION
        "Controller Name or Description (2 of 55)"
    ::= { regMap 209 }


regControllerName3 OBJECT-TYPE
    SYNTAX  Integer32
    MAX-ACCESS  read-write
    STATUS  current
    DESCRIPTION
        "Controller Name or Description (3 of 55)"
    ::= { regMap 210 }


regControllerName4 OBJECT-TYPE
    SYNTAX  Integer32
    MAX-ACCESS  read-write
    STATUS  current
    DESCRIPTION
        "Controller Name or Description (4 of 55)"
    ::= { regMap 211 }


regControllerName5 OBJECT-TYPE
    SYNTAX  Integer32
    MAX-ACCESS  read-write
    STATUS  current
    DESCRIPTION
        "Controller Name or Description (5 of 55)"
    ::= { regMap 212 }


regControllerName6 OBJECT-TYPE
    SYNTAX  Integer32
    MAX-ACCESS  read-write
    STATUS  current
    DESCRIPTION
        "Controller Name or Description (6 of 55)"
    ::= { regMap 213 }


regControllerName7 OBJECT-TYPE
    SYNTAX  Integer32
    MAX-ACCESS  read-write
    STATUS  current
    DESCRIPTION
        "Controller Name or Description (7 of 55)"
    ::= { regMap 214 }


regControllerName8 OBJECT-TYPE
    SYNTAX  Integer32
    MAX-ACCESS  read-write
    STATUS  current
    DESCRIPTION
        "Controller Name or Description (8 of 55)"
    ::= { regMap 215 }


regControllerName9 OBJECT-TYPE
    SYNTAX  Integer32
    MAX-ACCESS  read-write
    STATUS  current
    DESCRIPTION
        "Controller Name or Description (9 of 55)"
    ::= { regMap 216 }


regControllerName10 OBJECT-TYPE
    SYNTAX  Integer32
    MAX-ACCESS  read-write
    STATUS  current
    DESCRIPTION
        "Controller Name or Description (10 of 55)"
    ::= { regMap 217 }


regControllerName11 OBJECT-TYPE
    SYNTAX  Integer32
    MAX-ACCESS  read-write
    STATUS  current
    DESCRIPTION
        "Controller Name or Description (11 of 55)"
    ::= { regMap 218 }


regControllerName12 OBJECT-TYPE
    SYNTAX  Integer32
    MAX-ACCESS  read-write
    STATUS  current
    DESCRIPTION
        "Controller Name or Description (12 of 55)"
    ::= { regMap 219 }


regControllerName13 OBJECT-TYPE
    SYNTAX  Integer32
    MAX-ACCESS  read-write
    STATUS  current
    DESCRIPTION
        "Controller Name or Description (13 of 55)"
    ::= { regMap 220 }


regControllerName14 OBJECT-TYPE
    SYNTAX  Integer32
    MAX-ACCESS  read-write
    STATUS  current
    DESCRIPTION
        "Controller Name or Description (14 of 55)"
    ::= { regMap 221 }


regControllerName15 OBJECT-TYPE
    SYNTAX  Integer32
    MAX-ACCESS  read-write
    STATUS  current
    DESCRIPTION
        "Controller Name or Description (15 of 55)"
    ::= { regMap 222 }


regControllerName16 OBJECT-TYPE
    SYNTAX  Integer32
    MAX-ACCESS  read-write
    STATUS  current
    DESCRIPTION
        "Controller Name or Description (16 of 55)"
    ::= { regMap 223 }


regControllerName17 OBJECT-TYPE
    SYNTAX  Integer32
    MAX-ACCESS  read-write
    STATUS  current
    DESCRIPTION
        "Controller Name or Description (17 of 55)"
    ::= { regMap 224 }


regControllerName18 OBJECT-TYPE
    SYNTAX  Integer32
    MAX-ACCESS  read-write
    STATUS  current
    DESCRIPTION
        "Controller Name or Description (18 of 55)"
    ::= { regMap 225 }


regControllerName19 OBJECT-TYPE
    SYNTAX  Integer32
    MAX-ACCESS  read-write
    STATUS  current
    DESCRIPTION
        "Controller Name or Description (19 of 55)"
    ::= { regMap 226 }


regControllerName20 OBJECT-TYPE
    SYNTAX  Integer32
    MAX-ACCESS  read-write
    STATUS  current
    DESCRIPTION
        "Controller Name or Description (20 of 55)"
    ::= { regMap 227 }


regControllerName21 OBJECT-TYPE
    SYNTAX  Integer32
    MAX-ACCESS  read-write
    STATUS  current
    DESCRIPTION
        "Controller Name or Description (21 of 55)"
    ::= { regMap 228 }


regControllerName22 OBJECT-TYPE
    SYNTAX  Integer32
    MAX-ACCESS  read-write
    STATUS  current
    DESCRIPTION
        "Controller Name or Description (22 of 55)"
    ::= { regMap 229 }


regControllerName23 OBJECT-TYPE
    SYNTAX  Integer32
    MAX-ACCESS  read-write
    STATUS  current
    DESCRIPTION
        "Controller Name or Description (23 of 55)"
    ::= { regMap 230 }


regControllerName24 OBJECT-TYPE
    SYNTAX  Integer32
    MAX-ACCESS  read-write
    STATUS  current
    DESCRIPTION
        "Controller Name or Description (24 of 55)"
    ::= { regMap 231 }


regControllerName25 OBJECT-TYPE
    SYNTAX  Integer32
    MAX-ACCESS  read-write
    STATUS  current
    DESCRIPTION
        "Controller Name or Description (25 of 55)"
    ::= { regMap 232 }


regControllerName26 OBJECT-TYPE
    SYNTAX  Integer32
    MAX-ACCESS  read-write
    STATUS  current
    DESCRIPTION
        "Controller Name or Description (26 of 55)"
    ::= { regMap 233 }


regControllerName27 OBJECT-TYPE
    SYNTAX  Integer32
    MAX-ACCESS  read-write
    STATUS  current
    DESCRIPTION
        "Controller Name or Description (27 of 55)"
    ::= { regMap 234 }


regControllerName28 OBJECT-TYPE
    SYNTAX  Integer32
    MAX-ACCESS  read-write
    STATUS  current
    DESCRIPTION
        "Controller Name or Description (28 of 55)"
    ::= { regMap 235 }


regControllerName29 OBJECT-TYPE
    SYNTAX  Integer32
    MAX-ACCESS  read-write
    STATUS  current
    DESCRIPTION
        "Controller Name or Description (29 of 55)"
    ::= { regMap 236 }


regControllerName30 OBJECT-TYPE
    SYNTAX  Integer32
    MAX-ACCESS  read-write
    STATUS  current
    DESCRIPTION
        "Controller Name or Description (30 of 55)"
    ::= { regMap 237 }


regControllerName31 OBJECT-TYPE
    SYNTAX  Integer32
    MAX-ACCESS  read-write
    STATUS  current
    DESCRIPTION
        "Controller Name or Description (31 of 55)"
    ::= { regMap 238 }


regControllerName32 OBJECT-TYPE
    SYNTAX  Integer32
    MAX-ACCESS  read-write
    STATUS  current
    DESCRIPTION
        "Controller Name or Description (32 of 55)"
    ::= { regMap 239 }


regControllerName33 OBJECT-TYPE
    SYNTAX  Integer32
    MAX-ACCESS  read-write
    STATUS  current
    DESCRIPTION
        "Controller Name or Description (33 of 55)"
    ::= { regMap 240 }


regControllerName34 OBJECT-TYPE
    SYNTAX  Integer32
    MAX-ACCESS  read-write
    STATUS  current
    DESCRIPTION
        "Controller Name or Description (34 of 55)"
    ::= { regMap 241 }


regControllerName35 OBJECT-TYPE
    SYNTAX  Integer32
    MAX-ACCESS  read-write
    STATUS  current
    DESCRIPTION
        "Controller Name or Description (35 of 55)"
    ::= { regMap 242 }


regControllerName36 OBJECT-TYPE
    SYNTAX  Integer32
    MAX-ACCESS  read-write
    STATUS  current
    DESCRIPTION
        "Controller Name or Description (36 of 55)"
    ::= { regMap 243 }


regControllerName37 OBJECT-TYPE
    SYNTAX  Integer32
    MAX-ACCESS  read-write
    STATUS  current
    DESCRIPTION
        "Controller Name or Description (37 of 55)"
    ::= { regMap 244 }


regControllerName38 OBJECT-TYPE
    SYNTAX  Integer32
    MAX-ACCESS  read-write
    STATUS  current
    DESCRIPTION
        "Controller Name or Description (38 of 55)"
    ::= { regMap 245 }


regControllerName39 OBJECT-TYPE
    SYNTAX  Integer32
    MAX-ACCESS  read-write
    STATUS  current
    DESCRIPTION
        "Controller Name or Description (39 of 55)"
    ::= { regMap 246 }


regControllerName40 OBJECT-TYPE
    SYNTAX  Integer32
    MAX-ACCESS  read-write
    STATUS  current
    DESCRIPTION
        "Controller Name or Description (40 of 55)"
    ::= { regMap 247 }


regControllerName41 OBJECT-TYPE
    SYNTAX  Integer32
    MAX-ACCESS  read-write
    STATUS  current
    DESCRIPTION
        "Controller Name or Description (41 of 55)"
    ::= { regMap 248 }


regControllerName42 OBJECT-TYPE
    SYNTAX  Integer32
    MAX-ACCESS  read-write
    STATUS  current
    DESCRIPTION
        "Controller Name or Description (42 of 55)"
    ::= { regMap 249 }


regControllerName43 OBJECT-TYPE
    SYNTAX  Integer32
    MAX-ACCESS  read-write
    STATUS  current
    DESCRIPTION
        "Controller Name or Description (43 of 55)"
    ::= { regMap 250 }


regControllerName44 OBJECT-TYPE
    SYNTAX  Integer32
    MAX-ACCESS  read-write
    STATUS  current
    DESCRIPTION
        "Controller Name or Description (44 of 55)"
    ::= { regMap 251 }


regControllerName45 OBJECT-TYPE
    SYNTAX  Integer32
    MAX-ACCESS  read-write
    STATUS  current
    DESCRIPTION
        "Controller Name or Description (45 of 55)"
    ::= { regMap 252 }


regControllerName46 OBJECT-TYPE
    SYNTAX  Integer32
    MAX-ACCESS  read-write
    STATUS  current
    DESCRIPTION
        "Controller Name or Description (46 of 55)"
    ::= { regMap 253 }


regControllerName47 OBJECT-TYPE
    SYNTAX  Integer32
    MAX-ACCESS  read-write
    STATUS  current
    DESCRIPTION
        "Controller Name or Description (47 of 55)"
    ::= { regMap 254 }


regControllerName48 OBJECT-TYPE
    SYNTAX  Integer32
    MAX-ACCESS  read-write
    STATUS  current
    DESCRIPTION
        "Controller Name or Description (48 of 55)"
    ::= { regMap 255 }


regControllerName49 OBJECT-TYPE
    SYNTAX  Integer32
    MAX-ACCESS  read-write
    STATUS  current
    DESCRIPTION
        "Controller Name or Description (49 of 55)"
    ::= { regMap 256 }


regControllerName50 OBJECT-TYPE
    SYNTAX  Integer32
    MAX-ACCESS  read-write
    STATUS  current
    DESCRIPTION
        "Controller Name or Description (50 of 55)"
    ::= { regMap 257 }


regControllerName51 OBJECT-TYPE
    SYNTAX  Integer32
    MAX-ACCESS  read-write
    STATUS  current
    DESCRIPTION
        "Controller Name or Description (51 of 55)"
    ::= { regMap 258 }


regControllerName52 OBJECT-TYPE
    SYNTAX  Integer32
    MAX-ACCESS  read-write
    STATUS  current
    DESCRIPTION
        "Controller Name or Description (52 of 55)"
    ::= { regMap 259 }


regControllerName53 OBJECT-TYPE
    SYNTAX  Integer32
    MAX-ACCESS  read-write
    STATUS  current
    DESCRIPTION
        "Controller Name or Description (53 of 55)"
    ::= { regMap 260 }


regControllerName54 OBJECT-TYPE
    SYNTAX  Integer32
    MAX-ACCESS  read-write
    STATUS  current
    DESCRIPTION
        "Controller Name or Description (54 of 55)"
    ::= { regMap 261 }


regControllerName55 OBJECT-TYPE
    SYNTAX  Integer32
    MAX-ACCESS  read-write
    STATUS  current
    DESCRIPTION
        "Controller Name or Description (55 of 55)"
    ::= { regMap 262 }


regClockYear OBJECT-TYPE
    SYNTAX  Integer32
    MAX-ACCESS  read-write
    STATUS  current
    DESCRIPTION
        "Clock Year"
    ::= { regMap 263 }


regClockMonth OBJECT-TYPE
    SYNTAX  Integer32
    MAX-ACCESS  read-write
    STATUS  current
    DESCRIPTION
        "Clock Month (1-12)"
    ::= { regMap 264 }


regClockDay OBJECT-TYPE
    SYNTAX  Integer32
    MAX-ACCESS  read-write
    STATUS  current
    DESCRIPTION
        "Clock Day of Month (1-31)"
    ::= { regMap 265 }


regClockHour OBJECT-TYPE
    SYNTAX  Integer32
    MAX-ACCESS  read-write
    STATUS  current
    DESCRIPTION
        "Clock Hour (0-23)"
    ::= { regMap 266 }


regClockMinute OBJECT-TYPE
    SYNTAX  Integer32
    MAX-ACCESS  read-write
    STATUS  current
    DESCRIPTION
        "Clock Minute (0-59)"
    ::= { regMap 267 }


regClockSecond OBJECT-TYPE
    SYNTAX  Integer32
    MAX-ACCESS  read-write
    STATUS  current
    DESCRIPTION
        "Clock Second (0-59)"
    ::= { regMap 268 }


regDataLoggingInterval OBJECT-TYPE
    SYNTAX  Integer32
    MAX-ACCESS  read-write
    STATUS  current
    DESCRIPTION
        "Data Logging Interval in Seconds (1 - 3600)"
    ::= { regMap 269 }


regRelay1 OBJECT-TYPE
    SYNTAX  Integer32
    MAX-ACCESS  read-write
    STATUS  current
    DESCRIPTION
        "Relay 1, write zero for off, any non-zero value for on"
    ::= { regMap 280 }


regRelay2 OBJECT-TYPE
    SYNTAX  Integer32
    MAX-ACCESS  read-write
    STATUS  current
    DESCRIPTION
        "Relay 2, write zero for off, any non-zero value for on"
    ::= { regMap 281 }


regBatteryLowAlarmEnable OBJECT-TYPE
    SYNTAX  Integer32
    MAX-ACCESS  read-write
    STATUS  current
    DESCRIPTION
        "Battery Voltage Low Alarm Enable"
    ::= { regMap 290 }


regBatteryLowTriggerVoltage OBJECT-TYPE
    SYNTAX  Integer32
    MAX-ACCESS  read-write
    STATUS  current
    DESCRIPTION
        "Battery Voltage Low Alarm Trigger Voltage, 1/100th volt steps"
    ::= { regMap 291 }


regBatteryLowResetVoltage OBJECT-TYPE
    SYNTAX  Integer32
    MAX-ACCESS  read-write
    STATUS  current
    DESCRIPTION
        "Battery Voltage Low Alarm Reset Voltage"
    ::= { regMap 292 }


regBatteryHighAlarmEnable OBJECT-TYPE
    SYNTAX  Integer32
    MAX-ACCESS  read-write
    STATUS  current
    DESCRIPTION
        "Battery Voltage High Alarm Enable"
    ::= { regMap 293 }


regBatteryHighTriggerVoltage OBJECT-TYPE
    SYNTAX  Integer32
    MAX-ACCESS  read-write
    STATUS  current
    DESCRIPTION
        "Battery Voltage High Alarm Trigger Voltage"
    ::= { regMap 294 }


regBatteryHighResetVoltage OBJECT-TYPE
    SYNTAX  Integer32
    MAX-ACCESS  read-write
    STATUS  current
    DESCRIPTION
        "Battery Voltage High Alarm Reset Voltage"
    ::= { regMap 295 }


regTemperatureLowAlarmEnable OBJECT-TYPE
    SYNTAX  Integer32
    MAX-ACCESS  read-write
    STATUS  current
    DESCRIPTION
        "Temperature Low Alarm Enable"
    ::= { regMap 296 }


regTemperatureLowTrigger OBJECT-TYPE
    SYNTAX  Integer32
    MAX-ACCESS  read-write
    STATUS  current
    DESCRIPTION
        "Temperature Low Alarm Trigger Temperature, 1/10th degree C steps,
        signed"
    ::= { regMap 297 }


regTemperatureLowReset OBJECT-TYPE
    SYNTAX  Integer32
    MAX-ACCESS  read-write
    STATUS  current
    DESCRIPTION
        "Temperature Low Alarm Reset Temperature"
    ::= { regMap 298 }


regTemperatureHighAlarmEnable OBJECT-TYPE
    SYNTAX  Integer32
    MAX-ACCESS  read-write
    STATUS  current
    DESCRIPTION
        "Temperature High Alarm Enable"
    ::= { regMap 299 }


regTemperatureHighTrigger OBJECT-TYPE
    SYNTAX  Integer32
    MAX-ACCESS  read-write
    STATUS  current
    DESCRIPTION
        "Temperature High Alarm Trigger Temperature"
    ::= { regMap 300 }


regTemperatureHighReset OBJECT-TYPE
    SYNTAX  Integer32
    MAX-ACCESS  read-write
    STATUS  current
    DESCRIPTION
        "Temperature High Alarm Reset Temperature"
    ::= { regMap 301 }


regAnalog1LowAlarmEnable OBJECT-TYPE
    SYNTAX  Integer32
    MAX-ACCESS  read-write
    STATUS  current
    DESCRIPTION
        "Analog 1 Low Alarm Enable, 0 = disabled, 1 = 0-32V, 2 = 0-5V, 3 =
        4-20mA"
    ::= { regMap 302 }


regAnalog1LowTriggerVoltage OBJECT-TYPE
    SYNTAX  Integer32
    MAX-ACCESS  read-write
    STATUS  current
    DESCRIPTION
        "Analog 1 Low Alarm Trigger Voltage, 1/100th volt steps or Current
        1/100th mA"
    ::= { regMap 303 }


regAnalog1LowResetVoltage OBJECT-TYPE
    SYNTAX  Integer32
    MAX-ACCESS  read-write
    STATUS  current
    DESCRIPTION
        "Analog 1 Low Alarm Reset Voltage or Current"
    ::= { regMap 304 }


regAnalog1HighAlarmEnable OBJECT-TYPE
    SYNTAX  Integer32
    MAX-ACCESS  read-write
    STATUS  current
    DESCRIPTION
        "Analog 1 High Alarm Enable, 0 = disabled, 1 = 0-32V, 2 = 0-5V, 3 =
        4-20mA"
    ::= { regMap 305 }


regAnalog1HighTriggerVoltage OBJECT-TYPE
    SYNTAX  Integer32
    MAX-ACCESS  read-write
    STATUS  current
    DESCRIPTION
        "Analog 1 High Alarm Trigger Voltage or Current"
    ::= { regMap 306 }


regAnalog1HighResetVoltage OBJECT-TYPE
    SYNTAX  Integer32
    MAX-ACCESS  read-write
    STATUS  current
    DESCRIPTION
        "Analog 1 High Alarm Reset Voltage or Current"
    ::= { regMap 307 }


regAnalog2LowAlarmEnable OBJECT-TYPE
    SYNTAX  Integer32
    MAX-ACCESS  read-write
    STATUS  current
    DESCRIPTION
        "Analog 2 Low Alarm Enable, 0 = disabled, 1 = 0-32V, 2 = 0-5V, 3 =
        4-20mA"
    ::= { regMap 308 }


regAnalog2LowTriggerVoltage OBJECT-TYPE
    SYNTAX  Integer32
    MAX-ACCESS  read-write
    STATUS  current
    DESCRIPTION
        "Analog 2 Low Alarm Trigger Voltage  or Current"
    ::= { regMap 309 }


regAnalog2LowResetVoltage OBJECT-TYPE
    SYNTAX  Integer32
    MAX-ACCESS  read-write
    STATUS  current
    DESCRIPTION
        "Analog 2 Low Alarm Reset Voltage or Current"
    ::= { regMap 310 }


regAnalog2HighAlarmEnable OBJECT-TYPE
    SYNTAX  Integer32
    MAX-ACCESS  read-write
    STATUS  current
    DESCRIPTION
        "Analog 2 High Alarm Enable, 0 = disabled, 1 = 0-32V, 2 = 0-5V, 3 =
        4-20mA"
    ::= { regMap 311 }


regAnalog2HighTriggerVoltage OBJECT-TYPE
    SYNTAX  Integer32
    MAX-ACCESS  read-write
    STATUS  current
    DESCRIPTION
        "Analog 2 High Alarm Trigger Voltage or Current"
    ::= { regMap 312 }


regAnalog2HighResetVoltage OBJECT-TYPE
    SYNTAX  Integer32
    MAX-ACCESS  read-write
    STATUS  current
    DESCRIPTION
        "Analog 2 High Alarm Reset Voltage or Current"
    ::= { regMap 313 }


regDigital1TriggeredAlarmEnable OBJECT-TYPE
    SYNTAX  Integer32
    MAX-ACCESS  read-write
    STATUS  current
    DESCRIPTION
        "Digital 1 Triggered Alarm Enable"
    ::= { regMap 362 }


regDigital1TriggeredCycle OBJECT-TYPE
    SYNTAX  Integer32
    MAX-ACCESS  read-write
    STATUS  current
    DESCRIPTION
        "Digital 1 Triggered Alarm Cycle Time in minutes, 0 = no cycle just
        one shot alarm on edge"
    ::= { regMap 363 }


regDigital1OpenAlarmEnable OBJECT-TYPE
    SYNTAX  Integer32
    MAX-ACCESS  read-write
    STATUS  current
    DESCRIPTION
        "Digital 1 Open Alarm Enable"
    ::= { regMap 364 }


regDigital1OpenCycle OBJECT-TYPE
    SYNTAX  Integer32
    MAX-ACCESS  read-write
    STATUS  current
    DESCRIPTION
        "Digital 1 Open Alarm Cycle Time in minutes"
    ::= { regMap 365 }


regDigital2TriggeredAlarmEnable OBJECT-TYPE
    SYNTAX  Integer32
    MAX-ACCESS  read-write
    STATUS  current
    DESCRIPTION
        "Digital 2 Triggered Alarm Enable"
    ::= { regMap 366 }


regDigital2TriggeredCycle OBJECT-TYPE
    SYNTAX  Integer32
    MAX-ACCESS  read-write
    STATUS  current
    DESCRIPTION
        "Digital 2 Triggered Alarm Cycle Time in minutes"
    ::= { regMap 367 }


regDigital2OpenAlarmEnable OBJECT-TYPE
    SYNTAX  Integer32
    MAX-ACCESS  read-write
    STATUS  current
    DESCRIPTION
        "Digital 2 Open Alarm Enable"
    ::= { regMap 368 }


regDigital2OpenCycle OBJECT-TYPE
    SYNTAX  Integer32
    MAX-ACCESS  read-write
    STATUS  current
    DESCRIPTION
        "Digital 2 Open Alarm Cycle Time in minutes"
    ::= { regMap 369 }


regHardwareAlarmEnable OBJECT-TYPE
    SYNTAX  Integer32
    MAX-ACCESS  read-write
    STATUS  current
    DESCRIPTION
        "Hardware Alarm Enable"
    ::= { regMap 402 }


regHardwareAlarmCycle OBJECT-TYPE
    SYNTAX  Integer32
    MAX-ACCESS  read-write
    STATUS  current
    DESCRIPTION
        "Hardware Alarm Cycle Time in minutes, 0 = one shot"
    ::= { regMap 403 }


regBatteryZeroPoint OBJECT-TYPE
    SYNTAX  Integer32
    MAX-ACCESS  read-write
    STATUS  current
    DESCRIPTION
        "Battery A/D Zero Point, a dummy write here causes calibration of this
        point"
    ::= { regMap 410 }


regBatteryMidPoint OBJECT-TYPE
    SYNTAX  Integer32
    MAX-ACCESS  read-only
    STATUS  current
    DESCRIPTION
        "Battery A/D Mid Point, a write to the following register causes
        calibration of this point"
    ::= { regMap 411 }


regBatteryMidPointVoltage OBJECT-TYPE
    SYNTAX  Integer32
    MAX-ACCESS  read-write
    STATUS  current
    DESCRIPTION
        "Battery A/D Mid Point Voltage, a write here causes calibration of
        this point"
    ::= { regMap 412 }


regAnalog1ZeroPoint32V OBJECT-TYPE
    SYNTAX  Integer32
    MAX-ACCESS  read-write
    STATUS  current
    DESCRIPTION
        "Analog 1 A/D 0-32V Zero Point, a dummy write here causes calibration
        of this point"
    ::= { regMap 413 }


regAnalog1MidPoint32V OBJECT-TYPE
    SYNTAX  Integer32
    MAX-ACCESS  read-only
    STATUS  current
    DESCRIPTION
        "Analog 1 A/D 0-32V Mid Point, a write to the following register
        causes calibration of this point"
    ::= { regMap 414 }


regAnalog1MidPointVoltage32V OBJECT-TYPE
    SYNTAX  Integer32
    MAX-ACCESS  read-write
    STATUS  current
    DESCRIPTION
        "Analog 1 A/D 0-32V Mid Point Voltage, a write here causes calibration
        of this point"
    ::= { regMap 415 }


regAnalog1ZeroPoint5V OBJECT-TYPE
    SYNTAX  Integer32
    MAX-ACCESS  read-write
    STATUS  current
    DESCRIPTION
        "Analog 1 A/D 0-5V Zero Point, a dummy write here causes calibration
        of this point"
    ::= { regMap 416 }


regAnalog1MidPoint5V OBJECT-TYPE
    SYNTAX  Integer32
    MAX-ACCESS  read-only
    STATUS  current
    DESCRIPTION
        "Analog 1 A/D 0-5V Mid Point, a write to the following register causes
        calibration of this point"
    ::= { regMap 417 }


regAnalog1MidPointVoltage5V OBJECT-TYPE
    SYNTAX  Integer32
    MAX-ACCESS  read-write
    STATUS  current
    DESCRIPTION
        "Analog 1 A/D 0-5V Mid Point Voltage, a write here causes calibration
        of this point"
    ::= { regMap 418 }


regAnalog1ZeroPoint420mA OBJECT-TYPE
    SYNTAX  Integer32
    MAX-ACCESS  read-write
    STATUS  current
    DESCRIPTION
        "Analog 1 A/D 4-20mA Zero Point, a dummy write here causes calibration
        of this point"
    ::= { regMap 419 }


regAnalog1MidPoint420mA OBJECT-TYPE
    SYNTAX  Integer32
    MAX-ACCESS  read-only
    STATUS  current
    DESCRIPTION
        "Analog 1 A/D 4-20mA Mid Point, a write to the following register
        causes calibration of this point"
    ::= { regMap 420 }


regAnalog1MidPointCurrent420mA OBJECT-TYPE
    SYNTAX  Integer32
    MAX-ACCESS  read-write
    STATUS  current
    DESCRIPTION
        "Analog 1 A/D 4-20mA Mid Point Current, a write here causes
        calibration of this point"
    ::= { regMap 421 }


regAnalog2ZeroPoint32V OBJECT-TYPE
    SYNTAX  Integer32
    MAX-ACCESS  read-write
    STATUS  current
    DESCRIPTION
        "Analog 2 A/D 0-32V Zero Point, a dummy write here causes calibration
        of this point"
    ::= { regMap 422 }


regAnalog2MidPoint32V OBJECT-TYPE
    SYNTAX  Integer32
    MAX-ACCESS  read-only
    STATUS  current
    DESCRIPTION
        "Analog 2 A/D 0-32V Mid Point, a write to the following register
        causes calibration of this point"
    ::= { regMap 423 }


regAnalog2MidPointVoltage32V OBJECT-TYPE
    SYNTAX  Integer32
    MAX-ACCESS  read-write
    STATUS  current
    DESCRIPTION
        "Analog 2 A/D 0-32V Mid Point Voltage, a write here causes calibration
        of this point"
    ::= { regMap 424 }


regAnalog2ZeroPoint5V OBJECT-TYPE
    SYNTAX  Integer32
    MAX-ACCESS  read-write
    STATUS  current
    DESCRIPTION
        "Analog 2 A/D 0-5V Zero Point, a dummy write here causes calibration
        of this point"
    ::= { regMap 425 }


regAnalog2MidPoint5V OBJECT-TYPE
    SYNTAX  Integer32
    MAX-ACCESS  read-only
    STATUS  current
    DESCRIPTION
        "Analog 2 A/D 0-5V Mid Point, a write to the following register causes
        calibration of this point"
    ::= { regMap 426 }


regAnalog2MidPointVoltage5V OBJECT-TYPE
    SYNTAX  Integer32
    MAX-ACCESS  read-write
    STATUS  current
    DESCRIPTION
        "Analog 2 A/D 0-5V Mid Point Voltage, a write here causes calibration
        of this point"
    ::= { regMap 427 }


regAnalog2ZeroPoint420mA OBJECT-TYPE
    SYNTAX  Integer32
    MAX-ACCESS  read-write
    STATUS  current
    DESCRIPTION
        "Analog 2 A/D 4-20mA Zero Point, a dummy write here causes calibration
        of this point"
    ::= { regMap 428 }


regAnalog2MidPoint420mA OBJECT-TYPE
    SYNTAX  Integer32
    MAX-ACCESS  read-only
    STATUS  current
    DESCRIPTION
        "Analog 2 A/D 4-20mA Mid Point, a write to the following register
        causes calibration of this point"
    ::= { regMap 429 }


regAnalog2MidPointCurrent420mA OBJECT-TYPE
    SYNTAX  Integer32
    MAX-ACCESS  read-write
    STATUS  current
    DESCRIPTION
        "Analog 2 A/D 4-20mA Mid Point Current, a write here causes
        calibration of this point"
    ::= { regMap 430 }


regForceBuffers OBJECT-TYPE
    SYNTAX  Integer32
    MAX-ACCESS  read-write
    STATUS  current
    DESCRIPTION
        "Force buffers to be written to flash - write any non-zero value.  If
        not used, flash will only be updated when necessary in order to
        increase its lifetime (data may be lost in a power failure)."
    ::= { regMap 500 }

regAlarmActionBatLowTrigger OBJECT-TYPE
    SYNTAX  Integer32
    MAX-ACCESS  read-write
    STATUS  current
    DESCRIPTION
        "Action 0=No Action,1=R1 On,2=R1 Off,3=R2 On,4=R2 Off"
    ::= { regMap 600 }

regAlarmActionBatLowReset OBJECT-TYPE
    SYNTAX  Integer32
    MAX-ACCESS  read-write
    STATUS  current
    DESCRIPTION
        "Action 0=No Action,1=R1 On,2=R1 Off,3=R2 On,4=R2 Off"
    ::= { regMap 601 }

regAlarmActionBatHighTrigger OBJECT-TYPE
    SYNTAX  Integer32
    MAX-ACCESS  read-write
    STATUS  current
    DESCRIPTION
        "Action 0=No Action,1=R1 On,2=R1 Off,3=R2 On,4=R2 Off"
    ::= { regMap 602 }

regAlarmActionBatHighReset OBJECT-TYPE
    SYNTAX  Integer32
    MAX-ACCESS  read-write
    STATUS  current
    DESCRIPTION
        "Action 0=No Action,1=R1 On,2=R1 Off,3=R2 On,4=R2 Off"
    ::= { regMap 603 }

regAlarmActionTempLowTrigger OBJECT-TYPE
    SYNTAX  Integer32
    MAX-ACCESS  read-write
    STATUS  current
    DESCRIPTION
        "Action 0=No Action,1=R1 On,2=R1 Off,3=R2 On,4=R2 Off"
    ::= { regMap 604 }

regAlarmActionTempLowReset OBJECT-TYPE
    SYNTAX  Integer32
    MAX-ACCESS  read-write
    STATUS  current
    DESCRIPTION
        "Action 0=No Action,1=R1 On,2=R1 Off,3=R2 On,4=R2 Off"
    ::= { regMap 605 }

regAlarmActionTempHighTrigger OBJECT-TYPE
    SYNTAX  Integer32
    MAX-ACCESS  read-write
    STATUS  current
    DESCRIPTION
        "Action 0=No Action,1=R1 On,2=R1 Off,3=R2 On,4=R2 Off"
    ::= { regMap 606 }

regAlarmActionTempHighReset OBJECT-TYPE
    SYNTAX  Integer32
    MAX-ACCESS  read-write
    STATUS  current
    DESCRIPTION
        "Action 0=No Action,1=R1 On,2=R1 Off,3=R2 On,4=R2 Off"
    ::= { regMap 607 }

regAlarmActionAIN1LowTrigger OBJECT-TYPE
    SYNTAX  Integer32
    MAX-ACCESS  read-write
    STATUS  current
    DESCRIPTION
        "Action 0=No Action,1=R1 On,2=R1 Off,3=R2 On,4=R2 Off"
    ::= { regMap 608 }

regAlarmActionAIN1LowReset OBJECT-TYPE
    SYNTAX  Integer32
    MAX-ACCESS  read-write
    STATUS  current
    DESCRIPTION
        "Action 0=No Action,1=R1 On,2=R1 Off,3=R2 On,4=R2 Off"
    ::= { regMap 609 }

regAlarmActionAIN1HighTrigger OBJECT-TYPE
    SYNTAX  Integer32
    MAX-ACCESS  read-write
    STATUS  current
    DESCRIPTION
        "Action 0=No Action,1=R1 On,2=R1 Off,3=R2 On,4=R2 Off"
    ::= { regMap 610 }

regAlarmActionAIN1HighReset OBJECT-TYPE
    SYNTAX  Integer32
    MAX-ACCESS  read-write
    STATUS  current
    DESCRIPTION
        "Action 0=No Action,1=R1 On,2=R1 Off,3=R2 On,4=R2 Off"
    ::= { regMap 611 }

regAlarmActionAIN2LowTrigger OBJECT-TYPE
    SYNTAX  Integer32
    MAX-ACCESS  read-write
    STATUS  current
    DESCRIPTION
        "Action 0=No Action,1=R1 On,2=R1 Off,3=R2 On,4=R2 Off"
    ::= { regMap 612 }

regAlarmActionAIN2LowReset OBJECT-TYPE
    SYNTAX  Integer32
    MAX-ACCESS  read-write
    STATUS  current
    DESCRIPTION
        "Action 0=No Action,1=R1 On,2=R1 Off,3=R2 On,4=R2 Off"
    ::= { regMap 613 }

regAlarmActionAIN2HighTrigger OBJECT-TYPE
    SYNTAX  Integer32
    MAX-ACCESS  read-write
    STATUS  current
    DESCRIPTION
        "Action 0=No Action,1=R1 On,2=R1 Off,3=R2 On,4=R2 Off"
    ::= { regMap 614 }

regAlarmActionAIN2HighReset OBJECT-TYPE
    SYNTAX  Integer32
    MAX-ACCESS  read-write
    STATUS  current
    DESCRIPTION
        "Action 0=No Action,1=R1 On,2=R1 Off,3=R2 On,4=R2 Off"
    ::= { regMap 615 }

regAlarmActionDIN1Trigger OBJECT-TYPE
    SYNTAX  Integer32
    MAX-ACCESS  read-write
    STATUS  current
    DESCRIPTION
        "Action 0=No Action,1=R1 On,2=R1 Off,3=R2 On,4=R2 Off"
    ::= { regMap 648 }

regAlarmActionDIN1Reset OBJECT-TYPE
    SYNTAX  Integer32
    MAX-ACCESS  read-write
    STATUS  current
    DESCRIPTION
        "Action 0=No Action,1=R1 On,2=R1 Off,3=R2 On,4=R2 Off"
    ::= { regMap 649 }

regAlarmActionDIN2Trigger OBJECT-TYPE
    SYNTAX  Integer32
    MAX-ACCESS  read-write
    STATUS  current
    DESCRIPTION
        "Action 0=No Action,1=R1 On,2=R1 Off,3=R2 On,4=R2 Off"
    ::= { regMap 650 }

regAlarmActionDIN2Reset OBJECT-TYPE
    SYNTAX  Integer32
    MAX-ACCESS  read-write
    STATUS  current
    DESCRIPTION
        "Action 0=No Action,1=R1 On,2=R1 Off,3=R2 On,4=R2 Off"
    ::= { regMap 651 }

regBatteryVoltage OBJECT-TYPE
    SYNTAX  Integer32
    MAX-ACCESS  read-only
    STATUS  current
    DESCRIPTION
        "Battery Voltage, 1/100th Volt steps"
    ::= { regMap 1000 }


regTemperature OBJECT-TYPE
    SYNTAX  Integer32
    MAX-ACCESS  read-only
    STATUS  current
    DESCRIPTION
        "Temperature, 1/10th degree C steps, signed"
    ::= { regMap 1001 }


regAnalog132V OBJECT-TYPE
    SYNTAX  Integer32
    MAX-ACCESS  read-only
    STATUS  current
    DESCRIPTION
        "Analog 1, 1/100th Volt steps, 0 - 32 V"
    ::= { regMap 1002 }


regAnalog15V OBJECT-TYPE
    SYNTAX  Integer32
    MAX-ACCESS  read-only
    STATUS  current
    DESCRIPTION
        "Analog 1, 1/100th Volt steps, 0 - 5 V"
    ::= { regMap 1003 }


regAnalog1420mA OBJECT-TYPE
    SYNTAX  Integer32
    MAX-ACCESS  read-only
    STATUS  current
    DESCRIPTION
        "Analog 1, 1/100th mA steps, 4 - 20 mA"
    ::= { regMap 1004 }


regAnalog232V OBJECT-TYPE
    SYNTAX  Integer32
    MAX-ACCESS  read-only
    STATUS  current
    DESCRIPTION
        "Analog 2, 1/100th Volt steps, 0 - 32 V"
    ::= { regMap 1005 }


regAnalog25V OBJECT-TYPE
    SYNTAX  Integer32
    MAX-ACCESS  read-only
    STATUS  current
    DESCRIPTION
        "Analog 2, 1/100th Volt steps, 0 - 5 V"
    ::= { regMap 1006 }


regAnalog2420mA OBJECT-TYPE
    SYNTAX  Integer32
    MAX-ACCESS  read-only
    STATUS  current
    DESCRIPTION
        "Analog 2, 1/100th mA steps, 4 - 20 mA"
    ::= { regMap 1007 }


regDigital1 OBJECT-TYPE
    SYNTAX  Integer32
    MAX-ACCESS  read-only
    STATUS  current
    DESCRIPTION
        "Digital 1"
    ::= { regMap 1100 }


regDigital2 OBJECT-TYPE
    SYNTAX  Integer32
    MAX-ACCESS  read-only
    STATUS  current
    DESCRIPTION
        "Digital 2"
    ::= { regMap 1101 }


regLogPointCountHigh OBJECT-TYPE
    SYNTAX  Integer32
    MAX-ACCESS  read-only
    STATUS  current
    DESCRIPTION
        "Number of stored Log data points, long integer, MSWord"
    ::= { regMap 1200 }


regLogPointCountLow OBJECT-TYPE
    SYNTAX  Integer32
    MAX-ACCESS  read-only
    STATUS  current
    DESCRIPTION
        "Number of stored Log data points, long integer, LSWord"
    ::= { regMap 1201 }


regAlarmPointCount OBJECT-TYPE
    SYNTAX  Integer32
    MAX-ACCESS  read-only
    STATUS  current
    DESCRIPTION
        "Number of stored Alarm data points"
    ::= { regMap 1204 }


regRelayPointCount OBJECT-TYPE
    SYNTAX  Integer32
    MAX-ACCESS  read-only
    STATUS  current
    DESCRIPTION
        "Number of stored Relay data points"
    ::= { regMap 1205 }


regCurrentLogPointHigh OBJECT-TYPE
    SYNTAX  Integer32
    MAX-ACCESS  read-write
    STATUS  current
    DESCRIPTION
        "Current Log data point, MSWord.  Write here to select what registers
        1400 - 1499 will read.  Zero will select the earliest data point."
    ::= { regMap 1300 }


regCurrentLogPointLow OBJECT-TYPE
    SYNTAX  Integer32
    MAX-ACCESS  read-write
    STATUS  current
    DESCRIPTION
        "Current Log data point, LSWord.  Write here to select what registers
        1400 - 1499 will read.  Zero will select the earliest data point."
    ::= { regMap 1301 }


regCurrentAlarmPoint OBJECT-TYPE
    SYNTAX  Integer32
    MAX-ACCESS  read-write
    STATUS  current
    DESCRIPTION
        "Current Alarm data point.  Write here to select what registers 1500
        - 1599 will read."
    ::= { regMap 1304 }


regCurrentRelayPoint OBJECT-TYPE
    SYNTAX  Integer32
    MAX-ACCESS  read-write
    STATUS  current
    DESCRIPTION
        "Current Relay data point.  Write here to select what registers 1600
        - 1699 will read."
    ::= { regMap 1305 }


regEraseLogData OBJECT-TYPE
    SYNTAX  Integer32
    MAX-ACCESS  read-write
    STATUS  current
    DESCRIPTION
        "Erase Log Data - Any non-zero write here will erase the log data."
    ::= { regMap 1350 }


regEraseAlarmData OBJECT-TYPE
    SYNTAX  Integer32
    MAX-ACCESS  read-write
    STATUS  current
    DESCRIPTION
        "Erase Alarm Data - Any non-zero write here will erase the alarm
        data."
    ::= { regMap 1351 }


regEraseRelayData OBJECT-TYPE
    SYNTAX  Integer32
    MAX-ACCESS  read-write
    STATUS  current
    DESCRIPTION
        "Erase Relay Data - Any non-zero write here will erase the relay
        data."
    ::= { regMap 1352 }


regLogDateYear OBJECT-TYPE
    SYNTAX  Integer32
    MAX-ACCESS  read-only
    STATUS  current
    DESCRIPTION
        "Current Log Point, Year minus 2000"
    ::= { regMap 1400 }


regLogDateMonth OBJECT-TYPE
    SYNTAX  Integer32
    MAX-ACCESS  read-only
    STATUS  current
    DESCRIPTION
        "Current Log Point, Month"
    ::= { regMap 1401 }


regLogDateDay OBJECT-TYPE
    SYNTAX  Integer32
    MAX-ACCESS  read-only
    STATUS  current
    DESCRIPTION
        "Current Log Point, Day"
    ::= { regMap 1402 }


regLogDateHour OBJECT-TYPE
    SYNTAX  Integer32
    MAX-ACCESS  read-only
    STATUS  current
    DESCRIPTION
        "Current Log Point, Hour"
    ::= { regMap 1403 }


regLogDateMinute OBJECT-TYPE
    SYNTAX  Integer32
    MAX-ACCESS  read-only
    STATUS  current
    DESCRIPTION
        "Current Log Point, Minute"
    ::= { regMap 1404 }


regLogDateSecond OBJECT-TYPE
    SYNTAX  Integer32
    MAX-ACCESS  read-only
    STATUS  current
    DESCRIPTION
        "Current Log Point, Second"
    ::= { regMap 1405 }


regLogBatteryVoltage OBJECT-TYPE
    SYNTAX  Integer32
    MAX-ACCESS  read-only
    STATUS  current
    DESCRIPTION
        "Current Log Point, Battery Voltage x 100"
    ::= { regMap 1406 }


regLogTemperature OBJECT-TYPE
    SYNTAX  Integer32
    MAX-ACCESS  read-only
    STATUS  current
    DESCRIPTION
        "Current Log Point, Temperature degrees C x 10, signed"
    ::= { regMap 1407 }


regLogAnalog132V OBJECT-TYPE
    SYNTAX  Integer32
    MAX-ACCESS  read-only
    STATUS  current
    DESCRIPTION
        "Current Log Point, Analog 1, 0 - 32 V"
    ::= { regMap 1408 }


regLogAnalog15V OBJECT-TYPE
    SYNTAX  Integer32
    MAX-ACCESS  read-only
    STATUS  current
    DESCRIPTION
        "Current Log Point, Analog 1, 0 - 5 V"
    ::= { regMap 1409 }


regLogAnalog1420mA OBJECT-TYPE
    SYNTAX  Integer32
    MAX-ACCESS  read-only
    STATUS  current
    DESCRIPTION
        "Current Log Point, Analog 1, 4 - 20 mA"
    ::= { regMap 1410 }


regLogAnalog232V OBJECT-TYPE
    SYNTAX  Integer32
    MAX-ACCESS  read-only
    STATUS  current
    DESCRIPTION
        "Current Log Point, Analog 2, 0 - 32 V"
    ::= { regMap 1411 }


regLogAnalog25V OBJECT-TYPE
    SYNTAX  Integer32
    MAX-ACCESS  read-only
    STATUS  current
    DESCRIPTION
        "Current Log Point, Analog 2, 0 - 5 V"
    ::= { regMap 1412 }


regLogAnalog2420mA OBJECT-TYPE
    SYNTAX  Integer32
    MAX-ACCESS  read-only
    STATUS  current
    DESCRIPTION
        "Current Log Point, Analog 2, 4 - 20 mA"
    ::= { regMap 1413 }


regLogDigital1 OBJECT-TYPE
    SYNTAX  Integer32
    MAX-ACCESS  read-only
    STATUS  current
    DESCRIPTION
        "Current Log Point, Digital 1"
    ::= { regMap 1414 }


regLogDigital2 OBJECT-TYPE
    SYNTAX  Integer32
    MAX-ACCESS  read-only
    STATUS  current
    DESCRIPTION
        "Current Log Point, Digital 2"
    ::= { regMap 1415 }


regAdvanceLog OBJECT-TYPE
    SYNTAX  Integer32
    MAX-ACCESS  read-only
    STATUS  current
    DESCRIPTION
        "Advance Log Register - If this is read, it will increment the
        current log pointer to the next point."
    ::= { regMap 1416 }


regDecrementLog OBJECT-TYPE
    SYNTAX  Integer32
    MAX-ACCESS  read-write
    STATUS  current
    DESCRIPTION
        "Decrement Log Register - If this is written non-zero, it will move
        the log pointer back a point."
    ::= { regMap 1417 }


regAlarmDateYear OBJECT-TYPE
    SYNTAX  Integer32
    MAX-ACCESS  read-only
    STATUS  current
    DESCRIPTION
        "Current Alarm Point, Year minus 2000"
    ::= { regMap 1500 }


regAlarmDateMonth OBJECT-TYPE
    SYNTAX  Integer32
    MAX-ACCESS  read-only
    STATUS  current
    DESCRIPTION
        "Current Alarm Point, Month"
    ::= { regMap 1501 }


regAlarmDateDay OBJECT-TYPE
    SYNTAX  Integer32
    MAX-ACCESS  read-only
    STATUS  current
    DESCRIPTION
        "Current Alarm Point, Day"
    ::= { regMap 1502 }


regAlarmDateHour OBJECT-TYPE
    SYNTAX  Integer32
    MAX-ACCESS  read-only
    STATUS  current
    DESCRIPTION
        "Current Alarm Point, Hour"
    ::= { regMap 1503 }


regAlarmDateMinute OBJECT-TYPE
    SYNTAX  Integer32
    MAX-ACCESS  read-only
    STATUS  current
    DESCRIPTION
        "Current Alarm Point, Minute"
    ::= { regMap 1504 }


regAlarmDateSecond OBJECT-TYPE
    SYNTAX  Integer32
    MAX-ACCESS  read-only
    STATUS  current
    DESCRIPTION
        "Current Alarm Point, Second"
    ::= { regMap 1505 }


regAlarmID OBJECT-TYPE
    SYNTAX  Integer32
    MAX-ACCESS  read-only
    STATUS  current
    DESCRIPTION
        "Current Alarm Point, Alarm Identifier"
    ::= { regMap 1506 }


regAdvanceAlarm OBJECT-TYPE
    SYNTAX  Integer32
    MAX-ACCESS  read-only
    STATUS  current
    DESCRIPTION
        "Advance Alarm Register - If this is read, it will increment the
        current alarm pointer."
    ::= { regMap 1507 }


regDecrementAlarm OBJECT-TYPE
    SYNTAX  Integer32
    MAX-ACCESS  read-write
    STATUS  current
    DESCRIPTION
        "Decrement Alarm Register - If this is written non-zero, it will move
        the alarm pointer back a point."
    ::= { regMap 1508 }


regRelayDateYear OBJECT-TYPE
    SYNTAX  Integer32
    MAX-ACCESS  read-only
    STATUS  current
    DESCRIPTION
        "Current Relay Point, Year minus 2000"
    ::= { regMap 1600 }


regRelayDateMonth OBJECT-TYPE
    SYNTAX  Integer32
    MAX-ACCESS  read-only
    STATUS  current
    DESCRIPTION
        "Current Relay Point, Month"
    ::= { regMap 1601 }


regRelayDateDay OBJECT-TYPE
    SYNTAX  Integer32
    MAX-ACCESS  read-only
    STATUS  current
    DESCRIPTION
        "Current Relay Point, Day"
    ::= { regMap 1602 }


regRelayDateHour OBJECT-TYPE
    SYNTAX  Integer32
    MAX-ACCESS  read-only
    STATUS  current
    DESCRIPTION
        "Current Relay Point, Hour"
    ::= { regMap 1603 }


regRelayDateMinute OBJECT-TYPE
    SYNTAX  Integer32
    MAX-ACCESS  read-only
    STATUS  current
    DESCRIPTION
        "Current Relay Point, Minute"
    ::= { regMap 1604 }


regRelayDateSecond OBJECT-TYPE
    SYNTAX  Integer32
    MAX-ACCESS  read-only
    STATUS  current
    DESCRIPTION
        "Current Relay Point, Second"
    ::= { regMap 1605 }


regRelayID OBJECT-TYPE
    SYNTAX  Integer32
    MAX-ACCESS  read-only
    STATUS  current
    DESCRIPTION
        "Current Relay Point, Relay Identifier"
    ::= { regMap 1606 }


regRelayPosition OBJECT-TYPE
    SYNTAX  Integer32
    MAX-ACCESS  read-only
    STATUS  current
    DESCRIPTION
        "Current Relay Point, Position, 0 = off, 0xFF00 = on"
    ::= { regMap 1607 }


regAdvanceRelay OBJECT-TYPE
    SYNTAX  Integer32
    MAX-ACCESS  read-only
    STATUS  current
    DESCRIPTION
        "Advance Relay Register - If this is read, it will increment the
        current relay pointer."
    ::= { regMap 1608 }


regDecrementRelay OBJECT-TYPE
    SYNTAX  Integer32
    MAX-ACCESS  read-write
    STATUS  current
    DESCRIPTION
        "Decrement Relay Register - If this is written non-zero, it will move
        the relay pointer back a point."
    ::= { regMap 1609 }


regLog1DateYear OBJECT-TYPE
    SYNTAX  Integer32
    MAX-ACCESS  read-only
    STATUS  current
    DESCRIPTION
        "Current Log Point, Year minus 2000"
    ::= { regMap 2000 }


regLog1DateMonth OBJECT-TYPE
    SYNTAX  Integer32
    MAX-ACCESS  read-only
    STATUS  current
    DESCRIPTION
        "Current Log Point, Month"
    ::= { regMap 2001 }


regLog1DateDay OBJECT-TYPE
    SYNTAX  Integer32
    MAX-ACCESS  read-only
    STATUS  current
    DESCRIPTION
        "Current Log Point, Day"
    ::= { regMap 2002 }


regLog1DateHour OBJECT-TYPE
    SYNTAX  Integer32
    MAX-ACCESS  read-only
    STATUS  current
    DESCRIPTION
        "Current Log Point, Hour"
    ::= { regMap 2003 }


regLog1DateMinute OBJECT-TYPE
    SYNTAX  Integer32
    MAX-ACCESS  read-only
    STATUS  current
    DESCRIPTION
        "Current Log Point, Minute"
    ::= { regMap 2004 }


regLog1DateSecond OBJECT-TYPE
    SYNTAX  Integer32
    MAX-ACCESS  read-only
    STATUS  current
    DESCRIPTION
        "Current Log Point, Second"
    ::= { regMap 2005 }


regLog1BatteryVoltage OBJECT-TYPE
    SYNTAX  Integer32
    MAX-ACCESS  read-only
    STATUS  current
    DESCRIPTION
        "Current Log Point, Battery Voltage x 100"
    ::= { regMap 2006 }


regLog1Temperature OBJECT-TYPE
    SYNTAX  Integer32
    MAX-ACCESS  read-only
    STATUS  current
    DESCRIPTION
        "Current Log Point, Temperature degrees C x 10, signed"
    ::= { regMap 2007 }


regLog1Analog132V OBJECT-TYPE
    SYNTAX  Integer32
    MAX-ACCESS  read-only
    STATUS  current
    DESCRIPTION
        "Current Log Point, Analog 1, 0 - 32 V"
    ::= { regMap 2008 }


regLog1Analog15V OBJECT-TYPE
    SYNTAX  Integer32
    MAX-ACCESS  read-only
    STATUS  current
    DESCRIPTION
        "Current Log Point, Analog 1, 0 - 5 V"
    ::= { regMap 2009 }


regLog1Analog1420mA OBJECT-TYPE
    SYNTAX  Integer32
    MAX-ACCESS  read-only
    STATUS  current
    DESCRIPTION
        "Current Log Point, Analog 1, 4 - 20 mA"
    ::= { regMap 2010 }


regLog1Analog232V OBJECT-TYPE
    SYNTAX  Integer32
    MAX-ACCESS  read-only
    STATUS  current
    DESCRIPTION
        "Current Log Point, Analog 2, 0 - 32 V"
    ::= { regMap 2011 }


regLog1Analog25V OBJECT-TYPE
    SYNTAX  Integer32
    MAX-ACCESS  read-only
    STATUS  current
    DESCRIPTION
        "Current Log Point, Analog 2, 0 - 5 V"
    ::= { regMap 2012 }


regLog1Analog2420mA OBJECT-TYPE
    SYNTAX  Integer32
    MAX-ACCESS  read-only
    STATUS  current
    DESCRIPTION
        "Current Log Point, Analog 2, 4 - 20 mA"
    ::= { regMap 2013 }


regLog1Digital1 OBJECT-TYPE
    SYNTAX  Integer32
    MAX-ACCESS  read-only
    STATUS  current
    DESCRIPTION
        "Current Log Point, Digital 1"
    ::= { regMap 2014 }


regLog1Digital2 OBJECT-TYPE
    SYNTAX  Integer32
    MAX-ACCESS  read-only
    STATUS  current
    DESCRIPTION
        "Current Log Point, Digital 2"
    ::= { regMap 2015 }


regLog2DateYear OBJECT-TYPE
    SYNTAX  Integer32
    MAX-ACCESS  read-only
    STATUS  current
    DESCRIPTION
        "2nd Log Point, Year minus 2000"
    ::= { regMap 2016 }


regLog2DateMonth OBJECT-TYPE
    SYNTAX  Integer32
    MAX-ACCESS  read-only
    STATUS  current
    DESCRIPTION
        "2nd Log Point, Month"
    ::= { regMap 2017 }


regLog2DateDay OBJECT-TYPE
    SYNTAX  Integer32
    MAX-ACCESS  read-only
    STATUS  current
    DESCRIPTION
        "2nd Log Point, Day"
    ::= { regMap 2018 }


regLog2DateHour OBJECT-TYPE
    SYNTAX  Integer32
    MAX-ACCESS  read-only
    STATUS  current
    DESCRIPTION
        "2nd Log Point, Hour"
    ::= { regMap 2019 }


regLog2DateMinute OBJECT-TYPE
    SYNTAX  Integer32
    MAX-ACCESS  read-only
    STATUS  current
    DESCRIPTION
        "2nd Log Point, Minute"
    ::= { regMap 2020 }


regLog2DateSecond OBJECT-TYPE
    SYNTAX  Integer32
    MAX-ACCESS  read-only
    STATUS  current
    DESCRIPTION
        "2nd Log Point, Second"
    ::= { regMap 2021 }


regLog2BatteryVoltage OBJECT-TYPE
    SYNTAX  Integer32
    MAX-ACCESS  read-only
    STATUS  current
    DESCRIPTION
        "2nd Log Point, Battery Voltage x 100"
    ::= { regMap 2022 }


regLog2Temperature OBJECT-TYPE
    SYNTAX  Integer32
    MAX-ACCESS  read-only
    STATUS  current
    DESCRIPTION
        "2nd Log Point, Temperature degrees C x 10, signed"
    ::= { regMap 2023 }


regLog2Analog132V OBJECT-TYPE
    SYNTAX  Integer32
    MAX-ACCESS  read-only
    STATUS  current
    DESCRIPTION
        "2nd Log Point, Analog 1, 0 - 32 V"
    ::= { regMap 2024 }


regLog2Analog15V OBJECT-TYPE
    SYNTAX  Integer32
    MAX-ACCESS  read-only
    STATUS  current
    DESCRIPTION
        "2nd Log Point, Analog 1, 0 - 5 V"
    ::= { regMap 2025 }


regLog2Analog1420mA OBJECT-TYPE
    SYNTAX  Integer32
    MAX-ACCESS  read-only
    STATUS  current
    DESCRIPTION
        "2nd Log Point, Analog 1, 4 - 20 mA"
    ::= { regMap 2026 }


regLog2Analog232V OBJECT-TYPE
    SYNTAX  Integer32
    MAX-ACCESS  read-only
    STATUS  current
    DESCRIPTION
        "2nd Log Point, Analog 2, 0 - 32 V"
    ::= { regMap 2027 }


regLog2Analog25V OBJECT-TYPE
    SYNTAX  Integer32
    MAX-ACCESS  read-only
    STATUS  current
    DESCRIPTION
        "2nd Log Point, Analog 2, 0 - 5 V"
    ::= { regMap 2028 }


regLog2Analog2420mA OBJECT-TYPE
    SYNTAX  Integer32
    MAX-ACCESS  read-only
    STATUS  current
    DESCRIPTION
        "2nd Log Point, Analog 2, 4 - 20 mA"
    ::= { regMap 2029 }


regLog2Digital1 OBJECT-TYPE
    SYNTAX  Integer32
    MAX-ACCESS  read-only
    STATUS  current
    DESCRIPTION
        "2nd Log Point, Digital 1"
    ::= { regMap 2030 }


regLog2Digital2 OBJECT-TYPE
    SYNTAX  Integer32
    MAX-ACCESS  read-only
    STATUS  current
    DESCRIPTION
        "2nd Log Point, Digital 2"
    ::= { regMap 2031 }


regLog3DateYear OBJECT-TYPE
    SYNTAX  Integer32
    MAX-ACCESS  read-only
    STATUS  current
    DESCRIPTION
        "3rd Log Point, Year minus 2000"
    ::= { regMap 2032 }


regLog3DateMonth OBJECT-TYPE
    SYNTAX  Integer32
    MAX-ACCESS  read-only
    STATUS  current
    DESCRIPTION
        "3rd Log Point, Month"
    ::= { regMap 2033 }


regLog3DateDay OBJECT-TYPE
    SYNTAX  Integer32
    MAX-ACCESS  read-only
    STATUS  current
    DESCRIPTION
        "3rd Log Point, Day"
    ::= { regMap 2034 }


regLog3DateHour OBJECT-TYPE
    SYNTAX  Integer32
    MAX-ACCESS  read-only
    STATUS  current
    DESCRIPTION
        "3rd Log Point, Hour"
    ::= { regMap 2035 }


regLog3DateMinute OBJECT-TYPE
    SYNTAX  Integer32
    MAX-ACCESS  read-only
    STATUS  current
    DESCRIPTION
        "3rd Log Point, Minute"
    ::= { regMap 2036 }


regLog3DateSecond OBJECT-TYPE
    SYNTAX  Integer32
    MAX-ACCESS  read-only
    STATUS  current
    DESCRIPTION
        "3rd Log Point, Second"
    ::= { regMap 2037 }


regLog3BatteryVoltage OBJECT-TYPE
    SYNTAX  Integer32
    MAX-ACCESS  read-only
    STATUS  current
    DESCRIPTION
        "3rd Log Point, Battery Voltage x 100"
    ::= { regMap 2038 }


regLog3Temperature OBJECT-TYPE
    SYNTAX  Integer32
    MAX-ACCESS  read-only
    STATUS  current
    DESCRIPTION
        "3rd Log Point, Temperature degrees C x 10, signed"
    ::= { regMap 2039 }


regLog3Analog132V OBJECT-TYPE
    SYNTAX  Integer32
    MAX-ACCESS  read-only
    STATUS  current
    DESCRIPTION
        "3rd Log Point, Analog 1, 0 - 32 V"
    ::= { regMap 2040 }


regLog3Analog15V OBJECT-TYPE
    SYNTAX  Integer32
    MAX-ACCESS  read-only
    STATUS  current
    DESCRIPTION
        "3rd Log Point, Analog 1, 0 - 5 V"
    ::= { regMap 2041 }


regLog3Analog1420mA OBJECT-TYPE
    SYNTAX  Integer32
    MAX-ACCESS  read-only
    STATUS  current
    DESCRIPTION
        "3rd Log Point, Analog 1, 4 - 20 mA"
    ::= { regMap 2042 }


regLog3Analog232V OBJECT-TYPE
    SYNTAX  Integer32
    MAX-ACCESS  read-only
    STATUS  current
    DESCRIPTION
        "3rd Log Point, Analog 2, 0 - 32 V"
    ::= { regMap 2043 }


regLog3Analog25V OBJECT-TYPE
    SYNTAX  Integer32
    MAX-ACCESS  read-only
    STATUS  current
    DESCRIPTION
        "3rd Log Point, Analog 2, 0 - 5 V"
    ::= { regMap 2044 }


regLog3Analog2420mA OBJECT-TYPE
    SYNTAX  Integer32
    MAX-ACCESS  read-only
    STATUS  current
    DESCRIPTION
        "3rd Log Point, Analog 2, 4 - 20 mA"
    ::= { regMap 2045 }


regLog3Digital1 OBJECT-TYPE
    SYNTAX  Integer32
    MAX-ACCESS  read-only
    STATUS  current
    DESCRIPTION
        "3rd Log Point, Digital 1"
    ::= { regMap 2046 }


regLog3Digital2 OBJECT-TYPE
    SYNTAX  Integer32
    MAX-ACCESS  read-only
    STATUS  current
    DESCRIPTION
        "3rd Log Point, Digital 2"
    ::= { regMap 2047 }


regLog4DateYear OBJECT-TYPE
    SYNTAX  Integer32
    MAX-ACCESS  read-only
    STATUS  current
    DESCRIPTION
        "4th Log Point, Year minus 2000"
    ::= { regMap 2048 }


regLog4DateMonth OBJECT-TYPE
    SYNTAX  Integer32
    MAX-ACCESS  read-only
    STATUS  current
    DESCRIPTION
        "4th Log Point, Month"
    ::= { regMap 2049 }


regLog4DateDay OBJECT-TYPE
    SYNTAX  Integer32
    MAX-ACCESS  read-only
    STATUS  current
    DESCRIPTION
        "4th Log Point, Day"
    ::= { regMap 2050 }


regLog4DateHour OBJECT-TYPE
    SYNTAX  Integer32
    MAX-ACCESS  read-only
    STATUS  current
    DESCRIPTION
        "4th Log Point, Hour"
    ::= { regMap 2051 }


regLog4DateMinute OBJECT-TYPE
    SYNTAX  Integer32
    MAX-ACCESS  read-only
    STATUS  current
    DESCRIPTION
        "4th Log Point, Minute"
    ::= { regMap 2052 }


regLog4DateSecond OBJECT-TYPE
    SYNTAX  Integer32
    MAX-ACCESS  read-only
    STATUS  current
    DESCRIPTION
        "4th Log Point, Second"
    ::= { regMap 2053 }


regLog4BatteryVoltage OBJECT-TYPE
    SYNTAX  Integer32
    MAX-ACCESS  read-only
    STATUS  current
    DESCRIPTION
        "4th Log Point, Battery Voltage x 100"
    ::= { regMap 2054 }


regLog4Temperature OBJECT-TYPE
    SYNTAX  Integer32
    MAX-ACCESS  read-only
    STATUS  current
    DESCRIPTION
        "4th Log Point, Temperature degrees C x 10, signed"
    ::= { regMap 2055 }


regLog4Analog132V OBJECT-TYPE
    SYNTAX  Integer32
    MAX-ACCESS  read-only
    STATUS  current
    DESCRIPTION
        "4th Log Point, Analog 1, 0 - 32 V"
    ::= { regMap 2056 }


regLog4Analog15V OBJECT-TYPE
    SYNTAX  Integer32
    MAX-ACCESS  read-only
    STATUS  current
    DESCRIPTION
        "4th Log Point, Analog 1, 0 - 5 V"
    ::= { regMap 2057 }


regLog4Analog1420mA OBJECT-TYPE
    SYNTAX  Integer32
    MAX-ACCESS  read-only
    STATUS  current
    DESCRIPTION
        "4th Log Point, Analog 1, 4 - 20 mA"
    ::= { regMap 2058 }


regLog4Analog232V OBJECT-TYPE
    SYNTAX  Integer32
    MAX-ACCESS  read-only
    STATUS  current
    DESCRIPTION
        "4th Log Point, Analog 2, 0 - 32 V"
    ::= { regMap 2059 }


regLog4Analog25V OBJECT-TYPE
    SYNTAX  Integer32
    MAX-ACCESS  read-only
    STATUS  current
    DESCRIPTION
        "4th Log Point, Analog 2, 0 - 5 V"
    ::= { regMap 2060 }


regLog4Analog2420mA OBJECT-TYPE
    SYNTAX  Integer32
    MAX-ACCESS  read-only
    STATUS  current
    DESCRIPTION
        "4th Log Point, Analog 2, 4 - 20 mA"
    ::= { regMap 2061 }


regLog4Digital1 OBJECT-TYPE
    SYNTAX  Integer32
    MAX-ACCESS  read-only
    STATUS  current
    DESCRIPTION
        "4th Log Point, Digital 1"
    ::= { regMap 2062 }


regLog4Digital2 OBJECT-TYPE
    SYNTAX  Integer32
    MAX-ACCESS  read-only
    STATUS  current
    DESCRIPTION
        "4th Log Point, Digital 2"
    ::= { regMap 2063 }


regLog5DateYear OBJECT-TYPE
    SYNTAX  Integer32
    MAX-ACCESS  read-only
    STATUS  current
    DESCRIPTION
        "5th Log Point, Year minus 2000"
    ::= { regMap 2064 }


regLog5DateMonth OBJECT-TYPE
    SYNTAX  Integer32
    MAX-ACCESS  read-only
    STATUS  current
    DESCRIPTION
        "5th Log Point, Month"
    ::= { regMap 2065 }


regLog5DateDay OBJECT-TYPE
    SYNTAX  Integer32
    MAX-ACCESS  read-only
    STATUS  current
    DESCRIPTION
        "5th Log Point, Day"
    ::= { regMap 2066 }


regLog5DateHour OBJECT-TYPE
    SYNTAX  Integer32
    MAX-ACCESS  read-only
    STATUS  current
    DESCRIPTION
        "5th Log Point, Hour"
    ::= { regMap 2067 }


regLog5DateMinute OBJECT-TYPE
    SYNTAX  Integer32
    MAX-ACCESS  read-only
    STATUS  current
    DESCRIPTION
        "5th Log Point, Minute"
    ::= { regMap 2068 }


regLog5DateSecond OBJECT-TYPE
    SYNTAX  Integer32
    MAX-ACCESS  read-only
    STATUS  current
    DESCRIPTION
        "5th Log Point, Second"
    ::= { regMap 2069 }


regLog5BatteryVoltage OBJECT-TYPE
    SYNTAX  Integer32
    MAX-ACCESS  read-only
    STATUS  current
    DESCRIPTION
        "5th Log Point, Battery Voltage x 100"
    ::= { regMap 2070 }


regLog5Temperature OBJECT-TYPE
    SYNTAX  Integer32
    MAX-ACCESS  read-only
    STATUS  current
    DESCRIPTION
        "5th Log Point, Temperature degrees C x 10, signed"
    ::= { regMap 2071 }


regLog5Analog132V OBJECT-TYPE
    SYNTAX  Integer32
    MAX-ACCESS  read-only
    STATUS  current
    DESCRIPTION
        "5th Log Point, Analog 1, 0 - 32 V"
    ::= { regMap 2072 }


regLog5Analog15V OBJECT-TYPE
    SYNTAX  Integer32
    MAX-ACCESS  read-only
    STATUS  current
    DESCRIPTION
        "5th Log Point, Analog 1, 0 - 5 V"
    ::= { regMap 2073 }


regLog5Analog1420mA OBJECT-TYPE
    SYNTAX  Integer32
    MAX-ACCESS  read-only
    STATUS  current
    DESCRIPTION
        "5th Log Point, Analog 1, 4 - 20 mA"
    ::= { regMap 2074 }


regLog5Analog232V OBJECT-TYPE
    SYNTAX  Integer32
    MAX-ACCESS  read-only
    STATUS  current
    DESCRIPTION
        "5th Log Point, Analog 2, 0 - 32 V"
    ::= { regMap 2075 }


regLog5Analog25V OBJECT-TYPE
    SYNTAX  Integer32
    MAX-ACCESS  read-only
    STATUS  current
    DESCRIPTION
        "5th Log Point, Analog 2, 0 - 5 V"
    ::= { regMap 2076 }


regLog5Analog2420mA OBJECT-TYPE
    SYNTAX  Integer32
    MAX-ACCESS  read-only
    STATUS  current
    DESCRIPTION
        "5th Log Point, Analog 2, 4 - 20 mA"
    ::= { regMap 2077 }


regLog5Digital1 OBJECT-TYPE
    SYNTAX  Integer32
    MAX-ACCESS  read-only
    STATUS  current
    DESCRIPTION
        "5th Log Point, Digital 1"
    ::= { regMap 2078 }


regLog5Digital2 OBJECT-TYPE
    SYNTAX  Integer32
    MAX-ACCESS  read-only
    STATUS  current
    DESCRIPTION
        "5th Log Point, Digital 2"
    ::= { regMap 2079 }


regLog6DateYear OBJECT-TYPE
    SYNTAX  Integer32
    MAX-ACCESS  read-only
    STATUS  current
    DESCRIPTION
        "6th Log Point, Year minus 2000"
    ::= { regMap 2080 }


regLog6DateMonth OBJECT-TYPE
    SYNTAX  Integer32
    MAX-ACCESS  read-only
    STATUS  current
    DESCRIPTION
        "6th Log Point, Month"
    ::= { regMap 2081 }


regLog6DateDay OBJECT-TYPE
    SYNTAX  Integer32
    MAX-ACCESS  read-only
    STATUS  current
    DESCRIPTION
        "6th Log Point, Day"
    ::= { regMap 2082 }


regLog6DateHour OBJECT-TYPE
    SYNTAX  Integer32
    MAX-ACCESS  read-only
    STATUS  current
    DESCRIPTION
        "6th Log Point, Hour"
    ::= { regMap 2083 }


regLog6DateMinute OBJECT-TYPE
    SYNTAX  Integer32
    MAX-ACCESS  read-only
    STATUS  current
    DESCRIPTION
        "6th Log Point, Minute"
    ::= { regMap 2084 }


regLog6DateSecond OBJECT-TYPE
    SYNTAX  Integer32
    MAX-ACCESS  read-only
    STATUS  current
    DESCRIPTION
        "6th Log Point, Second"
    ::= { regMap 2085 }


regLog6BatteryVoltage OBJECT-TYPE
    SYNTAX  Integer32
    MAX-ACCESS  read-only
    STATUS  current
    DESCRIPTION
        "6th Log Point, Battery Voltage x 100"
    ::= { regMap 2086 }


regLog6Temperature OBJECT-TYPE
    SYNTAX  Integer32
    MAX-ACCESS  read-only
    STATUS  current
    DESCRIPTION
        "6th Log Point, Temperature degrees C x 10, signed"
    ::= { regMap 2087 }


regLog6Analog132V OBJECT-TYPE
    SYNTAX  Integer32
    MAX-ACCESS  read-only
    STATUS  current
    DESCRIPTION
        "6th Log Point, Analog 1, 0 - 32 V"
    ::= { regMap 2088 }


regLog6Analog15V OBJECT-TYPE
    SYNTAX  Integer32
    MAX-ACCESS  read-only
    STATUS  current
    DESCRIPTION
        "6th Log Point, Analog 1, 0 - 5 V"
    ::= { regMap 2089 }


regLog6Analog1420mA OBJECT-TYPE
    SYNTAX  Integer32
    MAX-ACCESS  read-only
    STATUS  current
    DESCRIPTION
        "6th Log Point, Analog 1, 4 - 20 mA"
    ::= { regMap 2090 }


regLog6Analog232V OBJECT-TYPE
    SYNTAX  Integer32
    MAX-ACCESS  read-only
    STATUS  current
    DESCRIPTION
        "6th Log Point, Analog 2, 0 - 32 V"
    ::= { regMap 2091 }


regLog6Analog25V OBJECT-TYPE
    SYNTAX  Integer32
    MAX-ACCESS  read-only
    STATUS  current
    DESCRIPTION
        "6th Log Point, Analog 2, 0 - 5 V"
    ::= { regMap 2092 }


regLog6Analog2420mA OBJECT-TYPE
    SYNTAX  Integer32
    MAX-ACCESS  read-only
    STATUS  current
    DESCRIPTION
        "6th Log Point, Analog 2, 4 - 20 mA"
    ::= { regMap 2093 }


regLog6Digital1 OBJECT-TYPE
    SYNTAX  Integer32
    MAX-ACCESS  read-only
    STATUS  current
    DESCRIPTION
        "6th Log Point, Digital 1"
    ::= { regMap 2094 }


regLog6Digital2 OBJECT-TYPE
    SYNTAX  Integer32
    MAX-ACCESS  read-only
    STATUS  current
    DESCRIPTION
        "6th Log Point, Digital 2"
    ::= { regMap 2095 }


regLog7DateYear OBJECT-TYPE
    SYNTAX  Integer32
    MAX-ACCESS  read-only
    STATUS  current
    DESCRIPTION
        "7th Log Point, Year minus 2000"
    ::= { regMap 2096 }


regLog7DateMonth OBJECT-TYPE
    SYNTAX  Integer32
    MAX-ACCESS  read-only
    STATUS  current
    DESCRIPTION
        "7th Log Point, Month"
    ::= { regMap 2097 }


regLog7DateDay OBJECT-TYPE
    SYNTAX  Integer32
    MAX-ACCESS  read-only
    STATUS  current
    DESCRIPTION
        "7th Log Point, Day"
    ::= { regMap 2098 }


regLog7DateHour OBJECT-TYPE
    SYNTAX  Integer32
    MAX-ACCESS  read-only
    STATUS  current
    DESCRIPTION
        "7th Log Point, Hour"
    ::= { regMap 2099 }


regLog7DateMinute OBJECT-TYPE
    SYNTAX  Integer32
    MAX-ACCESS  read-only
    STATUS  current
    DESCRIPTION
        "7th Log Point, Minute"
    ::= { regMap 2100 }


regLog7DateSecond OBJECT-TYPE
    SYNTAX  Integer32
    MAX-ACCESS  read-only
    STATUS  current
    DESCRIPTION
        "7th Log Point, Second"
    ::= { regMap 2101 }


regLog7BatteryVoltage OBJECT-TYPE
    SYNTAX  Integer32
    MAX-ACCESS  read-only
    STATUS  current
    DESCRIPTION
        "7th Log Point, Battery Voltage x 100"
    ::= { regMap 2102 }


regLog7Temperature OBJECT-TYPE
    SYNTAX  Integer32
    MAX-ACCESS  read-only
    STATUS  current
    DESCRIPTION
        "7th Log Point, Temperature degrees C x 10, signed"
    ::= { regMap 2103 }


regLog7Analog132V OBJECT-TYPE
    SYNTAX  Integer32
    MAX-ACCESS  read-only
    STATUS  current
    DESCRIPTION
        "7th Log Point, Analog 1, 0 - 32 V"
    ::= { regMap 2104 }


regLog7Analog15V OBJECT-TYPE
    SYNTAX  Integer32
    MAX-ACCESS  read-only
    STATUS  current
    DESCRIPTION
        "7th Log Point, Analog 1, 0 - 5 V"
    ::= { regMap 2105 }


regLog7Analog1420mA OBJECT-TYPE
    SYNTAX  Integer32
    MAX-ACCESS  read-only
    STATUS  current
    DESCRIPTION
        "7th Log Point, Analog 1, 4 - 20 mA"
    ::= { regMap 2106 }


regLog7Analog232V OBJECT-TYPE
    SYNTAX  Integer32
    MAX-ACCESS  read-only
    STATUS  current
    DESCRIPTION
        "7th Log Point, Analog 2, 0 - 32 V"
    ::= { regMap 2107 }


regLog7Analog25V OBJECT-TYPE
    SYNTAX  Integer32
    MAX-ACCESS  read-only
    STATUS  current
    DESCRIPTION
        "7th Log Point, Analog 2, 0 - 5 V"
    ::= { regMap 2108 }


regLog7Analog2420mA OBJECT-TYPE
    SYNTAX  Integer32
    MAX-ACCESS  read-only
    STATUS  current
    DESCRIPTION
        "7th Log Point, Analog 2, 4 - 20 mA"
    ::= { regMap 2109 }


regLog7Digital1 OBJECT-TYPE
    SYNTAX  Integer32
    MAX-ACCESS  read-only
    STATUS  current
    DESCRIPTION
        "7th Log Point, Digital 1"
    ::= { regMap 2110 }


regLog7Digital2 OBJECT-TYPE
    SYNTAX  Integer32
    MAX-ACCESS  read-only
    STATUS  current
    DESCRIPTION
        "7th Log Point, Digital 2"
    ::= { regMap 2111 }


regAdvance7Logs OBJECT-TYPE
    SYNTAX  Integer32
    MAX-ACCESS  read-only
    STATUS  current
    DESCRIPTION
        "Advance Log Register by 7 - If this is read, it will increment the
        current log pointer by 7."
    ::= { regMap 2112 }


regDecrement7Logs OBJECT-TYPE
    SYNTAX  Integer32
    MAX-ACCESS  read-write
    STATUS  current
    DESCRIPTION
        "Decrement Log Register by 7 - If this is written non-zero, it will
        move the log pointer back 7 points."
    ::= { regMap 2113 }


    
-- ******************************************************
--
-- TRAP DEFINITIONS (not actual readable values)
-- 
-- ******************************************************
trapContents        OBJECT IDENTIFIER ::= { trapMap 1 }

valueTrapItem   OBJECT-TYPE
    SYNTAX  ValueTrapItem
    MAX-ACCESS  accessible-for-notify
    STATUS      current
    DESCRIPTION
        "Trap Item structure."
    ::= { trapMap 2 }

ValueTrapItem   ::= SEQUENCE {
    valueControllerID       SnmpAdminString,
    valueTrapDesc           SnmpAdminString,
    valueCurrentValue       Integer32
    }


valueControllerID   OBJECT-TYPE
    SYNTAX  SnmpAdminString
    MAX-ACCESS  accessible-for-notify
    STATUS      current
    DESCRIPTION
        "Unit Name or ID sending the trap."
    ::= { trapContents 1 }


valueTrapDesc   OBJECT-TYPE
    SYNTAX  SnmpAdminString
    MAX-ACCESS  accessible-for-notify
    STATUS      current
    DESCRIPTION
        "Short description of trap item."
    ::= { trapContents 2 }


valueCurrentValue    OBJECT-TYPE
    SYNTAX  Integer32
    MAX-ACCESS  accessible-for-notify
    STATUS      current
    DESCRIPTION
        "Current value of the item."
    ::= { trapContents 3 }

-- ******************************************************
--
-- SNMP NOTIFICATIONS
-- 
-- ******************************************************

trapInputLevel      NOTIFICATION-TYPE
    OBJECTS {
        valueControllerID,
        valueTrapDesc,
        valueCurrentValue
    }
    STATUS      current
    DESCRIPTION
        "This trap is sent when an input with an associated value
        goes above or below a setpoint level if notifications are enabled 
        for the object."
    ::= { trapMap 1 }

trapSequenceInputLevel    NOTIFICATION-TYPE
    OBJECTS {
        valueTrapItem
    }
    STATUS      current
    DESCRIPTION
        "This trap is sent when an input with an associated value
        goes above or below a setpoint level if notifications are enabled 
        for the object. Same as trapInputLevel, but sent as a sequence."
    ::= { trapMap 2 }

END
