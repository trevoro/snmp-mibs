Nortel-MsCarrier-MscPassport-BaseSnmpMIB
DEFINITIONS ::= BEGIN



IMPORTS

      OBJECT-TYPE
   FROM RFC-1212

      IpAddress
   FROM RFC1155-SMI

      mscPassportMIBs
   FROM Nortel-MsCarrier-MscPassport-UsefulDefinitionsMIB

      TruthValue,
      DisplayString,
      StorageType,
      RowStatus,
      Status,
      Integer32,
      Unsigned32
   FROM Nortel-MsCarrier-MscPassport-StandardTextualConventionsMIB

      AsciiString,
      NonReplicated,
      HexString
   FROM Nortel-MsCarrier-MscPassport-TextualConventionsMIB

      mscVrIndex,
      mscVr
   FROM Nortel-MsCarrier-MscPassport-VirtualRouterMIB;




-- LAST-UPDATED   "9909010000Z"
-- ORGANIZATION   "Nortel Networks"
-- CONTACT-INFO   "
--         Nortel Carrier Data Network Management
--         
--         Postal:       P.O. Box 3511, Station C 
--                       Ottawa, Ontario 
--                       Canada  K1Y 4H7
--         
--         via the WEB:  http://www.nortelnetworks.com  
--                       select 'Contact Us' from the menu
--          
--         via phone:    1-800-4NORTEL"
-- DESCRIPTION
--    "The module describing the Nortel MsCarrier MscPassport
--     BaseSnmp Enterprise MIB."

baseSnmpMIB OBJECT IDENTIFIER ::= { mscPassportMIBs 36 }










-- Vr/Vr_String Snmp
-- This component contains all provisionable and operational data 
-- relating to the SNMP Management of a Virtual Router.

mscVrSnmp OBJECT IDENTIFIER ::= { mscVr 8 }



mscVrSnmpRowStatusTable OBJECT-TYPE
   SYNTAX     SEQUENCE OF MscVrSnmpRowStatusEntry
   ACCESS     not-accessible
   STATUS     mandatory
   DESCRIPTION
     "This entry controls the addition and deletion of 
      mscVrSnmp components."
::= { mscVrSnmp 1 }

mscVrSnmpRowStatusEntry OBJECT-TYPE
   SYNTAX     MscVrSnmpRowStatusEntry
   ACCESS     not-accessible
   STATUS     mandatory
   DESCRIPTION
     "A single entry in the table represents a single 
      mscVrSnmp component."
   INDEX {
      mscVrIndex,
      mscVrSnmpIndex }
::= { mscVrSnmpRowStatusTable 1 }

MscVrSnmpRowStatusEntry ::= SEQUENCE {
   mscVrSnmpRowStatus
      RowStatus,
   mscVrSnmpComponentName
      DisplayString,
   mscVrSnmpStorageType
      StorageType,
   mscVrSnmpIndex
      NonReplicated }

mscVrSnmpRowStatus OBJECT-TYPE
   SYNTAX     RowStatus 
   ACCESS     read-write
   STATUS     mandatory
   DESCRIPTION
     "This variable is used as the basis for SNMP naming of
      mscVrSnmp components.
      These components can be added and deleted."
::= { mscVrSnmpRowStatusEntry 1 }

mscVrSnmpComponentName OBJECT-TYPE
   SYNTAX     DisplayString 
   ACCESS     read-only
   STATUS     mandatory
   DESCRIPTION
     "This variable provides the component's string name for
      use with the ASCII Console Interface"
::= { mscVrSnmpRowStatusEntry 2 }

mscVrSnmpStorageType OBJECT-TYPE
   SYNTAX     StorageType 
   ACCESS     read-only
   STATUS     mandatory
   DESCRIPTION
     "This variable represents the storage type value for the
      mscVrSnmp tables."
::= { mscVrSnmpRowStatusEntry 4 }

mscVrSnmpIndex OBJECT-TYPE
   SYNTAX     NonReplicated 
   ACCESS     not-accessible
   STATUS     mandatory
   DESCRIPTION
     "This variable represents the index for the mscVrSnmp tables."
::= { mscVrSnmpRowStatusEntry 10 }

mscVrSnmpProvTable OBJECT-TYPE
   SYNTAX     SEQUENCE OF MscVrSnmpProvEntry
   ACCESS     not-accessible
   STATUS     mandatory
   DESCRIPTION
     "This group contains provisionable attributes defining the SNMP 
      management entity's capabilities, particularly in regards to 
      standardV1 and V2 traps."
::= { mscVrSnmp 20 }

mscVrSnmpProvEntry OBJECT-TYPE
   SYNTAX     MscVrSnmpProvEntry
   ACCESS     not-accessible
   STATUS     mandatory
   DESCRIPTION
     "An entry in the mscVrSnmpProvTable."
   INDEX {
      mscVrIndex,
      mscVrSnmpIndex }
::= { mscVrSnmpProvTable 1 }

MscVrSnmpProvEntry ::= SEQUENCE {
   mscVrSnmpV1EnableAuthenTraps
      Status,
   mscVrSnmpV2EnableAuthenTraps
      Status,
   mscVrSnmpAlarmsAsTraps
      Status,
   mscVrSnmpIpStack
      INTEGER,
   mscVrSnmpCidInEntTraps
      Status }

mscVrSnmpV1EnableAuthenTraps OBJECT-TYPE
   SYNTAX     Status 
   ACCESS     read-write
   STATUS     mandatory
   DESCRIPTION
     "This attribute controls whether the Snmp component will generate 
      V1 authentication failure traps or not. The attribute is derived from 
      rfc1213."
::= { mscVrSnmpProvEntry 1 }

mscVrSnmpV2EnableAuthenTraps OBJECT-TYPE
   SYNTAX     Status 
   ACCESS     read-write
   STATUS     mandatory
   DESCRIPTION
     "This attribute controls whether the Snmp component will generate 
      V2 authentication failure traps or not. The attribute is derived from 
      rfc1450."
::= { mscVrSnmpProvEntry 2 }

mscVrSnmpAlarmsAsTraps OBJECT-TYPE
   SYNTAX     Status 
   ACCESS     read-write
   STATUS     mandatory
   DESCRIPTION
     "This attribute controls whether the Snmp component will send 
      Alarms as SNMPv1 and SNMPv2 Traps. If enabled, Alarms will be 
      sent as SNMPv2 Traps to target Parties identified in 
      AccessPrivileges components where v2Trap privileges are allowed, 
      and as SNMPv1 Traps to Managers with v1Trap privileges 
      allowed."
::= { mscVrSnmpProvEntry 3 }

mscVrSnmpIpStack OBJECT-TYPE
   SYNTAX     INTEGER  {
                 vrIp(1),
                 ipiFrIpiVc(2) }
   ACCESS     read-write
   STATUS     mandatory
   DESCRIPTION
     "This attribute controls which IP stack the Snmp component will use 
      to send and receive Snmp traffic for Communites and Parties whose 
      tdomain attribute specifies snmpUdpDomain as the transport 
      protocol.
      If the value of this attribute is vrIp then Snmp Udp traffic will be 
      sent and received using Ip as provisioned under the VirtualRouter. 
      This requires provisioning of the ip feature.
      If the value of this attribute is ipiFrIpiVc then Snmp Udp traffic 
      will be sent and received using IpiFr (Ip over Frame Relay) or IpiVc 
      (Ip over Vc), whichever is provisioned. This requires provisioning 
      of one of the ipiVc or ipiFr features."
   DEFVAL     { vrIp }
::= { mscVrSnmpProvEntry 4 }

mscVrSnmpCidInEntTraps OBJECT-TYPE
   SYNTAX     Status 
   ACCESS     read-write
   STATUS     mandatory
   DESCRIPTION
     "This attribute controls whether the Customer Identifier (CID) will 
      be included in the SNMP Enterprise Traps. If enabled, the CID will 
      be included in the SNMP Enterprise traps."
::= { mscVrSnmpProvEntry 5 }

mscVrSnmpStateTable OBJECT-TYPE
   SYNTAX     SEQUENCE OF MscVrSnmpStateEntry
   ACCESS     not-accessible
   STATUS     mandatory
   DESCRIPTION
     "This group contains the three OSI State attributes and the six OSI 
      Status attributes. The descriptions generically indicate what each 
      attribute implies about the component. Note that not all the values 
      and state combinations described here are supported by every 
      component which uses this group. For component-specific 
      information and the valid state combinations, refer to NTP 241-
      7001-150, Passport Operations and Maintenance Guide."
::= { mscVrSnmp 21 }

mscVrSnmpStateEntry OBJECT-TYPE
   SYNTAX     MscVrSnmpStateEntry
   ACCESS     not-accessible
   STATUS     mandatory
   DESCRIPTION
     "An entry in the mscVrSnmpStateTable."
   INDEX {
      mscVrIndex,
      mscVrSnmpIndex }
::= { mscVrSnmpStateTable 1 }

MscVrSnmpStateEntry ::= SEQUENCE {
   mscVrSnmpAdminState
      INTEGER,
   mscVrSnmpOperationalState
      INTEGER,
   mscVrSnmpUsageState
      INTEGER,
   mscVrSnmpAvailabilityStatus
      OCTET STRING,
   mscVrSnmpProceduralStatus
      OCTET STRING,
   mscVrSnmpControlStatus
      OCTET STRING,
   mscVrSnmpAlarmStatus
      OCTET STRING,
   mscVrSnmpStandbyStatus
      INTEGER,
   mscVrSnmpUnknownStatus
      INTEGER }

mscVrSnmpAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component.
      
      The OSI Status attributes, if supported by the component, may 
      provide more details, qualifying the state of the component."
   DEFVAL     { unlocked }
::= { mscVrSnmpStateEntry 1 }

mscVrSnmpOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle.
      
      The OSI Status attributes, if supported by the component, may 
      provide more details, qualifying the state of the component."
   DEFVAL     { disabled }
::= { mscVrSnmpStateEntry 2 }

mscVrSnmpUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time.
      
      The OSI Status attributes, if supported by the component, may 
      provide more details, qualifying the state of the component."
   DEFVAL     { idle }
::= { mscVrSnmpStateEntry 3 }

mscVrSnmpAvailabilityStatus OBJECT-TYPE
   SYNTAX     OCTET STRING (SIZE (2))
   ACCESS     read-only
   STATUS     mandatory
   DESCRIPTION
     "If supported by the component, this attribute indicates the OSI 
      Availability status of the component. Note that, even though it is 
      defined as a multi-valued set, at most one value is shown to the user.
      
      When no values are in the set, this indicates that either the attribute 
      is not supported or that none of the status conditions described 
      below are present.
      
      The value inTest indicates that the resource is undergoing a test 
      procedure. If adminState is locked or shuttingDown, the normal 
      users are precluded from using the resource and controlStatus is 
      reservedForTest. Tests that do not exclude additional users can be 
      present in any operational or administrative state but the 
      reservedForTest condition should not be present.
      
      The value failed indicates that the component has an internal fault 
      that prevents it from operating. The operationalState is disabled.
      
      The value dependency indicates that the component cannot operate 
      because some other resource on which it depends is unavailable. 
      The operationalState is disabled.
      
      The value powerOff indicates the resource requires power to be 
      applied and it is not powered on. The operationalState is disabled.
      
      The value offLine indicates the resource requires a routine 
      operation (either manual, automatic, or both) to be performed to 
      place it on-line and make it available for use. The operationalState 
      is disabled.
      
      The value offDuty indicates the resource is inactive in accordance 
      with a predetermined time schedule. In the absence of other 
      disabling conditions, the operationalState is enabled or disabled.
      
      The value degraded indicates the service provided by the 
      component is degraded in some way, such as in speed or operating 
      capacity. However, the resource remains available for service. The 
      operationalState is enabled.
      
      The value notInstalled indicates the resource is not present. The 
      operationalState is disabled.
      
      The value logFull is not used.

      Description of bits:
      inTest(0)
      failed(1)
      powerOff(2)
      offLine(3)
      offDuty(4)
      dependency(5)
      degraded(6)
      notInstalled(7)
      logFull(8)"
::= { mscVrSnmpStateEntry 4 }

mscVrSnmpProceduralStatus OBJECT-TYPE
   SYNTAX     OCTET STRING (SIZE (1))
   ACCESS     read-only
   STATUS     mandatory
   DESCRIPTION
     "If supported by the component, this attribute indicates the OSI 
      Procedural status of the component. Note that, even though it is 
      defined as a multi-valued set, at most one value is shown to the user.
      
      When no values are in the set, this indicates that either the attribute 
      is not supported or that none of the status conditions described 
      below are present.
      
      The value initializationRequired indicates (for a resource which 
      doesn't initialize autonomously) that initialization is required before 
      it can perform its normal functions, and this procedure has not been 
      initiated. The operationalState is disabled.
      
      The value notInitialized indicates (for a resource which does 
      initialize autonomously) that initialization is required before it can 
      perform its normal functions, and this procedure has not been 
      initiated. The operationalState may be enabled or disabled.
      
      The value initializing indicates that initialization has been initiated 
      but is not yet complete. The operationalState may be enabled or 
      disabled.
      
      The value reporting indicates the resource has completed some 
      processing operation and is notifying the results. The 
      operationalState is enabled.
      
      The value terminating indicates the component is in a termination 
      phase. If the resource doesn't reinitialize autonomously, 
      operationalState is disabled; otherwise it is enabled or disabled.

      Description of bits:
      initializationRequired(0)
      notInitialized(1)
      initializing(2)
      reporting(3)
      terminating(4)"
::= { mscVrSnmpStateEntry 5 }

mscVrSnmpControlStatus OBJECT-TYPE
   SYNTAX     OCTET STRING (SIZE (1))
   ACCESS     read-only
   STATUS     mandatory
   DESCRIPTION
     "If supported by the component, this attribute indicates the OSI 
      Control status of the component. Note that, even though it is defined 
      as a multi-valued set, at most one value is shown to the user.
      
      When no values are in the set, this indicates that either the attribute 
      is not supported or that none of the status conditions described 
      below are present.
      
      The value subjectToTest indicates the resource is available but tests 
      may be conducted simultaneously at unpredictable times, which 
      may cause it to exhibit unusual characteristics.
      
      The value partOfServicesLocked indicates that part of the service is 
      restricted from users of a resource. The adminState is unlocked.
      
      The value reservedForTest indicates that the component is 
      administratively unavailable because it is undergoing a test 
      procedure. The adminState is locked.
      
      The value suspended indicates that the service has been 
      administratively suspended.

      Description of bits:
      subjectToTest(0)
      partOfServicesLocked(1)
      reservedForTest(2)
      suspended(3)"
::= { mscVrSnmpStateEntry 6 }

mscVrSnmpAlarmStatus OBJECT-TYPE
   SYNTAX     OCTET STRING (SIZE (1))
   ACCESS     read-only
   STATUS     mandatory
   DESCRIPTION
     "If supported by the component, this attribute indicates the OSI 
      Alarm status of the component. Note that, even though it is defined 
      as a multi-valued set, at most one value is shown to the user.
      
      When no values are in the set, this indicates that either the attribute 
      is not supported or that none of the status conditions described 
      below are present.
      
      The value underRepair indicates the component is currently being 
      repaired. The operationalState is enabled or disabled.
      
      The value critical indicates one or more critical alarms are 
      outstanding against the component. Other, less severe, alarms may 
      also be outstanding. The operationalState is enabled or disabled.
      
      The value major indicates one or more major alarms are 
      outstanding against the component. Other, less severe, alarms may 
      also be outstanding. The operationalState is enabled or disabled.
      
      The value minor indicates one or more minor alarms are 
      outstanding against the component. Other, less severe, alarms may 
      also be outstanding. The operationalState is enabled or disabled.
      
      The value alarmOutstanding generically indicates that an alarm of 
      some severity is outstanding against the component.

      Description of bits:
      underRepair(0)
      critical(1)
      major(2)
      minor(3)
      alarmOutstanding(4)"
::= { mscVrSnmpStateEntry 7 }

mscVrSnmpStandbyStatus OBJECT-TYPE
   SYNTAX     INTEGER  {
                 hotStandby(0),
                 coldStandby(1),
                 providingService(2),
                 notSet(15) }
   ACCESS     read-only
   STATUS     mandatory
   DESCRIPTION
     "If supported by the component, this attribute indicates the OSI 
      Standby status of the component.
      
      The value notSet indicates that either the attribute is not supported 
      or that none of the status conditions described below are present. 
      Note that this is a non-standard value, used because the original 
      specification indicated this attribute was set-valued and thus, did not 
      provide a value to indicate that none of the other three are 
      applicable.
      
      The value hotStandby indicates that the resource is not providing 
      service but will be immediately able to take over the role of the 
      resource to be backed up, without initialization activity, and 
      containing the same information as the resource to be backed up.
      
      The value coldStandby indicates the resource is a backup for 
      another resource but will not be immediately able to take over the 
      role of the backed up resource and will require some initialization 
      activity.
      
      The value providingService indicates that this component, as a 
      backup resource, is currently backing up another resource."
   DEFVAL     { notSet }
::= { mscVrSnmpStateEntry 8 }

mscVrSnmpUnknownStatus OBJECT-TYPE
   SYNTAX     INTEGER  {
                 false(0),
                 true(1) }
   ACCESS     read-only
   STATUS     mandatory
   DESCRIPTION
     "This attribute indicates the OSI Unknown status of the component.
      
      The value false indicates that all of the other OSI State and Status 
      attribute values can be considered accurate.
      
      The value true indicates that the actual state of the component is not 
      known for sure."
   DEFVAL     { false }
::= { mscVrSnmpStateEntry 9 }

mscVrSnmpStatsTable OBJECT-TYPE
   SYNTAX     SEQUENCE OF MscVrSnmpStatsEntry
   ACCESS     not-accessible
   STATUS     mandatory
   DESCRIPTION
     "This attribute group contains miscellaneous SNMP management 
      entity operational attributes. Statistics in the group are derived from 
      rfc 1450 and rfc 1213. Also included in the group are statistics due 
      to non-SNMP authorization errors, and non-SNMP statistics."
::= { mscVrSnmp 22 }

mscVrSnmpStatsEntry OBJECT-TYPE
   SYNTAX     MscVrSnmpStatsEntry
   ACCESS     not-accessible
   STATUS     mandatory
   DESCRIPTION
     "An entry in the mscVrSnmpStatsTable."
   INDEX {
      mscVrIndex,
      mscVrSnmpIndex }
::= { mscVrSnmpStatsTable 1 }

MscVrSnmpStatsEntry ::= SEQUENCE {
   mscVrSnmpLastOrChange
      Unsigned32,
   mscVrSnmpTrapsProcessed
      Unsigned32,
   mscVrSnmpTrapsDiscarded
      Unsigned32,
   mscVrSnmpLastAuthFailure
      Unsigned32,
   mscVrSnmpMgrOfLastAuthFailure
      IpAddress }

mscVrSnmpLastOrChange OBJECT-TYPE
   SYNTAX     Unsigned32 (0..4294967295)
   ACCESS     read-only
   STATUS     mandatory
   DESCRIPTION
     "This attribute indicates the value of sysUpTime (in 1/100's of a 
      second) at the time of the most recent change to a SNMPv2 Object 
      Resource entry. The attribute forms part of the SNMPv2 MIB Base 
      Object Resource Group found in rfc1450."
::= { mscVrSnmpStatsEntry 1 }

mscVrSnmpTrapsProcessed OBJECT-TYPE
   SYNTAX     Unsigned32 (0..4294967295)
   ACCESS     read-only
   STATUS     mandatory
   DESCRIPTION
     "This counter contains the cumulative number of Trap Indications 
      and Alarm Indications received from the DCS Collectors since the 
      processor last restarted. These Traps and Alarms are sent to 
      SNMPv1 Managers and SNMPv2 Parties which are configured to 
      receive Traps. This total includes the number discarded by the Snmp 
      component when it was locked or disabled."
   DEFVAL     { 0 }
::= { mscVrSnmpStatsEntry 2 }

mscVrSnmpTrapsDiscarded OBJECT-TYPE
   SYNTAX     Unsigned32 (0..4294967295)
   ACCESS     read-only
   STATUS     mandatory
   DESCRIPTION
     "This counter contains the cumulative number of Trap Indications 
      and Alarm Indications discarded since the processor last restarted. 
      They are discarded when the Snmp component is locked or 
      disabled."
   DEFVAL     { 0 }
::= { mscVrSnmpStatsEntry 3 }

mscVrSnmpLastAuthFailure OBJECT-TYPE
   SYNTAX     Unsigned32 (0..4294967295)
   ACCESS     read-only
   STATUS     mandatory
   DESCRIPTION
     "This attribute indicates the value of sysUpTime (in 1/100's of a 
      second) at the time the last authentication failure. This 
      attribute is a non-SNMP statistic."
   DEFVAL     { 0 }
::= { mscVrSnmpStatsEntry 4 }

mscVrSnmpMgrOfLastAuthFailure OBJECT-TYPE
   SYNTAX     IpAddress 
   ACCESS     read-only
   STATUS     mandatory
   DESCRIPTION
     "This attribute indicates the IP address of the manager station that 
      caused the last authentication failure. This attribute is a non-SNMP 
      statistic."
   DEFVAL     { '00000000'H }  -- "0.0.0.0"
::= { mscVrSnmpStatsEntry 5 }


-- VirtualRouter/string Snmp System
-- This component represents the SNMP System Group. The 
-- component attributes are derived from rfc1213.

mscVrSnmpSys OBJECT IDENTIFIER ::= { mscVrSnmp 2 }



mscVrSnmpSysRowStatusTable OBJECT-TYPE
   SYNTAX     SEQUENCE OF MscVrSnmpSysRowStatusEntry
   ACCESS     not-accessible
   STATUS     mandatory
   DESCRIPTION
     "This entry controls the addition and deletion of 
      mscVrSnmpSys components."
::= { mscVrSnmpSys 1 }

mscVrSnmpSysRowStatusEntry OBJECT-TYPE
   SYNTAX     MscVrSnmpSysRowStatusEntry
   ACCESS     not-accessible
   STATUS     mandatory
   DESCRIPTION
     "A single entry in the table represents a single 
      mscVrSnmpSys component."
   INDEX {
      mscVrIndex,
      mscVrSnmpIndex,
      mscVrSnmpSysIndex }
::= { mscVrSnmpSysRowStatusTable 1 }

MscVrSnmpSysRowStatusEntry ::= SEQUENCE {
   mscVrSnmpSysRowStatus
      RowStatus,
   mscVrSnmpSysComponentName
      DisplayString,
   mscVrSnmpSysStorageType
      StorageType,
   mscVrSnmpSysIndex
      NonReplicated }

mscVrSnmpSysRowStatus OBJECT-TYPE
   SYNTAX     RowStatus 
   ACCESS     read-only
   STATUS     mandatory
   DESCRIPTION
     "This variable is used as the basis for SNMP naming of
      mscVrSnmpSys components.
      These components cannot be added nor deleted."
::= { mscVrSnmpSysRowStatusEntry 1 }

mscVrSnmpSysComponentName OBJECT-TYPE
   SYNTAX     DisplayString 
   ACCESS     read-only
   STATUS     mandatory
   DESCRIPTION
     "This variable provides the component's string name for
      use with the ASCII Console Interface"
::= { mscVrSnmpSysRowStatusEntry 2 }

mscVrSnmpSysStorageType OBJECT-TYPE
   SYNTAX     StorageType 
   ACCESS     read-only
   STATUS     mandatory
   DESCRIPTION
     "This variable represents the storage type value for the
      mscVrSnmpSys tables."
::= { mscVrSnmpSysRowStatusEntry 4 }

mscVrSnmpSysIndex OBJECT-TYPE
   SYNTAX     NonReplicated 
   ACCESS     not-accessible
   STATUS     mandatory
   DESCRIPTION
     "This variable represents the index for the mscVrSnmpSys tables."
::= { mscVrSnmpSysRowStatusEntry 10 }

mscVrSnmpSysProvTable OBJECT-TYPE
   SYNTAX     SEQUENCE OF MscVrSnmpSysProvEntry
   ACCESS     not-accessible
   STATUS     mandatory
   DESCRIPTION
     "The group contains provisionable attributes relating to the SNMP 
      System Group. The attributes are derived from rfc1213."
::= { mscVrSnmpSys 10 }

mscVrSnmpSysProvEntry OBJECT-TYPE
   SYNTAX     MscVrSnmpSysProvEntry
   ACCESS     not-accessible
   STATUS     mandatory
   DESCRIPTION
     "An entry in the mscVrSnmpSysProvTable."
   INDEX {
      mscVrIndex,
      mscVrSnmpIndex,
      mscVrSnmpSysIndex }
::= { mscVrSnmpSysProvTable 1 }

MscVrSnmpSysProvEntry ::= SEQUENCE {
   mscVrSnmpSysContact
      AsciiString,
   mscVrSnmpSysName
      AsciiString,
   mscVrSnmpSysLocation
      AsciiString }

mscVrSnmpSysContact OBJECT-TYPE
   SYNTAX     AsciiString (SIZE (0..255))
   ACCESS     read-write
   STATUS     mandatory
   DESCRIPTION
     "This attribute identifies the contact person for this managed node, 
      together with information on how to contact this person."
::= { mscVrSnmpSysProvEntry 1 }

mscVrSnmpSysName OBJECT-TYPE
   SYNTAX     AsciiString (SIZE (0..255))
   ACCESS     read-write
   STATUS     mandatory
   DESCRIPTION
     "This attribute identifies the administratively assigned name for this 
      managed node. By convention, it is the node's fully qualified 
      domain name."
::= { mscVrSnmpSysProvEntry 2 }

mscVrSnmpSysLocation OBJECT-TYPE
   SYNTAX     AsciiString (SIZE (0..255))
   ACCESS     read-write
   STATUS     mandatory
   DESCRIPTION
     "This attribute identifies the physical location of this node. For 
      example, 'telephone closet, third floor'."
::= { mscVrSnmpSysProvEntry 3 }

mscVrSnmpSysOpTable OBJECT-TYPE
   SYNTAX     SEQUENCE OF MscVrSnmpSysOpEntry
   ACCESS     not-accessible
   STATUS     mandatory
   DESCRIPTION
     "The group contains operational attributes relating to the SNMP 
      System Group. The attributes are derived from rfc1213."
::= { mscVrSnmpSys 11 }

mscVrSnmpSysOpEntry OBJECT-TYPE
   SYNTAX     MscVrSnmpSysOpEntry
   ACCESS     not-accessible
   STATUS     mandatory
   DESCRIPTION
     "An entry in the mscVrSnmpSysOpTable."
   INDEX {
      mscVrIndex,
      mscVrSnmpIndex,
      mscVrSnmpSysIndex }
::= { mscVrSnmpSysOpTable 1 }

MscVrSnmpSysOpEntry ::= SEQUENCE {
   mscVrSnmpSysDescription
      AsciiString,
   mscVrSnmpSysObjectId
      OBJECT IDENTIFIER,
   mscVrSnmpSysUpTime
      Unsigned32,
   mscVrSnmpSysServices
      Unsigned32 }

mscVrSnmpSysDescription OBJECT-TYPE
   SYNTAX     AsciiString (SIZE (0..255))
   ACCESS     read-only
   STATUS     mandatory
   DESCRIPTION
     "This attribute presents a textual description of the entity. This value 
      should include the full name and version identification of the 
      system's hardware type, software operating-system, and networking 
      software."
::= { mscVrSnmpSysOpEntry 1 }

mscVrSnmpSysObjectId OBJECT-TYPE
   SYNTAX     OBJECT IDENTIFIER 
   ACCESS     read-only
   STATUS     mandatory
   DESCRIPTION
     "This attribute identifies the vendor's authoritative identification of 
      the network management subsystem contained in the entity. This 
      value is allocated within the Structure of Management Information 
      (SMI) enterprises subtree (1.3.6.1.4.1) and provides an easy and 
      unambiguous means for determining 'what kind of box' is being 
      managed."
::= { mscVrSnmpSysOpEntry 2 }

mscVrSnmpSysUpTime OBJECT-TYPE
   SYNTAX     Unsigned32 (0..4294967295)
   ACCESS     read-only
   STATUS     mandatory
   DESCRIPTION
     "This attribute represents the time (in hundredths of a second) since 
      the network management portion of the system was last re-
      initialized."
::= { mscVrSnmpSysOpEntry 3 }

mscVrSnmpSysServices OBJECT-TYPE
   SYNTAX     Unsigned32 (0..127)
   ACCESS     read-only
   STATUS     mandatory
   DESCRIPTION
     "This attribute indicates the set of services that this entity primarily 
      offers.
      The value is a sum. This sum initially takes the value zero, then, for 
      each layer, L, in the range 1 through 7, that this node performs 
      transactions for, 2 raised to (L-1) is added to the sum. For example, 
      a node which performs primarily routing functions would have a 
      value of 4 (2^(3-1)). In contrast, a node which is a host offering 
      application services would have a value of 72 ((2^4-1) + 2^(7-1)). 
      Note that in the context of the Internet suite of protocols, values 
      should be calculated accordingly:
      layer 1 - physical (for example, repeaters)
      layer 2 - datalink/subnetwork (for example, bridges)
      layer 3 - internet (for example, IP gateways)
      layer 4 - end-to-end (for example, IP hosts)
      layer 7 - applications (for example, mail relays)
      For systems including OSI protocols, layers 5 and 6 may also be 
      counted."
   DEFVAL     { 6 }
::= { mscVrSnmpSysOpEntry 4 }


-- VirtualRouter/string Snmp Community/n
-- This component represents an SNMPv1 Community. A community 
-- represents a pairing of an SNMP Agent with an arbitrary set of 
-- application entities. 
-- The combination of communityString and tDomain attributes must 
-- be unique across all Communies.

mscVrSnmpCom OBJECT IDENTIFIER ::= { mscVrSnmp 3 }



mscVrSnmpComRowStatusTable OBJECT-TYPE
   SYNTAX     SEQUENCE OF MscVrSnmpComRowStatusEntry
   ACCESS     not-accessible
   STATUS     mandatory
   DESCRIPTION
     "This entry controls the addition and deletion of 
      mscVrSnmpCom components."
::= { mscVrSnmpCom 1 }

mscVrSnmpComRowStatusEntry OBJECT-TYPE
   SYNTAX     MscVrSnmpComRowStatusEntry
   ACCESS     not-accessible
   STATUS     mandatory
   DESCRIPTION
     "A single entry in the table represents a single 
      mscVrSnmpCom component."
   INDEX {
      mscVrIndex,
      mscVrSnmpIndex,
      mscVrSnmpComIndex }
::= { mscVrSnmpComRowStatusTable 1 }

MscVrSnmpComRowStatusEntry ::= SEQUENCE {
   mscVrSnmpComRowStatus
      RowStatus,
   mscVrSnmpComComponentName
      DisplayString,
   mscVrSnmpComStorageType
      StorageType,
   mscVrSnmpComIndex
      Integer32 }

mscVrSnmpComRowStatus OBJECT-TYPE
   SYNTAX     RowStatus 
   ACCESS     read-write
   STATUS     mandatory
   DESCRIPTION
     "This variable is used as the basis for SNMP naming of
      mscVrSnmpCom components.
      These components can be added and deleted."
::= { mscVrSnmpComRowStatusEntry 1 }

mscVrSnmpComComponentName OBJECT-TYPE
   SYNTAX     DisplayString 
   ACCESS     read-only
   STATUS     mandatory
   DESCRIPTION
     "This variable provides the component's string name for
      use with the ASCII Console Interface"
::= { mscVrSnmpComRowStatusEntry 2 }

mscVrSnmpComStorageType OBJECT-TYPE
   SYNTAX     StorageType 
   ACCESS     read-only
   STATUS     mandatory
   DESCRIPTION
     "This variable represents the storage type value for the
      mscVrSnmpCom tables."
::= { mscVrSnmpComRowStatusEntry 4 }

mscVrSnmpComIndex OBJECT-TYPE
   SYNTAX     Integer32 (1..1024)
   ACCESS     not-accessible
   STATUS     mandatory
   DESCRIPTION
     "This variable represents the index for the mscVrSnmpCom tables."
::= { mscVrSnmpComRowStatusEntry 10 }

mscVrSnmpComProvTable OBJECT-TYPE
   SYNTAX     SEQUENCE OF MscVrSnmpComProvEntry
   ACCESS     not-accessible
   STATUS     mandatory
   DESCRIPTION
     "The group contains provisionable attributes relating to SNMPv1 
      Communities."
::= { mscVrSnmpCom 10 }

mscVrSnmpComProvEntry OBJECT-TYPE
   SYNTAX     MscVrSnmpComProvEntry
   ACCESS     not-accessible
   STATUS     mandatory
   DESCRIPTION
     "An entry in the mscVrSnmpComProvTable."
   INDEX {
      mscVrIndex,
      mscVrSnmpIndex,
      mscVrSnmpComIndex }
::= { mscVrSnmpComProvTable 1 }

MscVrSnmpComProvEntry ::= SEQUENCE {
   mscVrSnmpComCommunityString
      AsciiString,
   mscVrSnmpComAccessMode
      INTEGER,
   mscVrSnmpComViewIndex
      Unsigned32,
   mscVrSnmpComTDomain
      INTEGER }

mscVrSnmpComCommunityString OBJECT-TYPE
   SYNTAX     AsciiString (SIZE (1..255))
   ACCESS     read-write
   STATUS     mandatory
   DESCRIPTION
     "This attribute is the SNMPv1 Community name. The value of this 
      attribute is used to authenticate SNMP messages received from 
      SNMPv1 management entities, and is placed in SNMP messages 
      sent out by the SNMPv1 network management entity. The string 
      'public' is commonly used.
      When an SNMPv1 message is received, the community name in the 
      message is checked to ensure that it matches a Community string. If 
      there are no Manager subcomponents for that Community then the 
      level of access is determined by the accessMode attribute. If there 
      are Manager subcomponents for the Community then the 
      originating transport address in the message must match the 
      transportAddress of one of the Manager subcomponents, and the 
      level of access of the sending entity is determined by the privileges 
      attribute for that Manager.
      The combination of communityString and tDomain attributes must 
      be unique across all Communies."
   DEFVAL     { '7075626c6963'H }  -- "public"
::= { mscVrSnmpComProvEntry 1 }

mscVrSnmpComAccessMode OBJECT-TYPE
   SYNTAX     INTEGER  {
                 readOnly(1),
                 readWrite(2) }
   ACCESS     read-write
   STATUS     mandatory
   DESCRIPTION
     "Once the sending SNMP entity is authenticated as a member of a 
      community, the community access mode determines what level of 
      access it has for each object in its view."
   DEFVAL     { readOnly }
::= { mscVrSnmpComProvEntry 3 }

mscVrSnmpComViewIndex OBJECT-TYPE
   SYNTAX     Unsigned32 (1..1024)
   ACCESS     read-write
   STATUS     mandatory
   DESCRIPTION
     "The community view index selects an entry in the SnmpViewTable 
      that this community will use. This index must correspond to the first 
      index of one of the SnmpView entries. Note that SNMPv2 Views are 
      used for SNMPv1 communities, as the SNMPv2 View model is 
      sufficiently general to handle the SNMPv1 case."
::= { mscVrSnmpComProvEntry 4 }

mscVrSnmpComTDomain OBJECT-TYPE
   SYNTAX     INTEGER  {
                 snmpUdpDomain(1) }
   ACCESS     read-write
   STATUS     mandatory
   DESCRIPTION
     "This attribute indicates the kind of transport service by which the 
      community receives and sends network management traffic. 
      The combination of communityString and tDomain attributes must 
      be unique across all Communies"
   DEFVAL     { snmpUdpDomain }
::= { mscVrSnmpComProvEntry 5 }


-- VirtualRouter/string Snmp Community/n Manager/n
-- This component defines the access privileges for an SNMPv1 
-- Manager within the Community. If a Community has no Manager 
-- components, SNMPv1 messages are accepted from all source 
-- addresses using the proper communityString, and no Traps are sent 
-- out using the communityString. If at least one Manager component 
-- exists for a Community then SNMPv1 messages containing that 
-- Community string are only accepted if they originate from a 
-- transport address which matches the transportAddress of one of the 
-- Manager components.
-- The value of transportAddress must be unique for all Manager 
-- components under the same Community.

mscVrSnmpComMan OBJECT IDENTIFIER ::= { mscVrSnmpCom 2 }



mscVrSnmpComManRowStatusTable OBJECT-TYPE
   SYNTAX     SEQUENCE OF MscVrSnmpComManRowStatusEntry
   ACCESS     not-accessible
   STATUS     mandatory
   DESCRIPTION
     "This entry controls the addition and deletion of 
      mscVrSnmpComMan components."
::= { mscVrSnmpComMan 1 }

mscVrSnmpComManRowStatusEntry OBJECT-TYPE
   SYNTAX     MscVrSnmpComManRowStatusEntry
   ACCESS     not-accessible
   STATUS     mandatory
   DESCRIPTION
     "A single entry in the table represents a single 
      mscVrSnmpComMan component."
   INDEX {
      mscVrIndex,
      mscVrSnmpIndex,
      mscVrSnmpComIndex,
      mscVrSnmpComManIndex }
::= { mscVrSnmpComManRowStatusTable 1 }

MscVrSnmpComManRowStatusEntry ::= SEQUENCE {
   mscVrSnmpComManRowStatus
      RowStatus,
   mscVrSnmpComManComponentName
      DisplayString,
   mscVrSnmpComManStorageType
      StorageType,
   mscVrSnmpComManIndex
      Integer32 }

mscVrSnmpComManRowStatus OBJECT-TYPE
   SYNTAX     RowStatus 
   ACCESS     read-write
   STATUS     mandatory
   DESCRIPTION
     "This variable is used as the basis for SNMP naming of
      mscVrSnmpComMan components.
      These components can be added and deleted."
::= { mscVrSnmpComManRowStatusEntry 1 }

mscVrSnmpComManComponentName OBJECT-TYPE
   SYNTAX     DisplayString 
   ACCESS     read-only
   STATUS     mandatory
   DESCRIPTION
     "This variable provides the component's string name for
      use with the ASCII Console Interface"
::= { mscVrSnmpComManRowStatusEntry 2 }

mscVrSnmpComManStorageType OBJECT-TYPE
   SYNTAX     StorageType 
   ACCESS     read-only
   STATUS     mandatory
   DESCRIPTION
     "This variable represents the storage type value for the
      mscVrSnmpComMan tables."
::= { mscVrSnmpComManRowStatusEntry 4 }

mscVrSnmpComManIndex OBJECT-TYPE
   SYNTAX     Integer32 (0..100)
   ACCESS     not-accessible
   STATUS     mandatory
   DESCRIPTION
     "This variable represents the index for the mscVrSnmpComMan tables."
::= { mscVrSnmpComManRowStatusEntry 10 }

mscVrSnmpComManProvTable OBJECT-TYPE
   SYNTAX     SEQUENCE OF MscVrSnmpComManProvEntry
   ACCESS     not-accessible
   STATUS     mandatory
   DESCRIPTION
     "The group contains provisionable attributes relating to an SNMPv1 
      Community Manager."
::= { mscVrSnmpComMan 10 }

mscVrSnmpComManProvEntry OBJECT-TYPE
   SYNTAX     MscVrSnmpComManProvEntry
   ACCESS     not-accessible
   STATUS     mandatory
   DESCRIPTION
     "An entry in the mscVrSnmpComManProvTable."
   INDEX {
      mscVrIndex,
      mscVrSnmpIndex,
      mscVrSnmpComIndex,
      mscVrSnmpComManIndex }
::= { mscVrSnmpComManProvTable 1 }

MscVrSnmpComManProvEntry ::= SEQUENCE {
   mscVrSnmpComManTransportAddress
      AsciiString,
   mscVrSnmpComManPrivileges
      OCTET STRING }

mscVrSnmpComManTransportAddress OBJECT-TYPE
   SYNTAX     AsciiString (SIZE (1..100))
   ACCESS     read-write
   STATUS     mandatory
   DESCRIPTION
     "This attribute is the transport service address of SNMPv1 Manager, 
      formatted according to the value of SnmpV1Community tDomain. 
      The only currently supported format is that of a UDP Transport 
      Address. It must be of the form 'IpAddress-UDP Port', where UDP 
      Port = 162. For example, 23.45.67.89-162 is a suitable UDP 
      Transport Address. 
      The value of transportAddress must be unique for all Manager 
      components under the same Community."
::= { mscVrSnmpComManProvEntry 1 }

mscVrSnmpComManPrivileges OBJECT-TYPE
   SYNTAX     OCTET STRING (SIZE (1))
   ACCESS     read-write
   STATUS     mandatory
   DESCRIPTION
     "This attribute identifies the access privileges which govern what 
      management operations the SNMPv1 Manager may perform.
      v1trap operations are only allowed if the Community accessMode is 
      readOnly or readWrite.
      set operations are only allowed if the Community accessMode is 
      readWrite.
      get operations are only allowed if the Community accessMode is 
      readOnly or readWrite.

      Description of bits:
      sets(0)
      gets(1)
      v1trap(2)"
   DEFVAL     { '40'H }
::= { mscVrSnmpComManProvEntry 2 }


-- VirtualRouter/string Snmp AccessPrivileges/n,n,n
-- This component is used to add SNMPv2 Access Privilege Table 
-- Entries. The component attributes are derived from rfc1445, and 
-- rfc1447.
-- The target index identifies a SNMPv2 party which is the target of 
-- an access control policy. This index must correspond to the 
-- SnmpV2PartyEntry index of a provisioned SnmpV2Party.
-- The subject index identifies a SNMPv2 party which is the subject of 
-- an access control policy. This index must correspond to the 
-- SnmpV2PartyEntryProv index of one of the provisioned 
-- SnmpV2Party's.
-- If the party identified by target is local (SnmpV2PartyEntryProv 
-- local = true), then subject must identify a party that is non-local 
-- (SnmpV2PartyEntryProv local = false). If the party identified by 
-- target is non-local, then subject must indicate a local party.
-- The resources index identifies an SNMPv2 context in an access 
-- control policy. This index must correspond to the 
-- SnmpV2ContextEntryProv index of one of the provisioned 
-- SnmpV2Context's. 

mscVrSnmpAcl OBJECT IDENTIFIER ::= { mscVrSnmp 4 }



mscVrSnmpAclRowStatusTable OBJECT-TYPE
   SYNTAX     SEQUENCE OF MscVrSnmpAclRowStatusEntry
   ACCESS     not-accessible
   STATUS     obsolete
   DESCRIPTION
     "This entry controls the addition and deletion of 
      mscVrSnmpAcl components."
::= { mscVrSnmpAcl 1 }

mscVrSnmpAclRowStatusEntry OBJECT-TYPE
   SYNTAX     MscVrSnmpAclRowStatusEntry
   ACCESS     not-accessible
   STATUS     obsolete
   DESCRIPTION
     "A single entry in the table represents a single 
      mscVrSnmpAcl component."
   INDEX {
      mscVrIndex,
      mscVrSnmpIndex,
      mscVrSnmpAclTargetIndex,
      mscVrSnmpAclSubjectIndex,
      mscVrSnmpAclResourcesIndex }
::= { mscVrSnmpAclRowStatusTable 1 }

MscVrSnmpAclRowStatusEntry ::= SEQUENCE {
   mscVrSnmpAclRowStatus
      RowStatus,
   mscVrSnmpAclComponentName
      DisplayString,
   mscVrSnmpAclStorageType
      StorageType,
   mscVrSnmpAclTargetIndex
      Integer32,
   mscVrSnmpAclSubjectIndex
      Integer32,
   mscVrSnmpAclResourcesIndex
      Integer32 }

mscVrSnmpAclRowStatus OBJECT-TYPE
   SYNTAX     RowStatus 
   ACCESS     read-write
   STATUS     obsolete
   DESCRIPTION
     "This variable is used as the basis for SNMP naming of
      mscVrSnmpAcl components.
      These components can be added and deleted."
::= { mscVrSnmpAclRowStatusEntry 1 }

mscVrSnmpAclComponentName OBJECT-TYPE
   SYNTAX     DisplayString 
   ACCESS     read-only
   STATUS     obsolete
   DESCRIPTION
     "This variable provides the component's string name for
      use with the ASCII Console Interface"
::= { mscVrSnmpAclRowStatusEntry 2 }

mscVrSnmpAclStorageType OBJECT-TYPE
   SYNTAX     StorageType 
   ACCESS     read-only
   STATUS     obsolete
   DESCRIPTION
     "This variable represents the storage type value for the
      mscVrSnmpAcl tables."
::= { mscVrSnmpAclRowStatusEntry 4 }

mscVrSnmpAclTargetIndex OBJECT-TYPE
   SYNTAX     Integer32 (1..2048)
   ACCESS     not-accessible
   STATUS     obsolete
   DESCRIPTION
     "This variable represents an index for the mscVrSnmpAcl tables."
::= { mscVrSnmpAclRowStatusEntry 10 }

mscVrSnmpAclSubjectIndex OBJECT-TYPE
   SYNTAX     Integer32 (1..2048)
   ACCESS     not-accessible
   STATUS     obsolete
   DESCRIPTION
     "This variable represents an index for the mscVrSnmpAcl tables."
::= { mscVrSnmpAclRowStatusEntry 11 }

mscVrSnmpAclResourcesIndex OBJECT-TYPE
   SYNTAX     Integer32 (1..2048)
   ACCESS     not-accessible
   STATUS     obsolete
   DESCRIPTION
     "This variable represents an index for the mscVrSnmpAcl tables."
::= { mscVrSnmpAclRowStatusEntry 12 }

mscVrSnmpAclProvTable OBJECT-TYPE
   SYNTAX     SEQUENCE OF MscVrSnmpAclProvEntry
   ACCESS     not-accessible
   STATUS     obsolete
   DESCRIPTION
     "This group contains provisionable attributes relating to SNMPv2 
      Access Privilege Table Entries. The provisionable attributes are 
      derived from rfc1445, and rfc1447."
::= { mscVrSnmpAcl 10 }

mscVrSnmpAclProvEntry OBJECT-TYPE
   SYNTAX     MscVrSnmpAclProvEntry
   ACCESS     not-accessible
   STATUS     obsolete
   DESCRIPTION
     "An entry in the mscVrSnmpAclProvTable."
   INDEX {
      mscVrIndex,
      mscVrSnmpIndex,
      mscVrSnmpAclTargetIndex,
      mscVrSnmpAclSubjectIndex,
      mscVrSnmpAclResourcesIndex }
::= { mscVrSnmpAclProvTable 1 }

MscVrSnmpAclProvEntry ::= SEQUENCE {
   mscVrSnmpAclPrivileges
      OCTET STRING,
   mscVrSnmpAclRowStorageType
      INTEGER,
   mscVrSnmpAclStdRowStatus
      INTEGER }

mscVrSnmpAclPrivileges OBJECT-TYPE
   SYNTAX     OCTET STRING (SIZE (1))
   ACCESS     read-write
   STATUS     obsolete
   DESCRIPTION
     "This attribute identifies the access privileges which govern what 
      management operations a particular target part may perform with 
      respect to a particular SNMPv2 context when requested by a 
      particular subject party. Gets and set operations are only permitted 
      if the target Party is local (SnmpV2PartyEntryProv local = true). 
      Response and v2trap operations are only permitted if the target 
      Party is non-local (SnmpV2PartyEntryProv local = false).

      Description of bits:
      response(0)
      set(1)
      gets(2)
      v2trap(3)"
   DEFVAL     { '60'H }
::= { mscVrSnmpAclProvEntry 1 }

mscVrSnmpAclRowStorageType OBJECT-TYPE
   SYNTAX     INTEGER  {
                 nonVolatile(3) }
   ACCESS     read-write
   STATUS     obsolete
   DESCRIPTION
     "This attribute indicates the storage type for this conceptual row in 
      the SNMPv2 aclTable. This is a constant - nonVolatile."
   DEFVAL     { nonVolatile }
::= { mscVrSnmpAclProvEntry 2 }

mscVrSnmpAclStdRowStatus OBJECT-TYPE
   SYNTAX     INTEGER  {
                 active(1) }
   ACCESS     read-write
   STATUS     obsolete
   DESCRIPTION
     "This attribute indicates the status of this conceptual row in the 
      SNMPv2 aclTable. This is a constant - active."
   DEFVAL     { active }
::= { mscVrSnmpAclProvEntry 3 }


-- VirtualRouter/string Snmp Party/Int_Sequence
-- This component is used to add SNMPv2 Party Table Entries. The 
-- maximum number of Table Entries is 1024. The component 
-- attributes are derived from rfc1321, rfc1445, rfc1446, rfc1447, 
-- rfc1449, and rfc1450.

mscVrSnmpParty OBJECT IDENTIFIER ::= { mscVrSnmp 5 }



mscVrSnmpPartyRowStatusTable OBJECT-TYPE
   SYNTAX     SEQUENCE OF MscVrSnmpPartyRowStatusEntry
   ACCESS     not-accessible
   STATUS     obsolete
   DESCRIPTION
     "This entry controls the addition and deletion of 
      mscVrSnmpParty components."
::= { mscVrSnmpParty 1 }

mscVrSnmpPartyRowStatusEntry OBJECT-TYPE
   SYNTAX     MscVrSnmpPartyRowStatusEntry
   ACCESS     not-accessible
   STATUS     obsolete
   DESCRIPTION
     "A single entry in the table represents a single 
      mscVrSnmpParty component."
   INDEX {
      mscVrIndex,
      mscVrSnmpIndex,
      mscVrSnmpPartyIdentityIndex }
::= { mscVrSnmpPartyRowStatusTable 1 }

MscVrSnmpPartyRowStatusEntry ::= SEQUENCE {
   mscVrSnmpPartyRowStatus
      RowStatus,
   mscVrSnmpPartyComponentName
      DisplayString,
   mscVrSnmpPartyStorageType
      StorageType,
   mscVrSnmpPartyIdentityIndex
      OBJECT IDENTIFIER }

mscVrSnmpPartyRowStatus OBJECT-TYPE
   SYNTAX     RowStatus 
   ACCESS     read-write
   STATUS     obsolete
   DESCRIPTION
     "This variable is used as the basis for SNMP naming of
      mscVrSnmpParty components.
      These components can be added and deleted."
::= { mscVrSnmpPartyRowStatusEntry 1 }

mscVrSnmpPartyComponentName OBJECT-TYPE
   SYNTAX     DisplayString 
   ACCESS     read-only
   STATUS     obsolete
   DESCRIPTION
     "This variable provides the component's string name for
      use with the ASCII Console Interface"
::= { mscVrSnmpPartyRowStatusEntry 2 }

mscVrSnmpPartyStorageType OBJECT-TYPE
   SYNTAX     StorageType 
   ACCESS     read-only
   STATUS     obsolete
   DESCRIPTION
     "This variable represents the storage type value for the
      mscVrSnmpParty tables."
::= { mscVrSnmpPartyRowStatusEntry 4 }

mscVrSnmpPartyIdentityIndex OBJECT-TYPE
   SYNTAX     OBJECT IDENTIFIER 
   ACCESS     not-accessible
   STATUS     obsolete
   DESCRIPTION
     "This variable represents the index for the mscVrSnmpParty tables."
::= { mscVrSnmpPartyRowStatusEntry 10 }

mscVrSnmpPartyProvTable OBJECT-TYPE
   SYNTAX     SEQUENCE OF MscVrSnmpPartyProvEntry
   ACCESS     not-accessible
   STATUS     obsolete
   DESCRIPTION
     "This group contains provisionable attributes relating to SNMPv2 
      Party Table Entries.The attributes are derived from rfc1321, 
      rfc1445, rfc1446, rfc1447, and rfc1450."
::= { mscVrSnmpParty 10 }

mscVrSnmpPartyProvEntry OBJECT-TYPE
   SYNTAX     MscVrSnmpPartyProvEntry
   ACCESS     not-accessible
   STATUS     obsolete
   DESCRIPTION
     "An entry in the mscVrSnmpPartyProvTable."
   INDEX {
      mscVrIndex,
      mscVrSnmpIndex,
      mscVrSnmpPartyIdentityIndex }
::= { mscVrSnmpPartyProvTable 1 }

MscVrSnmpPartyProvEntry ::= SEQUENCE {
   mscVrSnmpPartyStdIndex
      Unsigned32,
   mscVrSnmpPartyTDomain
      INTEGER,
   mscVrSnmpPartyTransportAddress
      AsciiString,
   mscVrSnmpPartyMaxMessageSize
      Unsigned32,
   mscVrSnmpPartyLocal
      TruthValue,
   mscVrSnmpPartyAuthProtocol
      INTEGER,
   mscVrSnmpPartyAuthPrivate
      HexString,
   mscVrSnmpPartyAuthPublic
      HexString,
   mscVrSnmpPartyAuthLifetime
      Unsigned32,
   mscVrSnmpPartyPrivProtocol
      INTEGER,
   mscVrSnmpPartyRowStorageType
      INTEGER,
   mscVrSnmpPartyStdRowStatus
      INTEGER }

mscVrSnmpPartyStdIndex OBJECT-TYPE
   SYNTAX     Unsigned32 (1..2048)
   ACCESS     read-only
   STATUS     obsolete
   DESCRIPTION
     "This attribute represents the SNMPv2 Party table partyIndex. This 
      index is unique and its value is automatically selected for you."
::= { mscVrSnmpPartyProvEntry 1 }

mscVrSnmpPartyTDomain OBJECT-TYPE
   SYNTAX     INTEGER  {
                 snmpUdpDomain(1) }
   ACCESS     read-write
   STATUS     obsolete
   DESCRIPTION
     "This attribute indicates the kind of transport service by which the 
      party receives and sends network management traffic."
   DEFVAL     { snmpUdpDomain }
::= { mscVrSnmpPartyProvEntry 2 }

mscVrSnmpPartyTransportAddress OBJECT-TYPE
   SYNTAX     AsciiString (SIZE (1..100))
   ACCESS     read-write
   STATUS     obsolete
   DESCRIPTION
     "This attribute is the transport service address by which the party 
      receives network management traffic, formatted according to the 
      corresponding value of tDomain. 
      For local (Agent) Parties (SnmpV2PartyEntryProv local = true) this 
      is the address of the Virtual Router. 
      For non-local (Manager) Parties (SnmpV2PartyEntryProv local = 
      false) this is the address of the SNMP Manager.
      The only currently supported format is that of a UDP Transport 
      Address. It must be of the form 'IpAddress-UDP Port', where UDP 
      Port = 161 for a local Party and UDP Port = 162 for a non-local 
      Party. For example, 23.45.67.89-161 or 23.45.67.89-162 are suitable 
      UDP Transport Addresses."
::= { mscVrSnmpPartyProvEntry 3 }

mscVrSnmpPartyMaxMessageSize OBJECT-TYPE
   SYNTAX     Unsigned32 (484..65507)
   ACCESS     read-write
   STATUS     obsolete
   DESCRIPTION
     "This attribute is the maximum length in octets of a SNMPv2 
      message that this party will accept. For local (Agent) Parties 
      (SnmpV2PartyEntryProv local = true) this cannot be set to greater 
      than the fixed Agent maximum of 1400. For non-local (Manager) 
      Parties (SnmpV2PartyEntryProv local = false) the maximum is 
      65507."
   DEFVAL     { 1400 }
::= { mscVrSnmpPartyProvEntry 4 }

mscVrSnmpPartyLocal OBJECT-TYPE
   SYNTAX     TruthValue 
   ACCESS     read-write
   STATUS     obsolete
   DESCRIPTION
     "This attribute indicates whether this party executes at this SNMPv2 
      entity. If this attribute has a value of true, then the SNMPv2 entity 
      is an Agent, and will listen for SNMPv2 messages on the ipAddress 
      associated with this party. If this attribute has the value false, then 
      the SNMPv2 entity is a Manager."
::= { mscVrSnmpPartyProvEntry 5 }

mscVrSnmpPartyAuthProtocol OBJECT-TYPE
   SYNTAX     INTEGER  {
                 noAuth(1),
                 v2Md5AuthProtocol(4) }
   ACCESS     read-write
   STATUS     obsolete
   DESCRIPTION
     "This attribute indicates the authentication protocol by which all 
      messages generated by the party are authenticated as to origin and 
      integrity. The value noAuth signifies that messages generated by the 
      party are not authenticated."
   DEFVAL     { noAuth }
::= { mscVrSnmpPartyProvEntry 6 }

mscVrSnmpPartyAuthPrivate OBJECT-TYPE
   SYNTAX     HexString (SIZE (0..16))
   ACCESS     write-only
   STATUS     obsolete
   DESCRIPTION
     "This attribute is the Party's private authentication key. As with 
      passwords this attribute cannot be displayed by the display 
      command and is stored in encoded form. For Parties with an 
      authentication protocol, this key must be provisioned."
   DEFVAL     { ''H }  -- ""
::= { mscVrSnmpPartyProvEntry 7 }

mscVrSnmpPartyAuthPublic OBJECT-TYPE
   SYNTAX     HexString (SIZE (0..16))
   ACCESS     read-write
   STATUS     obsolete
   DESCRIPTION
     "This attribute is the Party's public authentication key. It is the 
      'public information' used by the Party's authentication protocol."
   DEFVAL     { ''H }  -- ""
::= { mscVrSnmpPartyProvEntry 8 }

mscVrSnmpPartyAuthLifetime OBJECT-TYPE
   SYNTAX     Unsigned32 (0..2147483647)
   ACCESS     read-write
   STATUS     obsolete
   DESCRIPTION
     "This attribute represents the maximum acceptable delivery delay 
      (lifetime) in seconds for messages from this Party."
   DEFVAL     { 300 }
::= { mscVrSnmpPartyProvEntry 9 }

mscVrSnmpPartyPrivProtocol OBJECT-TYPE
   SYNTAX     INTEGER  {
                 noPriv(2) }
   ACCESS     read-write
   STATUS     obsolete
   DESCRIPTION
     "This attribute identifies the privacy protocol by which all protocol 
      messages received by the party are protected from disclosure. The 
      value noPriv signifies that messages received by the party are not 
      protected. As DES is not supported, this is a constant noPriv."
   DEFVAL     { noPriv }
::= { mscVrSnmpPartyProvEntry 10 }

mscVrSnmpPartyRowStorageType OBJECT-TYPE
   SYNTAX     INTEGER  {
                 nonVolatile(3) }
   ACCESS     read-write
   STATUS     obsolete
   DESCRIPTION
     "The attribute indicates the storage type for this conceptual row in 
      the SNMPv2 aclTable. This is a constant - nonVolatile."
   DEFVAL     { nonVolatile }
::= { mscVrSnmpPartyProvEntry 11 }

mscVrSnmpPartyStdRowStatus OBJECT-TYPE
   SYNTAX     INTEGER  {
                 active(1) }
   ACCESS     read-write
   STATUS     obsolete
   DESCRIPTION
     "This attribute indicates the status of this conceptual row in the 
      SNMPv2 partyTable. This is a constant - active."
   DEFVAL     { active }
::= { mscVrSnmpPartyProvEntry 12 }

mscVrSnmpPartyOpTable OBJECT-TYPE
   SYNTAX     SEQUENCE OF MscVrSnmpPartyOpEntry
   ACCESS     not-accessible
   STATUS     obsolete
   DESCRIPTION
     "This group contains Operational Attributes relating SNMPv2 
      parties. based upon rfc1321, rfc1445, rfc1446, rfc1447, and 
      rfc1450."
::= { mscVrSnmpParty 11 }

mscVrSnmpPartyOpEntry OBJECT-TYPE
   SYNTAX     MscVrSnmpPartyOpEntry
   ACCESS     not-accessible
   STATUS     obsolete
   DESCRIPTION
     "An entry in the mscVrSnmpPartyOpTable."
   INDEX {
      mscVrIndex,
      mscVrSnmpIndex,
      mscVrSnmpPartyIdentityIndex }
::= { mscVrSnmpPartyOpTable 1 }

MscVrSnmpPartyOpEntry ::= SEQUENCE {
   mscVrSnmpPartyTrapNumbers
      Unsigned32,
   mscVrSnmpPartyAuthClock
      Unsigned32 }

mscVrSnmpPartyTrapNumbers OBJECT-TYPE
   SYNTAX     Unsigned32 (0..4294967295)
   ACCESS     read-only
   STATUS     obsolete
   DESCRIPTION
     "This attribute is a count of the total number of SNMPv2 traps sent 
      to a SNMPv2 non-Local (Manager) party (SnmpV2PartyEntryProv 
      local = false). This counter is never incremented for Local (Agent) 
      parties (SnmpV2PartyEntryProv local = true)."
   DEFVAL     { 0 }
::= { mscVrSnmpPartyOpEntry 1 }

mscVrSnmpPartyAuthClock OBJECT-TYPE
   SYNTAX     Unsigned32 (0..4294967295)
   ACCESS     read-write
   STATUS     obsolete
   DESCRIPTION
     "This attribute is the authentication clock which represents the notion 
      of current time specific to a Party. This value is not permitted to 
      'roll-over'. In other words once it reaches the maximum it stays 
      there, unless explicitly decremented."
   DEFVAL     { 0 }
::= { mscVrSnmpPartyOpEntry 2 }


-- VirtualRouter/string Snmp Context/Int_Sequence
-- This component is used to add SNMPv2 Context Table Entries. The 
-- maximum number of Table Entries is 1024. The component 
-- attributes are derived from rfc1445, and rfc1447. 

mscVrSnmpCon OBJECT IDENTIFIER ::= { mscVrSnmp 6 }



mscVrSnmpConRowStatusTable OBJECT-TYPE
   SYNTAX     SEQUENCE OF MscVrSnmpConRowStatusEntry
   ACCESS     not-accessible
   STATUS     obsolete
   DESCRIPTION
     "This entry controls the addition and deletion of 
      mscVrSnmpCon components."
::= { mscVrSnmpCon 1 }

mscVrSnmpConRowStatusEntry OBJECT-TYPE
   SYNTAX     MscVrSnmpConRowStatusEntry
   ACCESS     not-accessible
   STATUS     obsolete
   DESCRIPTION
     "A single entry in the table represents a single 
      mscVrSnmpCon component."
   INDEX {
      mscVrIndex,
      mscVrSnmpIndex,
      mscVrSnmpConIdentityIndex }
::= { mscVrSnmpConRowStatusTable 1 }

MscVrSnmpConRowStatusEntry ::= SEQUENCE {
   mscVrSnmpConRowStatus
      RowStatus,
   mscVrSnmpConComponentName
      DisplayString,
   mscVrSnmpConStorageType
      StorageType,
   mscVrSnmpConIdentityIndex
      OBJECT IDENTIFIER }

mscVrSnmpConRowStatus OBJECT-TYPE
   SYNTAX     RowStatus 
   ACCESS     read-write
   STATUS     obsolete
   DESCRIPTION
     "This variable is used as the basis for SNMP naming of
      mscVrSnmpCon components.
      These components can be added and deleted."
::= { mscVrSnmpConRowStatusEntry 1 }

mscVrSnmpConComponentName OBJECT-TYPE
   SYNTAX     DisplayString 
   ACCESS     read-only
   STATUS     obsolete
   DESCRIPTION
     "This variable provides the component's string name for
      use with the ASCII Console Interface"
::= { mscVrSnmpConRowStatusEntry 2 }

mscVrSnmpConStorageType OBJECT-TYPE
   SYNTAX     StorageType 
   ACCESS     read-only
   STATUS     obsolete
   DESCRIPTION
     "This variable represents the storage type value for the
      mscVrSnmpCon tables."
::= { mscVrSnmpConRowStatusEntry 4 }

mscVrSnmpConIdentityIndex OBJECT-TYPE
   SYNTAX     OBJECT IDENTIFIER 
   ACCESS     not-accessible
   STATUS     obsolete
   DESCRIPTION
     "This variable represents the index for the mscVrSnmpCon tables."
::= { mscVrSnmpConRowStatusEntry 10 }

mscVrSnmpConProvTable OBJECT-TYPE
   SYNTAX     SEQUENCE OF MscVrSnmpConProvEntry
   ACCESS     not-accessible
   STATUS     obsolete
   DESCRIPTION
     "This group contains provisionable attributes relating to SNMPv2 
      Contexts Table Entries. The attributes are derived from rfc1445, and 
      rfc1447."
::= { mscVrSnmpCon 10 }

mscVrSnmpConProvEntry OBJECT-TYPE
   SYNTAX     MscVrSnmpConProvEntry
   ACCESS     not-accessible
   STATUS     obsolete
   DESCRIPTION
     "An entry in the mscVrSnmpConProvTable."
   INDEX {
      mscVrIndex,
      mscVrSnmpIndex,
      mscVrSnmpConIdentityIndex }
::= { mscVrSnmpConProvTable 1 }

MscVrSnmpConProvEntry ::= SEQUENCE {
   mscVrSnmpConStdIndex
      Unsigned32,
   mscVrSnmpConLocal
      INTEGER,
   mscVrSnmpConViewIndex
      Unsigned32,
   mscVrSnmpConLocalTime
      INTEGER,
   mscVrSnmpConRowStorageType
      INTEGER,
   mscVrSnmpConStdRowStatus
      INTEGER }

mscVrSnmpConStdIndex OBJECT-TYPE
   SYNTAX     Unsigned32 (1..1024)
   ACCESS     read-only
   STATUS     obsolete
   DESCRIPTION
     "This attribute represents the SNMPv2 Contexts table contextIndex. 
      This index is unique and its value is automatically selected for you."
::= { mscVrSnmpConProvEntry 1 }

mscVrSnmpConLocal OBJECT-TYPE
   SYNTAX     INTEGER  {
                 true(1) }
   ACCESS     read-write
   STATUS     obsolete
   DESCRIPTION
     "This attribute indicates whether this context is realized by this 
      SNMPv2 entity. This is a constant - true."
   DEFVAL     { true }
::= { mscVrSnmpConProvEntry 2 }

mscVrSnmpConViewIndex OBJECT-TYPE
   SYNTAX     Unsigned32 (1..1024)
   ACCESS     read-write
   STATUS     obsolete
   DESCRIPTION
     "The SNMPv2 Contexts view index selects a particular MIB view 
      entry in the SNMPv2 viewTable. This index must correspond to the 
      first replication index (index) of one of the entries in the SnmpView. 
      The value of the localTime attribute provides further information on 
      the temporal domain of the MIB view."
::= { mscVrSnmpConProvEntry 3 }

mscVrSnmpConLocalTime OBJECT-TYPE
   SYNTAX     INTEGER  {
                 currentTime(1) }
   ACCESS     read-write
   STATUS     obsolete
   DESCRIPTION
     "This attribute identifies the temporal context of the management 
      information in the MIB view identified by the viewIndex attribute. 
      This is a constant - currentTime. The SNMPv2 alternatives 
      restartTime and cacheTime are not currently supported."
   DEFVAL     { currentTime }
::= { mscVrSnmpConProvEntry 4 }

mscVrSnmpConRowStorageType OBJECT-TYPE
   SYNTAX     INTEGER  {
                 nonVolatile(3) }
   ACCESS     read-write
   STATUS     obsolete
   DESCRIPTION
     "The attribute indicates the storage type for this conceptual row in 
      the SNMPv2 contextTable. This is a constant - nonVolatile."
   DEFVAL     { nonVolatile }
::= { mscVrSnmpConProvEntry 5 }

mscVrSnmpConStdRowStatus OBJECT-TYPE
   SYNTAX     INTEGER  {
                 active(1) }
   ACCESS     read-write
   STATUS     obsolete
   DESCRIPTION
     "This attribute indicates the status of this conceptual row in the 
      SNMPv2 aclTable. This is a constant - active."
   DEFVAL     { active }
::= { mscVrSnmpConProvEntry 6 }


-- VirtualRouter/string Snmp View/n,Int_Sequence
-- This component is used to add SNMPv2 View Table Entries. These 
-- Views can also used by SNMPv1 Communities. The index index 
-- represents the SNMPv2 Table Entry viewIndex and the subTree 
-- index identifies a MIB subTree.The component attributes are 
-- derived from rfc1445, and rfc1447. 

mscVrSnmpView OBJECT IDENTIFIER ::= { mscVrSnmp 7 }



mscVrSnmpViewRowStatusTable OBJECT-TYPE
   SYNTAX     SEQUENCE OF MscVrSnmpViewRowStatusEntry
   ACCESS     not-accessible
   STATUS     mandatory
   DESCRIPTION
     "This entry controls the addition and deletion of 
      mscVrSnmpView components."
::= { mscVrSnmpView 1 }

mscVrSnmpViewRowStatusEntry OBJECT-TYPE
   SYNTAX     MscVrSnmpViewRowStatusEntry
   ACCESS     not-accessible
   STATUS     mandatory
   DESCRIPTION
     "A single entry in the table represents a single 
      mscVrSnmpView component."
   INDEX {
      mscVrIndex,
      mscVrSnmpIndex,
      mscVrSnmpViewIndex,
      mscVrSnmpViewSubtreeIndex }
::= { mscVrSnmpViewRowStatusTable 1 }

MscVrSnmpViewRowStatusEntry ::= SEQUENCE {
   mscVrSnmpViewRowStatus
      RowStatus,
   mscVrSnmpViewComponentName
      DisplayString,
   mscVrSnmpViewStorageType
      StorageType,
   mscVrSnmpViewIndex
      Integer32,
   mscVrSnmpViewSubtreeIndex
      OBJECT IDENTIFIER }

mscVrSnmpViewRowStatus OBJECT-TYPE
   SYNTAX     RowStatus 
   ACCESS     read-write
   STATUS     mandatory
   DESCRIPTION
     "This variable is used as the basis for SNMP naming of
      mscVrSnmpView components.
      These components can be added and deleted."
::= { mscVrSnmpViewRowStatusEntry 1 }

mscVrSnmpViewComponentName OBJECT-TYPE
   SYNTAX     DisplayString 
   ACCESS     read-only
   STATUS     mandatory
   DESCRIPTION
     "This variable provides the component's string name for
      use with the ASCII Console Interface"
::= { mscVrSnmpViewRowStatusEntry 2 }

mscVrSnmpViewStorageType OBJECT-TYPE
   SYNTAX     StorageType 
   ACCESS     read-only
   STATUS     mandatory
   DESCRIPTION
     "This variable represents the storage type value for the
      mscVrSnmpView tables."
::= { mscVrSnmpViewRowStatusEntry 4 }

mscVrSnmpViewIndex OBJECT-TYPE
   SYNTAX     Integer32 (1..1024)
   ACCESS     not-accessible
   STATUS     mandatory
   DESCRIPTION
     "This variable represents an index for the mscVrSnmpView tables."
::= { mscVrSnmpViewRowStatusEntry 10 }

mscVrSnmpViewSubtreeIndex OBJECT-TYPE
   SYNTAX     OBJECT IDENTIFIER 
   ACCESS     not-accessible
   STATUS     mandatory
   DESCRIPTION
     "This variable represents an index for the mscVrSnmpView tables."
::= { mscVrSnmpViewRowStatusEntry 11 }

mscVrSnmpViewProvTable OBJECT-TYPE
   SYNTAX     SEQUENCE OF MscVrSnmpViewProvEntry
   ACCESS     not-accessible
   STATUS     mandatory
   DESCRIPTION
     "This group contains provisionable attributes relating to SNMPv2 
      View Table SubTrees. The attributes are derived from rfc1445, and 
      rfc1447."
::= { mscVrSnmpView 10 }

mscVrSnmpViewProvEntry OBJECT-TYPE
   SYNTAX     MscVrSnmpViewProvEntry
   ACCESS     not-accessible
   STATUS     mandatory
   DESCRIPTION
     "An entry in the mscVrSnmpViewProvTable."
   INDEX {
      mscVrIndex,
      mscVrSnmpIndex,
      mscVrSnmpViewIndex,
      mscVrSnmpViewSubtreeIndex }
::= { mscVrSnmpViewProvTable 1 }

MscVrSnmpViewProvEntry ::= SEQUENCE {
   mscVrSnmpViewMask
      HexString,
   mscVrSnmpViewType
      INTEGER,
   mscVrSnmpViewRowStorageType
      INTEGER,
   mscVrSnmpViewStdRowStatus
      INTEGER }

mscVrSnmpViewMask OBJECT-TYPE
   SYNTAX     HexString (SIZE (0..16))
   ACCESS     read-write
   STATUS     mandatory
   DESCRIPTION
     "This attribute is the View mask which, in combination with the 
      corresponding instance of SnmpView subTree, defines a family of 
      view subtrees. 
      Each bit of this bit mask corresponds to a subindentifier of 
      SnmpView subTree, with the most significant bit of the i-th octet of 
      this octet string value (extended if necessary, see below) 
      corresponding to the (8*i - 7)-th sub-identifier, and the least 
      significant bit of the i-th octet of this octet string corresponding to 
      the (8*i)-th sub-identifier, where i is in the range 1 through 16.
      Each bit of this bit mask specifies whether or not the corresponding 
      sub-identifiers must match when determining if an OBJECT 
      IDENTIFIER is in this family of view subtrees; a '1' indicates that 
      an exact match must occur; a '0' indicates 'wild card', meaning that 
      any sub-identifier value matches.
      Thus, the OBJECT IDENTIFIER X of an object instance is 
      contained in a family of view subtrees if the following criteria are 
      met:
      For each sub-identifier of the value of SnmpView subTree, either the 
      i-th bit of mask is 0, or the i-th sub-identifier of X is equal to the i-th 
      sub-identifier of the value of SnmpView subTree. 
      If the value of this bit mask is M bits long and there are more than 
      M sub-identifiers in the corresponding instance of SnmpView 
      subTree, then the bit mask is extended with 1's to be the required 
      length.
      Note that when the value of this object is the zero-length string, this 
      extension rule results in a mask of all 1's being used (no wild card) 
      and the family of SnmpView subTrees is the one snmpView subTree 
      uniquely identified by the corresponding instance of subTree."
   DEFVAL     { ''H }  -- ""
::= { mscVrSnmpViewProvEntry 1 }

mscVrSnmpViewType OBJECT-TYPE
   SYNTAX     INTEGER  {
                 includedSubtree(1),
                 excludedSubtree(2) }
   ACCESS     read-write
   STATUS     mandatory
   DESCRIPTION
     "This attribute indicates whether the particular family of view 
      subtrees is included or excluded in the SNMPv2 context's (or 
      SNMPv1 community's) MIB view.
      The value 'includedSubtree' indicates that the corresponding 
      instances of subTree and mask define a family of view subtrees 
      included in the MIB view.
      The value 'excludedSubtree' indicates that the corresponding 
      instances of subTree and mask define a family of view subtrees 
      excluded in the MIB view."
   DEFVAL     { includedSubtree }
::= { mscVrSnmpViewProvEntry 2 }

mscVrSnmpViewRowStorageType OBJECT-TYPE
   SYNTAX     INTEGER  {
                 nonVolatile(3) }
   ACCESS     read-write
   STATUS     mandatory
   DESCRIPTION
     "The attribute indicates the storage type for this conceptual row in 
      the SNMPv2 viewTable. This is a constant - nonVolatile."
   DEFVAL     { nonVolatile }
::= { mscVrSnmpViewProvEntry 3 }

mscVrSnmpViewStdRowStatus OBJECT-TYPE
   SYNTAX     INTEGER  {
                 active(1) }
   ACCESS     read-write
   STATUS     mandatory
   DESCRIPTION
     "This attribute indicates the status of this conceptual row in the 
      SNMPv2 snmpViewTable. This is a constant - active."
   DEFVAL     { active }
::= { mscVrSnmpViewProvEntry 4 }


-- Vr/Vr_String Snmp ObjectResource/n
-- This component represents an entry in the SNMPv2 Object 
-- Resources Table (rfc1450). It lists the MIBs currently supported by 
-- the SNMP management entity.

mscVrSnmpOr OBJECT IDENTIFIER ::= { mscVrSnmp 8 }



mscVrSnmpOrRowStatusTable OBJECT-TYPE
   SYNTAX     SEQUENCE OF MscVrSnmpOrRowStatusEntry
   ACCESS     not-accessible
   STATUS     mandatory
   DESCRIPTION
     "This entry controls the addition and deletion of 
      mscVrSnmpOr components."
::= { mscVrSnmpOr 1 }

mscVrSnmpOrRowStatusEntry OBJECT-TYPE
   SYNTAX     MscVrSnmpOrRowStatusEntry
   ACCESS     not-accessible
   STATUS     mandatory
   DESCRIPTION
     "A single entry in the table represents a single 
      mscVrSnmpOr component."
   INDEX {
      mscVrIndex,
      mscVrSnmpIndex,
      mscVrSnmpOrIndex }
::= { mscVrSnmpOrRowStatusTable 1 }

MscVrSnmpOrRowStatusEntry ::= SEQUENCE {
   mscVrSnmpOrRowStatus
      RowStatus,
   mscVrSnmpOrComponentName
      DisplayString,
   mscVrSnmpOrStorageType
      StorageType,
   mscVrSnmpOrIndex
      Integer32 }

mscVrSnmpOrRowStatus OBJECT-TYPE
   SYNTAX     RowStatus 
   ACCESS     read-only
   STATUS     mandatory
   DESCRIPTION
     "This variable is used as the basis for SNMP naming of
      mscVrSnmpOr components.
      These components cannot be added nor deleted."
::= { mscVrSnmpOrRowStatusEntry 1 }

mscVrSnmpOrComponentName OBJECT-TYPE
   SYNTAX     DisplayString 
   ACCESS     read-only
   STATUS     mandatory
   DESCRIPTION
     "This variable provides the component's string name for
      use with the ASCII Console Interface"
::= { mscVrSnmpOrRowStatusEntry 2 }

mscVrSnmpOrStorageType OBJECT-TYPE
   SYNTAX     StorageType 
   ACCESS     read-only
   STATUS     mandatory
   DESCRIPTION
     "This variable represents the storage type value for the
      mscVrSnmpOr tables."
::= { mscVrSnmpOrRowStatusEntry 4 }

mscVrSnmpOrIndex OBJECT-TYPE
   SYNTAX     Integer32 (1..1024)
   ACCESS     not-accessible
   STATUS     mandatory
   DESCRIPTION
     "This variable represents the index for the mscVrSnmpOr tables."
::= { mscVrSnmpOrRowStatusEntry 10 }

mscVrSnmpOrOrTable OBJECT-TYPE
   SYNTAX     SEQUENCE OF MscVrSnmpOrOrEntry
   ACCESS     not-accessible
   STATUS     mandatory
   DESCRIPTION
     "The attributes of this group describe a MIB currently supported by 
      the SNMP agent. SNMP managers make use of these entries to 
      determine what is supported. The group is derived from rfc 1450."
::= { mscVrSnmpOr 10 }

mscVrSnmpOrOrEntry OBJECT-TYPE
   SYNTAX     MscVrSnmpOrOrEntry
   ACCESS     not-accessible
   STATUS     mandatory
   DESCRIPTION
     "An entry in the mscVrSnmpOrOrTable."
   INDEX {
      mscVrIndex,
      mscVrSnmpIndex,
      mscVrSnmpOrIndex }
::= { mscVrSnmpOrOrTable 1 }

MscVrSnmpOrOrEntry ::= SEQUENCE {
   mscVrSnmpOrId
      OBJECT IDENTIFIER,
   mscVrSnmpOrDescr
      AsciiString }

mscVrSnmpOrId OBJECT-TYPE
   SYNTAX     OBJECT IDENTIFIER 
   ACCESS     read-only
   STATUS     mandatory
   DESCRIPTION
     "This attribute represents the authoritative identification of a 
      dynamically-configurable management entity object resource. This 
      is a MIB Object Identifier."
::= { mscVrSnmpOrOrEntry 2 }

mscVrSnmpOrDescr OBJECT-TYPE
   SYNTAX     AsciiString (SIZE (0..255))
   ACCESS     read-only
   STATUS     mandatory
   DESCRIPTION
     "This attribute represents the textual description of a dynamically-
      configurable management entity object resource. This is an ASCII 
      description of a supported MIB."
::= { mscVrSnmpOrOrEntry 3 }


-- This component contains statistics based upon the SnmpV2 
-- Management Information Base SnmpV2 Statistics group (rfc1450).

mscVrSnmpV2Stats OBJECT IDENTIFIER ::= { mscVrSnmp 9 }



mscVrSnmpV2StatsRowStatusTable OBJECT-TYPE
   SYNTAX     SEQUENCE OF MscVrSnmpV2StatsRowStatusEntry
   ACCESS     not-accessible
   STATUS     obsolete
   DESCRIPTION
     "This entry controls the addition and deletion of 
      mscVrSnmpV2Stats components."
::= { mscVrSnmpV2Stats 1 }

mscVrSnmpV2StatsRowStatusEntry OBJECT-TYPE
   SYNTAX     MscVrSnmpV2StatsRowStatusEntry
   ACCESS     not-accessible
   STATUS     obsolete
   DESCRIPTION
     "A single entry in the table represents a single 
      mscVrSnmpV2Stats component."
   INDEX {
      mscVrIndex,
      mscVrSnmpIndex,
      mscVrSnmpV2StatsIndex }
::= { mscVrSnmpV2StatsRowStatusTable 1 }

MscVrSnmpV2StatsRowStatusEntry ::= SEQUENCE {
   mscVrSnmpV2StatsRowStatus
      RowStatus,
   mscVrSnmpV2StatsComponentName
      DisplayString,
   mscVrSnmpV2StatsStorageType
      StorageType,
   mscVrSnmpV2StatsIndex
      NonReplicated }

mscVrSnmpV2StatsRowStatus OBJECT-TYPE
   SYNTAX     RowStatus 
   ACCESS     read-only
   STATUS     obsolete
   DESCRIPTION
     "This variable is used as the basis for SNMP naming of
      mscVrSnmpV2Stats components.
      These components cannot be added nor deleted."
::= { mscVrSnmpV2StatsRowStatusEntry 1 }

mscVrSnmpV2StatsComponentName OBJECT-TYPE
   SYNTAX     DisplayString 
   ACCESS     read-only
   STATUS     obsolete
   DESCRIPTION
     "This variable provides the component's string name for
      use with the ASCII Console Interface"
::= { mscVrSnmpV2StatsRowStatusEntry 2 }

mscVrSnmpV2StatsStorageType OBJECT-TYPE
   SYNTAX     StorageType 
   ACCESS     read-only
   STATUS     obsolete
   DESCRIPTION
     "This variable represents the storage type value for the
      mscVrSnmpV2Stats tables."
::= { mscVrSnmpV2StatsRowStatusEntry 4 }

mscVrSnmpV2StatsIndex OBJECT-TYPE
   SYNTAX     NonReplicated 
   ACCESS     not-accessible
   STATUS     obsolete
   DESCRIPTION
     "This variable represents the index for the mscVrSnmpV2Stats tables."
::= { mscVrSnmpV2StatsRowStatusEntry 10 }

mscVrSnmpV2StatsStatsTable OBJECT-TYPE
   SYNTAX     SEQUENCE OF MscVrSnmpV2StatsStatsEntry
   ACCESS     not-accessible
   STATUS     obsolete
   DESCRIPTION
     "This attribute group contains the collection of statistics as defined 
      by SNMPv2 providing basic instrumentation of a SNMPv2 Agent. 
      The group is derived from rfc 1450. As the implementation is fully 
      bilingual in regards to Snmp V2/V1, statistics which apply only to 
      unilingual V2 Agents do not appear as attributes. Similarly as 
      privacy protocols are not supported, the relevant statistics have no 
      corresponding attributes."
::= { mscVrSnmpV2Stats 10 }

mscVrSnmpV2StatsStatsEntry OBJECT-TYPE
   SYNTAX     MscVrSnmpV2StatsStatsEntry
   ACCESS     not-accessible
   STATUS     obsolete
   DESCRIPTION
     "An entry in the mscVrSnmpV2StatsStatsTable."
   INDEX {
      mscVrIndex,
      mscVrSnmpIndex,
      mscVrSnmpV2StatsIndex }
::= { mscVrSnmpV2StatsStatsTable 1 }

MscVrSnmpV2StatsStatsEntry ::= SEQUENCE {
   mscVrSnmpV2StatsPackets
      Unsigned32,
   mscVrSnmpV2StatsEncodingErrors
      Unsigned32,
   mscVrSnmpV2StatsUnknownSrcParties
      Unsigned32,
   mscVrSnmpV2StatsBadAuths
      Unsigned32,
   mscVrSnmpV2StatsNotInLifetime
      Unsigned32,
   mscVrSnmpV2StatsWrongDigestValues
      Unsigned32,
   mscVrSnmpV2StatsUnknownContexts
      Unsigned32,
   mscVrSnmpV2StatsBadOperations
      Unsigned32,
   mscVrSnmpV2StatsSilentDrops
      Unsigned32 }

mscVrSnmpV2StatsPackets OBJECT-TYPE
   SYNTAX     Unsigned32 (0..4294967295)
   ACCESS     read-only
   STATUS     obsolete
   DESCRIPTION
     "This attribute represents the total number of SNMP messages 
      received by the SNMP management entity from the transport 
      service. This has the same value as inPackets in the 
      SnmpMibIIStatsOp group."
   DEFVAL     { 0 }
::= { mscVrSnmpV2StatsStatsEntry 1 }

mscVrSnmpV2StatsEncodingErrors OBJECT-TYPE
   SYNTAX     Unsigned32 (0..4294967295)
   ACCESS     read-only
   STATUS     obsolete
   DESCRIPTION
     "This attribute represents the total number of SNMP messages 
      received by the SNMP management entity which were improperly 
      BER encoded or had an invalid ASN.1 syntax. This has the same 
      value as inAsnParseErrs in the SnmpMibIIStatsOp group."
   DEFVAL     { 0 }
::= { mscVrSnmpV2StatsStatsEntry 2 }

mscVrSnmpV2StatsUnknownSrcParties OBJECT-TYPE
   SYNTAX     Unsigned32 (0..4294967295)
   ACCESS     read-only
   STATUS     obsolete
   DESCRIPTION
     "This attribute represents the total number of SNMPv2 messages 
      received by the SNMP management entity for which the message 
      source Party was not locally recognized."
   DEFVAL     { 0 }
::= { mscVrSnmpV2StatsStatsEntry 3 }

mscVrSnmpV2StatsBadAuths OBJECT-TYPE
   SYNTAX     Unsigned32 (0..4294967295)
   ACCESS     read-only
   STATUS     obsolete
   DESCRIPTION
     "This attribute represents the total number of SNMPv2 messages 
      received by the SNMP management entity for which the message 
      authentication protocol did not match that of the local source Party."
   DEFVAL     { 0 }
::= { mscVrSnmpV2StatsStatsEntry 4 }

mscVrSnmpV2StatsNotInLifetime OBJECT-TYPE
   SYNTAX     Unsigned32 (0..4294967295)
   ACCESS     read-only
   STATUS     obsolete
   DESCRIPTION
     "This attribute represents the total number of SNMPv2 messages 
      received by the SNMP management entity for which the message 
      source TimeStamp was less than the combination of the local source 
      Party's clock and lifetime."
   DEFVAL     { 0 }
::= { mscVrSnmpV2StatsStatsEntry 5 }

mscVrSnmpV2StatsWrongDigestValues OBJECT-TYPE
   SYNTAX     Unsigned32 (0..4294967295)
   ACCESS     read-only
   STATUS     obsolete
   DESCRIPTION
     "This attribute represents the total number of SNMPv2 messages 
      received by the SNMP management entity for which the message 
      authentication Digest Value was invalid."
   DEFVAL     { 0 }
::= { mscVrSnmpV2StatsStatsEntry 6 }

mscVrSnmpV2StatsUnknownContexts OBJECT-TYPE
   SYNTAX     Unsigned32 (0..4294967295)
   ACCESS     read-only
   STATUS     obsolete
   DESCRIPTION
     "This attribute represents the total number of SNMPv2 messages 
      received by the SNMP management entity for which the message 
      Context was not locally known."
   DEFVAL     { 0 }
::= { mscVrSnmpV2StatsStatsEntry 7 }

mscVrSnmpV2StatsBadOperations OBJECT-TYPE
   SYNTAX     Unsigned32 (0..4294967295)
   ACCESS     read-only
   STATUS     obsolete
   DESCRIPTION
     "This attribute represents the total number of SNMPv2 messages 
      received by the SNMP management entity for which the PDU type 
      was not allowed in the local Access Privileges Entry."
   DEFVAL     { 0 }
::= { mscVrSnmpV2StatsStatsEntry 8 }

mscVrSnmpV2StatsSilentDrops OBJECT-TYPE
   SYNTAX     Unsigned32 (0..4294967295)
   ACCESS     read-only
   STATUS     obsolete
   DESCRIPTION
     "This attribute represents the total number of SNMPv2 messages 
      received by the SNMP management entity which were silently 
      ignored because an alternate response message was greater than a 
      local constraint or greater than the maximum message size allowed 
      for the source Party. In other words, this attribute counts the number 
      of error responses pdu's which could not be generated due to size 
      constraints."
   DEFVAL     { 0 }
::= { mscVrSnmpV2StatsStatsEntry 9 }


-- This component contains statistics based upon the SnmpV2 
-- Management Information Base SnmpV1 Statistics group (rfc1450).

mscVrSnmpV1Stats OBJECT IDENTIFIER ::= { mscVrSnmp 10 }



mscVrSnmpV1StatsRowStatusTable OBJECT-TYPE
   SYNTAX     SEQUENCE OF MscVrSnmpV1StatsRowStatusEntry
   ACCESS     not-accessible
   STATUS     mandatory
   DESCRIPTION
     "This entry controls the addition and deletion of 
      mscVrSnmpV1Stats components."
::= { mscVrSnmpV1Stats 1 }

mscVrSnmpV1StatsRowStatusEntry OBJECT-TYPE
   SYNTAX     MscVrSnmpV1StatsRowStatusEntry
   ACCESS     not-accessible
   STATUS     mandatory
   DESCRIPTION
     "A single entry in the table represents a single 
      mscVrSnmpV1Stats component."
   INDEX {
      mscVrIndex,
      mscVrSnmpIndex,
      mscVrSnmpV1StatsIndex }
::= { mscVrSnmpV1StatsRowStatusTable 1 }

MscVrSnmpV1StatsRowStatusEntry ::= SEQUENCE {
   mscVrSnmpV1StatsRowStatus
      RowStatus,
   mscVrSnmpV1StatsComponentName
      DisplayString,
   mscVrSnmpV1StatsStorageType
      StorageType,
   mscVrSnmpV1StatsIndex
      NonReplicated }

mscVrSnmpV1StatsRowStatus OBJECT-TYPE
   SYNTAX     RowStatus 
   ACCESS     read-only
   STATUS     mandatory
   DESCRIPTION
     "This variable is used as the basis for SNMP naming of
      mscVrSnmpV1Stats components.
      These components cannot be added nor deleted."
::= { mscVrSnmpV1StatsRowStatusEntry 1 }

mscVrSnmpV1StatsComponentName OBJECT-TYPE
   SYNTAX     DisplayString 
   ACCESS     read-only
   STATUS     mandatory
   DESCRIPTION
     "This variable provides the component's string name for
      use with the ASCII Console Interface"
::= { mscVrSnmpV1StatsRowStatusEntry 2 }

mscVrSnmpV1StatsStorageType OBJECT-TYPE
   SYNTAX     StorageType 
   ACCESS     read-only
   STATUS     mandatory
   DESCRIPTION
     "This variable represents the storage type value for the
      mscVrSnmpV1Stats tables."
::= { mscVrSnmpV1StatsRowStatusEntry 4 }

mscVrSnmpV1StatsIndex OBJECT-TYPE
   SYNTAX     NonReplicated 
   ACCESS     not-accessible
   STATUS     mandatory
   DESCRIPTION
     "This variable represents the index for the mscVrSnmpV1Stats tables."
::= { mscVrSnmpV1StatsRowStatusEntry 10 }

mscVrSnmpV1StatsStatsTable OBJECT-TYPE
   SYNTAX     SEQUENCE OF MscVrSnmpV1StatsStatsEntry
   ACCESS     not-accessible
   STATUS     mandatory
   DESCRIPTION
     "This attribute group contains the collection of statistics as defined 
      by SNMPv2 providing basic instrumentation of a SNMPv2 Agent 
      which also implements SNMPv1. The group is derived from rfc 
      1450."
::= { mscVrSnmpV1Stats 10 }

mscVrSnmpV1StatsStatsEntry OBJECT-TYPE
   SYNTAX     MscVrSnmpV1StatsStatsEntry
   ACCESS     not-accessible
   STATUS     mandatory
   DESCRIPTION
     "An entry in the mscVrSnmpV1StatsStatsTable."
   INDEX {
      mscVrIndex,
      mscVrSnmpIndex,
      mscVrSnmpV1StatsIndex }
::= { mscVrSnmpV1StatsStatsTable 1 }

MscVrSnmpV1StatsStatsEntry ::= SEQUENCE {
   mscVrSnmpV1StatsBadCommunityNames
      Unsigned32,
   mscVrSnmpV1StatsBadCommunityUses
      Unsigned32 }

mscVrSnmpV1StatsBadCommunityNames OBJECT-TYPE
   SYNTAX     Unsigned32 (0..4294967295)
   ACCESS     read-only
   STATUS     mandatory
   DESCRIPTION
     "This attribute counts the SNMPv1 messages received by the SNMP 
      management entity which had an unknown SNMPv1 Community 
      string. This has the same value as the attribute 
      inBadCommunityNames under the SnmpMibIIStats component."
   DEFVAL     { 0 }
::= { mscVrSnmpV1StatsStatsEntry 1 }

mscVrSnmpV1StatsBadCommunityUses OBJECT-TYPE
   SYNTAX     Unsigned32 (0..4294967295)
   ACCESS     read-only
   STATUS     mandatory
   DESCRIPTION
     "This attribute counts the SNMPv1 messages received by the SNMP 
      management entity which attempted to perform an operation not 
      allowed for the indicated SNMPv1 Community. This has the same 
      value as the attribute inBadCommunityUses under the 
      SnmpMibIIStats component."
   DEFVAL     { 0 }
::= { mscVrSnmpV1StatsStatsEntry 2 }


-- This component contains statistics based upon the MIB II Snmp 
-- group (rfc1213).

mscVrSnmpMibIIStats OBJECT IDENTIFIER ::= { mscVrSnmp 11 }



mscVrSnmpMibIIStatsRowStatusTable OBJECT-TYPE
   SYNTAX     SEQUENCE OF MscVrSnmpMibIIStatsRowStatusEntry
   ACCESS     not-accessible
   STATUS     mandatory
   DESCRIPTION
     "This entry controls the addition and deletion of 
      mscVrSnmpMibIIStats components."
::= { mscVrSnmpMibIIStats 1 }

mscVrSnmpMibIIStatsRowStatusEntry OBJECT-TYPE
   SYNTAX     MscVrSnmpMibIIStatsRowStatusEntry
   ACCESS     not-accessible
   STATUS     mandatory
   DESCRIPTION
     "A single entry in the table represents a single 
      mscVrSnmpMibIIStats component."
   INDEX {
      mscVrIndex,
      mscVrSnmpIndex,
      mscVrSnmpMibIIStatsIndex }
::= { mscVrSnmpMibIIStatsRowStatusTable 1 }

MscVrSnmpMibIIStatsRowStatusEntry ::= SEQUENCE {
   mscVrSnmpMibIIStatsRowStatus
      RowStatus,
   mscVrSnmpMibIIStatsComponentName
      DisplayString,
   mscVrSnmpMibIIStatsStorageType
      StorageType,
   mscVrSnmpMibIIStatsIndex
      NonReplicated }

mscVrSnmpMibIIStatsRowStatus OBJECT-TYPE
   SYNTAX     RowStatus 
   ACCESS     read-only
   STATUS     mandatory
   DESCRIPTION
     "This variable is used as the basis for SNMP naming of
      mscVrSnmpMibIIStats components.
      These components cannot be added nor deleted."
::= { mscVrSnmpMibIIStatsRowStatusEntry 1 }

mscVrSnmpMibIIStatsComponentName OBJECT-TYPE
   SYNTAX     DisplayString 
   ACCESS     read-only
   STATUS     mandatory
   DESCRIPTION
     "This variable provides the component's string name for
      use with the ASCII Console Interface"
::= { mscVrSnmpMibIIStatsRowStatusEntry 2 }

mscVrSnmpMibIIStatsStorageType OBJECT-TYPE
   SYNTAX     StorageType 
   ACCESS     read-only
   STATUS     mandatory
   DESCRIPTION
     "This variable represents the storage type value for the
      mscVrSnmpMibIIStats tables."
::= { mscVrSnmpMibIIStatsRowStatusEntry 4 }

mscVrSnmpMibIIStatsIndex OBJECT-TYPE
   SYNTAX     NonReplicated 
   ACCESS     not-accessible
   STATUS     mandatory
   DESCRIPTION
     "This variable represents the index for the mscVrSnmpMibIIStats tables."
::= { mscVrSnmpMibIIStatsRowStatusEntry 10 }

mscVrSnmpMibIIStatsStatsTable OBJECT-TYPE
   SYNTAX     SEQUENCE OF MscVrSnmpMibIIStatsStatsEntry
   ACCESS     not-accessible
   STATUS     mandatory
   DESCRIPTION
     "This attribute group contains the collection of statistics as defined 
      by MIB II providing basic instrumentation of a SNMP Agent. The 
      group is derived from rfc 1213. Statistics which are only relevant 
      for SNMP Managers do not appear."
::= { mscVrSnmpMibIIStats 10 }

mscVrSnmpMibIIStatsStatsEntry OBJECT-TYPE
   SYNTAX     MscVrSnmpMibIIStatsStatsEntry
   ACCESS     not-accessible
   STATUS     mandatory
   DESCRIPTION
     "An entry in the mscVrSnmpMibIIStatsStatsTable."
   INDEX {
      mscVrIndex,
      mscVrSnmpIndex,
      mscVrSnmpMibIIStatsIndex }
::= { mscVrSnmpMibIIStatsStatsTable 1 }

MscVrSnmpMibIIStatsStatsEntry ::= SEQUENCE {
   mscVrSnmpMibIIStatsInPackets
      Unsigned32,
   mscVrSnmpMibIIStatsInBadCommunityNames
      Unsigned32,
   mscVrSnmpMibIIStatsInBadCommunityUses
      Unsigned32,
   mscVrSnmpMibIIStatsInAsnParseErrs
      Unsigned32,
   mscVrSnmpMibIIStatsOutPackets
      Unsigned32,
   mscVrSnmpMibIIStatsInBadVersions
      Unsigned32,
   mscVrSnmpMibIIStatsInTotalReqVars
      Unsigned32,
   mscVrSnmpMibIIStatsInTotalSetVars
      Unsigned32,
   mscVrSnmpMibIIStatsInGetRequests
      Unsigned32,
   mscVrSnmpMibIIStatsInGetNexts
      Unsigned32,
   mscVrSnmpMibIIStatsInSetRequests
      Unsigned32,
   mscVrSnmpMibIIStatsOutTooBigs
      Unsigned32,
   mscVrSnmpMibIIStatsOutNoSuchNames
      Unsigned32,
   mscVrSnmpMibIIStatsOutBadValues
      Unsigned32,
   mscVrSnmpMibIIStatsOutGenErrs
      Unsigned32,
   mscVrSnmpMibIIStatsOutGetResponses
      Unsigned32,
   mscVrSnmpMibIIStatsOutTraps
      Unsigned32 }

mscVrSnmpMibIIStatsInPackets OBJECT-TYPE
   SYNTAX     Unsigned32 (0..4294967295)
   ACCESS     read-only
   STATUS     mandatory
   DESCRIPTION
     "This attribute represents the total number of SNMP messages 
      received by the SNMP management entity."
   DEFVAL     { 0 }
::= { mscVrSnmpMibIIStatsStatsEntry 1 }

mscVrSnmpMibIIStatsInBadCommunityNames OBJECT-TYPE
   SYNTAX     Unsigned32 (0..4294967295)
   ACCESS     read-only
   STATUS     mandatory
   DESCRIPTION
     "This attribute counts the SNMPv1 messages received by the SNMP 
      management entity which had an unknown SNMPv1 Community 
      string. This has the same value as the attribute 
      badCommunityNames under the SnmpV1Stats component."
   DEFVAL     { 0 }
::= { mscVrSnmpMibIIStatsStatsEntry 2 }

mscVrSnmpMibIIStatsInBadCommunityUses OBJECT-TYPE
   SYNTAX     Unsigned32 (0..4294967295)
   ACCESS     read-only
   STATUS     mandatory
   DESCRIPTION
     "This attribute counts the SNMPv1 messages received by the SNMP 
      management entity which attempted to perform an operation not 
      allowed for the indicated SNMPv1 Community. This has the same 
      value as the attribute badCommunityUses under the SnmpV1Stats 
      component."
   DEFVAL     { 0 }
::= { mscVrSnmpMibIIStatsStatsEntry 3 }

mscVrSnmpMibIIStatsInAsnParseErrs OBJECT-TYPE
   SYNTAX     Unsigned32 (0..4294967295)
   ACCESS     read-only
   STATUS     mandatory
   DESCRIPTION
     "This attribute counts the SNMP messages received by the SNMP 
      management entity which were improperly BER encoded or had an 
      invalid ASN.1 syntax."
   DEFVAL     { 0 }
::= { mscVrSnmpMibIIStatsStatsEntry 4 }

mscVrSnmpMibIIStatsOutPackets OBJECT-TYPE
   SYNTAX     Unsigned32 (0..4294967295)
   ACCESS     read-only
   STATUS     mandatory
   DESCRIPTION
     "This attribute counts the SNMP messages transmitted by the SNMP 
      management entity."
   DEFVAL     { 0 }
::= { mscVrSnmpMibIIStatsStatsEntry 5 }

mscVrSnmpMibIIStatsInBadVersions OBJECT-TYPE
   SYNTAX     Unsigned32 (0..4294967295)
   ACCESS     read-only
   STATUS     mandatory
   DESCRIPTION
     "This attribute counts the SNMPv1 messages received by the SNMP 
      management entity with an invalid SNMP version number."
   DEFVAL     { 0 }
::= { mscVrSnmpMibIIStatsStatsEntry 6 }

mscVrSnmpMibIIStatsInTotalReqVars OBJECT-TYPE
   SYNTAX     Unsigned32 (0..4294967295)
   ACCESS     read-only
   STATUS     mandatory
   DESCRIPTION
     "This attribute counts the MIB objects successfully retrieved by Get, 
      and Get-Next requests."
   DEFVAL     { 0 }
::= { mscVrSnmpMibIIStatsStatsEntry 7 }

mscVrSnmpMibIIStatsInTotalSetVars OBJECT-TYPE
   SYNTAX     Unsigned32 (0..4294967295)
   ACCESS     read-only
   STATUS     mandatory
   DESCRIPTION
     "This attribute counts the MIB objects successfully Set by SNMP 
      requests."
   DEFVAL     { 0 }
::= { mscVrSnmpMibIIStatsStatsEntry 8 }

mscVrSnmpMibIIStatsInGetRequests OBJECT-TYPE
   SYNTAX     Unsigned32 (0..4294967295)
   ACCESS     read-only
   STATUS     mandatory
   DESCRIPTION
     "This attribute counts the Get requests accepted and processed by the 
      SNMP management entity."
   DEFVAL     { 0 }
::= { mscVrSnmpMibIIStatsStatsEntry 9 }

mscVrSnmpMibIIStatsInGetNexts OBJECT-TYPE
   SYNTAX     Unsigned32 (0..4294967295)
   ACCESS     read-only
   STATUS     mandatory
   DESCRIPTION
     "This attribute counts the Get-Next requests accepted and processed 
      by the SNMP management entity."
   DEFVAL     { 0 }
::= { mscVrSnmpMibIIStatsStatsEntry 10 }

mscVrSnmpMibIIStatsInSetRequests OBJECT-TYPE
   SYNTAX     Unsigned32 (0..4294967295)
   ACCESS     read-only
   STATUS     mandatory
   DESCRIPTION
     "This attribute counts the Set requests accepted and processed by the 
      SNMP management entity."
   DEFVAL     { 0 }
::= { mscVrSnmpMibIIStatsStatsEntry 11 }

mscVrSnmpMibIIStatsOutTooBigs OBJECT-TYPE
   SYNTAX     Unsigned32 (0..4294967295)
   ACCESS     read-only
   STATUS     mandatory
   DESCRIPTION
     "This attribute counts the responses generated by the SNMP 
      management entity with an error-status field of tooBig."
   DEFVAL     { 0 }
::= { mscVrSnmpMibIIStatsStatsEntry 12 }

mscVrSnmpMibIIStatsOutNoSuchNames OBJECT-TYPE
   SYNTAX     Unsigned32 (0..4294967295)
   ACCESS     read-only
   STATUS     mandatory
   DESCRIPTION
     "This attribute counts the SNMPv1 responses generated by the 
      SNMP management entity with an error status field of 
      noSuchName."
   DEFVAL     { 0 }
::= { mscVrSnmpMibIIStatsStatsEntry 13 }

mscVrSnmpMibIIStatsOutBadValues OBJECT-TYPE
   SYNTAX     Unsigned32 (0..4294967295)
   ACCESS     read-only
   STATUS     mandatory
   DESCRIPTION
     "This attribute counts the SNMPv1 responses generated by the 
      SNMP management entity with an error status field of badValue."
   DEFVAL     { 0 }
::= { mscVrSnmpMibIIStatsStatsEntry 14 }

mscVrSnmpMibIIStatsOutGenErrs OBJECT-TYPE
   SYNTAX     Unsigned32 (0..4294967295)
   ACCESS     read-only
   STATUS     mandatory
   DESCRIPTION
     "This attribute counts the SNMP responses generated by the SNMP 
      management entity with an error-status field of genErr."
   DEFVAL     { 0 }
::= { mscVrSnmpMibIIStatsStatsEntry 15 }

mscVrSnmpMibIIStatsOutGetResponses OBJECT-TYPE
   SYNTAX     Unsigned32 (0..4294967295)
   ACCESS     read-only
   STATUS     mandatory
   DESCRIPTION
     "This attribute counts the Get responses generated by the SNMP 
      management entity."
   DEFVAL     { 0 }
::= { mscVrSnmpMibIIStatsStatsEntry 16 }

mscVrSnmpMibIIStatsOutTraps OBJECT-TYPE
   SYNTAX     Unsigned32 (0..4294967295)
   ACCESS     read-only
   STATUS     mandatory
   DESCRIPTION
     "This attribute counts the Traps generated by the SNMP management 
      entity."
   DEFVAL     { 0 }
::= { mscVrSnmpMibIIStatsStatsEntry 17 }


-- VirtualRouter/string SnmpInitialConfiguration
-- This component contains the information required for the definition 
-- of SNMPv2 initial parties, contexts, views, and access control 
-- policies. The definition of initial parties is described in rfc1447.
-- If this component is present and its attributes are properly set when 
-- the Snmp component is added, then the initial instances of Acl, 
-- Party, Context, and View components will be added automatically. 
-- If this component is not present or its attributes are not set, then 
-- when the Snmp component is added, no initial instances of the 
-- aforementioned components will be added.

mscVrInitSnmpConfig OBJECT IDENTIFIER ::= { mscVr 9 }



mscVrInitSnmpConfigRowStatusTable OBJECT-TYPE
   SYNTAX     SEQUENCE OF MscVrInitSnmpConfigRowStatusEntry
   ACCESS     not-accessible
   STATUS     obsolete
   DESCRIPTION
     "This entry controls the addition and deletion of 
      mscVrInitSnmpConfig components."
::= { mscVrInitSnmpConfig 1 }

mscVrInitSnmpConfigRowStatusEntry OBJECT-TYPE
   SYNTAX     MscVrInitSnmpConfigRowStatusEntry
   ACCESS     not-accessible
   STATUS     obsolete
   DESCRIPTION
     "A single entry in the table represents a single 
      mscVrInitSnmpConfig component."
   INDEX {
      mscVrIndex,
      mscVrInitSnmpConfigIndex }
::= { mscVrInitSnmpConfigRowStatusTable 1 }

MscVrInitSnmpConfigRowStatusEntry ::= SEQUENCE {
   mscVrInitSnmpConfigRowStatus
      RowStatus,
   mscVrInitSnmpConfigComponentName
      DisplayString,
   mscVrInitSnmpConfigStorageType
      StorageType,
   mscVrInitSnmpConfigIndex
      NonReplicated }

mscVrInitSnmpConfigRowStatus OBJECT-TYPE
   SYNTAX     RowStatus 
   ACCESS     read-write
   STATUS     obsolete
   DESCRIPTION
     "This variable is used as the basis for SNMP naming of
      mscVrInitSnmpConfig components.
      These components can be added and deleted."
::= { mscVrInitSnmpConfigRowStatusEntry 1 }

mscVrInitSnmpConfigComponentName OBJECT-TYPE
   SYNTAX     DisplayString 
   ACCESS     read-only
   STATUS     obsolete
   DESCRIPTION
     "This variable provides the component's string name for
      use with the ASCII Console Interface"
::= { mscVrInitSnmpConfigRowStatusEntry 2 }

mscVrInitSnmpConfigStorageType OBJECT-TYPE
   SYNTAX     StorageType 
   ACCESS     read-only
   STATUS     obsolete
   DESCRIPTION
     "This variable represents the storage type value for the
      mscVrInitSnmpConfig tables."
::= { mscVrInitSnmpConfigRowStatusEntry 4 }

mscVrInitSnmpConfigIndex OBJECT-TYPE
   SYNTAX     NonReplicated 
   ACCESS     not-accessible
   STATUS     obsolete
   DESCRIPTION
     "This variable represents the index for the mscVrInitSnmpConfig tables."
::= { mscVrInitSnmpConfigRowStatusEntry 10 }

mscVrInitSnmpConfigProvTable OBJECT-TYPE
   SYNTAX     SEQUENCE OF MscVrInitSnmpConfigProvEntry
   ACCESS     not-accessible
   STATUS     obsolete
   DESCRIPTION
     "This group contains provisionable attributes required for the 
      definition of initial SNMPv2 parties, contexts, views, and access 
      control policies, as defined in rfc1447."
::= { mscVrInitSnmpConfig 10 }

mscVrInitSnmpConfigProvEntry OBJECT-TYPE
   SYNTAX     MscVrInitSnmpConfigProvEntry
   ACCESS     not-accessible
   STATUS     obsolete
   DESCRIPTION
     "An entry in the mscVrInitSnmpConfigProvTable."
   INDEX {
      mscVrIndex,
      mscVrInitSnmpConfigIndex }
::= { mscVrInitSnmpConfigProvTable 1 }

MscVrInitSnmpConfigProvEntry ::= SEQUENCE {
   mscVrInitSnmpConfigAgentAddress
      AsciiString,
   mscVrInitSnmpConfigManagerAddress
      AsciiString }

mscVrInitSnmpConfigAgentAddress OBJECT-TYPE
   SYNTAX     AsciiString (SIZE (1..80))
   ACCESS     read-write
   STATUS     obsolete
   DESCRIPTION
     "This attribute is the address of the Virtual Router where the initial 
      Agent parties will receive network management traffic. It is used to 
      initialize the transport address of the initial local parties and also is 
      used to define initial party and context identifiers.
      The format of the agentAddress is an IpAddress."
::= { mscVrInitSnmpConfigProvEntry 1 }

mscVrInitSnmpConfigManagerAddress OBJECT-TYPE
   SYNTAX     AsciiString (SIZE (1..80))
   ACCESS     read-write
   STATUS     obsolete
   DESCRIPTION
     "This attribute is the address of the SNMPv2 manager. It is used to 
      initialize the transport address of the initial non-local parties.
      The format of the managerAddress is an IpAddress."
::= { mscVrInitSnmpConfigProvEntry 2 }




-- 
-- Version and Compliance statements
-- 



-- Object-Group Statement:
-- A list of all current accessible leaf objects.

-- OBJECTS { mscVrSnmpSysObjectId,
--           mscVrSnmpMibIIStatsOutNoSuchNames,
--           mscVrSnmpMibIIStatsInSetRequests,
--           mscVrSnmpAvailabilityStatus,
--           mscVrSnmpMibIIStatsOutBadValues,
--           mscVrSnmpMibIIStatsInAsnParseErrs,
--           mscVrSnmpComManTransportAddress,
--           mscVrSnmpCidInEntTraps,
--           mscVrSnmpMibIIStatsInBadCommunityUses,
--           mscVrSnmpMibIIStatsOutGenErrs,
--           mscVrSnmpMibIIStatsInGetRequests,
--           mscVrSnmpAlarmStatus,
--           mscVrSnmpComAccessMode,
--           mscVrSnmpMibIIStatsInPackets,
--           mscVrSnmpV1StatsComponentName,
--           mscVrSnmpUnknownStatus,
--           mscVrSnmpStandbyStatus,
--           mscVrSnmpAlarmsAsTraps,
--           mscVrSnmpSysDescription,
--           mscVrSnmpTrapsDiscarded,
--           mscVrSnmpStorageType,
--           mscVrSnmpMibIIStatsInTotalSetVars,
--           mscVrSnmpViewComponentName,
--           mscVrSnmpComTDomain,
--           mscVrSnmpComStorageType,
--           mscVrSnmpComManPrivileges,
--           mscVrSnmpOrId,
--           mscVrSnmpMibIIStatsOutGetResponses,
--           mscVrSnmpOrStorageType,
--           mscVrSnmpSysComponentName,
--           mscVrSnmpV1StatsBadCommunityUses,
--           mscVrSnmpComViewIndex,
--           mscVrSnmpIpStack,
--           mscVrSnmpSysStorageType,
--           mscVrSnmpComRowStatus,
--           mscVrSnmpSysName,
--           mscVrSnmpControlStatus,
--           mscVrSnmpAdminState,
--           mscVrSnmpV1StatsBadCommunityNames,
--           mscVrSnmpSysServices,
--           mscVrSnmpOrRowStatus,
--           mscVrSnmpMibIIStatsInGetNexts,
--           mscVrSnmpViewStorageType,
--           mscVrSnmpRowStatus,
--           mscVrSnmpMibIIStatsInBadCommunityNames,
--           mscVrSnmpSysContact,
--           mscVrSnmpProceduralStatus,
--           mscVrSnmpMgrOfLastAuthFailure,
--           mscVrSnmpMibIIStatsComponentName,
--           mscVrSnmpComComponentName,
--           mscVrSnmpViewType,
--           mscVrSnmpV2EnableAuthenTraps,
--           mscVrSnmpLastOrChange,
--           mscVrSnmpUsageState,
--           mscVrSnmpSysRowStatus,
--           mscVrSnmpMibIIStatsOutTraps,
--           mscVrSnmpViewRowStorageType,
--           mscVrSnmpComponentName,
--           mscVrSnmpOrDescr,
--           mscVrSnmpV1StatsStorageType,
--           mscVrSnmpTrapsProcessed,
--           mscVrSnmpComManRowStatus,
--           mscVrSnmpMibIIStatsOutPackets,
--           mscVrSnmpMibIIStatsRowStatus,
--           mscVrSnmpV1EnableAuthenTraps,
--           mscVrSnmpViewRowStatus,
--           mscVrSnmpOrComponentName,
--           mscVrSnmpOperationalState,
--           mscVrSnmpComManStorageType,
--           mscVrSnmpLastAuthFailure,
--           mscVrSnmpSysUpTime,
--           mscVrSnmpMibIIStatsInTotalReqVars,
--           mscVrSnmpViewStdRowStatus,
--           mscVrSnmpViewMask,
--           mscVrSnmpComCommunityString,
--           mscVrSnmpSysLocation,
--           mscVrSnmpComManComponentName,
--           mscVrSnmpMibIIStatsInBadVersions,
--           mscVrSnmpMibIIStatsOutTooBigs,
--           mscVrSnmpMibIIStatsStorageType,
--           mscVrSnmpV1StatsRowStatus }
-- STATUS  mandatory
-- DESCRIPTION
--   "A list of all current accessible leaf objects."

baseSnmpGroup OBJECT IDENTIFIER ::= { baseSnmpMIB 1 }
baseSnmpGroupCA OBJECT IDENTIFIER ::= { baseSnmpGroup 1 }
baseSnmpGroupCA02 OBJECT IDENTIFIER ::= { baseSnmpGroupCA 3 }
baseSnmpGroupCA02A OBJECT IDENTIFIER ::= { baseSnmpGroupCA02 2 }



-- Agent-Capabilities Statement:

-- PRODUCT-RELEASE "MscPassport Release 1.2 BaseSnmp."
-- STATUS          mandatory
-- DESCRIPTION     "Carrier Passport BaseSnmp MIB: MIB Version CA02A,
--                  Software Version CA02S9C."
-- SUPPORTS        Nortel-MsCarrier-MscPassport-BaseSnmpMIB
--    INCLUDES     { baseSnmpGroupCA02A }
--       rfc1213 (MIB II)
-- 
-- SUPPORTS          RFC1213-MIB
--    INCLUDES	        { system, interfaces, snmp }
-- 
--       variations for SNMP group of rfc1213
-- 
--    VARIATION		snmpInTooBigs
--       ACCESS		not-implemented
--       DESCRIPTION	"Not applicable for Agent"
-- 
--    VARIATION		snmpInNoSuchNames
--       ACCESS		not-implemented
--       DESCRIPTION	"Not applicable for Agent"
-- 
--    VARIATION		snmpInBadValues
--       ACCESS		not-implemented
--       DESCRIPTION	"Not applicable for Agent"
-- 
--    VARIATION		snmpInReadOnlys
--       ACCESS		not-implemented
--       DESCRIPTION	"Not applicable for Agent"
-- 
--    VARIATION		snmpInGenErrs
--       ACCESS		not-implemented
--       DESCRIPTION	"Not applicable for Agent"
-- 
--    VARIATION		snmpInGetResponses
--       ACCESS		not-implemented
--       DESCRIPTION	"Not applicable for Agent"
-- 
--    VARIATION		snmpInTraps
--       ACCESS		not-implemented
--       DESCRIPTION	"Not applicable for Agent"
-- 
--    VARIATION		snmpOutGetRequests
--       ACCESS		not-implemented
--       DESCRIPTION	"Not applicable for Agent"
-- 
--    VARIATION		snmpOutGetNexts
--       ACCESS		not-implemented
--       DESCRIPTION	"Not applicable for Agent"
-- 
--    VARIATION		snmpOutSetRequests
--       ACCESS		not-implemented
--       DESCRIPTION	"Not applicable for Agent"
-- 
-- 
--    rfc1450
-- 
-- SUPPORTS SNMPv2-MIB
--    INCLUDES          { snmpStats, snmpV1, snmpOR, snmpTrap, snmpSet }
-- 
--       variations for snmpStats group
-- 
--    VARIATION		snmpStats30Something
--       ACCESS		not-implemented
--       DESCRIPTION	"Inapplicable for an agent supporting V1"
-- 
--    VARIATION		snmpStatsUnknownDstParties
--       ACCESS		not-implemented
--       DESCRIPTION	"Inapplicable since privacy not supported"
-- 
--    VARIATION 		snmpStatsDstPartyMismatches
--       ACCESS		not-implemented
--       DESCRIPTION	"Inapplicable since privacy not supported"
-- 
-- 

baseSnmpCapabilities OBJECT IDENTIFIER ::= { baseSnmpMIB 3 }
baseSnmpCapabilitiesCA OBJECT IDENTIFIER ::= { baseSnmpCapabilities 1 }
baseSnmpCapabilitiesCA02 OBJECT IDENTIFIER ::= { baseSnmpCapabilitiesCA 3 }
baseSnmpCapabilitiesCA02A OBJECT IDENTIFIER ::= { baseSnmpCapabilitiesCA02 2 }





END
