XEDIA-DIALBACKUP-MIB DEFINITIONS ::= BEGIN

IMPORTS 
    MODULE-IDENTITY, OBJECT-TYPE
        FROM SNMPv2-SMI
    MODULE-COMPLIANCE, OBJECT-GROUP
        FROM SNMPv2-CONF
    DisplayString
        FROM SNMPv2-TC
    ifIndex
        FROM IF-MIB
    xediaMibs
        FROM XEDIA-REG
    ;

xediaDialBackupMIB MODULE-IDENTITY
    LAST-UPDATED "9908112155Z" -- August 11, 1999
    ORGANIZATION "Xedia Corp."
    CONTACT-INFO
        "support@xedia.com"
    DESCRIPTION
        "This module defines objects for management of Xedia's Dial
        Backup capabilities."
    ::= { xediaMibs 36 }


-- ****************************************************************
-- Top-level organization of the MIB
-- ****************************************************************

dialBackupObjects          OBJECT IDENTIFIER ::= { xediaDialBackupMIB 1 }
dialBackupConformance      OBJECT IDENTIFIER ::= { xediaDialBackupMIB 2 }

-- ****************************************************************
-- Object Definitions
-- ****************************************************************

dialBackupConfigurationTable OBJECT-TYPE
    SYNTAX      SEQUENCE OF DialBackupConfigurationEntry
    MAX-ACCESS  not-accessible
    STATUS      current
    DESCRIPTION
        ""
    ::= { dialBackupObjects 1 }

dialBackupConfigurationEntry OBJECT-TYPE
    SYNTAX      DialBackupConfigurationEntry
    MAX-ACCESS  not-accessible
    STATUS      current
    DESCRIPTION
        ""
    INDEX { ifIndex }
    ::= { dialBackupConfigurationTable 1 }

DialBackupConfigurationEntry ::= SEQUENCE {
    dialBackupPrimaryInterface      DisplayString,
    dialBackupFailoverTime          INTEGER,
    dialBackupFailbackTime          INTEGER,
    dialBackupStatus                INTEGER
    }

dialBackupPrimaryInterface OBJECT-TYPE
    SYNTAX      DisplayString
    MAX-ACCESS  read-write
    STATUS      current
    DESCRIPTION
        ""
    DEFVAL      { "none" }
    ::= { dialBackupConfigurationEntry 1 }

dialBackupFailoverTime OBJECT-TYPE
    SYNTAX      INTEGER (0..2147483647)
    UNITS       "seconds"
    MAX-ACCESS  read-write
    STATUS      current
    DESCRIPTION
        ""
    DEFVAL      { 0 }
    ::= { dialBackupConfigurationEntry 2 }

dialBackupFailbackTime OBJECT-TYPE
    SYNTAX      INTEGER (0..2147483647)
    UNITS       "seconds"
    MAX-ACCESS  read-write
    STATUS      current
    DESCRIPTION
        ""
    DEFVAL      { 0 }
    ::= { dialBackupConfigurationEntry 3 }


dialBackupStatus OBJECT-TYPE
    SYNTAX      INTEGER {
                    enabled(1),
                    disabled(2)
                }
    MAX-ACCESS  read-write
    STATUS      current 
    DESCRIPTION
        ""
    DEFVAL      { disabled }
    ::= { dialBackupConfigurationEntry 4 }


-- ****************************************************************
-- Conformance Statements
-- ****************************************************************

dialBackupCompliances OBJECT IDENTIFIER ::= { dialBackupConformance 1 }
dialBackupGroups      OBJECT IDENTIFIER ::= { dialBackupConformance 2 }

--
-- Compliance Statements
--

dialBackupCompliance MODULE-COMPLIANCE
    STATUS      current
    DESCRIPTION
        "The compliance statement for all agents that support this
        MIB. A compliant agent implements all objects defined in this
        MIB."
    MODULE  -- this module
    MANDATORY-GROUPS {
        dialBackupAllGroup
    }
    ::= { dialBackupCompliances 1 }

--
-- Object Groups
--

dialBackupAllGroup OBJECT-GROUP
    OBJECTS {
        dialBackupPrimaryInterface,
        dialBackupFailoverTime,
        dialBackupFailbackTime,
        dialBackupStatus
    }
    STATUS      current
    DESCRIPTION
        "The set of all accessible objects in this MIB."
    ::= { dialBackupGroups 1 }
END
