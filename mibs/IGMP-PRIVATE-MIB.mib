IGMP-PRIVATE-MIB DEFINITIONS ::= BEGIN

-- Referencing the parent branch.

IMPORTS
            MODULE-IDENTITY, OBJECT-TYPE	  	FROM SNMPv2-SMI
	    RowStatus					FROM SNMPv2-TC
	    cjnProtocol                             	FROM Cajun-ROOT; 

cjnIgmp MODULE-IDENTITY
        LAST-UPDATED "9909210000Z" -- Tuesday Sept 21, 1999"
        ORGANIZATION "Lucent's Concord Technology Center (CTC)"
        CONTACT-INFO
	        "Erick Crowell -- ecrowell@lucent.com
		 Raj Duggal (Group Leader) -- rduggal@lucent.com
		 Marie Pacini -- mfpacini@lucent.com
		 Ira Steckler -- (MIB God) isteckler@lucent.com"
		
	DESCRIPTION
       		"Cajun IGMP PRIVATE MIB"
	::= { cjnProtocol 11 }

-- IGMP Global Group
--
	cjnIgmpGblGroup	OBJECT IDENTIFIER ::= { cjnIgmp 1 }
	
	cjnIgmpIsEnabled OBJECT-TYPE
              SYNTAX  INTEGER {
	      	false(0),
		true(1)
	      }	
              MAX-ACCESS  read-write
              STATUS  current
              DESCRIPTION
            	   "Enable IGMP - default to FALSE."
	       DEFVAL {1}
    	  ::= { cjnIgmpGblGroup 1 }

	cjnIpIgmpGblStatsReset  OBJECT-TYPE
	    SYNTAX  INTEGER {
	      enable(1),
	      disable(2)
	    }	
	   MAX-ACCESS read-write
	   STATUS current
	   DESCRIPTION
	   "When set to the value enable (1) all IGMP statistics are
	  reset to zero after which the value of this MIB
	  object returns to disable(2)"
	   ::= { cjnIgmpGblGroup 2 }

--
-- The following are Global Stats. 
--
       	cjnIgmpGblStatsGroup	OBJECT IDENTIFIER ::= { cjnIgmp 2 }

	cjnIgmpRxReport OBJECT-TYPE
              SYNTAX  INTEGER
              MAX-ACCESS  read-write
              STATUS  current
              DESCRIPTION
            	   "Number of Group Membership Reports Received."
	      ::= { cjnIgmpGblStatsGroup 1 }

	cjnIgmpRxQuery OBJECT-TYPE
              SYNTAX  INTEGER
              MAX-ACCESS  read-write
              STATUS  current
              DESCRIPTION
            	   "Number of Group Membership Queries Received."
	      ::= { cjnIgmpGblStatsGroup 2 }

	cjnIgmpTxQuery OBJECT-TYPE
              SYNTAX  INTEGER
              MAX-ACCESS  read-write
              STATUS  current
              DESCRIPTION
            	   "Number of Group Membership Queries Transmitted."
	      ::= { cjnIgmpGblStatsGroup 3 }

	cjnIgmpRxUnknownCode OBJECT-TYPE
              SYNTAX  INTEGER
              MAX-ACCESS  read-write
              STATUS  current
              DESCRIPTION
            	   "Number of Unknown Messages Received."
	      ::= { cjnIgmpGblStatsGroup 4 }

-- IGMP Interface Group
--
	cjnIgmpIfGroup		OBJECT IDENTIFIER ::= { cjnIgmp 3 }

	cjnIgmpIfTable OBJECT-TYPE
              SYNTAX  SEQUENCE OF CjnIgmpIfEntry
              MAX-ACCESS  not-accessible
              STATUS  current
              DESCRIPTION
                      "A list of Cajun IGMP interface entries.  The number of
                      entries is given by the value of cjnIgmpIfNumber."
              ::= { cjnIgmpIfGroup 1 }

	
        cjnIgmpIfEntry OBJECT-TYPE
              SYNTAX  CjnIgmpIfEntry
              MAX-ACCESS  not-accessible
              STATUS  current
              DESCRIPTION
                      "An cajun IGMP Interface instance "
              INDEX   { cjnIgmpIfIndex }
              ::= { cjnIgmpIfTable 1 }

        CjnIgmpIfEntry ::=
              SEQUENCE {
		cjnIgmpIfIndex
			INTEGER,
		cjnIgmpIfRowStatus
			RowStatus,	
		cjnIgmpIfIsVersion
			INTEGER,
        	cjnIgmpIfMaxGroups
			INTEGER,
        	cjnIgmpIfIsQuerier
			INTEGER,
        	cjnIgmpIfProcessLeaves
			INTEGER,
        	cjnIgmpIfQueryReqIntvl
			INTEGER,
        	cjnIgmpIfQueryRspIntvl
			INTEGER,
        	cjnIgmpIfNbrQueryTimeout
			INTEGER,
        	cjnIgmpIfRobustVariable
			INTEGER,
        	cjnIgmpIfState
			INTEGER
        	}

	cjnIgmpIfIndex OBJECT-TYPE
              SYNTAX  INTEGER	
              MAX-ACCESS  read-only
              STATUS  current
              DESCRIPTION
                      "The globally unique identifier for this interface. This number
                    	MUST correlate with the IfTable's IfIndex in MIB-II or RFC2233"
	      ::= { cjnIgmpIfEntry 1 } 

	cjnIgmpIfRowStatus OBJECT-TYPE
              SYNTAX  RowStatus	
              MAX-ACCESS  read-create
              STATUS  current
              DESCRIPTION
                      "The Status of this entry in the table.  Note the
		available states: 
		active(1), -- Obviously Active.
		notInService(2) -- Interface configured but disabled.
		notReady(3), -- Interface NOT configured.
		createAndGo(4), 
		createAndWait(5)  
		or destroy(6) "
	      ::= { cjnIgmpIfEntry 2 }

	cjnIgmpIfIsVersion OBJECT-TYPE
              SYNTAX  INTEGER {
		              v1(1),
		              v2(2)
		}	
              MAX-ACCESS  read-create
              STATUS  current
              DESCRIPTION
                      "IGMP version running. 1=V1 2=V2. default is 2=V2."
	      DEFVAL {v2}
	      ::= { cjnIgmpIfEntry 3 }

	cjnIgmpIfMaxGroups OBJECT-TYPE
              SYNTAX  INTEGER ( 1..2000 )
              MAX-ACCESS  read-create
              STATUS  current
              DESCRIPTION
                      "Maximum number of groups allowed on interface 1-2000. default is 32."
	      DEFVAL {32}
	      ::= { cjnIgmpIfEntry 4 }

	cjnIgmpIfIsQuerier OBJECT-TYPE
              SYNTAX  INTEGER {
		              false(0),
		              true(1)
		}	
              MAX-ACCESS  read-create
              STATUS  current
              DESCRIPTION
                      "For this interface are Group Queries Enabled? . default is 0=disabled."
	      DEFVAL {0}
	      ::= { cjnIgmpIfEntry 5 }

	cjnIgmpIfProcessLeaves OBJECT-TYPE
              SYNTAX  INTEGER {
		              false(0),
		              true(1)
		}	
              MAX-ACCESS  read-create
              STATUS  current
              DESCRIPTION
                      "For this interface is the processing of Leave Requests Enabled? . default is 1=enabled."
	      DEFVAL {1}
	      ::= { cjnIgmpIfEntry 6 }

	cjnIgmpIfQueryReqIntvl OBJECT-TYPE
              SYNTAX  INTEGER ( 1..65535 )
              MAX-ACCESS  read-create
              STATUS  current
              DESCRIPTION
                      " Interval between General Queries sent. 1-65535. default is 125 seconds."
	      DEFVAL {125}
	      ::= { cjnIgmpIfEntry 7 }

	cjnIgmpIfQueryRspIntvl OBJECT-TYPE
              SYNTAX  INTEGER ( 1..25 )
              MAX-ACCESS  read-create
              STATUS  current
              DESCRIPTION
                      "Max Response Time inserted into the periodic General Queries 1-25. 
                       default is 10 seconds. QueryRsp must be less than QueryReq"
	      DEFVAL {10}
	      ::= { cjnIgmpIfEntry 8 }

	cjnIgmpIfNbrQueryTimeout OBJECT-TYPE
              SYNTAX  INTEGER ( 60..300 )
              MAX-ACCESS  read-create
              STATUS  current
              DESCRIPTION
                      "Neighbor group querier timeout in seconds. 60-300. default is 255 seconds."
	      DEFVAL {255}
	      ::= { cjnIgmpIfEntry 9 }

	cjnIgmpIfRobustVariable OBJECT-TYPE
              SYNTAX  INTEGER ( 1..65535 )
              MAX-ACCESS  read-create
              STATUS  current
              DESCRIPTION
                      "Robustness variable. Expected packet loss on a network. 1-65535. default is 2."
	      DEFVAL {2}
	      ::= { cjnIgmpIfEntry 10 }

	 cjnIgmpIfState OBJECT-TYPE
              SYNTAX  INTEGER {
		 down(0),
		 init(1),
		 querier(2),
		 nonQuerier(3)
              }
	      MAX-ACCESS  read-create
              STATUS  current
              DESCRIPTION
            	   "The current state of IGMP on this interface. When the circuit first comes up the state is DOWN."
	      ::= { cjnIgmpIfEntry 11 }


-- IGMP Interface Statistics Group
--
	cjnIgmpIfStatGroup		OBJECT IDENTIFIER ::= { cjnIgmp 4 }
	  
	cjnIgmpIfStatTable OBJECT-TYPE
              SYNTAX  SEQUENCE OF CjnIgmpIfStatEntry
              MAX-ACCESS  not-accessible
              STATUS  current
              DESCRIPTION
                      "A list of Cajun IGMP interface statistics entries.  The number of
                      entries is given by the value of cjnIgmpIfNumber."
              ::= { cjnIgmpIfStatGroup 1 }

	
        cjnIgmpIfStatEntry OBJECT-TYPE
              SYNTAX  CjnIgmpIfStatEntry
              MAX-ACCESS  not-accessible
              STATUS  current
              DESCRIPTION
                      "An cajun IGMP Interface Statistics instance "
              INDEX   { cjnIgmpIfIndex }
              ::= { cjnIgmpIfStatTable 1 }

        CjnIgmpIfStatEntry ::=
              SEQUENCE {	  
	  	cjnIgmpIfQval
			INTEGER,
        	cjnIgmpIfQpval
			INTEGER,
        	cjnIgmpIfJoins
			INTEGER,
        	cjnIgmpIfLeaves
			INTEGER,
        	cjnIgmpIfRptRcvd
			INTEGER,
        	cjnIgmpIfQueryRcvd
			INTEGER,
        	cjnIgmpIfQueryXmit
			INTEGER,
        	cjnIgmpIfWrongVer
			INTEGER,
        	cjnIgmpIfCurGrps
			INTEGER
		}

  	cjnIgmpIfQval OBJECT-TYPE
              SYNTAX  INTEGER
              MAX-ACCESS  read-write
              STATUS  current
              DESCRIPTION
            	   "Next Query Request in seconds."
	      ::= { cjnIgmpIfStatEntry 1 }

  	cjnIgmpIfQpval OBJECT-TYPE
              SYNTAX  INTEGER
              MAX-ACCESS  read-write
              STATUS  current
              DESCRIPTION
            	   "Neighbor Querier Timeout in seconds."
	      ::= { cjnIgmpIfStatEntry 2 }

  	cjnIgmpIfJoins OBJECT-TYPE
              SYNTAX  INTEGER
              MAX-ACCESS  read-write
              STATUS  current
              DESCRIPTION
            	   "Number of Group Join Requests Received on this interface."
	      ::= { cjnIgmpIfStatEntry 3 }

  	cjnIgmpIfLeaves OBJECT-TYPE
              SYNTAX  INTEGER
              MAX-ACCESS  read-write
              STATUS  current
              DESCRIPTION
            	   "Number of Group Leave Requests Received on this interface."
	      ::= { cjnIgmpIfStatEntry 4 }

  	cjnIgmpIfRptRcvd OBJECT-TYPE
              SYNTAX  INTEGER
              MAX-ACCESS  read-write
              STATUS  current
              DESCRIPTION
            	   "Number of Group Reports Received on this interface."
	      ::= { cjnIgmpIfStatEntry 5 }

  	cjnIgmpIfQueryRcvd OBJECT-TYPE
              SYNTAX  INTEGER
              MAX-ACCESS  read-write
              STATUS  current
              DESCRIPTION
            	   "Number of Query Messages Received on this interface."
	      ::= { cjnIgmpIfStatEntry 6 }

  	cjnIgmpIfQueryXmit OBJECT-TYPE
              SYNTAX  INTEGER
              MAX-ACCESS  read-write
              STATUS  current
              DESCRIPTION
            	   "Number of Query Messages Transmitted on this interface."
	      ::= { cjnIgmpIfStatEntry 7 }

-- The following cjnIgmpIfWrongver is in the WEB but not being counted in the code.
  	cjnIgmpIfWrongVer OBJECT-TYPE
              SYNTAX  INTEGER
              MAX-ACCESS  read-write
              STATUS  current
              DESCRIPTION
            	   "Number of Unknown Messages Received on this interface."
	      ::= { cjnIgmpIfStatEntry 8 }
        
  	cjnIgmpIfCurGrps OBJECT-TYPE
              SYNTAX  INTEGER
              MAX-ACCESS  read-write
              STATUS  current
              DESCRIPTION
            	   "Number of Current Groups on this interface."
	      ::= { cjnIgmpIfStatEntry 9 }

END
