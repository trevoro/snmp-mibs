XEDIA-BGP-MIB DEFINITIONS ::= BEGIN

IMPORTS 
    RowStatus, TruthValue
        FROM SNMPv2-TC
   bgpPeerEntry, bgp4PathAttrEntry
	FROM BGP4-MIB
    MODULE-IDENTITY, OBJECT-TYPE, IpAddress
        FROM SNMPv2-SMI
    MODULE-COMPLIANCE, OBJECT-GROUP
        FROM SNMPv2-CONF
    xediaMibs
        FROM XEDIA-REG
    ;    

xediaBgpMIB MODULE-IDENTITY
    LAST-UPDATED "9711212155Z" -- November 21, 1997
    ORGANIZATION "Xedia Corp."
    CONTACT-INFO
        "support@xedia.com"
    DESCRIPTION
        "This module defines additional objects for management of BGP 
        in Xedia devices, above and beyond what is defined in the
        standard rfc1657, and proposed drafts."
    ::= { xediaMibs 9 }

-- Top-level organization of the MIB

xbgpObjects          OBJECT IDENTIFIER ::= { xediaBgpMIB 1 }
xbgpConformance      OBJECT IDENTIFIER ::= { xediaBgpMIB 2 }

--
-- A BGP on/off control
--
xbgpAdminStatus OBJECT-TYPE
    SYNTAX      INTEGER {
                    enabled(1),
                    disabled(2)
                }
    MAX-ACCESS  read-create
    STATUS      current
    DESCRIPTION
        "The administrative status of BGP in the router. It is the 
        desired state of BGP.  The value 'enabled(1)' indicates that 
	the BGP process should be active in the router, while 
	'disabled(2)' indicates that BGP shold not be active in the router."
    DEFVAL      { disabled }
    ::= { xbgpObjects 1 }

--
-- A BGP Operational state
--
xbgpOperStatus OBJECT-TYPE
    SYNTAX      INTEGER {
                    up(1),
                    down(2)
                }
    MAX-ACCESS  read-only
    STATUS      current
    DESCRIPTION
        "The current operational state of BGP on the router."
    ::= { xbgpObjects 2 }

xbgpReflection OBJECT-TYPE
    SYNTAX      INTEGER {
                    full(1),
                    noClientToClient(2),
                    none(3)
                }
    MAX-ACCESS  read-create
    STATUS      current
    DESCRIPTION
        "The administrative status of BGP route reflection.
        The value 'full(1)' indicates that BGP will perform full
        route reflection among client and non-client peers. A
        value of 'nonClientToClient(2)' indicates that routes will only
        be reflected between clients and non-clients, not among clients.
        A value of 'none(3)' indicates that no reflection will occur, 
        regardless of the specific peer configuration."
    DEFVAL      { none }
    ::= { xbgpObjects 3 }

xbgpClusterId OBJECT-TYPE
    SYNTAX      INTEGER (0..2147483647)
    MAX-ACCESS  read-create
    STATUS      current
    DESCRIPTION
        "The route reflector cluster id used when there are multiple
        route reflectors in a cluster."
    ::= { xbgpObjects 4 }

xbgpConfiguredMaxRoutes OBJECT-TYPE
    SYNTAX      INTEGER (0..500000)
    MAX-ACCESS  read-create
    STATUS      current
    DESCRIPTION
	     "The maximum number of routed Networks in the internal
	 Route Table.  It is the maximum total number of Dest/Mask 
	 (network) route entries.  Depending upon system configuration
	 and the number of route entries in the route table that are
	 destination addresses with multple masks, it may not be 
	 possible to have a route table with the maximum number of
	 routed networks.  If this variable is changed, it will not
	 take effect until the box is reset."
    DEFVAL  { 81920 }
    ::= { xbgpObjects 5 }

xbgpOperationalMaxRoutes OBJECT-TYPE
    SYNTAX      INTEGER (0..500000)
    MAX-ACCESS  read-only
    STATUS      current
    DESCRIPTION
	     "The maximum number of routed Networks in the internal
	 Route Table.  It is the maximum total number of Dest/Mask 
	 (network) route entries.  Depending upon system configuration
	 and the number of route entries in the route table that are
	 destination addresses with multple masks, it may not be 
	 possible to have a route table with the maximum number of
	 routed networks.  If this variable is changed, it will not
	 take effect until the box is reset."
    ::= { xbgpObjects 6 }

xbgpConfiguredMaxPaths OBJECT-TYPE
    SYNTAX      INTEGER (0..100000)
    MAX-ACCESS  read-create
    STATUS      current
    DESCRIPTION
	     ""
    DEFVAL  { 20480 }
    ::= { xbgpObjects 7 }

xbgpOperationalMaxPaths OBJECT-TYPE
    SYNTAX      INTEGER (0..100000)
    MAX-ACCESS  read-only
    STATUS      current
    DESCRIPTION
	     ""
    ::= { xbgpObjects 8 }

--xbgpNodeStatistics OBJECT IDENTIFIER ::= { xbgpObjects 9 }
--skip table numbers for objects below, mostly due to ported code hassles
xbgpConfiguredPeers OBJECT-TYPE
    SYNTAX      INTEGER
    MAX-ACCESS  read-only
    STATUS      current
    DESCRIPTION
             "The number of peers currently configured."
    ::= { xbgpObjects 12 }

xbgpEstablishedPeers OBJECT-TYPE
    SYNTAX      INTEGER
    MAX-ACCESS  read-only
    STATUS      current
    DESCRIPTION
             "The number of peers currently configured and in the established state."
    ::= { xbgpObjects 13 }



-- ***************************************
-- Additions to the BGP Peer Table
-- ***************************************
xBgpPeerTable        OBJECT-TYPE
    SYNTAX      SEQUENCE OF XBgpPeerEntry
    MAX-ACCESS  not-accessible
    STATUS      current
    DESCRIPTION
            "A list of BGP Peer entries."
    ::= { xbgpObjects 10 }
 
xBgpPeerEntry        OBJECT-TYPE
    SYNTAX      XBgpPeerEntry
    MAX-ACCESS  not-accessible
    STATUS      current
    DESCRIPTION
            "An entry containing additional management information
            applicable to a particular BGP Peer."
    AUGMENTS    { bgpPeerEntry }
    ::= { xBgpPeerTable 1 }

XBgpPeerEntry ::=
    SEQUENCE {
      xbgpPeerRowStatus RowStatus,
      xbgpPeerReflectionClient TruthValue 
    }

xbgpPeerRowStatus OBJECT-TYPE
    SYNTAX       RowStatus
    MAX-ACCESS   read-create
    STATUS       current
    DESCRIPTION
    "This variable displays the status of  the  entry.  
     Setting it to 'destroy' or 'notInService' removes 
     the entry from the table.  Setting it to  either 
     'create', or 'active' will add a row
     to the table."
     ::= { xBgpPeerEntry 1 }
 
xbgpPeerReflectionClient OBJECT-TYPE
    SYNTAX       TruthValue
    MAX-ACCESS   read-create
    STATUS       current
    DESCRIPTION
    "Enables a peer to receive IBGP routes reflected from 
     this speaker."
    DEFVAL       { false }
    ::= { xBgpPeerEntry 2 }

-- ***************************************
-- Additions to the BGP 4 Path Attr Table
-- ***************************************
xBgp4PathAttrTable      OBJECT-TYPE
    SYNTAX              SEQUENCE OF XBgp4PathAttrEntry
    MAX-ACCESS          not-accessible
    STATUS              current
    DESCRIPTION
            "A list of BGP Peer entries."
    ::= { xbgpObjects 11 }
 
xBgp4PathAttrEntry      OBJECT-TYPE
    SYNTAX              XBgp4PathAttrEntry
    MAX-ACCESS          not-accessible
    STATUS              current
    DESCRIPTION
            "An entry containing additional management information
            applicable to a particular BGP Path."
    AUGMENTS    { bgp4PathAttrEntry }
    ::= { xBgp4PathAttrTable 1 }

XBgp4PathAttrEntry ::=
    SEQUENCE {
      xbgp4PathAttrCommunity   OCTET STRING,
      xbgp4PathAttrOrigId      IpAddress,
      xbgp4PathAttrClusterList OCTET STRING,
      xbgp4PathAttrDistance    INTEGER
    }

xbgp4PathAttrCommunity   OBJECT-TYPE
    SYNTAX               OCTET STRING (SIZE (0..255))
    MAX-ACCESS           read-only
    STATUS               current
    DESCRIPTION
    "The Community attribute specified for a path."
     ::= { xBgp4PathAttrEntry 1 }

xbgp4PathAttrOrigId   OBJECT-TYPE
    SYNTAX     IpAddress
    MAX-ACCESS read-only
    STATUS     current
    DESCRIPTION
    "The address of the originator of the route in the AS created
     by a route reflector."
    ::= { xBgp4PathAttrEntry 2 }

xbgp4PathAttrClusterList OBJECT-TYPE
    SYNTAX               OCTET STRING (SIZE (0..255))
    MAX-ACCESS           read-only
    STATUS               current
    DESCRIPTION
    "The cluster list for a reflected path."
     ::= { xBgp4PathAttrEntry 3 }

xbgp4PathAttrDistance OBJECT-TYPE
    SYNTAX               INTEGER(0..255)
    MAX-ACCESS           read-only
    STATUS               current
    DESCRIPTION
    "Administrative distance of the path."
     ::= { xBgp4PathAttrEntry 4 }

 
-- ****************************************************************
-- Conformance Information
-- ****************************************************************

xbgpCompliances OBJECT IDENTIFIER ::= { xbgpConformance 1 }
xbgpGroups      OBJECT IDENTIFIER ::= { xbgpConformance 2 }

--
-- Compliance Statements
--

xbgpCompliance MODULE-COMPLIANCE
    STATUS      current
    DESCRIPTION
        "The compliance statement for all agents that support this
        MIB. A compliant agent implements all objects defined in this
        MIB."
    MODULE  -- this module
    MANDATORY-GROUPS {
        xbgpAllGroup
    }
    ::= { xbgpCompliances 1 }

--
-- All Object Groups
--
xbgpAllGroup OBJECT-GROUP
    OBJECTS {
        xbgpAdminStatus,
        xbgpOperStatus,
        xbgpReflection,
        xbgpClusterId,
        xbgpConfiguredMaxRoutes,
        xbgpOperationalMaxRoutes,
        xbgpConfiguredMaxPaths,
        xbgpOperationalMaxPaths,
        xbgpConfiguredPeers,
        xbgpEstablishedPeers,
        xbgpPeerRowStatus,
        xbgpPeerReflectionClient,
        xbgp4PathAttrCommunity,
        xbgp4PathAttrOrigId,
        xbgp4PathAttrClusterList,
        xbgp4PathAttrDistance
    }
    STATUS      current
    DESCRIPTION
        "The set of all accessible objects in this MIB."
    ::= { xbgpGroups 1 }

END
