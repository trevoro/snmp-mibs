-- Copyright 1995 General DataComm Ind., Inc. All Rights Reserved.
--
-- Reproduction of this document is authorized on condition that the
-- foregoing copyright notice is included. This General DataComm, GDC,
-- SNMP Management Information Base Specification embodies GDCs'
-- confidential and proprietary intellectual property. GDC retains all
-- title and ownership in the Specification, including any revisions.
--
-- It is GDCs intent to encourage the widespread use of this Specification
-- in connection with the management of GDC's products. GDC grants vendors,
-- end-users, and other interested parties a non-exclusive license to use
-- this Specification in connection with the management of GDC's products.
--
-- This Specification is supplied "AS IS," and GDC makes no warranty,
-- either expressed or implied, as to the use operation, condition, or
-- performance of the Specification.
--
-- Revision History
--
-- Version   Date       Name            Description
-- 1.00A    30-Nov-95	E. Moreno-Leon	Initial Revision
-- 1.00B    23-Feb-96   E. Moreno-Leon  Remove comments
-- 1.00C    13-Mar-96	E. Moreno-Leon  Added Major and Minor BER Alarms

GDCSC613-MIB DEFINITIONS	   ::=	   BEGIN

IMPORTS

	enterprises			FROM RFC1155-SMI
	DisplayString                   FROM RFC1213-MIB
	OBJECT-TYPE                     FROM RFC-1212
	SCinstance                      FROM GDCMACRO-MIB;

gdc          OBJECT IDENTIFIER ::= { enterprises 498 }
bql2	     OBJECT IDENTIFIER ::= { gdc 12 }
bql613	     OBJECT IDENTIFIER ::= { bql2 1 }


-- This is the GDC MIB for SC613 objects for ISDN 2B1Q.
--
-- This MIB is only usable when the configuration is software controllable.
--
-- See the GDC MIB requirements document to determine how the standard MIB's
-- are supported.
--
--*****************************************************************************
-- 	SCinstance is defined as the addressing/indexing method of accessing
--	table objects in this MIB. The SCinstance represents the SpectraComm
--	shelf Slot, Line, Drop and interface address.
--	Represented as SLDi, (Slot, Line, Drop, interface).
--
--
--*****************************************************************************



--**************************************************************************
--		GDC SC613
--**************************************************************************

bql613MIBVersion	OBJECT-TYPE
	SYNTAX	DisplayString (SIZE (5))
	ACCESS	read-only
	STATUS  mandatory
	DESCRIPTION
		"The version number of the MIB, to allow products to
		know which MIB is being supported.  The version number
		will be x.yzT where x is a major revision (1-9), y is a minor
		revision(0-9), z is a typo revision (0-9) and T indicates the
		MIB is still a test revision(A-Z).  When a release is complete
		no T should exist."
	::= { bql613 1 }


--*****************************************************************************
--                    WHAT ARE YOU TABLE
--*****************************************************************************
--
-- This table contains network element information indexed by SLDi.
--
-- This table uses SCinstance as SLDi where D and i are always 0.
--
--
bql613WhatAreYouTable OBJECT-TYPE
	SYNTAX	SEQUENCE OF Bql613WhatAreYouEntry
	ACCESS  not-accessible
	STATUS  mandatory
	DESCRIPTION
			"The GDC SC613 What Are You Table."
	::= { bql613 2 }

bql613WhatAreYouEntry OBJECT-TYPE
	SYNTAX	Bql613WhatAreYouEntry
	ACCESS  not-accessible
	STATUS  mandatory
	DESCRIPTION
			"An entry in the GDC SC613 What Are You table."
	INDEX	{ bql613WhatAreYouIndex }
	::= { bql613WhatAreYouTable 1 }

Bql613WhatAreYouEntry ::=
	SEQUENCE  {
		  bql613WhatAreYouIndex		SCinstance,
		  bql613CodeRev			DisplayString,
		  bql613AlarmStatus             OCTET STRING
		  }

bql613WhatAreYouIndex OBJECT-TYPE
	SYNTAX  SCinstance
	ACCESS  read-only
	STATUS  mandatory
	DESCRIPTION
	       "This object is the identifier of the SC613 What Are You table."
	::= { bql613WhatAreYouEntry 1 }

bql613CodeRev OBJECT-TYPE
	SYNTAX  DisplayString (SIZE (4))
	ACCESS  read-only
	STATUS  mandatory
	DESCRIPTION
		"This function returns the firmware code level.
		 Example A-  ,B-  "
	::= { bql613WhatAreYouEntry 2 }

bql613AlarmStatus OBJECT-TYPE
	SYNTAX	  OCTET STRING (SIZE (1..255))
	ACCESS	  read-only
	STATUS	  mandatory
	DESCRIPTION
		"The current alarms of the unit without the alarm masks."
	::= { bql613WhatAreYouEntry 3 }




--*****************************************************************************
-- 			CONFIGURATION TABLE
--*****************************************************************************
--
-- This table contains the network element's configuration information
-- indexed by SLDi.
--
-- This table uses SCinstance as SLDi where i is Loop 1, 2, or 3.
--
--

bql613ConfigTable OBJECT-TYPE
	SYNTAX	SEQUENCE OF Bql613ConfigEntry
	ACCESS  not-accessible
	STATUS  mandatory
	DESCRIPTION
		"The GDC SC613."
	::= { bql613 3 }

bql613ConfigEntry OBJECT-TYPE
	SYNTAX	Bql613ConfigEntry
	ACCESS  not-accessible
	STATUS  mandatory
	DESCRIPTION
		"A listing of GDC 2B1Q SC613 options."
	INDEX	{ bql613ConfigIndex }
	::= { bql613ConfigTable 1 }

Bql613ConfigEntry ::=
	SEQUENCE        {
			bql613ConfigIndex		SCinstance,
			bql613TestPattern		INTEGER,
			bql613RLTimeout			INTEGER,
			bql613MasterTXClkSrc    	INTEGER,
			bql613DTEDataRate	        INTEGER,
			bql613RespRdl			INTEGER
			}

bql613ConfigIndex OBJECT-TYPE
	SYNTAX  SCinstance
	ACCESS  read-only
	STATUS  mandatory
	DESCRIPTION
		"A unique index for the Configuration Table."
	::= { bql613ConfigEntry 1 }

bql613TestPattern OBJECT-TYPE
	SYNTAX	INTEGER {
			pattern2047(1),
			pattern511(2)
			}
	ACCESS    read-write
	STATUS    mandatory
	DESCRIPTION     "Object to select loop and channel test pattern
			 for SC613."
	::= { bql613ConfigEntry 2 }

bql613RLTimeout OBJECT-TYPE
	SYNTAX	INTEGER {
			noTimeout(1),
			timeoutAfter10Min(2)
			}
	ACCESS    read-write
	STATUS    mandatory
	DESCRIPTION     "Object to select remote loop time out."
	::= { bql613ConfigEntry 3 }

bql613MasterTXClkSrc OBJECT-TYPE
	SYNTAX  INTEGER {
			internal(1),
			external(2)
			}
	ACCESS    read-write
	STATUS    mandatory
	DESCRIPTION
			"Object to option the Loop master transmit clock source."
        ::= { bql613ConfigEntry 4 }

bql613DTEDataRate OBJECT-TYPE
	SYNTAX  INTEGER  {
			 kBps64000(9),
			 kBps128000(10)
			 }
	ACCESS  read-write
	STATUS  mandatory
	DESCRIPTION
	   "Object to option a SC613 Loop interface to a K bit per second rate."
	::= { bql613ConfigEntry 5 }

bql613RespRdl OBJECT-TYPE
	SYNTAX  INTEGER  {
			 enable(1),
			 disable(2)
			 }
	ACCESS  read-write
	STATUS  mandatory
	DESCRIPTION
	   "Object to option V54 Response RDL to enable or disable."
	::= { bql613ConfigEntry 6 }


--*****************************************************************************
--                    DIAGNOSTICS TABLE
--*****************************************************************************
--
-- This table contains the network element's diagnostic test information indexed by
-- SLDi.
--
-- This table uses SCinstance as SLDi where i can be 1, 2, or 3.

bql613DiagnosticTable OBJECT-TYPE
	SYNTAX	SEQUENCE OF Bql613DiagnosticEntry
	ACCESS    not-accessible
	STATUS    mandatory
	DESCRIPTION
			"The GDC SC613 diagnostics table."
	::= { bql613 4 }

bql613DiagnosticEntry OBJECT-TYPE
	SYNTAX	  Bql613DiagnosticEntry
	ACCESS    not-accessible
	STATUS    mandatory
	DESCRIPTION
			"A listing of GDC SC613 diagnostic tests"
	INDEX	   { bql613DiagnosticIndex }
	::= { bql613DiagnosticTable 1 }

Bql613DiagnosticEntry	::=
	SEQUENCE        {
			bql613DiagnosticIndex		SCinstance,
			bql613DiagnosticTest		INTEGER,
			bql613DiagnosticActive 		INTEGER,
			bql613DiagnosticResults		INTEGER,
			bql613DiagnosticErrorCount	INTEGER
			}

bql613DiagnosticIndex OBJECT-TYPE
	SYNTAX    SCinstance
	ACCESS    read-only
	STATUS    mandatory
	DESCRIPTION
			"A unique index for the Diagnostic Table."
	::= { bql613DiagnosticEntry 1 }


bql613DiagnosticTest OBJECT-TYPE
	SYNTAX  INTEGER (0..63)
	ACCESS	  read-write
	STATUS    mandatory
	DESCRIPTION
			"This function selects or reads the test.
			 0  = no test currently operating
			 1  = remote loopback test
			 2  = channel loopback test
			 4  = data loopback test
			 8  = selftest
			 16 = line loopback test
			 32 = terminate test

			 All other values are test combinations such as
			 9 = selftest and remote loopback."

	::= { bql613DiagnosticEntry 2 }

bql613DiagnosticActive OBJECT-TYPE
	SYNTAX  INTEGER {
			notActive (1),
			active (2)
			}
	ACCESS    read-only
	STATUS    mandatory
	DESCRIPTION
			"This function represents the test condition."
	::= { bql613DiagnosticEntry 3 }

bql613DiagnosticResults OBJECT-TYPE
	SYNTAX  INTEGER (0..16383)
	ACCESS    read-only
	STATUS    mandatory
	DESCRIPTION
			"This function reads the self test results in
			 bit errors."
	::= { bql613DiagnosticEntry 4 }


bql613DiagnosticErrorCount OBJECT-TYPE
	SYNTAX  INTEGER {
		  normal(1),
		  reset(2)
		   	}
	ACCESS    read-write
	STATUS    mandatory
	DESCRIPTION
			"This function resets the selftest error count for a
			 SC613."
	::= { bql613DiagnosticEntry 5 }


--********************************************************************************
--	ALARMS SC613 2B1Q - INDIVIDUALLY IDENTIFIED FOR THE CONTROLLER
--********************************************************************************

bql613Alarm  OBJECT IDENTIFIER ::= { bql2 7 }

bql613AlarmData OBJECT IDENTIFIER ::= { bql613Alarm 1 }

-- no response alarm (this is a SCM generated alarm)
bql613NoResponseAlm OBJECT IDENTIFIER     			::= { bql613AlarmData 1 }

-- no diagnostic receive error alarm (this is a SCM generated alarm)
bql613DiagRxErrAlm OBJECT IDENTIFIER      			::= { bql613AlarmData 2 }

-- power up alarm
bql613PowerUpAlm OBJECT IDENTIFIER        			::= { bql613AlarmData 3 }

-- LOOP x 2B1Q out of sync alarm
bql613Lp2B1QOutofSyncAlm OBJECT IDENTIFIER    			::= { bql613AlarmData 4 }

-- Loop x Tx Clock Out of Tolerance alarm
bql613LpTxClockOutOfTolerance OBJECT IDENTIFIER			::= { bql613AlarmData 5 }

-- Loop x external transmit clock absent alarm
bql613LpExtTxClkAlm OBJECT IDENTIFIER 	    			::= { bql613AlarmData 6 }

-- Loop x Sealing Current Non-Continuity
bql613LpSealingCurrentNoContinuityAlm OBJECT IDENTIFIER		::= { bql613AlarmData 7 }

-- Loop x Major alarm Bit Error Rate
bql613LpMajorBERAlm OBJECT IDENTIFIER 	    			::= { bql613AlarmData 8 }

-- Loop x Minor alarm Bit Error Rate
bql613LpMinorBERAlm OBJECT IDENTIFIER   			::= { bql613AlarmData 9 }


-- ALARM                             Maskable   Valid interfaces   thresholds
-- ==========================================================================
-- bql613NoResponseAlm                   no         unit		no
-- bql613DiagRxErrAlm                    no         unit		no
-- bql613PowerUpAlm                      no         unit		no
-- bql613Lp2B1QOutofSyncAlm              yes        loop 1,2,3		no
-- bql613LpTxClockOutOfTolerance  	 yes        loop 1,2,3		no
-- bql613LpExtTxClkAlm		         yes        loop 1,2,3		no
-- bql613LpSealingCurrentNoContinuityAlm yes	    loop 1,2,3		no
-- bql613LpMajorBERAlm		         yes	    loop 1,2,3		yes
-- bql613LpMinorBERAlm		         yes	    loop 1,2,3		yes

--*****************************************************************************
--       Alarm Config  Table FOR SC613.
--*****************************************************************************

bql613AlarmConfigTable OBJECT-TYPE
     SYNTAX SEQUENCE OF Bql613AlarmConfigEntry
     ACCESS not-accessible
     STATUS mandatory
     DESCRIPTION
	 "The bql613AlarmConfigTable contains entries that configure alarm
	 reporting.  The structure of the table is such that alarm
	 configuration is supported on a unit and interface basis, and
	 then on an alarm type basis within the interface.  For
	 simplicity sake alarms, be they unit or interface
	 related, are represented in one table."
     ::= { bql613Alarm 2 }

bql613AlarmConfigEntry OBJECT-TYPE
     SYNTAX Bql613AlarmConfigEntry
     ACCESS not-accessible
     STATUS mandatory
     DESCRIPTION
	 "An entry in the bql613AlarmConfigTable table."
     INDEX { bql613AlarmConfigIndex, bql613AlarmConfigIdentifier }
     ::= { bql613AlarmConfigTable 1 }

Bql613AlarmConfigEntry ::=
     SEQUENCE {
	 bql613AlarmConfigIndex
	     SCinstance,
	 bql613AlarmConfigIdentifier
	     OBJECT IDENTIFIER,
	 bql613AlarmThreshold
	     INTEGER
     }

bql613AlarmConfigIndex OBJECT-TYPE
     SYNTAX SCinstance
     ACCESS read-only
     STATUS mandatory
     DESCRIPTION
	 "The index value which uniquely identifies the interface to
	 which this entry is applicable."
     ::= { bql613AlarmConfigEntry 1 }

bql613AlarmConfigIdentifier OBJECT-TYPE
     SYNTAX OBJECT IDENTIFIER
     ACCESS read-only
     STATUS mandatory
     DESCRIPTION
	 "The unique alarm identifier assigned to this alarm type.
	 The format of this identifier is an OBJECT IDENTIFIER that has
	 the following format: {iso(1) org(3) dod(6) internet(1)
	 private(4) enterprises(1) gdc(498) xxx(x) alarm(z) yyy(y) 
	 where xxx(x) is the administratively assigned family object 
	 identifier (z) is the object identifier for alarms in the family
	 defined MIB and yyy(y) is the administratively assigned alarm 
	 type identifier for this alarm."

     ::= { bql613AlarmConfigEntry 2 }


bql613AlarmThreshold OBJECT-TYPE
    SYNTAX INTEGER {
			thres10E03(1),
			thres10E04(2),
			thres10E05(3),
			thres10E06(4)
		}
	ACCESS  read-write
	STATUS  mandatory
	DESCRIPTION
		"This function sets/reads the Major or Minor BER alarm threshold criteria."
  ::= { bql613AlarmConfigEntry 3 }


--*****************************************************************************
--		      CONTROL TABLE FOR 2B1Q SC613
--*****************************************************************************
--
-- This table contains the SC613 control functions indexed by
-- SLDi.
--
-- This table uses SCinstance as SLDi where D and i are always 0.
--

bql613ControlTable OBJECT-TYPE
	SYNTAX	SEQUENCE OF Bql613ControlEntry
	ACCESS  not-accessible
	STATUS  mandatory
	DESCRIPTION
			"The GDC SC613 Control Table."
	::= { bql613 6 }

bql613ControlEntry OBJECT-TYPE
	SYNTAX	Bql613ControlEntry
	ACCESS  not-accessible
	STATUS  mandatory
	DESCRIPTION
			"An entry in the GDC SC613 Control table."
	INDEX	{ bql613ControlIndex }
	::= { bql613ControlTable 1 }

Bql613ControlEntry ::=
	SEQUENCE {
		  bql613ControlIndex	SCinstance,
		  bql613SoftReset	INTEGER,
		  bql613EraseConfig	INTEGER,
		  bql613FrontPanel	INTEGER,
		  bql613LEDStatus	OCTET STRING
		  }

bql613ControlIndex OBJECT-TYPE
	SYNTAX  SCinstance
	ACCESS  read-only
	STATUS  mandatory
	DESCRIPTION
	       "This object is the identifier of the SC613 Control table."
	::= { bql613ControlEntry 1 }

bql613SoftReset OBJECT-TYPE
	SYNTAX  INTEGER  {
			 normal(1),
			 reset(2)
			 }
        ACCESS  read-write
	STATUS  mandatory
	DESCRIPTION
                "Forces a soft reset on the network element.
                 The reset selection is write only. The normal
                 selection is read only."
	::= { bql613ControlEntry 2 }

bql613EraseConfig OBJECT-TYPE
	SYNTAX  INTEGER  {
			 normal(1),
			 erase(2)
			 }
        ACCESS  read-write
	STATUS  mandatory
	DESCRIPTION
		"Forces an erase of the stored configuration in the
                 network element. The erase selection is write only.
                 The normal selection is read only."
	::= { bql613ControlEntry 3 }

bql613FrontPanel OBJECT-TYPE
	SYNTAX  INTEGER {
			enable(1),
			disable(2)
			}
	ACCESS    read-write
	STATUS    mandatory
	DESCRIPTION
			"Object used to enable or disable the units front panel
			 switches."
	::= { bql613ControlEntry 4 }

bql613LEDStatus OBJECT-TYPE
	SYNTAX	OCTET STRING (SIZE (3))
	ACCESS  read-only
	STATUS  mandatory
	DESCRIPTION
			"The GDC SC613 front panel LED Status.
			 A value of 1 means on, 0 is off.
			 byte 1 bit 7 (1.7) - not used
			 1.6 - test mode
			 1.5 - alarm on
			 1.4 - loop 1 line loopback
			 1.3 - loop 1 send data transitions
			 1.2 - loop 1 receive data transitions
			 1.1 - loop 1 request to send
			 1.0 - loop 1 data carrier on

			 2.7 - not used
			 2.6 - not used
			 2.5 - not used
			 2.4 - loop 2 line loopback
			 2.3 - loop 2 send data transitions
			 2.2 - loop 2 receive data transitions
			 2.1 - loop 2 request to send
			 2.0 - loop 2 data carrier on

			 3.7 - not used
			 3.6 - not used
			 3.5 - not used
			 3.4 - loop 3 line loopback
			 3.3 - loop 3 send data transitions
			 3.2 - loop 3 receive data transitions
			 3.1 - loop 3 request to send
			 3.0 - loop 3 data carrier on"


	::= { bql613ControlEntry 5}



--*****************************************************************************
--           STATISTICS TABLE - CURRENT 15 MINUTE INTERVAL TABLE
--*****************************************************************************
--
-- The SC613 current table contains various statistics being
-- collected for the current 15 minute interval.
-- It is indexed by SLDi.
--
-- This table uses SCinstance as SLDi where i is Loop 1, 2, or 3.
--

bql613CurrentTable OBJECT-TYPE
             SYNTAX  SEQUENCE OF Bql613CurrentEntry
             ACCESS  not-accessible
             STATUS  mandatory
             DESCRIPTION
                "The SC613 Current table."
            ::= { bql613 7 }

bql613CurrentEntry OBJECT-TYPE
             SYNTAX  Bql613CurrentEntry
             ACCESS  not-accessible
             STATUS  mandatory
             DESCRIPTION
                "An entry in the SC613 Current table."
            INDEX   { bql613CurrentIndex }
            ::= { bql613CurrentTable 1 }

Bql613CurrentEntry ::=
         SEQUENCE {
                  bql613CurrentIndex	SCinstance,
                  bql613CurrentStats    OCTET STRING
                  }

bql613CurrentIndex OBJECT-TYPE
             SYNTAX  SCinstance
             ACCESS  read-only
             STATUS  mandatory
             DESCRIPTION
                "The index value which uniquely identifies  the
                SC613 interface to which this entry
		is applicable."
            ::= { bql613CurrentEntry 1 }

bql613CurrentStats OBJECT-TYPE
             SYNTAX  OCTET STRING (SIZE (12))
             ACCESS  read-only
             STATUS  mandatory
             DESCRIPTION
                "The number of Errored Seconds, Severely Errored Seconds &
		 Unavailable Errored Seconds  encountered  by
                an ISDN interface in the current 15 minute interval."
            ::= { bql613CurrentEntry 2 }

--*****************************************************************************
--           STATISTICS TABLE - 15 MINUTE INTERVAL TABLE
--*****************************************************************************
--
-- The SC613 Interval Table contains various statistics
-- collected by each ISDN Interface over the previous 24 hours of
-- operation.  The past 24 hours are broken into 96 completed
-- 15 minute intervals. This table is indexed by SLDi and Interval Number.
--
-- This table uses SCinstance as SLDi where i can be 1, 2, or 3 and Interval Number
-- is a number between 1 and 96. Where 1 is the most recently completed 15 minute
-- interval and 96 is the least recently completed 15 minute interval.
--

bql613IntervalTable OBJECT-TYPE
             SYNTAX  SEQUENCE OF Bql613IntervalEntry
             ACCESS  not-accessible
             STATUS  mandatory
             DESCRIPTION
                "The SC613 Interval table."
            ::= { bql613 8 }

bql613IntervalEntry OBJECT-TYPE
             SYNTAX  Bql613IntervalEntry
             ACCESS  not-accessible
             STATUS  mandatory
             DESCRIPTION
                "An entry in the SC613 Interval table."
            INDEX   { bql613IntervalIndex, bql613IntervalNumber }
            ::= { bql613IntervalTable 1 }

Bql613IntervalEntry ::=
         SEQUENCE {
                  bql613IntervalIndex	SCinstance,
                  bql613IntervalNumber	INTEGER,
                  bql613IntervalStats	OCTET STRING
		  }

bql613IntervalIndex OBJECT-TYPE
             SYNTAX  SCinstance
             ACCESS  read-only
             STATUS  mandatory
             DESCRIPTION
                "The index value which uniquely identifies  the
                ISDN  interface  to which this entry is applicable."
            ::= { bql613IntervalEntry 1 }

bql613IntervalNumber OBJECT-TYPE
             SYNTAX  INTEGER (1..96)
             ACCESS  read-only
             STATUS  mandatory
             DESCRIPTION
                "A number between 1 and 96, where 1 is the most
                recently completed 15 minute interval and 96 is
                the least recently completed 15 minute  inter-
                val   (assuming   that  all  96  intervals  are
                valid)."
            ::= { bql613IntervalEntry 2 }

bql613IntervalStats OBJECT-TYPE
             SYNTAX  OCTET STRING (SIZE (12))
             ACCESS  read-only
             STATUS  mandatory
             DESCRIPTION
                "The number of Errored Seconds, Severely Errored Seconds and
		 Unavailable Errored Seconds  encountered by a DS1  interface in one of the 
		 previous 96, individual 15 minute, intervals."
            ::= { bql613IntervalEntry 3 }

--*****************************************************************************
--           STATISTICS TABLE - TOTAL OF INTERVALS TABLE
--*****************************************************************************
--
-- The SC613 Total Table contains the cumulative sum of the
-- various statistics for the 24 hour period preceding the
-- current interval. It is indexed by SLDi.
--
-- This table uses SCinstance as SLDi where i is Loop 1, 2, or 3.
--

bql613TotalTable OBJECT-TYPE
             SYNTAX  SEQUENCE OF Bql613TotalEntry
             ACCESS  not-accessible
             STATUS  mandatory
             DESCRIPTION
                "The SC613 Total table.  24 hour interval."
            ::= { bql613 9 }

bql613TotalEntry OBJECT-TYPE
             SYNTAX  Bql613TotalEntry
             ACCESS  not-accessible
             STATUS  mandatory
             DESCRIPTION
                "An entry in the SC613 Total table."
            INDEX   { bql613TotalIndex }
            ::= { bql613TotalTable 1 }

Bql613TotalEntry ::=
         SEQUENCE {
                  bql613TotalIndex	SCinstance,
                  bql613TotalStats	OCTET STRING
                  }

bql613TotalIndex OBJECT-TYPE
             SYNTAX  SCinstance
             ACCESS  read-only
             STATUS  mandatory
             DESCRIPTION
                "The index value which uniquely identifies  the
                ISDN interface  to which this entry is applicable."
            ::= { bql613TotalEntry 1 }

bql613TotalStats OBJECT-TYPE
             SYNTAX  OCTET STRING (SIZE(12))
             ACCESS  read-only
             STATUS  mandatory
             DESCRIPTION
                "The number of Errored Seconds,Severely Errored Seconds & Unavailable Errored
		 Seconds  encountered  by  an ISDN interface in the previous 24 hour interval."
            ::= { bql613TotalEntry 2 }

--*****************************************************************************
--       LOOP Performance Interval Maintenance Table FOR SC613.
--*****************************************************************************
bql613IntervalMaintenanceTable OBJECT-TYPE
     	SYNTAX SEQUENCE OF Bql613IntervalMaintenanceEntry
     	ACCESS not-accessible
     	STATUS mandatory
    	DESCRIPTION
     		"The SC613  Loop Interval  Maintenance table. "
         ::= { bql613 10 }

bql613IntervalMaintenanceEntry OBJECT-TYPE
 	SYNTAX Bql613IntervalMaintenanceEntry
     	ACCESS not-accessible
     	STATUS mandatory
     	DESCRIPTION
     		"The SC613 Interval Maintenance table entry. "
     	INDEX { bql613IntervalMaintenanceIndex }
     	::= { bql613IntervalMaintenanceTable 1 }

Bql613IntervalMaintenanceEntry ::=
     	SEQUENCE {
     	    	 bql613IntervalMaintenanceIndex SCinstance,
         	 bql613ResetIntervals           INTEGER,
		 bql613NumberofValidIntervals   INTEGER,
		 bql613ResetMajorAlarm		INTEGER,
		 bql613ResetMinorAlarm		INTEGER
     		 }

bql613IntervalMaintenanceIndex OBJECT-TYPE
     	SYNTAX SCinstance
     	ACCESS read-only
     	STATUS mandatory
     	DESCRIPTION
     		"The index value which uniquely identifies the interface to
     		which this entry is applicable.  This has the form of a
     		SCinstance which defines the slot, line, drop, and interface,
		where is can be 1, 2, or 3."
     	::= { bql613IntervalMaintenanceEntry 1 }

bql613ResetIntervals OBJECT-TYPE
     	SYNTAX INTEGER {
     		       norm(1),
     		       reset(2)
     		       }
     	ACCESS read-write
     	STATUS mandatory
        DESCRIPTION " This variable is used to reset Loop performance intervals.
 		      When it is set to reset, the Loop performance tables are
 		      reset to zero."
     	::= { bql613IntervalMaintenanceEntry 2 }

bql613NumberofValidIntervals OBJECT-TYPE
     	SYNTAX INTEGER (0..96)
     	ACCESS read-only
     	STATUS mandatory
        DESCRIPTION " This variable is used to read the number of intervals collected.
		      Each interval is an increment of 15 minutes."
     	::= { bql613IntervalMaintenanceEntry 3 }

bql613ResetMajorAlarm	OBJECT-TYPE
	SYNTAX	INTEGER {
			reset(1),
			norm(2)
			}
     	ACCESS read-write 
     	STATUS mandatory
         DESCRIPTION " This variable is used to reset alarm per Loop basis."
     	::= { bql613IntervalMaintenanceEntry 4 }
 
bql613ResetMinorAlarm	OBJECT-TYPE
	SYNTAX	INTEGER {
			reset(1),
			norm(2)
			}
     	ACCESS read-write 
     	STATUS mandatory
         DESCRIPTION " This variable is used to reset alarm per Loop basis."
     	::= { bql613IntervalMaintenanceEntry 5 }


END
