-- CPU Version: V07.01.C00





ACMIB DEFINITIONS ::= BEGIN
 
               IMPORTS
                  MODULE-IDENTITY, OBJECT-TYPE, OBJECT-IDENTITY, 
                  NOTIFICATION-TYPE, Counter32, Integer32, IpAddress, 
                  TimeTicks,  enterprises
                      FROM SNMPv2-SMI
                  TEXTUAL-CONVENTION, DisplayString,
                  TimeStamp, RowStatus, DateAndTime
                      FROM SNMPv2-TC
                  MODULE-COMPLIANCE, OBJECT-GROUP
                      FROM SNMPv2-CONF
                  ifIndex, mib-2
                      FROM RFC1213-MIB;
 
lucent    OBJECT IDENTIFIER ::= { enterprises 1751 }
 
mibs      OBJECT IDENTIFIER ::= { lucent 2 }
 
acMIB           MODULE-IDENTITY
                    LAST-UPDATED "000204081230Z"
                    ORGANIZATION "Lucent Technologies, Inc."
                    CONTACT-INFO
                      "
                      "

                    DESCRIPTION
                     "Lucent Access Concentrator, Release 6.2"
                    ::= { mibs 18 }

          IntfIndex ::= TEXTUAL-CONVENTION
              STATUS    current
              DESCRIPTION "A INTEGER "
              SYNTAX Integer32

-- For new Connection status data type

        ConnFailureCause ::= TEXTUAL-CONVENTION
        STATUS  current
        DESCRIPTION     "General connection failure cause"
        SYNTAX  INTEGER {
                           none(1),
                           physical(2)
                        }


        FrConnFailureCause ::= TEXTUAL-CONVENTION
        STATUS  current
        DESCRIPTION "Frame Relay connection failure cause"
        SYNTAX  INTEGER {
                            none(1),
                            physical(2),
                            lmi(3),
                            dlci(4)
                        }

AtmConnFailureCause ::= TEXTUAL-CONVENTION
        STATUS  current
        DESCRIPTION  "ATM connection failure cause"
        SYNTAX  INTEGER {
                            none(1),
                            physical(2),
                            oamAis(3),
                            oamRdi(4)
                        }

-- End of adding new connection status data type

-- added imaGrpChannelEndState type

      ImaGrpChannelEndState ::= TEXTUAL-CONVENTION
        STATUS current
        DESCRIPTION "The current operational state of the Near-end or far-end IM
                     A Group State Machine."
        SYNTAX INTEGER  {
                            notConfigured(1),
                            startUp(2),
                            startUpAck(3),
                            cfgAbtUnsupportedM(4),
                            cfgAbtIncSymmetry(5),
                            cfgAbtOther(6),
                            insufficientLinks(7),
                            blocked(8),
                            operational(9)
                        }

          -- Groups in the Access Concentrator MIB

          sysConfig             OBJECT IDENTIFIER ::=   { acMIB 1 }

          equipConfig           OBJECT IDENTIFIER ::=   { acMIB 2 }

          channelConfig         OBJECT IDENTIFIER ::=   { acMIB 3 }

          intfConfig            OBJECT IDENTIFIER ::=   { acMIB 5 }

          connectionConfig      OBJECT IDENTIFIER ::=   { acMIB 6 }

          userServiceConfig     OBJECT IDENTIFIER ::=   { acMIB 7 }

          sysTraps              OBJECT IDENTIFIER ::=   { acMIB 8 }
          systemEvents          OBJECT IDENTIFIER ::=   { sysTraps 1 }
          moduleEvents          OBJECT IDENTIFIER ::=   { sysTraps 2 }
          interfaceEvents       OBJECT IDENTIFIER ::=   { sysTraps 3 }
          connectionEvents      OBJECT IDENTIFIER ::=   { sysTraps 4 }

          sysStatistics         OBJECT IDENTIFIER ::=   { acMIB 9 }

          equipStatistics       OBJECT IDENTIFIER ::=   { acMIB 10 }

          intfStatistics        OBJECT IDENTIFIER ::=   { acMIB 11 }
 
          connectionStatistics  OBJECT IDENTIFIER ::=   { acMIB 12 }
 
          ipAtmGroup            OBJECT IDENTIFIER ::=   { acMIB 13 }
 
          iispRouting           OBJECT IDENTIFIER ::=   { acMIB 14 }
 
          returnCode            OBJECT IDENTIFIER ::=   { acMIB 15 }
 
          sysControl            OBJECT IDENTIFIER ::=   { acMIB 16 }
 
          stratumConfig         OBJECT IDENTIFIER ::=   { acMIB 17 }
 
          cellTest              OBJECT IDENTIFIER ::=   { acMIB 18 }

          sysInfo               OBJECT IDENTIFIER ::=   { acMIB 19 }

          ethernetConfig        OBJECT IDENTIFIER ::=   { acMIB 20 }

          alarmConfig              OBJECT IDENTIFIER ::=   { acMIB 21 }

          sysTest               OBJECT IDENTIFIER ::=   { acMIB 22 }

          fwDriverSup           OBJECT IDENTIFIER ::=   { acMIB 23 }

          viprConfig            OBJECT IDENTIFIER ::=   { acMIB 24 }

          toneAnnceControl      OBJECT IDENTIFIER ::=   { acMIB 25 } 

          gr303Config           OBJECT IDENTIFIER ::=   { acMIB 26 }

          gr303Stats            OBJECT IDENTIFIER ::=   { acMIB 27 }

          atmTrunkingMIBObjects   OBJECT IDENTIFIER ::= { acMIB 28 }

          protectionGroup       OBJECT IDENTIFIER ::=   { acMIB 29 }

          h248Config            OBJECT IDENTIFIER ::=   { acMIB 30 }

          h248SysControl        OBJECT IDENTIFIER ::=   { acMIB 31 }

 
-- System Configuration Group sysConfig

siteName          OBJECT-TYPE
                  SYNTAX DisplayString (SIZE(20))
                  MAX-ACCESS read-write
                  STATUS current
                  DESCRIPTION "site name - ascii"
                  ::= { sysConfig 1 }

siteID            OBJECT-TYPE
                  SYNTAX OCTET STRING (SIZE(4))
                  MAX-ACCESS read-write
                  STATUS current
                  DESCRIPTION "site id - numerical"
                  ::= { sysConfig 2 }

siteEtherIpAddr   OBJECT-TYPE
                  SYNTAX IpAddress
                  MAX-ACCESS read-write
                  STATUS current
                  DESCRIPTION "ip address for ethernet access to the site
                               (switch)"
                  ::= { sysConfig 3 }

siteEtherIpMask OBJECT-TYPE
                SYNTAX IpAddress
                MAX-ACCESS read-write
                STATUS current
                DESCRIPTION "ip mask for ethernet access to the site
                               (switch)"
                 ::= { sysConfig 4 }

siteGatewayAddr OBJECT-TYPE
                SYNTAX IpAddress
                MAX-ACCESS read-write
                STATUS current
                DESCRIPTION "ip address for gateway access to the site
                              (switch)"
                 ::= { sysConfig 5 }

siteAtmAddrPrefix1 OBJECT-TYPE
                SYNTAX OCTET STRING (SIZE(13))
                MAX-ACCESS read-write
                STATUS current
                DESCRIPTION "This is one of the two atm address prefix 
                             of this switch. "
                ::= { sysConfig 6 }

siteAtmAddrUser1 OBJECT-TYPE
                SYNTAX OCTET STRING (SIZE(7))
                MAX-ACCESS read-write
                STATUS current
                DESCRIPTION "This is one of the two atm address user part 
                              of this switch."
                ::= { sysConfig 7 }

siteRemoteMgrAddr1 OBJECT-TYPE
                SYNTAX IpAddress
                MAX-ACCESS read-write
                STATUS current
                DESCRIPTION "remote manager IP Address, where TRAP will be
                             sent to."
                ::= { sysConfig 8 }

siteRemoteMgrAddr2 OBJECT-TYPE
                SYNTAX IpAddress
                MAX-ACCESS read-write
                STATUS current
                DESCRIPTION "remote manager IP Address, where TRAP will be
                              sent to."
                ::= { sysConfig 9 }

siteRemoteMgrAddr3 OBJECT-TYPE
                SYNTAX IpAddress
                MAX-ACCESS read-write
                STATUS current
                DESCRIPTION "remote manager IP Address, where TRAP will be
                              sent to."
                 ::= { sysConfig 10 }

siteRemoteMgrAddr4 OBJECT-TYPE
                SYNTAX IpAddress
                MAX-ACCESS read-write
                STATUS current
                DESCRIPTION "remote manager IP Address, where TRAP will be
                              sent to."
                 ::= { sysConfig 11 }

siteRemoteMgrAddr5 OBJECT-TYPE
                SYNTAX IpAddress
                MAX-ACCESS read-write
                STATUS current
                DESCRIPTION "remote manager IP Address, where TRAP will be
                             sent to."
                  ::= { sysConfig 12 }

siteMasterNodeAtmAddr1 OBJECT-TYPE
                SYNTAX OCTET STRING (SIZE(20))
                MAX-ACCESS read-write
                STATUS current
                DESCRIPTION "Master node atm address, where TRAP will be
                             sent to."
                ::= { sysConfig 13 }

siteMasterNodeAtmAddr2 OBJECT-TYPE
                SYNTAX OCTET STRING (SIZE(20))
                MAX-ACCESS read-write
                STATUS current
                DESCRIPTION "Master node atm address, where TRAP will be
                             sent to."
                ::= { sysConfig 14 }

siteEnhanceFeatures OBJECT-TYPE
                SYNTAX INTEGER (1..255)
                MAX-ACCESS read-only
                STATUS current
                DESCRIPTION "enhancement features capability -
                              number consists of a sum to represent
                              the following:
                                 1: securedAtm
                                 2: isdn
                                 4: frameRelay "
                ::= { sysConfig 15 }

siteTrapDialOutFeature  OBJECT-TYPE
                SYNTAX INTEGER {
                                disabled(1),
                                dialTerminal(2),
                                dialBeeper(3)
                                }
                MAX-ACCESS read-write
                STATUS current
                DESCRIPTION "Enables the dialing out to a remote terminal
                             or beeper for trap notification."
                ::= { sysConfig 16 }

siteTrapDialOutPhoneNum OBJECT-TYPE
               SYNTAX DisplayString (SIZE(20))
               MAX-ACCESS read-write
               STATUS current
               DESCRIPTION "Phone number of the terminal to dial when
                             trap notifications are phoned out"
                ::= { sysConfig 17 }

siteTrapDialOutBeeperData OBJECT-TYPE
                SYNTAX DisplayString (SIZE(20))
                MAX-ACCESS read-write
                STATUS current
                DESCRIPTION "Data (phone digits) to send to beeper if the
                             dialBeeper option is selected."
                ::= { sysConfig 18 } 

siteDateAndTime OBJECT-TYPE
                SYNTAX DateAndTime
                MAX-ACCESS read-write
                STATUS current
                DESCRIPTION "Current date and time: 11 octets
                             octet#  contents            range
                             ------  --------            -----
                               1-2   year                0..65536
                                3    month               1..12
                                4    day                 1..31
                                5    hour                0..23
                                6    minutes             0..59
                                7    seconds      0..60(60=leap second)
                                8    deci-seconds         0..9
                                9    direction from UTC  '+'/'-'
                               10    hours from UTC      0..11
                               11    minutes from UTC    0..59"
                ::= { sysConfig 19 }

siteSoftwareVersion OBJECT-TYPE
                SYNTAX DisplayString (SIZE(15))
                MAX-ACCESS read-only
                STATUS current
                DESCRIPTION "Constant value representing the version number
                             of the current software."
                ::= { sysConfig 20 }


--        Objects added for NEC
csTcpServerIpAddress OBJECT-TYPE
                SYNTAX IpAddress
                MAX-ACCESS read-write
                STATUS current
                DESCRIPTION "The IP address of CS"
                ::= { sysConfig 21 }

csTcpServerPortNumber OBJECT-TYPE
                SYNTAX INTEGER ( 1025..65535 )
                MAX-ACCESS read-write
                STATUS current
                DESCRIPTION "The Port Number used for communication
                with CS.
                NOTE: Port # 5000 and 6000 have been 
                              reservered for AC products.
                              DO NOT USED THEM !!! "
                DEFVAL { 1025 }
                ::= { sysConfig 22 }

keepAliveTimer  OBJECT-TYPE
                SYNTAX INTEGER ( 0..999999999 )
                MAX-ACCESS read-write
                STATUS current
                DESCRIPTION " keep alive timer can be set inbetween
                        0 and 999999999"
                ::= { sysConfig 23 }

inactiveTimer   OBJECT-TYPE
                SYNTAX INTEGER( 0..999999999 )
                MAX-ACCESS read-write
                STATUS current
                DESCRIPTION " inactive timer can be set inbetween
                        0 and 999999999"
                ::= { sysConfig 24 }


siteMasterNodeAddrType1 OBJECT-TYPE
                SYNTAX INTEGER {
                                nsap(1),
                                e164(2),
                                e164nsap(3)
                               }
                MAX-ACCESS read-write
                STATUS current
                DESCRIPTION "Type of address specified for master node atm 
                             address, where TRAP will be sent to."
                DEFVAL { nsap }
                ::= { sysConfig 25 }

siteMasterNodeAddrType2 OBJECT-TYPE
                SYNTAX INTEGER {
                                nsap(1),
                                e164(2),
                                e164nsap(3)
                               }
                MAX-ACCESS read-write
                STATUS current
                DESCRIPTION "Type of address specified for master node atm 
                             address, where TRAP will be sent to."
                DEFVAL { nsap }
                ::= { sysConfig 26 }

inBandPrimaryIpAddress OBJECT-TYPE
                SYNTAX IpAddress
                MAX-ACCESS read-write
                STATUS current
                DESCRIPTION "IP address of the switch when the switch is 
                             accessed over the primary in-band connection."
                ::= { sysConfig 27 }

inBandPrimaryIpMask OBJECT-TYPE
                SYNTAX OCTET STRING (SIZE(4))
                MAX-ACCESS read-write
                STATUS current
                DESCRIPTION "IP address subnet mask of the primary in-band
                             management IP address."
                ::= { sysConfig 28 }

inBandBackupIpAddress OBJECT-TYPE
                SYNTAX IpAddress
                MAX-ACCESS read-only
                STATUS current
                DESCRIPTION "IP address of the switch when the switch is 
                          accessed over the secondary in-band connection."
                ::= { sysConfig 29 }

inBandBackupIpMask OBJECT-TYPE
               SYNTAX OCTET STRING (SIZE(4))
               MAX-ACCESS read-only
               STATUS current
               DESCRIPTION "IP address subnet mask of the secondary in-band
                            management IP address."
               ::= { sysConfig 30 }

inBandSvcConnectionsAllowed OBJECT-TYPE
                SYNTAX INTEGER {
                                enabled(1),
                                disabled(2)
                               }
                MAX-ACCESS read-write
                STATUS current
                DESCRIPTION "Flag indicating whether in-band management should
                             be supported over SVCs."
                DEFVAL { disabled }
                ::= { sysConfig 31 }

atmArpServer        OBJECT-TYPE
                SYNTAX INTEGER {
                                enabled(1),
                                disabled(2)
                               }
                MAX-ACCESS read-write
                STATUS current
                DESCRIPTION "This flag indicates if this switch is an ATM ARP 
                             server."
                DEFVAL { disabled }
                ::= { sysConfig 32 }

atmArpServerRemoteConnectionType OBJECT-TYPE
                SYNTAX INTEGER {
                                svc(1),
                                pvc(2)
                               }
                MAX-ACCESS read-write
                STATUS current
                DESCRIPTION "When this switch is not the ATM ARP server,
                             indicates whether the connection to the ATM ARP 
                             server uses SVCs or PVCs."
                DEFVAL { svc }
                ::= { sysConfig 33 }

atmArpServerRemoteAtmAddress OBJECT-TYPE
                SYNTAX OCTET STRING (SIZE(20))
                MAX-ACCESS read-write
                STATUS current
                DESCRIPTION "The ATM address of the ATM ARP server when this 
                             switch is not the ATM ARP server and the 
                             connection to the ATM ARP server uses SVCs."
                ::= { sysConfig 34 }

atmArpServerRemoteAddrType OBJECT-TYPE
                SYNTAX INTEGER {
                                nsap(1),
                                e164(2),
                                e164nsap(3)
                               }
                MAX-ACCESS read-write
                STATUS current
                DESCRIPTION "The format of the ATM address of the ATM ARP 
                             server when this switch is not the ATM ARP server 
                             and the connection to the ATM ARP server uses 
                             SVCs."
                DEFVAL { nsap }
                ::= { sysConfig 35 }

atmArpServerRemoteIpAddress OBJECT-TYPE
                SYNTAX IpAddress
                MAX-ACCESS read-write
                STATUS current
                DESCRIPTION "The IP address of the ATM ARP server when this 
                             switch is not the ATM ARP server and the 
                             connection to the ATM ARP server uses PVCs."
                ::= { sysConfig 36 }

atmArpServerRemoteIpMask OBJECT-TYPE
                SYNTAX OCTET STRING (SIZE(4))
                MAX-ACCESS read-write
                STATUS current
                DESCRIPTION "The IP address subnet mask of the ATM ARP server
                                  when this switch is not the ATM ARP server and the 
                                  connection to the ATM ARP server uses PVCs."
                ::= { sysConfig 37 }

atmArpServerEncapsulation OBJECT-TYPE
                SYNTAX INTEGER {
                                llc-snap(1)
                                         }
                MAX-ACCESS read-only
                STATUS current
                DESCRIPTION "The type of encapsulation used for IP packets over
                                  ATM in in-band management."
                DEFVAL { llc-snap }
                ::= { sysConfig 38 }



siteFallbackSoftwareVersion OBJECT-TYPE
                SYNTAX DisplayString (SIZE(15))
                MAX-ACCESS read-only
                STATUS current
                DESCRIPTION "Constant value representing the version number
                             of the software to fallback to."
                ::= { sysConfig 41 }

siteUpgradeSoftwareVersion OBJECT-TYPE
                SYNTAX DisplayString (SIZE(15))
                MAX-ACCESS read-only
                STATUS current
                DESCRIPTION "Constant value representing the version number
                             of the software to upgrade to."
                ::= { sysConfig 42 }

siteSwitchIpAddr OBJECT-TYPE
                SYNTAX IpAddress
                MAX-ACCESS read-write
                STATUS current
                DESCRIPTION "IP Address for communication with the switch, 
                             regardless of which cpu is primary."
                ::= { sysConfig 43 }


muxTcpType OBJECT-TYPE
                SYNTAX INTEGER {
                                server(1),
                                client(2)
                               }
                MAX-ACCESS read-write
                STATUS current
                DESCRIPTION "The type of mux TCP."
                DEFVAL { client }
                ::= { sysConfig 44 }


loopbackLocationID OBJECT-TYPE
                SYNTAX OCTET STRING (SIZE(16))
                MAX-ACCESS read-write
                STATUS current
                DESCRIPTION "ID of the ATM Node where the loopback is to occur."
                DEFVAL { 'FFFFFFFFFFFFFFFFFFFFFFFFFFFFFFFF'H }
                ::= { sysConfig 45 }

oamDebouncingPeriod OBJECT-TYPE
                SYNTAX INTEGER (1000..300000)
                MAX-ACCESS read-write
                STATUS current
                DESCRIPTION "Debouncing period in milli seconds for clearing
                             AIS/RDI state."
                DEFVAL { 3000 }
                ::= { sysConfig 46 }

svcPointToPointCalls OBJECT-TYPE
                SYNTAX Integer32 
                MAX-ACCESS read-write
                STATUS current
                DESCRIPTION "The total number of SVC point-to-point calls, 
                                both legs are SVCs."
               DEFVAL { 2000 }
                ::= { sysConfig 47 }

svcPointToMultiPointCalls OBJECT-TYPE
                SYNTAX Integer32 
                MAX-ACCESS read-write
                STATUS current
                DESCRIPTION "The total number of SVC point-to-multipoint 
                                calls, both legs are SVCs."
               DEFVAL { 2000 }
                ::= { sysConfig 48 }

svcPointToMultiPointParties OBJECT-TYPE
                SYNTAX Integer32 
                MAX-ACCESS read-write
                STATUS current
                DESCRIPTION "The total number of parties on SVC 
                        point-to-multipoint calls, both legs are SVCs."
               DEFVAL { 2000 }
                ::= { sysConfig 49 }

spvcCePointToPointCalls OBJECT-TYPE
                SYNTAX Integer32 
                MAX-ACCESS read-write
                STATUS current
                DESCRIPTION "The total number of circuit emulation SPVC 
                                calls."
               DEFVAL { 2000 }
                ::= { sysConfig 50 }

spvcTePointToPointCalls OBJECT-TYPE
                SYNTAX Integer32 
                MAX-ACCESS read-write
                STATUS current
                DESCRIPTION "The total number of terminal emulation SPVC 
                                calls."
               DEFVAL { 2000 }
                ::= { sysConfig 51 }

spvcAtmPointToPointCalls OBJECT-TYPE
                SYNTAX Integer32 
                MAX-ACCESS read-write
                STATUS current
                DESCRIPTION "The total number of ATM SPVC calls."
                DEFVAL { 2000 }
                ::= { sysConfig 52 }

cgApiCirEmCirEmPvcCalls OBJECT-TYPE
                SYNTAX Integer32 
                MAX-ACCESS read-write
                STATUS current
                DESCRIPTION "The total number of circuit emulation to 
                                circuit emulation calls for Sapphire API."
               DEFVAL { 0 }
                ::= { sysConfig 53 }

cgApiCirEmAtmPvcCalls OBJECT-TYPE
                SYNTAX Integer32 
                MAX-ACCESS read-write
                STATUS current
                DESCRIPTION "The total number of circuit emulation to ATM 
                                calls for Sapphire APIs"
                DEFVAL { 0 }
                ::= { sysConfig 54 }

cgApiAtmAtmPvcCalls OBJECT-TYPE
                SYNTAX Integer32 
                MAX-ACCESS read-write
                STATUS current
                DESCRIPTION "The total number of ATM to ATM calls for 
                                Sapphire APIs"
                DEFVAL { 0 }
                ::= { sysConfig 55 }

cgApiPointToPointSvcCalls OBJECT-TYPE
                SYNTAX Integer32 
                MAX-ACCESS read-write
                STATUS current
                DESCRIPTION "The total number of point-to-point SVC calls 
                        for Sapphire APIs"
               DEFVAL { 0 }
                ::= { sysConfig 56 }

cgApiPointToMultiPointSvcCalls OBJECT-TYPE
                SYNTAX Integer32 
                MAX-ACCESS read-write
                STATUS current
                DESCRIPTION "The total number of point-to-multipoint SVC 
                                calls for Sapphire APIs"
                DEFVAL { 0 }
                ::= { sysConfig 57 }

cgApiPointToMultiPointParties OBJECT-TYPE
                SYNTAX Integer32 
                MAX-ACCESS read-write
                STATUS current
                DESCRIPTION "The total number of parties for Sapphire APIs"
                DEFVAL { 0 }
                ::= { sysConfig 58 }

callContrlResAllocApply OBJECT-TYPE
                SYNTAX INTEGER (0..1)
                MAX-ACCESS read-write
                STATUS current
                DESCRIPTION "0 - not apply, 1 - apply the call control resouce
                             allocation modification"
                DEFVAL { 0 }
                ::= { sysConfig 59 } 

callContrlResAllocUsage OBJECT-TYPE
                SYNTAX Integer32 
                MAX-ACCESS read-only
                STATUS current
                DESCRIPTION "The percentage of memory usage for call 
                                control resource."
                DEFVAL { 100 }
                ::= { sysConfig 60 } 

siteFirmwarePatchNumber OBJECT-TYPE
                SYNTAX Integer32
                MAX-ACCESS read-only
                STATUS current
                DESCRIPTION "Constant value representing the patch number
                             of the patch release."
                ::= { sysConfig 61 }


spvcActRestartAll OBJECT-TYPE
                SYNTAX INTEGER  {
                        spvcActAtmRestartAll(1),
                        spvcActCeRestartAll(2),
                        spvcActTeRestartAll(3),
                    spvcActFrRestartAll(4)
                }
                MAX-ACCESS read-write
                STATUS current
                DESCRIPTION
                        "Restart all ATM-to-ATM,CE-to-CE,TE-to-TE,FR-to-FR active 
                        unconnected spvc connections"
                DEFVAL { spvcActAtmRestartAll }
                ::= { sysConfig 62 }

cgSvcCutThroughOption OBJECT-TYPE
                SYNTAX INTEGER  {
                    cgSvcAcImplicitCutThrough(1),
                    cgSvcCgExplicitCutThrough(2)
                }
                MAX-ACCESS read-write
                STATUS current
                DESCRIPTION
                " Cut Through option for SVC calls going to CG 
                  cgSvcAcImplicitCutThrough (1) - AC implicitly cuts
                  through.
                  cgSvcCgExplicitCutThrough (2) - CG sends explcit 
                  PATH_ETABLISH_REQ to request AC to cut through."
       DEFVAL { cgSvcAcImplicitCutThrough } 
                ::= { sysConfig 63 }

sgApiCirEmEndPoints OBJECT-TYPE
                SYNTAX Integer32
                MAX-ACCESS read-write
                STATUS current
                DESCRIPTION "The total number of circuit emulation
                        endpoints for Sapphire API."
                DEFVAL { 0 }
                ::= { sysConfig 64 }

sgApiAtmSvcEndPoints OBJECT-TYPE
                SYNTAX Integer32 
                MAX-ACCESS read-write
                STATUS current
                DESCRIPTION "The total number of ATM SVC
                        endpoints for Sapphire APIs"
                DEFVAL { 0 }
                ::= { sysConfig 65 }

siteRemoteMgrSrcAddr1 OBJECT-TYPE
                SYNTAX INTEGER{
                        ethernet(1),
                        ibm(2),
                        interface(3)
                }
                MAX-ACCESS read-write
                STATUS current
                DESCRIPTION "This is the source IP address used in all traps sent to remote manager"
                DEFVAL { interface }
                ::= { sysConfig 66 }

siteRemoteMgrSrcAddr2 OBJECT-TYPE
                SYNTAX INTEGER{
                        ethernet(1),
                        ibm(2),
                        interface(3)
                }
                MAX-ACCESS read-write
                STATUS current
                DESCRIPTION "This is the source IP address used in all traps sent to remote manager"
                DEFVAL { interface }
                ::= { sysConfig 67 }

siteRemoteMgrSrcAddr3 OBJECT-TYPE
                SYNTAX INTEGER{
                        ethernet(1),
                        ibm(2),
                        interface(3)
                }
                MAX-ACCESS read-write
                STATUS current
                DESCRIPTION "This is the source IP address used in all traps sent to remote manager"
                DEFVAL { interface }
                ::= { sysConfig 68 }

siteRemoteMgrSrcAddr4 OBJECT-TYPE
                SYNTAX INTEGER{
                        ethernet(1),
                        ibm(2),
                        interface(3)
                }
                MAX-ACCESS read-write
                STATUS current
                DESCRIPTION "This is the source IP address used in all traps sent to remote manager"
                DEFVAL { interface }
                ::= { sysConfig 69 }

siteRemoteMgrSrcAddr5 OBJECT-TYPE
                SYNTAX INTEGER{
                        ethernet(1),
                        ibm(2),
                        interface(3)
                }
                MAX-ACCESS read-write
                STATUS current
                DESCRIPTION "This is the source IP address used in all traps sent to remote manager"
                DEFVAL { interface }
                ::= { sysConfig 70 }

spvcFrPointToPointCalls OBJECT-TYPE
                SYNTAX Integer32
                MAX-ACCESS read-write
                STATUS current
                DESCRIPTION "The total number of FR SPVC calls."
                DEFVAL { 1000 }
                ::= { sysConfig 71 }

inBandAppAtmAddress OBJECT-TYPE
                SYNTAX OCTET STRING (SIZE(20))
                MAX-ACCESS read-write
                STATUS current
                DESCRIPTION "The ATM address of the inBand application"
                ::= { sysConfig 72 }

inBandAppAtmAddrType OBJECT-TYPE
                SYNTAX INTEGER {
                                nsap(1),
                                e164(2),
                                e164nsap(3)
                               }
                MAX-ACCESS read-write
                STATUS current
                DESCRIPTION "The format of the ATM address of the inBand
                             application"
                DEFVAL { nsap }
                ::= { sysConfig 73 }

atmArpServer2RemoteAtmAddress OBJECT-TYPE
                SYNTAX OCTET STRING (SIZE(20))
                MAX-ACCESS read-write
                STATUS current
                DESCRIPTION "The ATM address of the ATM ARP server when 
this
                             switch is not the ATM ARP server and the
                             connection to the ATM ARP server uses SVCs."
                ::= { sysConfig 74 }

atmArpServer2RemoteAddrType OBJECT-TYPE
                SYNTAX INTEGER {
                                nsap(1),
                                e164(2),
                                e164nsap(3)
                               }
                MAX-ACCESS read-write
                STATUS current
                DESCRIPTION "The format of the ATM address of the ATM ARP
                             server when this switch is not the ATM ARP 
server
                             and the connection to the ATM ARP server uses
                             SVCs."
                DEFVAL { nsap }
                ::= { sysConfig 75 }

tasmMaxAnnceDiskSpace OBJECT-TYPE
                SYNTAX INTEGER  (1..36)
                MAX-ACCESS read-write
                STATUS current
                DESCRIPTION "Specifies the maximum disk size in MBytes
                             reserved for compressed announcements on
                             the CPU hard disk."
                DEFVAL { 20 }
                ::= { sysConfig 76 }

tasmMaxAnnce OBJECT-TYPE
                SYNTAX INTEGER  (1..10000)
                MAX-ACCESS read-write
                STATUS current
                DESCRIPTION "Specifies the maximum number of tones and
                             announcements that can be played simultaneously.
                             This will depend on the number of control blocks 
                             allocated for collecting digits and for line 
                             tests as the memory comes from the same pool. 
                             The tasmControlBlockResAllocUsage field will be 
                             updated to indicate this."
                DEFVAL { 1 }
                ::= { sysConfig 77 }

tasmMaxStdTones OBJECT-TYPE
                SYNTAX INTEGER  (1..10)
                MAX-ACCESS read-write
                STATUS current
                DESCRIPTION "Specifies the maximum number of
                             tones that can be played simutaneously. This field
                             has been obsoleted for optimisation of resources."
                DEFVAL { 10 }
                ::= { sysConfig 78 }

tasmMemoryAction OBJECT-TYPE
                SYNTAX INTEGER {
                                re-initialize(1)
                                }
                MAX-ACCESS read-write
                STATUS current
                DESCRIPTION "Specifies the action to be performed 
                        on the memory in the TASM card used for
                        storing announcements."
                DEFVAL { 1 }
                ::= { sysConfig 79 }

--
-- Announcement configuration for the management of announcement files in 
-- the system.
--

tasAnnceTable OBJECT-TYPE
                SYNTAX SEQUENCE OF TasAnnceEntry
                MAX-ACCESS not-accessible
                STATUS current
                DESCRIPTION "Table of announcements for the Tone
                             Announcement server ."
                ::= { sysConfig 80 }

tasAnnceEntry OBJECT-TYPE
                SYNTAX TasAnnceEntry
                MAX-ACCESS not-accessible
                STATUS current
                DESCRIPTION "Row definition for Tone Announcement server
                             table announcement entries."
                INDEX { tasAnnceId }
                ::= { tasAnnceTable 1 }

TasAnnceEntry ::= SEQUENCE {
                tasAnnceId                  INTEGER,
                tasAnnceType                INTEGER,
                tasAnnceCmprsType           INTEGER,
                tasAnnceValid               INTEGER,
                tasAnnceDescription         DisplayString
                }

tasAnnceId OBJECT-TYPE
                SYNTAX INTEGER (1..100)
                MAX-ACCESS not-accessible
                STATUS current
                DESCRIPTION "Announcement ID."
                ::= { tasAnnceEntry 1 }

tasAnnceType OBJECT-TYPE
                SYNTAX INTEGER {
                                voice(1),
                                toneVoice(2),
                                userTones(3),
                                music(4),
                                musicVoice(5),
                                toneMusic(6)
                               }
                MAX-ACCESS read-only
                STATUS current
                DESCRIPTION "The type of this announcement:
                             voice indicates it is a pure voice
                             announcement file.
                             toneVoice indicates it is a file with tones
                             at the beginning followed by voice.
                             userTones indicates it is a file with purely
                             user generated tones.
                             music indicates it is a file with pure music.
                             musicVoice indicates it is a file with music
                             at the beginning followed by voice.
                             toneMusic indicates it is a file with tones
                             at the beginning followed by music."
                ::= { tasAnnceEntry 2 }

tasAnnceCmprsType OBJECT-TYPE
                SYNTAX INTEGER {
                                uncompressed(1),
                                compress8k(2),
                                compress16k(3),
                                compress32k(4)
                               }
                MAX-ACCESS read-only
                STATUS current
                DESCRIPTION "The type of compression used for
                             storing this announcement:
                             compress8k indicates 8k compression algorithm
                             should be used. compress16k indicates 16k 
                             compression algorithm should be used.
                             compress32k indicates 32k compression algorithm
                             should be used."
                ::= { tasAnnceEntry 3 }

tasAnnceValid OBJECT-TYPE
                SYNTAX INTEGER {
                                good(1),
                                olderVersion(2),
                                corrupted(3)
                               }
                MAX-ACCESS read-only
                STATUS current
                DESCRIPTION "Indicates the condition of this announcement,
                             whether it is good, it is stored using an older
                             compression algorithm, or it is corrupted."
                ::= { tasAnnceEntry 4 }

tasAnnceDescription OBJECT-TYPE
                SYNTAX DisplayString (SIZE(255))
                MAX-ACCESS read-only
                STATUS current
                DESCRIPTION "Description for this announcement."
                ::= { tasAnnceEntry 5 }

--
-- Configuration for the standard tones in the system.
--
tasToneConfigTable OBJECT-TYPE
                SYNTAX SEQUENCE OF TasToneConfigEntry
                MAX-ACCESS not-accessible
                STATUS current
                DESCRIPTION "Table of standard physical tone attributes"
                ::= { sysConfig 81 }

tasToneConfigEntry OBJECT-TYPE
                SYNTAX TasToneConfigEntry
                MAX-ACCESS not-accessible
                STATUS current
                DESCRIPTION "Row definition for TASM announcement entries."
                INDEX { tasToneId }
                ::= { tasToneConfigTable 1 }

TasToneConfigEntry ::= SEQUENCE {
                tasToneId                   INTEGER,
                tasToneType                 INTEGER,
                tasToneFirstFreq            INTEGER,
                tasToneSecondFreq           INTEGER,
                tasToneThirdFreq            INTEGER,
                tasToneOnTime               INTEGER,
                tasToneOffTime              INTEGER,
                tasToneLevel                INTEGER
                }

tasToneId OBJECT-TYPE
                SYNTAX INTEGER (1..10)
                MAX-ACCESS not-accessible
                STATUS current
                DESCRIPTION "Tone ID."
                ::= { tasToneConfigEntry 1 }

tasToneType OBJECT-TYPE
                SYNTAX INTEGER {
                                dialTone(1),
                                reorderTone(2),
                                sitTone(3)
                               }
                MAX-ACCESS read-write
                STATUS current
                DESCRIPTION "The type of this standard tone."
                ::= { tasToneConfigEntry 2 }

tasToneFirstFreq OBJECT-TYPE
                SYNTAX Integer32
                MAX-ACCESS read-write
                STATUS current
                DESCRIPTION "The first frequency value for this tone."
                ::= { tasToneConfigEntry 3 }

tasToneSecondFreq OBJECT-TYPE
                SYNTAX Integer32
                MAX-ACCESS read-write
                STATUS current
                DESCRIPTION "The second frequency value for this tone."
                ::= { tasToneConfigEntry 4 }

tasToneThirdFreq OBJECT-TYPE
                SYNTAX Integer32
                MAX-ACCESS read-write
                STATUS current
                DESCRIPTION "The third frequency value for this tone."
                ::= { tasToneConfigEntry 5 }

tasToneOnTime OBJECT-TYPE
                SYNTAX Integer32
                MAX-ACCESS read-write
                STATUS current
                DESCRIPTION "The on time in the tone duty cycle."
                ::= { tasToneConfigEntry 6 }

tasToneOffTime OBJECT-TYPE
                SYNTAX Integer32
                MAX-ACCESS read-write
                STATUS current
                DESCRIPTION "The off time in the tone duty cycle."
                ::= { tasToneConfigEntry 7 }

tasToneLevel OBJECT-TYPE
                SYNTAX Integer32
                MAX-ACCESS read-write
                STATUS current
                DESCRIPTION "The level of this tone in dBm."
                ::= { tasToneConfigEntry 8 }


atmArpServerAtmAddr  OBJECT-TYPE
                SYNTAX OCTET STRING (SIZE(20))
                MAX-ACCESS read-write
                STATUS current
                DESCRIPTION "The ATM address of the ATM ARP server when this
                             switch is configured as the ATM ARP server ."
                ::= { sysConfig 82 }

atmArpServerAddrType OBJECT-TYPE
                SYNTAX INTEGER {
                                nsap(1),
                                e164(2),
                                e164nsap(3)
                               }
                MAX-ACCESS read-write
                STATUS current
                DESCRIPTION "The format of the ATM address of the ATM ARP
                             server when this switch is  configured as the 
                             ATM ARP server."
                DEFVAL { nsap }
                ::= { sysConfig 83 }

spvcPointToMultiPointCalls OBJECT-TYPE
                SYNTAX Integer32 
                MAX-ACCESS read-write
                STATUS current
                DESCRIPTION "The total number of SPVC point-to-multipoint 
                                calls"
               DEFVAL { 500 }
                ::= { sysConfig 84 }

spvcPointToMultiPointParties OBJECT-TYPE
                SYNTAX Integer32 
                MAX-ACCESS read-write
                STATUS current
                DESCRIPTION "The total number of parties on SPVC 
                            point-to-multipoint calls."
               DEFVAL { 1000 }
                ::= { sysConfig 85 }


consoleIPAddr1 OBJECT-TYPE
                SYNTAX IpAddress
                MAX-ACCESS read-write
                STATUS current
                DESCRIPTION "console IP Address, where TRAP will be
                             sent."
                ::= { sysConfig 86 }

consoleIPAddr2 OBJECT-TYPE
                SYNTAX IpAddress
                MAX-ACCESS read-write
                STATUS current
                DESCRIPTION "console IP Address, where TRAP will be
                             sent."
                ::= { sysConfig 87 }

consoleIPAddr3 OBJECT-TYPE
                SYNTAX IpAddress
                MAX-ACCESS read-write
                STATUS current
                DESCRIPTION "console IP Address, where TRAP will be
                             sent."
                ::= { sysConfig 88 }


consolePort1    OBJECT-TYPE
                SYNTAX INTEGER (1..32767)
                MAX-ACCESS read-write
                STATUS current
                DESCRIPTION "port number on host where TRAP will be
                                sent"
                ::= { sysConfig 89 }

consolePort2    OBJECT-TYPE
                SYNTAX INTEGER (1..32767)
                MAX-ACCESS read-write
                STATUS current
                DESCRIPTION "port number on host where TRAP will be
                                sent"
                ::= { sysConfig 90 }

consolePort3    OBJECT-TYPE
                SYNTAX INTEGER (1..32767)
                MAX-ACCESS read-write
                STATUS current
                DESCRIPTION "port number on host where TRAP will be
                                sent"
                ::= { sysConfig 91 }

featureTable OBJECT-TYPE
             SYNTAX SEQUENCE OF FeatureEntry
                MAX-ACCESS not-accessible
                STATUS current
                DESCRIPTION "Table of features to be turned on/off"
                ::= { sysConfig 92 }

featureEntry OBJECT-TYPE
             SYNTAX FeatureEntry
             MAX-ACCESS not-accessible
             STATUS current
             DESCRIPTION "Row definition for feature table"
             INDEX { featureId }
             ::= { featureTable 1 }

FeatureEntry ::= SEQUENCE {
                featureId                  INTEGER,
                featureStaticMem           Integer32,
                featureDesiredStatus       INTEGER,
                featureCurrentStatus       INTEGER
             }


featureId    OBJECT-TYPE
             SYNTAX INTEGER {
               pnni(1),
               gr303(2),
               vipr(3),
	       h248(4)
             }
             MAX-ACCESS not-accessible
             STATUS current
             DESCRIPTION "feature ID."
             ::= { featureEntry 1 }

featureStaticMem OBJECT-TYPE
             SYNTAX Integer32
             MAX-ACCESS read-only
             STATUS current
             DESCRIPTION "Minimum memory required to run this feature"
             ::= { featureEntry 2 }

featureDesiredStatus OBJECT-TYPE
             SYNTAX INTEGER {
                 enable (1),
                 disable (2)
             }
             MAX-ACCESS read-write
             STATUS current
             DESCRIPTION "To enable / disable this feature"
             ::= { featureEntry 3 }

featureCurrentStatus OBJECT-TYPE
             SYNTAX INTEGER {
                  enabled (1),
                  disabled (2)
             }
             MAX-ACCESS read-only
             STATUS current
             DESCRIPTION "This feature is enabled / disabled"
             ::= { featureEntry 4 }

mediaGatewayControlType OBJECT-TYPE
             SYNTAX INTEGER {
                            sapphire (1),
                            h248 (2)
                            }
             MAX-ACCESS read-write 
             STATUS current
             DESCRIPTION "Choose to use H.248 protocol or
                        sapphire protocol"
             ::= { sysConfig 93 }


--DSP resource Table 

dspResourceTable  OBJECT-TYPE
     	    SYNTAX SEQUENCE OF DspResourceEntry
  	    MAX-ACCESS not-accessible	
            STATUS current
            DESCRIPTION "Table of DSP resource usage for the whole system." 
            ::= { sysConfig 94 }

dspResourceEntry  OBJECT-TYPE
            SYNTAX  DspResourceEntry
            MAX-ACCESS not-accessible
            STATUS current
            DESCRIPTION  "Row definition for DSP resource usage
                          table entries."
            INDEX { dspResourceId }
            ::= { dspResourceTable 1 }

DspResourceEntry  ::= SEQUENCE {
                         dspResourceId            INTEGER,
                         dspResourceAvail         Integer32,
                         dspResourceUsed          Integer32,
                         dspResourceUsedFailed    Integer32,
                         dspResourceAvailFailed   Integer32               
		                }

dspResourceId  OBJECT-TYPE
            SYNTAX INTEGER  {
                         algoSet1-aal2-non-multiplexed(1),
                         algoSet1-aal2-std(2),
                         algoSet2-aal2-non-multiplexed(3),
                         algoSet2-aal2-std(4),
                         algoSet3-aal2-non-multiplexed(5),
                         algoSet3-aal2-std(6),
                         algoSet5-aal1(7),
                         algoSet6-aal2-std(8),
                         tone-annce-cas(9),
                         tone-annce-tas(10)
                               }
             MAX-ACCESS not-accessible
             STATUS current
             DESCRIPTION "DSP resource type enumerations. The algoSets describe 
                          the mode of the DSP card. Each mode corresponds to a 
                          set  of algorithms supported by the IO card. 
                          Aal modes describe the aal type used. 

                          algoSet1-aal2-non-multiplexed:
                            resource type for algoSet1 DSP mode and 
                            non-multiplexed aal2 AAL mode.

                          algoSet1-aal2-std :     
	                    resource type for algoSet1 DSP mode and standard 
                            aal2 AAL mode. 

                          algoSet2-aal2-non-multiplexed:
                            resource type for algoSet2 DSP mode and 
                            non-multiplexed aal2 AAL mode.aal2 AAL mode.

                          algoSet2-aal2-std:                                   
                            resource type for algoSet2 DSP mode and standard 
                            aal2 AAL mode. 

                          algoSet3-aal2-non-multiplexed:
                            resource type for algoSet3 DSP mode and 
                            non-multiplexed aal2 AAL mode.

                          algoSet3-aal2-std:
                            resource type for algoSet3 DSP mode and standard 
                            aal2 AAL mode. 
                             
                          algoSet5-aal1:
                            resource type for algoSet5 DSP mode and 
                            aal1 AAL mode.                                                                       
                          algoSet6-aal2-std:                               
                            resource type for algoSet6 DSP mode and standard 
                            aal2 AAL mode.
                                                                                                                      
                          tone-annce-cas: 
                            resource type for the tone announcement interface 
                            and CAS mode of the TASM card.

                          tone-annce-tas:
     		            resource type for the tone announcement interface 
                            and TAS mode of the TASM card.                       
                             "
             ::= { dspResourceEntry  1 }

dspResourceAvail  OBJECT-TYPE
             SYNTAX Integer32
             MAX-ACCESS read-only
             STATUS current
             DESCRIPTION " The available DSP resource counts how many 
                           connections can be made using this available 
                           DSP resource type in the system. "
             ::= {  dspResourceEntry  2 }

dspResourceUsed  OBJECT-TYPE
             SYNTAX Integer32
             MAX-ACCESS read-only
             STATUS current
             DESCRIPTION " The used DSP resource counts how many 
                           connections are already made using this 
                           available DSP resource type in the system."
             ::= {  dspResourceEntry  3 }

dspResourceUsedFailed  OBJECT-TYPE
             SYNTAX Integer32
             MAX-ACCESS read-only
             STATUS current
             DESCRIPTION " The used but failed DSP resource counts 
                           how many connections are already made 
                           using currently failed DSP resource type in
                           the system."
             ::= {  dspResourceEntry  4 }

dspResourceAvailFailed  OBJECT-TYPE
            SYNTAX Integer32
            MAX-ACCESS read-only
            STATUS current
            DESCRIPTION " The available but failed DSP resource counts 
                          how many connections can be  made if using 
                          currently failed DSP resource type in the 
                          system."
           ::= {  dspResourceEntry  5 }

-- End of DSP resource Table.

tasmMaxDigitControlBlocks OBJECT-TYPE
                SYNTAX INTEGER (1..10000)
                MAX-ACCESS read-write
                STATUS current
                DESCRIPTION "Specifies the maximum number of digit collection
                             that can be initiated simultaneously. This will 
                             depend on the number of control blocks allocated
                             for playing tones and announcements and for line 
                             tests as the memory comes from the same pool.
                             The tasmControlBlockResAllocUsage field will be 
                             updated to indicate this ."
                DEFVAL { 1 }
                ::= { sysConfig 95 }

tasmMaxTestControlBlocks OBJECT-TYPE
                SYNTAX INTEGER (1..10000)
                MAX-ACCESS read-write
                STATUS current
                DESCRIPTION "Specifies the maximum number of TDM line tests
                             that can be initiated simultaneously. This will 
                             depend on the number of control blocks allocated
                             for playing tones and announcements and for digit
                             collection as the memory comes from the same pool.
                             The tasmControlBlockResAllocUsage field will be 
                             updated to indicate this. "
                DEFVAL { 1 }
                ::= { sysConfig 96 }

tasmMaxMemResvd OBJECT-TYPE
                SYNTAX Integer32
                MAX-ACCESS read-only
                STATUS current
                DESCRIPTION "Specifies the maximum amount of memory 
                             in megabytes reserved for TASM."
                ::= { sysConfig 97 }

tasmControlBlockResAllocUsage OBJECT-TYPE
                SYNTAX Integer32
                MAX-ACCESS read-only
                STATUS current
                DESCRIPTION "The percentage of memory usage for tones, 
                             announcements, digit collection and line tests
                             control blocks."
                ::= { sysConfig 98 }



tasmAnnceCacheMemResAllocUsage OBJECT-TYPE
                SYNTAX Integer32
                MAX-ACCESS read-only
                STATUS current
                DESCRIPTION "The percentage of memory usage for caching 
                             announcements in memory. Everytime an announcement
                             is compressed this field will be updated to reflect
                             the cache memory that will be taken up by this
                             announcement. Once this field shows a 100 percent
                             usage it is an indication to the user that any 
                             additional announcement will cause the system to
                             thrash as it clears an announcement in cache to 
                             make room for the new announcement."
                ::= { sysConfig 99 }

siteAlternateGatewayAddr OBJECT-TYPE
             SYNTAX IpAddress
             MAX-ACCESS read-write
             STATUS current
             DESCRIPTION "Alternate ip address of gateway to access the site
                          (switch),Can be used only over the InBand PVC
                          connection when the OAM is enabled on InBand PVCs"
             ::= { sysConfig 100 }


ipThrottlingConfig OBJECT IDENTIFIER  ::=  {sysConfig 101}

ipThrottlingFeatureStatus      OBJECT-TYPE
                SYNTAX INTEGER  {
                                 disabled (0),
                                 enabled (1)
                                }
                MAX-ACCESS read-write
                STATUS current
                DESCRIPTION "CPU card IP throttling feature: off/on"
                DEFVAL { disabled }
                ::= { ipThrottlingConfig 1 }

ipThrottlingAllowedInFrameRate OBJECT-TYPE
                SYNTAX INTEGER (1..20000)
                MAX-ACCESS read-write
                STATUS current
                DESCRIPTION "CPU card IP throttling: allowed input
                             frames per second"
                DEFVAL { 2000 }
                ::= { ipThrottlingConfig 2 }

ipThrottlingLeakyBucketSize OBJECT-TYPE
                SYNTAX INTEGER (1..20000)
                MAX-ACCESS read-write
                STATUS current
                DESCRIPTION "CPU card IP throttling: the size of leaky
                             bucket"
                DEFVAL { 32 }
                ::= { ipThrottlingConfig 3 }

ipThrottlingStatsOdometerTimer OBJECT-TYPE
                SYNTAX Integer32
                MAX-ACCESS read-only
                STATUS current
                DESCRIPTION "CPU card IP throttling: Number of seconds
                             since odometer was reset."
                ::= { ipThrottlingConfig 4 }

ipThrottlingStatsOdometerReset OBJECT-TYPE
                SYNTAX INTEGER {
                               reset (1)
                               }
                MAX-ACCESS read-write
                STATUS current
                DESCRIPTION "CPU card IP throttling: Odometer reset
                             button."
                ::= { ipThrottlingConfig 5 }

ipThrottlingInPackets OBJECT-TYPE
                SYNTAX Integer32
                MAX-ACCESS read-only
                STATUS current
                DESCRIPTION "CPU card IP throttling: the total number of
                             input packets from both Ethernet port and
                             In-band-mgmt of the CPU card."
                ::= { ipThrottlingConfig 6 }

ipThrottlingInPacketsPassedEi OBJECT-TYPE
                SYNTAX Integer32
                MAX-ACCESS read-only
                STATUS current
                DESCRIPTION "CPU card IP throttling: the number of input
                             packets passed through the Ethernet port
                             of the CPU card."
                ::= { ipThrottlingConfig 7 }

ipThrottlingInPacketsDroppedEi OBJECT-TYPE
                SYNTAX Integer32
                MAX-ACCESS read-only
                STATUS current
                DESCRIPTION "CPU card IP throttling: the number of input
                             packets dropped from the Ethernet port of
                             the CPU card."
                ::= { ipThrottlingConfig 8 }

ipThrottlingInPacketsPassedIBM OBJECT-TYPE
                SYNTAX Integer32
                MAX-ACCESS read-only
                STATUS current
                DESCRIPTION "CPU card IP throttling: the number of input
                             packets passed from the In-Band-Management
                             of the CPU card."
                ::= { ipThrottlingConfig 9 }

ipThrottlingInPacketsDroppedIBM OBJECT-TYPE
                SYNTAX Integer32
                MAX-ACCESS read-only
                STATUS current
                DESCRIPTION "CPU card IP throttling: the number of input
                             packets dropped from the In-Band-Management of
                             the CPU card."
                ::= { ipThrottlingConfig 10 }


csSapphireInterfaceAddress OBJECT-TYPE
                SYNTAX IpAddress
                MAX-ACCESS read-write
                STATUS current
                DESCRIPTION "The IP address to be specified as the source 
                             address in the TCP connect message that is
                             sent to the SoftSwitch running as server and PSAX
                             running as client."
                ::= { sysConfig 102 }

trapActivationTable OBJECT-TYPE
             SYNTAX SEQUENCE OF TrapActivationEntry
                MAX-ACCESS not-accessible
                STATUS current
                DESCRIPTION "Table of traps be turned on/off"
                ::= { sysConfig 103 }

trapActivationEntry OBJECT-TYPE
             SYNTAX TrapActivationEntry
             MAX-ACCESS not-accessible
             STATUS current
             DESCRIPTION "Row definition for trapActivation table"
             INDEX { trapGroupId,trapIndex }
             ::= { trapActivationTable 1 }

TrapActivationEntry ::= SEQUENCE {
             trapGroupId             INTEGER,
             trapIndex               Integer32,
             trapActivationStatus    INTEGER,
             trapNames               DisplayString,
             resetAction             INTEGER
             }

trapGroupId    OBJECT-TYPE
             SYNTAX INTEGER {
             systemEvents      (1),
             moduleEvents      (2),
             interfaceEvents   (3),
             connectionEvents  (4)
            }
             MAX-ACCESS not-accessible
             STATUS current
             DESCRIPTION "trap group ID."
             ::= { trapActivationEntry 1 }

trapIndex    OBJECT-TYPE
             SYNTAX Integer32
             MAX-ACCESS not-accessible
             STATUS current
             DESCRIPTION "trap index in each group."
             ::= { trapActivationEntry 2 }


trapActivationStatus OBJECT-TYPE
             SYNTAX INTEGER {
                  activated(1),
                  deactivated(2),
                  permanently-activated(3)
             }
             MAX-ACCESS read-write
             STATUS current
             DESCRIPTION "activated: trap message activated.
                          deactivated: trap message deactivated.
                          permanently-activated: trap message can not be
                                                deactivated."
             DEFVAL { activated }
            ::= { trapActivationEntry 3 }


trapNames    OBJECT-TYPE
             SYNTAX DisplayString (SIZE(50))
             MAX-ACCESS read-only
             STATUS current
             DESCRIPTION "Name of the trap"
             ::= { trapActivationEntry 4 }

resetAction OBJECT-TYPE
             SYNTAX INTEGER {
                  set-all-active(1),
                  set-all-deactive(2)
             }
             MAX-ACCESS read-write
             STATUS current
             DESCRIPTION "set-all-active: set all trap active one group.
                          set-all-deactive: set all trap deactive in a group."
             DEFVAL { set-all-active }
            ::= { trapActivationEntry 5 }

spvcGlobalPriorityScheme OBJECT-TYPE
                SYNTAX INTEGER {
                                enabled(1),
                                disabled(2)
                               }
                MAX-ACCESS read-write
                STATUS current
                DESCRIPTION "Flag indicating whether priority scheme should
                             be supported across SPVCs and SPVC-trunks."
                DEFVAL { disabled }
                ::= { sysConfig 104 }

spvcPriorityScheme OBJECT-TYPE
                SYNTAX INTEGER {
                                enabled(1),
                                disabled(2)
                               }
                MAX-ACCESS read-write
                STATUS current
                DESCRIPTION "Flag indicating whether priority scheme should
                             be supported in SPVCs."
                DEFVAL { disabled }
                ::= { sysConfig 105 }

spvcTrunkingPriorityScheme OBJECT-TYPE
                SYNTAX INTEGER {
                                enabled(1),
                                disabled(2)
                               }
                MAX-ACCESS read-write
                STATUS current
                DESCRIPTION "Flag indicating whether priority scheme should
                             be supported in SPVC-trunks."
                DEFVAL { disabled }
                ::= { sysConfig 106 }


atmTrunkVccs OBJECT-TYPE
                SYNTAX Integer32
                MAX-ACCESS read-write
                STATUS current
                DESCRIPTION "The total number of ATM Trunk VCCs (including SigVccs
                             and Bearer Vccs)."
                DEFVAL { 100 }
                ::= { sysConfig 107 }

atmTrunkNarrowBandCalls OBJECT-TYPE
                SYNTAX Integer32
                MAX-ACCESS read-write
                STATUS current
                DESCRIPTION "The total number of ATM Trunking Narrow Band Calls 
                             supported"
                DEFVAL { 1000 }
                ::= { sysConfig 108 }

dspResourceFeatureConfig OBJECT IDENTIFIER  ::=  { sysConfig 109 }

dspReroutingFeature     OBJECT-TYPE
                    SYNTAX INTEGER  {
                                     disabled (1),
                                     auto-rerouting-enabled (2)
                                    }
                    MAX-ACCESS read-write
                    STATUS current
                    DESCRIPTION "Dsp2 Rerouting Feature.This is used to
                         enable or disable rerouting of connections
                         when a dsp chip or card fails."
                    DEFVAL { auto-rerouting-enabled }
                    ::= { dspResourceFeatureConfig 1 }


-- Stratum Configuration Group stratumConfig



-- Equipment Configuration Group
-- The switch supports the following loopback configurations for some of the
-- interface ports, e.g., ds3, ds1, e1, e3, and oc3.

--                noLoop mode

--                The interface is not in a loop back state and signal
--                flow is normal.

--                  __________________________
--                 [                          ]
--                 [  SWITCH                  ]  ___ signal flow
--                 [                          ] /
--         ==<=================<====================<==
-- I/O port ===>  ##                          ##  <===  I/O port
--         ==>=================>====================>==
--                 [                          ] \___ signal flow
--                 [                          ]
--                 [__________________________]


--                localLoop mode

--                The signal received from far end I/O port, that is supposed
--                to be transmitted out at this interface does go through the
--                device (maximum penetration) but is looped back out.

--                  __________________________
--                 [                          ]
--                 [  SWITCH                  ]
--                 [                          ]
--                 [ ====<==========================<==
-- I/O port ===>  ## |                        ##  <===  I/O port
--                 [ ====>==========================>==
--                 [                          ]
--                 [                          ]
--                 [__________________________]


--                lineLoop mode

--                The received signal at this interface does not go through
--                the device (minimum penetration) but is looped back out.

--                  __________________________
--                 [                          ]
--                 [  SWITCH                  ]
--                 [                          ]
--         ==>=======                         ]
-- I/O port ===>  ## |                        ##  <===  I/O port
--         ==<=======                         ]
--                 [                          ]
--                 [                          ]
--                 [__________________________]


--                payloadLoop mode

--                The received signal at this interface goes through the
--                device (maximum penetration) but is looped back out.

--                  __________________________
--                 [                          ]
--                 [  SWITCH                  ]
--                 [                          ]
--         ==>==========================>==== ]
-- I/O port ===>  ##                        | ##  <===  I/O port
--         ==<==========================<==== ]
--                 [                          ]
--                 [                          ]
--                 [__________________________]


cardTable       OBJECT-TYPE
                SYNTAX SEQUENCE OF CardEntry
                MAX-ACCESS not-accessible
                STATUS current
                DESCRIPTION "Table of card configuration data"
                ::= { equipConfig 1 }
 
cardEntry       OBJECT-TYPE
                SYNTAX CardEntry
                MAX-ACCESS not-accessible
                STATUS current
                DESCRIPTION "Row definition for ac120 card"
                INDEX { cardSlot }
                ::= { cardTable 1 }
 
CardEntry       ::= SEQUENCE {
                cardSlot                INTEGER,
                cardType                INTEGER,
                cardProtectionStatus    INTEGER,
                cardOperStatus          INTEGER,
                cardAdminStatus         INTEGER,
                cardAlarmStatus         INTEGER,
                cardCleiCode            DisplayString,
                cardRevision            Integer32,
                cardSerialNumber        DisplayString,
                cardOperatingMode       INTEGER,
                protectionConfigMode    INTEGER,
                protectionStatus        INTEGER,
                protectionSlot          INTEGER 
                }
 
cardSlot        OBJECT-TYPE
                SYNTAX INTEGER (1..24)
                MAX-ACCESS not-accessible
                STATUS current
                DESCRIPTION "Physical slot location.  Valid range is a number
                             between 1 and 24."
                ::= { cardEntry 1 }
 
cardType        OBJECT-TYPE
                SYNTAX INTEGER  {
                                none(1),
                                taxi(2),
                                oC-3c(3),
                                dS3-ATM(4),
                                dS1-CE(5),
                                dS1-ATM(6),
                                e1-CE(7),
                                e3-ATM(8),
                                highSpeed(9),
                                mSerial(10),
                                dSP1(11),
                                tWStation(12),
                                tWOffice(13),
                                cPU(14),
                                stratum(15),
                                pwrSupply(16),
                                protectionCard(17),
                                e1-ATM(18),
                                ethernet(19),
                                enhDS1(20),
                                enhE1(21),
                                oC-3cMMAQ(22),
                                oC-3cMMTS(23),
                                oC-3cSMAQ(24),
                                oC-3cSMTS(25),
                                sTM-1SMAQ(26),
                                sTM-1SMTS(27),
                                sTM-1MMAQ(28),
                                sTM-1MMTS(29),
                                dS3-FR(30),
                                dSP2A(31),
                                dS1-IMA(32),
                                e1-IMA(33),
                                alarm(34),
                                dSP2B(35),
                                aps-OC-3cSM(36),
                                aps-OC-3cMM(37),
                                msp-STM-1SM(38),
                                msp-STM-1MM(39),
                                cH-DS3(40),
                                cH-STS1(41),
                                rT-S(42),
                                cC-Server(43),
                                hD-E1(44),
                                hD-DS1(45),
                                dS3-IMA(46),
                                dSP2C(47),
                                tasm(48),
                                mD-DS1(49),
                                quadSerial(50),
                                mD-DS1-IMA(51),
                                mD-E1-IMA(52),
                                hD-DS1-IMA(53),
                                hD-E1-IMA(54),
                                chDS3STS1-3P(55),
                                unstDS3E3-3P(56),
                                dS3E3-ATM-3P(57),
                                oC12c-STM4-MM(58),
                                oC12c-STM4-SM(59),
                                dSP2D(60),
                                ethernet-4P(61),
                                chDS3STS1-3P-Prot(62),
                                alarm-fan(63),
                                dS1-Nx64CAS(64)
                                }
                MAX-ACCESS read-only
                STATUS current
                DESCRIPTION "Type of card in a physical slot.  A specific type 
                             of card is associated with each number.
                 none(1)                 no board present
                taxi(2)                 Taxi
                oC-3c(3)                OC3
                dS3-ATM(4)              DS3 ATM
                dS1-CE(5)               DS1 circuit emulation
                dS1-ATM(6)              DS1 ATM
                e1-CE(7)                E1 circuit emulation
                e3-ATM(8)               E3 ATM
                highSpeed(9)            High Speed Serial
                mSerial(10)             Multi Serial
                dSP1(11)                DSP
                tWStation(12)           Two Wire Station
                tWOffice(13)            Two Wire Office
                cPU(14)                 Central Processor Unit
                stratum(15)             Stratum
                pwrSupply(16)           Power Supply
                protectionCard(17)      protection card
                e1-ATM(18)              E1 ATM
                ethernet(19)            Ethernet
                enhDS1(20)              Enhanced DS1
                enhE1(21)               Enhanced E1
                oC-3cMMAQ(22)           OC3 Multimode Aqueman
                oC-3cMMTS(23)           OC3 Multimode Traffic Shaping
                oC-3cSMAQ(24)           OC3 Singlemode Aqueman
                oC-3cSMTS(25)           OC3 Singlemode Traffic Shaping
                sTM-1SMAQ(26)           STM1 Singlemode Aqueman
                sTM-1SMTS(27)           STM1 Singlemode Traffic Shaping
                sTM-1MMAQ(28)           STM1 Multimode Aqueman
                sTM-1MMTS(29)           STM1 Multimode Traffic Shaping
                dS3-FR(30)              DS3 Frame Relay
                dSP2A(31)               DSP2 card revision 2A
                dS1-IMA(32)             DS1 Inverse Multiplexing over
                                        ATM (IMA) I/O card
                e1-IMA(33)              E1 IMA
                alarm(34)               alarm card
                dSP2B(35)               DSP card revision 2B
                aps-OC-3cSM(36)         Automatic Protection Switching
                                        OC3 Single Mode
                aps-OC-3cMM(37)         Automatic Protection Switching
                                        OC3 Multi Mode
                msp-STM-1SM(38)         Multi Switch Protection STM1
                                        Singemode
                msp-STM-1MM(39)         Multi Switch Protection STM1
                                        Multimode
                cH-DS3(40)              Channelized DS3
                cH-STS1(41)             Channelized STS1
                rT-S(42)                Route Server
                cC-Server(43)           Continuity Check Server
                hD-E1(44)               High Density E1
                hD-DS1(45)              High Density DS1
                dS3-IMA(46)             DS3 IMA
                dSP2C(47)               DSP card revision 2C
                tasm(48)                Tone Announcement Service Module
                mD-DS1(49)              Medium Density DS1
                quadSerial(50)          Quad Serial
                mD-DS1-IMA(51)          Medium Density DS1 IMA
                mD-E1-IMA(52)           Medium Density E1 IMA
                hD-DS1-IMA(53)          High Density DS1 IMA
                hD-E1-IMA(54)           High Density E1 IMA
                chDS3STS1-3P(55)        3-port channelized DS3 STS1
                unstDS3E3-3P(56)        3-port unstructured DS3 E3
                dS3E3-ATM-3P(57)        3-port DS3 E3 ATM
                oC12c-STM4-MM(58)       OC12 STM4 Multimode
                oC12c-STM4-SM(59)       OC12 STM4 Singlemode
                dSP2D(60)               DSP card revision 2D
                ethernet-4P(61)         4-port Ethernet
                chDS3STS1-3P-Prot(62)   3-port channelized DS3 STS1
                                        protection
                alarm-fan(63)           alarm fan card
                dS1-Nx64CAS(64)         DS1 card supporting N x 64 CAS"
                DEFVAL { none }
                ::= { cardEntry 2 }
 
cardProtectionStatus    OBJECT-TYPE
                SYNTAX INTEGER  {
                                none(1),
                                protected(2),
                                wrongType(3)
                                }
                MAX-ACCESS read-only
                STATUS current
                DESCRIPTION "Current protection status of the card: 
                        none if the card is un-protected; protected
                        if it is under the protection of another card; 
                        wrongType if the card types of protection card
                        and protected card are different."
                DEFVAL { none }
                ::= { cardEntry 3 }
 
cardOperStatus OBJECT-TYPE
                SYNTAX INTEGER  {
                                primary(1),
                                standby(2),
                                unknown(3)
                                }
                MAX-ACCESS read-only
                STATUS current
                DESCRIPTION "Current operational status of the card.
                        For I/O card, it is primary if configured, 
                        it is unknown if unconfigured, or removed.
                        For CPU, it is primary if the CPU is master
                        CPU, or standby if the CPU is slave CPU."
                DEFVAL { unknown }
                ::= { cardEntry 4 }

cardAdminStatus OBJECT-TYPE
                SYNTAX INTEGER  {
                                switchProtection(1)
                                }
                MAX-ACCESS read-write
                STATUS current
                DESCRIPTION "administrative status"
                ::= { cardEntry 5 }
 
cardAlarmStatus  OBJECT-TYPE
                SYNTAX INTEGER  {
                                noAlarm(1),
                                wrongCardType(2),
                                lineFailed(3),
                                cardRemoved(4),
                                referenceClockFailed(5),
                                compositeClockFailed(6),
                                overload(7),
                                plus5vFailed(8),
                                plus120vFailed(9),
                                minus48vFailed(10),
                                unknownAlarm(11),
                                completeClockFailed(12),
                                backplaneCircuitryFailed(13),
                                powerFailed(14),
                                inputPortClkFailed(15)
                                }
                MAX-ACCESS read-only
                STATUS current
                DESCRIPTION "last alarm occurred"
                DEFVAL { noAlarm }
                ::= { cardEntry 6 }

cardCleiCode        OBJECT-TYPE
                SYNTAX DisplayString (SIZE(10))
                MAX-ACCESS read-only
                STATUS current
                DESCRIPTION "CLEI code"
                ::= { cardEntry 7}

cardRevision        OBJECT-TYPE
                SYNTAX Integer32 
                MAX-ACCESS read-only
                STATUS current
                DESCRIPTION "Card Revision number"
                ::= { cardEntry 8}

cardSerialNumber OBJECT-TYPE
                SYNTAX DisplayString (SIZE(12))
                MAX-ACCESS read-only
                STATUS current
                DESCRIPTION "Serial Number"
                ::= { cardEntry 9}

cardOperatingMode        OBJECT-TYPE
                SYNTAX INTEGER  {
                                none(1),
                                dS3(2), 
                                e3(3),  
                                sTS1e(4),
                                oC12(5),
                                sTM4(6)
                                } 
                MAX-ACCESS read-write
                STATUS current 
                DESCRIPTION "Mode of operation for a card. This is 
                applicable
                to those card types which can be configured in a dual mode.
                e.g. unstDS3E3-3P can be operational as either a 3 port 
                DS3 or
                E3 card. All ports on the card will be of the same type
                depending on the card's operating mode."
        DEFVAL { none }
                ::= { cardEntry 10 }

protectionConfigMode          OBJECT-TYPE
                    SYNTAX INTEGER  {
                              unprotected(1),
                              protection(2),
                              working(3)
                              }
                    MAX-ACCESS read-write
                    STATUS current
                    DESCRIPTION "Protection Configuration Mode of a Card
                       unprotected: Card is not in protection or protected state
                       protection: Card is in protection state
                       working: Card is in protected/working state and this 
                               state is read only and cannot be set by the user"
                    DEFVAL { unprotected }
                    ::= { cardEntry 11 }

protectionStatus             OBJECT-TYPE
                    SYNTAX INTEGER  {
                              none(1),
                              inservice-Active(2),
                              inservice-Standby(3),
                              outOfService-Active(4),
                              outOfService-Standby(5)
                              }
                    MAX-ACCESS read-only
                    STATUS current
                    DESCRIPTION "Protection Status of a card. Inservice and 
                              OutofService indicates if the card has failed or 
                              still operational.
                              Active or Standby state indicates if it is 
                              carrying active traffic or not."
                    DEFVAL { none }
                    ::= { cardEntry 12 }

protectionSlot              OBJECT-TYPE 
                    SYNTAX INTEGER (0..15)
                    MAX-ACCESS read-only
                    STATUS current
                    DESCRIPTION "If Protection Config Mode is Working then 
                              this field gives the protection slot."
                    ::= { cardEntry 13 }

 
taxiPortConfigTable OBJECT-TYPE
                SYNTAX SEQUENCE OF TaxiPortConfigEntry
                MAX-ACCESS not-accessible
                STATUS current
                DESCRIPTION "Table of common physical Port attributes"
                ::= { equipConfig 2 }

taxiPortConfigEntry OBJECT-TYPE
                SYNTAX TaxiPortConfigEntry
                MAX-ACCESS not-accessible
                STATUS current
                DESCRIPTION "Row definition for common physical
                             port attributes"
                INDEX { taxiPortId }
                ::= { taxiPortConfigTable 1 }

TaxiPortConfigEntry ::= SEQUENCE {
                taxiPortId                Integer32,
                taxiPortType                INTEGER,
                taxiLineStatus                INTEGER,
                taxiOutputTransferRate        INTEGER
                }

taxiPortId      OBJECT-TYPE
                SYNTAX Integer32
                MAX-ACCESS not-accessible
                STATUS current
                DESCRIPTION "interface index - SSPP"
                ::= { taxiPortConfigEntry 1 }

taxiPortType OBJECT-TYPE
                SYNTAX INTEGER  {
                                taxi100(1),
                                taxi140(2)
                                }
                MAX-ACCESS read-write
                STATUS current
                DESCRIPTION " taxi type"
                DEFVAL { taxi100 }
                ::= { taxiPortConfigEntry 2 }

taxiLineStatus  OBJECT-TYPE
                SYNTAX INTEGER (1..2)
                MAX-ACCESS read-only
                STATUS current
                DESCRIPTION "taxi line status:
                        1: NoAlarm
                        2: Loss of Signal  "
                DEFVAL { 1 }
                ::= { taxiPortConfigEntry 3 }

taxiOutputTransferRate OBJECT-TYPE
                SYNTAX INTEGER  {
                                fullRate(1),
                                halfRate(2)
                                }
                MAX-ACCESS read-write
                STATUS current
                DESCRIPTION "User selectable parameter which allows the 
                               outgoing rate of the port to be reduced to 50%
                             taxi, halfRate, only on AQueMan."
                DEFVAL { fullRate }
                ::= { taxiPortConfigEntry 4 }


ds3PortConfigTable  OBJECT-TYPE
                SYNTAX SEQUENCE OF Ds3PortConfigEntry
                MAX-ACCESS not-accessible
                STATUS current
                DESCRIPTION "Table of ds3 specific port attributes"
                ::= { equipConfig 3 }

ds3PortConfigEntry  OBJECT-TYPE
                SYNTAX Ds3PortConfigEntry
                MAX-ACCESS not-accessible
                STATUS current
                DESCRIPTION "Row definition for ds3 specific
                             port attributes"
                INDEX { ds3PortId }
                ::= { ds3PortConfigTable 1 }

Ds3PortConfigEntry  ::= SEQUENCE {
                ds3PortId               Integer32,
                ds3LineType             INTEGER,
                ds3LineCoding           INTEGER,
                ds3LoopbackConfig       INTEGER,
                ds3TransmitClockSource  INTEGER,
                ds3LineStatus           INTEGER,
                ds3LineBuildOut         INTEGER,
                ds3LineScramble         INTEGER,
                ds3CellMapping          INTEGER,
                ds3SendCode             INTEGER,
                ds3OutputTxRate         INTEGER
                }
 
ds3PortId       OBJECT-TYPE
                SYNTAX Integer32 
                MAX-ACCESS not-accessible
                STATUS current
                DESCRIPTION "slot/port: SSPP"
                ::= { ds3PortConfigEntry 1 }
 
ds3LineType     OBJECT-TYPE
                SYNTAX INTEGER  {
                                cbitParity(1),
                                clearChannel(2),
                                m13(3),
                                m23(4)
                                }
                MAX-ACCESS read-write
                STATUS current
                DESCRIPTION "This variable indicates the variety of DS3 C-bit
                                  implementing this interface.  The type of
                                   interface affects the interpretation of the
                                   usage and error statistics.
                                   The rate of DS3 is 44.736 Mbps.
                                   The dsx3ClearChannel value means that 
                                   the C-bits are not used except for
                                   sending/receiving AIS.
                                   The values, in sequence, describe:
                                   TITLE:            SPECIFICATION:
                                   dsx3CbitParity     ANSI T1.107a-1989
                                   dsx3ClearChannel   ANSI T1.102-1987."
                DEFVAL { cbitParity }
                ::= { ds3PortConfigEntry 2 }
 
ds3LineCoding   OBJECT-TYPE
                SYNTAX INTEGER  {
                                b3zs(1)
                                }
                MAX-ACCESS read-only
                STATUS current
                DESCRIPTION "This variable describes the variety of Zero Code
                                   Suppression used on this interface, which in turn
                                   affects a number of its characteristics.
 
                                   ds3B3ZS refers to the use of specified
                                  patterns of normal bits and bipolar violations
                                   which are used to replace sequences of zero bits
                             of a specified length."
                DEFVAL { b3zs }
                ::= { ds3PortConfigEntry 3 }

ds3LoopbackConfig       OBJECT-TYPE
                SYNTAX INTEGER  {
                                noLoop(1),
                                localLoop(2),
                                lineLoop(3),
                                payloadLoop(4)
                                }
                MAX-ACCESS read-write
                STATUS current
                DESCRIPTION "This variable represents the loopback 
                                    configuration of the DS3 interface.

                                    See above diagrams for explanations of loops."
                DEFVAL { noLoop }
                ::= { ds3PortConfigEntry 4 }
 
ds3TransmitClockSource  OBJECT-TYPE
                SYNTAX INTEGER  {
                                loopTiming(1),
                                localTiming(2),
                                cardFreeRun(3),
                                adaptiveTiming(4)  
                                }
                MAX-ACCESS read-write
                STATUS current
                DESCRIPTION "The source of Tranmit Clock.
                               'loopTiming' indicates that the recovered  re-
                               ceive clock is used as the transmit clock.
                              'localTiming' indicates that a local clock
                               source is used.
                              'cardFreeRun' indicates that a local oscillator on 
                               the I/O card is used as the transmit clock.
                             'adaptiveTiming'  indicates that the adaptive clocking
                               mechanism is used"
                DEFVAL { localTiming }
                ::= { ds3PortConfigEntry 5 }

ds3LineStatus  OBJECT-TYPE
                SYNTAX INTEGER (1..32767)
                MAX-ACCESS read-only
                STATUS current
                DESCRIPTION "ds3 line status:
                1: dsx3NoAlarm: No alarm present
                2: dsx3RcvRAIFailure: Receiving Yellow/Remote Alarm Indication
                4: dsx3XmitRAIAlarm: Transmitting Yellow/Remote Alarm Indication
                8: dsx3RcvAIS: Receiving AIS failure state
                16: dsx3XmitAIS: Transmitting AIS failure statue
                32: dsx3LOF: Receiving LOF failure state
                64: dsx3LOS: Reveiving LOS failure state
                128: dsx3LoopbackState: Looping the received signal
                256: dsx3RcvTestCode: Receiving a Test Pattern
                512: dsx3OtherFailure: any line status not defined 
                1024: dsx3RcvRmtAIS: 
                2048: dsx3RcvRmtOOF: 
                4096: dsx3RcvRmtLOS: 
                8192: dsx3RcvRmtIdle: 
                16384: dsx3RmtLoopback: Far end remote loopback"
                DEFVAL { 1 }
                ::= { ds3PortConfigEntry 6 }

ds3LineBuildOut  OBJECT-TYPE
                SYNTAX INTEGER  {
                                short(1),
                                long(2)
                                }
                MAX-ACCESS read-write
                STATUS current
                DESCRIPTION "ds3 line build out"
                DEFVAL { short }
                ::= { ds3PortConfigEntry 7 }

ds3LineScramble  OBJECT-TYPE
                SYNTAX INTEGER  {
                                enabled(1),
                                disabled(2)
                                }
                MAX-ACCESS read-write
                STATUS current
                DESCRIPTION "ds3 line scramble"
                DEFVAL { enabled }
                ::= { ds3PortConfigEntry 8 }

ds3CellMapping  OBJECT-TYPE
                SYNTAX INTEGER  {
                                plcp(1),
                                directMapping(2)
                                }
                MAX-ACCESS read-write
                STATUS current
                DESCRIPTION "ds3 cell mapping method"
                DEFVAL { plcp }
                ::= { ds3PortConfigEntry 9 }

ds3SendCode        OBJECT-TYPE
                SYNTAX INTEGER  {
                                noCode(1),
                                lineLoopCode(2),
                                deactivateCode(3),
                                testPattern(4)
                                }
                MAX-ACCESS read-write
                STATUS current
                DESCRIPTION "This variable indicates what type of code is being
                             sent across the ds3 interface by the device.  The
                             values mean:
                             'noCode' - sending looped or normal data
                             'lineLoopCode' - sending a request for a line
                               loopback
                             'deactivateCode' - sending a loopback deactivation
                               request
                             'testPattern' - sending a test pattern"
                DEFVAL { noCode }
                ::= { ds3PortConfigEntry 10 }

ds3OutputTxRate        OBJECT-TYPE
                SYNTAX INTEGER (1..100)
                MAX-ACCESS read-write
                STATUS current
                DESCRIPTION "The ability to adjust the bandwidth of DS3 in tx
                             direction.  The adjustable DS3 bandwidth
                             will support 1% increments."
                DEFVAL { 100 }
                ::= { ds3PortConfigEntry 11 }

msPortConfigTable OBJECT-TYPE
                SYNTAX SEQUENCE OF MsPortConfigEntry
                MAX-ACCESS not-accessible
                STATUS current
                DESCRIPTION "Table of multi-serial card's port attributes"
                ::= { equipConfig 4 }

msPortConfigEntry OBJECT-TYPE
                SYNTAX MsPortConfigEntry
                MAX-ACCESS not-accessible
                STATUS current
                DESCRIPTION "Row definition for multi-serial port attributes"
                INDEX { msPortId }
                ::= { msPortConfigTable 1 }

MsPortConfigEntry ::= SEQUENCE {
                msPortId                IntfIndex,
                msLineCoding                INTEGER,
                msBaudRate                INTEGER,
                msProtocol                INTEGER,
                msEquipmentType                INTEGER,
                msRs232XmitMode         INTEGER,
                msRs232Parity                INTEGER,
                msRs232DataBits         INTEGER,
                msRs232StopBits         INTEGER,
                msTxDataClkSrcForDte        INTEGER,
                msTxDataClkSrcForDce        INTEGER,
                msRxDataClkSrcForDce        INTEGER,
                msRxClkPolarity                INTEGER,
                msTxClkPolarity                INTEGER,
                msKgResync                INTEGER,
                msHandshake                INTEGER,
                msSpeedAdaption                INTEGER,
                msBitStuffing                INTEGER,
                msLineStatus             INTEGER,
                msRxDataPolarity        INTEGER,
                msTxDataPolarity          INTEGER,
                msLoopbackConfig        INTEGER,
                msLOSDetection          INTEGER
                }

msPortId        OBJECT-TYPE
                SYNTAX IntfIndex 
                MAX-ACCESS not-accessible
                STATUS current
                DESCRIPTION "slot/port: SSPP"
                ::= { msPortConfigEntry 1 }

msLineCoding    OBJECT-TYPE
                SYNTAX INTEGER {
                                nrz(1)
                               }
                MAX-ACCESS read-only
                STATUS current
                DESCRIPTION " Line Coding."
                DEFVAL { nrz }
                ::= { msPortConfigEntry 2 }


msBaudRate        OBJECT-TYPE
                SYNTAX INTEGER {
                                baud300(1),
                                baud600(2),
                                baud900(3),
                                baud1200(4),
                                baud1800(5),
                                baud2400(6),
                                baud3600(7),
                                baud4800(8),
                                baud7200(9),
                                baud9600(10),
                                baud14400(11),
                                baud19200(12),
                                baud28800(13),
                                baud38400(14),
                                baud57600(15),
                                baud76800(16),
                                baud115200(17),
                                baud16k(18),
                                baud32k(19),
                                baud56k(20),
                                baud64k(21),
                                baud112k(22),
                                baud128k(23),
                                baud168k(24),
                                baud192k(25),
                                baud224k(26),
                                baud256k(27),
                                baud280k(28),
                                baud320k(29),
                                baud336k(30),
                                baud384k(31),
                                baud392k(32),
                                baud448k(33),
                                baud504k(34),
                                baud512k(35),
                                baud560k(36),
                                baud576k(37),
                                baud616k(38),
                                baud640k(39),
                                baud672k(40),
                                baud704k(41),
                                baud728k(42),
                                baud768k(43),
                                baud784k(44),
                                baud832k(45),
                                baud840k(46),
                                baud896k(47),
                                baud952k(48),
                                baud960k(49),
                                baud1008k(50),
                                baud1024k(51),
                                baud1064k(52),
                                baud1088k(53),
                                baud1120k(54),
                                baud1152k(55),
                                baud1176k(56),
                                baud1216k(57),
                                baud1232k(58),
                                baud1280k(59),
                                baud1288k(60),
                                baud1344k(61),
                                baud1400k(62),
                                baud1408k(63),
                                baud1456k(64),
                                baud1472k(65),
                                baud1512k(66),
                                baud1536k(67),
                                baud1568k(68),
                                baud1600k(69),
                                baud1624k(70),
                                baud1664k(71),
                                baud1680k(72),
                                baud1728k(73),
                                baud1736k(74),
                                baud1792k(75),
                                baud1856k(76),
                                baud1920k(77),
                                baud1984k(78),
                                baud2048k(79),
                                baud75(80),
                                baud1848k(81),   
                                baud1904k(82),   
                                baud1960k(83),   
                                baud2016k(84),
                                baud2072k(85),
                                baud2112k(86),
                                baud2128k(87),
                                baud2176k(88),   
                                baud2184k(89),
                                baud2240k(90),
                                baud2296k(91),    
                                baud2304k(92), 
                                baud2352k(93),     
                                baud2368k(94),
                                baud2408k(95),    
                                baud2432k(96),
                                baud2464k(97),    
                                baud2496k(98),
                                baud2520k(99),   
                                baud2560k(100),
                                baud2576k(101),
                                baud2624k(102),
                                baud2632k(103),   
                                baud2688k(104),
                                baud2744k(105),   
                                baud2752k(106),
                                baud2800k(107),  
                                baud2816k(108),
                                baud2856k(109),   
                                baud2880k(110),
                                baud2912k(111),
                                baud2944k(112),
                                baud2968k(113),  
                                baud3008k(114),
                                baud3024k(115),   
                                baud3072k(116),
                                baud3080k(117),   
                                baud3136k(118),
                                baud3192k(119),    
                                baud3200k(120),
                                baud3248k(121),    
                                baud3264k(122),
                                baud3304k(123),   
                                baud3328k(124),
                                baud3360k(125),    
                                baud3392k(126),
                                baud3416k(127),   
                                baud3456k(128),
                                baud3472k(129),
                                baud3520k(130),
                                baud3528k(131),    
                                baud3584k(132),
                                baud3640k(133),    
                                baud3648k(134),
                                baud3696k(135),  
                                baud3712k(136),
                                baud3752k(137),  
                                baud3776k(138),
                                baud3808k(139),   
                                baud3840k(140),
                                baud3864k(141),    
                                baud3904k(142),
                                baud3920k(143),    
                                baud3968k(144),
                                baud3976k(145),    
                                baud4032k(146),
                                baud4088k(147),    
                                baud4096k(148),
                                baud4144k(149),    
                                baud4160k(150),
                                baud4200k(151),    
                                baud4224k(152),
                                baud4256k(153),
                                baud4288k(154),
                                baud4312k(155),                
                                baud4352k(156),
                                baud4368k(157),                                
                                baud4416k(158),
                                baud4424k(159),                
                                baud4480k(160),                                    
                                baud4536k(161),  
                                baud4544k(162),
                                baud4592k(163),   
                                baud4608k(164),
                                baud4648k(165),   
                                baud4672k(166),
                                baud4704k(167),   
                                baud4736k(168),
                                baud4760k(169),  
                                baud4800k(170),
                                baud4816k(171),   
                                baud4864k(172),
                                baud4872k(173),    
                                baud4928k(174),
                                baud4984k(175),  
                                baud4992k(176),
                                baud5040k(177),   
                                baud5056k(178), 
                                baud5096k(179),   
                                baud5120k(180),
                                baud5152k(181),
                                baud5184k(182),
                                baud5208k(183),   
                                baud5248k(184),
                                baud5264k(185),   
                                baud5312k(186),
                                baud5320k(187),   
                                baud5376k(188),
                                baud5432k(189),   
                                baud5440k(190),
                                baud5488k(191),   
                                baud5504k(192),
                                baud5544k(193),    
                                baud5568k(194),
                                baud5600k(195),   
                                baud5632k(196),
                                baud5656k(197),   
                                baud5696k(198), 
                                baud5712k(199),
                                baud5760k(200),
                                baud5768k(201),
                                baud5824k(202),    
                                baud5880k(203),
                                baud5888k(204),
                                baud5936k(205),   
                                baud5952k(206),
                                baud5992k(207),  
                                baud6016k(208),
                                baud6048k(209),    
                                baud6080k(210),
                                baud6104k(211),    
                                baud6144k(212),
                                baud6160k(213),    
                                baud6208k(214),
                                baud6216k(215),    
                                baud6272k(216),
                                baud6328k(217),    
                                baud6336k(218),
                                baud6384k(219),   
                                baud6400k(220),
                                baud6440k(221),    
                                baud6464k(222),
                                baud6496k(223),    
                                baud6528k(224),
                                baud6552k(225),    
                                baud6592k(226),
                                baud6608k(227),    
                                baud6656k(228),
                                baud6664k(229),    
                                baud6720k(230),
                                baud6776k(231),    
                                baud6784k(232),
                                baud6832k(233),    
                                baud6848k(234),
                                baud6888k(235),    
                                baud6912k(236),
                                baud6944k(237),    
                                baud6976k(238),
                                baud7000k(239),    
                                baud7040k(240),
                                baud7056k(241),    
                                baud7104k(242),
                                baud7112k(243),  
                                baud7168k(244),
                                baud7224k(245),   
                                baud7232k(246),
                                baud7280k(247),
                                baud7296k(248),
                                baud7336k(249),   
                                baud7360k(250),
                                baud7392k(251),
                                baud7424k(252),
                                baud7448k(253),   
                                baud7488k(254),
                                baud7504k(255),   
                                baud7552k(256),   
                                baud7560k(257),
                                baud7616k(258),   
                                baud7680k(259),
                                baud7672k(260),   
                                baud7728k(261),
                                baud7744k(262),   
                                baud7784k(263),
                                baud7808k(264),   
                                baud7840k(265),
                                baud7872k(266),    
                                baud7896k(267),
                                baud7936k(268),
                                baud7952k(269),    
                                baud8000k(270),
                                baud8008k(271),   
                                baud8064k(272),
                                baud8120k(273),   
                                baud8128k(274),
                                baud8176k(275),
                                baud8192k(276),
                                baud8232k(277),   
                                baud8256k(278),
                                baud8288k(279),   
                                baud8320k(280),
                                baud8344k(281),   
                                baud8384k(282),
                                baud8400k(283),   
                                baud8448k(284),
                                baud8456k(285),   
                                baud8512k(286),
                                baud8568k(287),    
                                baud8576k(288),
                                baud8624k(289),   
                                baud8640k(290),
                                baud8680k(291),   
                                baud8704k(292),
                                baud8736k(293),   
                                baud8768k(294),
                                baud8792k(295),    
                                baud8832k(296),
                                baud8848k(297),   
                                baud8896k(298),
                                baud8904k(299),   
                                baud8960k(300),
                                baud9016k(301),   
                                baud9024k(302),
                                baud9072k(303),
                                baud9088k(304),
                                baud9128k(305),   
                                baud9152k(306),
                                baud9184k(307),   
                                baud9216k(308),
                                baud9240k(309),   
                                baud9280k(310),
                                baud9296k(311),   
                                baud9344k(312),
                                baud9352k(313),  
                                baud9408k(314),
                                baud9464k(315),   
                                baud9472k(316),
                                baud9520k(317),   
                                baud9536k(318),
                                baud9576k(319),    
                                baud9600k(320),
                                baud9632k(321),   
                                baud9664k(322),
                                baud9688k(323),  
                                baud9728k(324),
                                baud9744k(325),  
                                baud9792k(326),
                                baud9800k(327),   
                                baud9856k(328),
                                baud9912k(329),   
                                baud9920k(330),
                                baud9968k(331),   
                                baud9984k(332),
                                baud10024k(333),   
                                baud10048k(334),
                                baud10080k(335),   
                                baud10112k(336),
                                baud10136k(337),   
                                baud10176k(338),
                                baud10192k(339),  
                                baud10240k(340),
                                baud10248k(341),   
                                baud10304k(342),
                                baud10360k(343),
                                baud10368k(344),
                                baud10416k(345),  
                                baud10432k(346),
                                baud10472k(347),   
                                baud10496k(348),
                                baud10528k(349),   
                                baud10560k(350),
                                baud10584k(351),   
                                baud10624k(352),
                                baud10640k(353),    
                                baud10688k(354),
                                baud10696k(355),  
                                baud10752k(356),
                                baud10808k(357),   
                                baud10816k(358),
                                baud10864k(359),  
                                baud10880k(360),
                                baud10920k(361),  
                                baud10944k(362),
                                baud10976k(363),
                                baud11008k(364), 
                                baud11032k(365),  
                                baud11072k(366),
                                baud11088k(367),   
                                baud11136k(368),
                                baud11144k(369),  
                                baud11200k(370),
                                baud11256k(371), 
                                baud11264k(372), 
                                baud11312k(373),
                                baud11328k(374),
                                baud11368k(375),  
                                baud11392k(376),
                                baud11424k(377), 
                                baud11456k(378),
                                baud11480k(379),   
                                baud11520k(380),
                                baud11536k(381),  
                                baud11584k(382),
                                baud11592k(383),   
                                baud11648k(384),
                                baud11704k(385),  
                                baud11712k(386),
                                baud11760k(387),  
                                baud11776k(388),
                                baud11816k(389),   
                                baud11840k(390),
                                baud11872k(391),   
                                baud11904k(392),
                                baud11928k(393),   
                                baud11968k(394),
                                baud11984k(395),  
                                baud12032k(396),
                                baud12040k(397),   
                                baud12096k(398),
                                baud12152k(399),   
                                baud12160k(400),
                                baud12208k(401),  
                                baud12224k(402),
                                baud12264k(403),  
                                baud12288k(404),
                                baud12320k(405),  
                                baud12352k(406),
                                baud12376k(407),  
                                baud12416k(408),
                                baud12432k(409),   
                                baud12480k(410),
                                baud12488k(411),  
                                baud12544k(412),
                                baud12600k(413),  
                                baud12608k(414),
                                baud12656k(415),   
                                baud12672k(416),
                                baud12712k(417),  
                                baud12736k(418),
                                baud12768k(419),  
                                baud12800k(420),
                                baud12824k(421),  
                                baud12864k(422),
                                baud12880k(423),   
                                baud12928k(424),
                                baud12936k(425),  
                                baud12992k(426),
                                baud13048k(427),  
                                baud13056k(428),
                                baud13104k(429),   
                                baud13120k(430),
                                baud13160k(431), 
                                baud13184k(432),
                                baud13216k(433),  
                                baud13248k(434),
                                baud13272k(435),  
                                baud13312k(436),
                                baud13328k(437),   
                                baud13376k(438),
                                baud13384k(439),  
                                baud13440k(440),
                                baud13496k(441),  
                                baud13504k(442),
                                baud13552k(443),   
                                baud13568k(444),
                                baud13608k(445),   
                                baud13632k(446),
                                baud13664k(447),   
                                baud13696k(448),
                                baud13720k(449),   
                                baud13760k(450),
                                baud13776k(451),  
                                baud13824k(452),
                                baud13832k(453),   
                                baud13888k(454),
                                baud13944k(455),  
                                baud13952k(456),
                                baud14000k(457),  
                                baud14016k(458),
                                baud14056k(459),   
                                baud14080k(460),
                                baud14112k(461),   
                                baud14144k(462),
                                baud14168k(463),   
                                baud14208k(464),
                                baud14224k(465),   
                                baud14272k(466),
                                baud14280k(467),  
                                baud14336k(468),   
                                baud14400k(469),  
                                baud14464k(470),   
                                baud14528k(471),    
                                baud14592k(472),   
                                baud14656k(473),  
                                baud14720k(474),   
                                baud14784k(475),  
                                baud14848k(476),  
                                baud14912k(477),   
                                baud14976k(478),  
                                baud15040k(479),   
                                baud15104k(480),   
                                baud15168k(481),  
                                baud15232k(482),   
                                baud15296k(483),   
                                baud15360k(484),    
                                baud15424k(485),    
                                baud15488k(486),    
                                baud15552k(487),    
                                baud15616k(488),    
                                baud15680k(489),   
                                baud15744k(490),   
                                baud15808k(491),   
                                baud15872k(492),   
                                baud15936k(493),    
                                baud16000k(494),  
                                baud16064k(495),   
                                baud16128k(496),    
                                baud16192k(497),   
                                baud16256k(498),  
                                baud16320k(499),  
                                baud16384k(500),
                                baud1544k(501),
                                baud230400(502),
                                baud150(503)
                                }
                MAX-ACCESS read-write
                STATUS current
                DESCRIPTION "baud rate is determined by 
                        multiplying this number by the 
                        msBaudRateMultiplier"
                DEFVAL { baud300 }
                ::= { msPortConfigEntry 3 }

msProtocol        OBJECT-TYPE
                SYNTAX INTEGER {
                                rs232(1),
                                rs449(2),
                                rs530(3),
                                v35(4),
                                x21(5),
                                kg(6),
                                rs530A(7)
                               }
                MAX-ACCESS read-write
                STATUS current
                DESCRIPTION "protocol type for serial port"
                DEFVAL { rs449 }
                ::= { msPortConfigEntry 4 }

msEquipmentType      OBJECT-TYPE
                SYNTAX INTEGER {
                                dte(1),
                                dce(2)
                               }
                MAX-ACCESS read-write
                STATUS current
                DESCRIPTION "Equipment type"
                DEFVAL { dte }
                ::= { msPortConfigEntry 5 }

msRs232XmitMode OBJECT-TYPE
                SYNTAX INTEGER {
                                synchronous(1),
                                asynchronous(2)
                               }
                MAX-ACCESS read-write
                STATUS current
                DESCRIPTION "transmit mode for rs232 DTE/DCE serial port"
                DEFVAL { synchronous }
                ::= { msPortConfigEntry 6 }

msRs232Parity        OBJECT-TYPE
                SYNTAX INTEGER {
                                none(1),
                                odd(2),
                                even(3)
                               }
                MAX-ACCESS read-write
                STATUS current
                DESCRIPTION "parity for rs232 DTE/DCE serial port"
                DEFVAL { none }
                ::= { msPortConfigEntry 7 }

msRs232DataBits OBJECT-TYPE
                SYNTAX INTEGER {
                                eight(1),
                                seven(2),
                                six(3)
                               }
                MAX-ACCESS read-write
                STATUS current
                DESCRIPTION "data bits for rs232 DTE/DCE serial port"
                DEFVAL { eight }
                ::= { msPortConfigEntry 8 }

msRs232StopBits OBJECT-TYPE
                SYNTAX INTEGER {
                                one(1),
                                two(2)
                               }
                MAX-ACCESS read-write
                STATUS current
                DESCRIPTION "stop bits for rs232 DTE/DCE serial port"
                DEFVAL { one }
                ::= { msPortConfigEntry 9 }

msTxDataClkSrcForDte OBJECT-TYPE
                SYNTAX INTEGER {
                                localTiming(1),
                                txRxTiming(2),
                                txTiming(3)
                               }
                MAX-ACCESS read-write
                STATUS current
                DESCRIPTION "Transmit data clock source for DTE,
                             externalTx in is not valid for rs232.
                             This field is ignored if the local side is DCE."
                DEFVAL { localTiming }
                ::= { msPortConfigEntry 10 }

msTxDataClkSrcForDce OBJECT-TYPE
                SYNTAX INTEGER {
                                localTiming(1),
                                loopTiming(2)
                               }
                MAX-ACCESS read-write
                STATUS current
                DESCRIPTION "Transmit data clock source for DCE
                             localTiming: a local clock source is used. (e.g., from 
                             backplane (stratum)
                             loopTiming: from remote
                             This field is ignored if the local side is DTE"
                DEFVAL { localTiming }
                ::= { msPortConfigEntry 11 }

msRxDataClkSrcForDce OBJECT-TYPE
                SYNTAX INTEGER {
                                localTiming(1),
                                externalTiming(2)
                               }
                MAX-ACCESS read-write
                STATUS current
                DESCRIPTION "Receive data clock source for DCE
                             localTiming: a local clock source is used. (e.g., from
                             backplane (stratum)
                             loopTiming: from remote
                             This field is ignored if the local side is DTE"
                DEFVAL { localTiming }
                ::= { msPortConfigEntry 12 }


msRxClkPolarity OBJECT-TYPE
                SYNTAX INTEGER {
                                standard(1),
                                inverted (2)
                               }
                MAX-ACCESS read-write
                STATUS current
                DESCRIPTION "Whether or not to reverse the receive clock"
                DEFVAL { standard }
                ::= { msPortConfigEntry 13 }

msTxClkPolarity OBJECT-TYPE
                SYNTAX INTEGER {
                                standard(1),
                                inverted (2)
                               }
                MAX-ACCESS read-write
                STATUS current
                DESCRIPTION "Whether or not to reverse the transmit clock"
                DEFVAL { standard }
                ::= { msPortConfigEntry 14 }

msKgResync        OBJECT-TYPE
                SYNTAX INTEGER {
                                enabled(1),
                                disabled(2)
                               }
                MAX-ACCESS read-write
                STATUS current
                DESCRIPTION "Turn KG resync on/off"
                DEFVAL { enabled }
                ::= { msPortConfigEntry 15 }

msHandshake        OBJECT-TYPE
                SYNTAX INTEGER {
                                observed(1),
                                ignored(2)
                               }
                MAX-ACCESS read-write
                STATUS current
                DESCRIPTION " Multiserial Module handshake:
                              observed : used with AAL1 to monitor
                                        RTS/CTS exchange."
                DEFVAL { ignored }
                ::= { msPortConfigEntry 16 }

msSpeedAdaption OBJECT-TYPE
                SYNTAX INTEGER {
                                enabled(1),
                                disabled(2)
                               }
                MAX-ACCESS read-write
                STATUS current
                DESCRIPTION "The state of allowing speed adaption"
                DEFVAL { enabled }
                ::= { msPortConfigEntry 17 }

msBitStuffing OBJECT-TYPE
                SYNTAX INTEGER {
                                disabled(1),
                                enabled(2)
                                }
                MAX-ACCESS read-write
                STATUS current
                 DESCRIPTION "When msBitStuffing is enabled, 
                        CAC throughput is (1 + 1/7) user throughtput.
                  Otherwise the CAC throughput is the same as the user throughput. 
                  msBitStuffing can only be enabled for circuit emulation interfaces.
                        " 
                DEFVAL { disabled }
                ::= { msPortConfigEntry 18 }

msLineStatus  OBJECT-TYPE
                SYNTAX INTEGER (1..2)
                MAX-ACCESS read-only
                STATUS current
                DESCRIPTION "line status on the port:
                        The msLineStatus is a bit map representation.
                        It can represent multiple failures (alarms) 
                        if supported by the card.  
                        
                        NoAlarm should be set if and only if 
                                no other flag is set.

                        The various bit positions are:
                        1: NoAlarm
                        2: Loss of Signal  "
                DEFVAL { 1 }
                ::= { msPortConfigEntry 19 }


msRxDataPolarity OBJECT-TYPE
                SYNTAX INTEGER {
                                standard(1),
                                inverted (2)
                                }
                MAX-ACCESS read-write
                STATUS current
                DESCRIPTION "Whether or not to reverse the receive data"
                DEFVAL { standard }
                ::= { msPortConfigEntry 20}

msTxDataPolarity OBJECT-TYPE
                SYNTAX INTEGER {
                                standard(1),
                                inverted (2)
                                }
                MAX-ACCESS read-write
                STATUS current
                DESCRIPTION "Whether or not to reverse the transmit data"
                DEFVAL { standard }
                ::= { msPortConfigEntry 21 }

msLoopbackConfig OBJECT-TYPE
                SYNTAX INTEGER  {
                                noLoop(1),
                                localLoop(2),
                                lineLoop(3)
                                }
                MAX-ACCESS read-write
                STATUS current
                DESCRIPTION "This variable represents the loopback 
                               configuration of the Serial port."
                DEFVAL { noLoop }
                ::= { msPortConfigEntry 22 }

msLOSDetection OBJECT-TYPE
                SYNTAX INTEGER {
                          disabled(1),
                        enabled(2)        
                                }
                MAX-ACCESS read-write
                STATUS current
                DESCRIPTION "State of detection of LOS by IO card. 
         LOS detection is always enabled when msBitStuffing is enabled. 
               When the interface is not circuit emulation, the IO card does not report any LOS."
                DEFVAL { disabled }
                ::= { msPortConfigEntry 23 } 

             

ds1PortConfigTable  OBJECT-TYPE
                SYNTAX SEQUENCE OF Ds1PortConfigEntry
                MAX-ACCESS not-accessible
                STATUS current
                DESCRIPTION "Table of ds1 specific port attributes"
                ::= { equipConfig 5 }

ds1PortConfigEntry  OBJECT-TYPE
                SYNTAX Ds1PortConfigEntry
                MAX-ACCESS not-accessible
                STATUS current
                DESCRIPTION "Row definition for ds1 specific
                             port attributes"
                INDEX { ds1PortId }
                ::= { ds1PortConfigTable 1 }

Ds1PortConfigEntry  ::= SEQUENCE {
                ds1PortId               Integer32,
                ds1Channelization       INTEGER,
                ds1LineType             INTEGER,
                ds1LineCoding           INTEGER,
                ds1LoopbackConfig       INTEGER,
                ds1TransmitClockSource  INTEGER,
                ds1LineBuildOut         INTEGER,
                ds1LineStatus           INTEGER,

                ds1EnhanceFeatureSet1   INTEGER,

                ds1DataTransferType     INTEGER,
                ds1OamInterworkingType  INTEGER,

                ds1ConnGatewayFeature   INTEGER,

                ds1InLineCode           INTEGER
                }
 
ds1PortId       OBJECT-TYPE
                SYNTAX Integer32 
                MAX-ACCESS not-accessible
                STATUS current
                DESCRIPTION "interface index - slot/port: SSPP"
                ::= { ds1PortConfigEntry 1 }
 
ds1Channelization        OBJECT-TYPE
                SYNTAX INTEGER  {
                                 disabled(1),
                                 enabled(2)
                                }
                MAX-ACCESS read-write
                STATUS current
                DESCRIPTION "ds1 interface type"
                DEFVAL { disabled }
                ::= { ds1PortConfigEntry 2 }
 
ds1LineType     OBJECT-TYPE
                SYNTAX INTEGER  {
                                esf(1),
                                d4(2)
                                }
                MAX-ACCESS read-write
                STATUS current
                DESCRIPTION "ds1 interface type"
                DEFVAL { esf }
                ::= { ds1PortConfigEntry 3 }
 
ds1LineCoding   OBJECT-TYPE
                SYNTAX INTEGER  {
                                b8zs(1),
                                ami(2)
                                }
                MAX-ACCESS read-write
                STATUS current
                DESCRIPTION "ds1 interface type"
                DEFVAL { b8zs }
                ::= { ds1PortConfigEntry 4 }
   
ds1LoopbackConfig       OBJECT-TYPE
                SYNTAX INTEGER  {
                                noLoop(1),
                                localLoop(2),
                                lineLoop(3),
                                payloadLoop(4)
                                }
                MAX-ACCESS read-write
                STATUS current
                DESCRIPTION "This variable represents the loopback
                               configuration of the ds1 interface"
                DEFVAL { noLoop }
                ::= { ds1PortConfigEntry 5 }
 
ds1TransmitClockSource  OBJECT-TYPE
                SYNTAX INTEGER  {
                                loopTiming(1),
                                localTiming(2),
                                adaptive(3)
                                }
                MAX-ACCESS read-write
                STATUS current
                DESCRIPTION "ds1 timing source"
                DEFVAL { localTiming }
                ::= { ds1PortConfigEntry 6 }

ds1LineBuildOut   OBJECT-TYPE
                SYNTAX INTEGER  {
                                upTo133Feet(1),
                                upTo266Feet(2),
                                upTo399Feet(3),
                                upTo533Feet(4),
                                upTo655Feet(5),
                                negative7-5Db(6),
                                negative15Db(7),
                                negative22-5Db(8)
                                }
                MAX-ACCESS read-write
                STATUS current
                DESCRIPTION "ds1 line build out"
                ::= { ds1PortConfigEntry 7 }

ds1LineStatus  OBJECT-TYPE
                SYNTAX INTEGER (1..16383)
                MAX-ACCESS read-only
                STATUS current
                DESCRIPTION "This variable indicates the Line Status of the
                             interface. It contains loopback, failure, re-
                             ceived 'alarm' and transmitted 'alarm' infor-
                             mation.

                                  The dsx1LineStatus is a bit map represented  
                             as a sum, therefore, it can represent multiple 
                             failures (alarms) and a LoopbackState 
                             simultaneously.

                                  ds1NoAlarm should be set if and only if no other 
                             flag is set.

                                  If the ds1LoopbackState bit is set, the loopbak
                             in effect can be determined from the 
                             ds1LoopbackConfig object.

                     The various bit positions are:
                  1:       dsx1NoAlarm:          No Alarm Present
                  2:       dsx1RcvFarEndLOF:     Far end LOF (a.k.a., Yellow 
                                               Alarm)
                  4:       dsx1XmtFarEndLOF:     Near end sending LOF Indication
                  8:       dsx1RcvAIS:           Far end sending AIS
                 16:      dsx1XmtAIS:           Near end sending AIS
                 32:      dsx1LossOfFrame:      Near end LOF (a.k.a., Red Alarm)
                 64:      dsx1LossOfSignal:     Near end Loss Of Signal
                128:     dsx1LoopbackState:    Near end is looped
                256:     dsx1T16AIS:           E1 TS16 AIS
                512:     dsx1RcvFarEndLOMF:    Far End Sending TS16 LOMF
                       1024:    dsx1XmtFarEndLOMF:    Near End Sending TS16 LOMF
                       2048:    dsx1RcvTestCode:      Near End detects a test code
                       4096:    dsx1OtherFailure:     any line status not defined 
                                               here
                       8192:    dsx1RmtLoopback:      Far end loopback"
                DEFVAL { 1 }
                ::= { ds1PortConfigEntry 8 }





--        Object added for NEC
ds1EnhanceFeatureSet1 OBJECT-TYPE
                SYNTAX INTEGER  {
                                disabled(1),
                                enabled(2)
                                }
                MAX-ACCESS read-write
                STATUS current
                DESCRIPTION "To enable/disable a proprietary ab signaling
                             scheme, it applies to all DS0s in the port.  No
                             individual DS0 signaling can be configured under
                             this scheme."
                DEFVAL { disabled }
                ::= { ds1PortConfigEntry 10 }


ds1DataTransferType OBJECT-TYPE
                SYNTAX INTEGER  {
                                structured(1),
                                unstructured(2)
                                }
                MAX-ACCESS read-write
                STATUS current
                DESCRIPTION "DS1 data transfer type is only applicable in 
                             Circuit Emulation where unstructured CE packets 
                             entire T1 frame including the F-bit into the AAL1
                             for data tranfer, whereas, the structured CE 
                             packets the entire T1 frame except the F-bit."
                DEFVAL { structured }
                ::= { ds1PortConfigEntry 11 }
 

ds1OamInterworkingType OBJECT-TYPE
                SYNTAX INTEGER {
                        trunkCond(1),
                        unframed1s(2)
                        }
                MAX-ACCESS read-write
                STATUS current
                DESCRIPTION "Specifies whether the interworking is done 
                             by trunk conditioning or unframed1s"
                DEFVAL {trunkCond}
                ::= {ds1PortConfigEntry 12 }


ds1ConnGatewayFeature OBJECT-TYPE
                SYNTAX INTEGER  {
                                disabled(1),
                                enabled(2)
                                }
                MAX-ACCESS read-write
                STATUS current
                DESCRIPTION "To enable/disable connection gateway
                                (Sapphire) API."
                 DEFVAL { disabled }
                ::= { ds1PortConfigEntry 14 }


ds1InLineCode    OBJECT-TYPE
                SYNTAX INTEGER  {
                                aNSI(1),
                                ds1-ANI(2)
                                }
                MAX-ACCESS read-write
                STATUS current
                DESCRIPTION "To select and support the inlinecode option
                                in either ANSI or DS1_ANI
                                (ANI: Access Network Interface)"
                DEFVAL { aNSI }
                ::= { ds1PortConfigEntry 15 }

oc3PortConfigTable OBJECT-TYPE
                SYNTAX SEQUENCE OF Oc3PortConfigEntry
                MAX-ACCESS not-accessible
                STATUS current
                DESCRIPTION "Table of common physical Port attributes"
                ::= { equipConfig 6 }
 
oc3PortConfigEntry OBJECT-TYPE
                SYNTAX Oc3PortConfigEntry
                MAX-ACCESS not-accessible
                STATUS current
                DESCRIPTION "Row definition for common physical
                             port attributes"
                INDEX { oc3PortId }
                ::= { oc3PortConfigTable 1 }
 
Oc3PortConfigEntry ::= SEQUENCE {
                oc3PortId               Integer32,
                oc3LoopbackConfig        INTEGER,
                oc3TransmitClockSource        INTEGER,
                oc3LineStatus                INTEGER,
                oc3OutputTransferRate        INTEGER,
                oc3APSConfiguration             INTEGER
                }
 
oc3PortId      OBJECT-TYPE
                SYNTAX Integer32
                MAX-ACCESS not-accessible
                STATUS current
                DESCRIPTION "interface index - SSPP"
                ::= { oc3PortConfigEntry 1 }

oc3LoopbackConfig       OBJECT-TYPE
                SYNTAX INTEGER  {
                                noLoop(1),
                                localLoop(2),
                                lineLoop(3)
                                }
                MAX-ACCESS read-write
                STATUS current
                DESCRIPTION "This variable represents the loopback
                               configuration of the OC3 interface
 
                                    See above diagrams for explanations of loops."
                DEFVAL { noLoop }
                ::= { oc3PortConfigEntry 2 }
 
oc3TransmitClockSource  OBJECT-TYPE
                SYNTAX INTEGER  {
                                loopTiming(1),
                                localTiming(2)
                                }
                MAX-ACCESS read-write
                STATUS current
                DESCRIPTION "The source of Tranmit Clock.
                               'loopTiming' indicates that the recovered  re-
                             ceive clock is used as the transmit clock.
 
                              'localTiming' indicates  that  a  local  clock
                             source is used."
                DEFVAL {localTiming  }
                ::= { oc3PortConfigEntry 3 }

oc3LineStatus  OBJECT-TYPE
                SYNTAX INTEGER (1..8191)
                MAX-ACCESS read-only
                STATUS current
                DESCRIPTION "oc3 line status -
                1: oc3NoAlarm: No alarm present
                2: oc3RcvRAIFailure: Receiving Yellow/Remote Alarm Indication
                4: oc3XmitRAIAlarm: Transmitting Yellow/Remote Alarm Indication
                8: oc3RcvAIS: Receiving AIS failure state
                16: oc3XmitAIS: Transmitting AIS failure statue
                32: oc3LOF: Receiving LOF failure state
                64: oc3LOS: Reveiving LOS failure state
                128: oc3LoopbackState: Looping the received signal
                256: oc3RcvTestCode: Receiving a Test Pattern
                512: oc3OtherFailure: any line status not defined
                1024: oc3LCD: Receiving Loss Of Cell Delineation 
                2048: oc3LRDI: Receiving Line RDI failure state
                4096: oc3PRDI: Receiving Path RDI failure state"  
                DEFVAL { 1 }
                ::= { oc3PortConfigEntry 4 }

oc3OutputTransferRate OBJECT-TYPE
                SYNTAX INTEGER  {
                                fullRate(1),
                                halfRate(2)
                                }
                MAX-ACCESS read-write
                STATUS current
                DESCRIPTION "User selectable parameter which allows the 
                               outgoing rate of the port to be reduced to 50%
                             oc3, halfRate, only on AQueMan."
                DEFVAL { fullRate }
                ::= { oc3PortConfigEntry 5 }

oc3APSConfiguration OBJECT-TYPE
                SYNTAX INTEGER  {
                                unprotected(1),
                                working (2),
                                protection(3)
                                } 
                MAX-ACCESS read-write
                STATUS current 
                DESCRIPTION "Indicates whether APS is configured for this 
                                port ." 
                DEFVAL { unprotected } 
                ::= { oc3PortConfigEntry 6 }


oc3APS OBJECT IDENTIFIER ::= { equipConfig 16 }

oc3APSPairConfigTable OBJECT-TYPE
                SYNTAX SEQUENCE OF Oc3APSPairConfigEntry
                MAX-ACCESS not-accessible
                STATUS current
                DESCRIPTION "Table of common physical Port attributes"
                ::= { oc3APS 1 }
 
oc3APSPairConfigEntry OBJECT-TYPE
                SYNTAX Oc3APSPairConfigEntry
                MAX-ACCESS not-accessible
                STATUS current
                DESCRIPTION "Row definition for common physical
                             port attributes"
                INDEX { oc3APSPairId }
                ::= { oc3APSPairConfigTable 1 }
 
Oc3APSPairConfigEntry ::= SEQUENCE {
                oc3APSPairId                        Integer32,
                oc3APSPairMode                        INTEGER,
                oc3APSPairOption                INTEGER,
                oc3APSPairWorkingSFBERThreshold        INTEGER,
                oc3APSPairProtectionSFBERThreshold        INTEGER,
                oc3APSPairWorkingSDBERThreshold        INTEGER,
                oc3APSPairProtectionSDBERThreshold        INTEGER,
                oc3APSPairWTRPeriod                INTEGER,
                oc3APSWorkingSlot                Integer32,
                oc3APSProtectionSlot                Integer32,
                oc3APSActiveSlot                Integer32,
                oc3APSPairStatus                INTEGER,
                oc3APSPairUserCommand                INTEGER,
                oc3APSPairCurrentState          INTEGER,
                oc3APSPairWorkingLineSignalStatus         INTEGER,
                oc3APSPairProtectionLineSignalStatus        INTEGER
                }
 
oc3APSPairId       OBJECT-TYPE
                SYNTAX Integer32
                MAX-ACCESS not-accessible
                STATUS current
                DESCRIPTION "APS Pair Port index - SSPP"
                ::= { oc3APSPairConfigEntry 1 }
 
oc3APSPairMode OBJECT-TYPE
                SYNTAX INTEGER  {
                                unidirectional(1),
                                bidirectional(2)
                                }
                MAX-ACCESS read-write
                STATUS current
                DESCRIPTION "Unidirectional or Bidirectional mode:
                             Uni - Each pair operates independently
                                   i.e. a switch over in one pair does not
                                   effect the remote pair.
                             Bi - both remote and local pairs have to
                                   switch together."
                DEFVAL { unidirectional }
                ::= { oc3APSPairConfigEntry 2 }
 
oc3APSPairOption OBJECT-TYPE
                SYNTAX INTEGER {
                                nonrevertive(1),
                                revertive(2)
                                }
                MAX-ACCESS read-only
                STATUS current
                DESCRIPTION " Nonrevertive - After a switch to Prot port,
                             even if the working comes up there is no
                             switch to the working port back.
                             Revertive - traffic is switched back to
                             work port after it comes back."
                DEFVAL { nonrevertive }
                ::= { oc3APSPairConfigEntry 3 }

oc3APSPairWorkingSFBERThreshold OBJECT-TYPE
                SYNTAX INTEGER {
                                tenToMinus4(1),
                                tenToMinus5(2)
                                }
                MAX-ACCESS read-write
                STATUS current
                DESCRIPTION "Bits error Rate threshold to declare signal failure"
                DEFVAL { tenToMinus4 }
                ::= { oc3APSPairConfigEntry 4 }


oc3APSPairProtectionSFBERThreshold OBJECT-TYPE
                SYNTAX INTEGER {
                                tenToMinus4(1),
                                tenToMinus5(2)
                                }
                MAX-ACCESS read-write
                STATUS current
                DESCRIPTION "Bits error Rate threshold to declare signal failure"
                DEFVAL { tenToMinus4 }
                ::= { oc3APSPairConfigEntry 6 }

oc3APSPairWorkingSDBERThreshold OBJECT-TYPE
                SYNTAX INTEGER {
                                tenToMinus5(1),
                                tenToMinus6(2),
                                tenToMinus7(3),
                                tenToMinus8(4)
                                }
                MAX-ACCESS read-write
                STATUS current
                DESCRIPTION "Bits error Rate threshold to declare signal degrade"
                DEFVAL { tenToMinus5 }
                ::= { oc3APSPairConfigEntry 5 }

oc3APSPairProtectionSDBERThreshold OBJECT-TYPE
                SYNTAX INTEGER {
                                tenToMinus5(1),
                                tenToMinus6(2),
                                tenToMinus7(3),
                                tenToMinus8(4)
                                }
                MAX-ACCESS read-write
                STATUS current
                DESCRIPTION "Bits error Rate threshold to declare signal degrade" 
                DEFVAL { tenToMinus5 }
                ::= { oc3APSPairConfigEntry 7 }

 
oc3APSPairWTRPeriod OBJECT-TYPE
                SYNTAX INTEGER (5..12)
                MAX-ACCESS read-write
                STATUS current
                DESCRIPTION " Duration for Wait To Restore Period between 5
                             to 12 minutes. Ref: BellCore GR-253-Core,
                             Issue 3, page 200, R5-56."
                DEFVAL { 5 }
                ::= { oc3APSPairConfigEntry 8 }

oc3APSWorkingSlot OBJECT-TYPE
                SYNTAX Integer32
                MAX-ACCESS read-only
                STATUS current
                DESCRIPTION "Working slot of APS pair."
                ::= { oc3APSPairConfigEntry 9 }

oc3APSProtectionSlot OBJECT-TYPE
                SYNTAX Integer32
                MAX-ACCESS read-only
                STATUS current
                DESCRIPTION "Protection slot of APS pair."
                ::= { oc3APSPairConfigEntry 10 }

oc3APSActiveSlot OBJECT-TYPE
                SYNTAX Integer32
                MAX-ACCESS read-only
                STATUS current
                DESCRIPTION "Active slot of APS pair."
                ::= { oc3APSPairConfigEntry 11 }

oc3APSPairStatus OBJECT-TYPE
                SYNTAX INTEGER {
                                noFailure(1),
                                modeMismatch(2),
                                swByteFailure(3),
                                chMismatch(4)
                                }
                MAX-ACCESS read-only
                STATUS current
                DESCRIPTION "noFailure   : The protection line is not in use.
                            modeMismatch : one end is configured unidirectional 
                                           and the other is bidirectional (both 
                                           the ends should be configured in the same mode).
                                           Also when one end is configured for 1:1 architechture 
                                           and the other end indicates it is configured for 
                                           1:n architechture.(Bidirectional mode only)
                            swByteFailure: protection switching byte failure - defect declared 
                                           when invalid / persistantly unacceptable codes are 
                                           received in the K1 byte. failure declared if defect 
                                           persists for an extended period.
                                           Invalid code is when the incoming K1 byte contains 
                                           an unused code or a code irrelevant for the specific 
                                           switching operation.(Only in bi-directional mode)
                            chMismatch   : channel mismatch is declared when the channel numbers 
                                           in the transmitted K1 byte and the received K2 byte
                                           do not match for 50 ms.Channel mismatch is monitored 
                                           only in bidirectional mode."
                                                          
                DEFVAL { noFailure }
                ::= { oc3APSPairConfigEntry 12 }


oc3APSPairUserCommand OBJECT-TYPE
                SYNTAX INTEGER {
                                noAction(1),
                                manualSwitchToWorkingPort(2),
                                manualSwitchToProtectionPort(3),
                                forcedSwitchToWorkingPort(4),
                                forcedSwitchToProtectionPort(5),
                                lockoutProtection(6),
                                clear(7)
                                }
                MAX-ACCESS read-write
                STATUS current
                DESCRIPTION "APS Pair User Command"
                DEFVAL { noAction }
                ::= { oc3APSPairConfigEntry 13 }


oc3APSPairCurrentState OBJECT-TYPE
                SYNTAX INTEGER {
                                localprotectDoNotRevert(1),
                                localprotectManualSw(8),
                                localprotectSD(10),
                                localprotectSF(12), 
                                localprotectForced(14),
                                localprotectLockOut(15),
                                   localworkingDoNotRevert(17),
                                   localworkingManualSw(24),
                                   localworkingSD(26),
                                localworkingSF(28),
                                localworkingForced(30),
                                remoteprotectDoNotRevert(33),
                                remoteprotectManualSw(40),
                                remoteprotectSD(42),
                                remoteprotectSF(44),
                                remoteprotectForced(46),
                                remoteprotectLockOut(47),
                                   noRequest(48),
                                remoteworkingDoNotRevert(49),
                                remoteworkingManualSw(56),
                                remoteworkingSD(58),
                                remoteworkingSF(60),
                                remoteworkingForced(62)
                                }
                MAX-ACCESS read-only
                STATUS current
                DESCRIPTION "Current State of the APS state machine"
                DEFVAL { noRequest }
                ::= { oc3APSPairConfigEntry 14 }

oc3APSPairWorkingLineSignalStatus OBJECT-TYPE
                SYNTAX INTEGER {
                                noAlarm(1),
                                signalDegradation(2),
                                signalFailure(4),
                                lostCellDelineation(8),
                                switchByteFailure(16),
                                ais-l(32),
                                ais-p(64),
                                lop(128),
                                lof(256),
                                los(512),
                                moduleFailure(1024),
                                lineLoopBack(2048),
                                protocolFailure(4096),
                                adminOutOfService(8192)
                                }
                MAX-ACCESS read-only
                STATUS current
                DESCRIPTION "Signal Status of the working port
                              (LOS / LOF / LCD / AIS etc.)"
                ::= { oc3APSPairConfigEntry 15 }

oc3APSPairProtectionLineSignalStatus OBJECT-TYPE
                SYNTAX INTEGER {
                                noAlarm(1),
                                signalDegradation(2),
                                signalFailure(4),
                                lostCellDelineation(8),
                                switchByteFailure(16),
                                ais-l(32),
                                ais-p(64),
                                lop(128),
                                lof(256),
                                los(512),
                                moduleFailure(1024),
                                lineLoopBack(2048),
                                protocolFailure(4096),    
                                adminOutOfService(8192)
                                }
                MAX-ACCESS read-only
                STATUS current
                DESCRIPTION "Signal Status of the protection
                             port (LOS / LOF / LCD / AIS etc.)"
                ::= { oc3APSPairConfigEntry 16 }


oc3APSPairStatsTable OBJECT-TYPE
                SYNTAX SEQUENCE OF Oc3APSPairStatsEntry
                MAX-ACCESS not-accessible
                STATUS current
                DESCRIPTION "Table of statisics for a OC3 port"
                ::= { equipStatistics 8 }

oc3APSPairStatsEntry OBJECT-TYPE
                SYNTAX Oc3APSPairStatsEntry
                MAX-ACCESS not-accessible
                STATUS current
                DESCRIPTION "Row definition for the OC3 port statistics
                             table"
                INDEX { oc3APSPairStatsId }
                ::= { oc3APSPairStatsTable 1 }

Oc3APSPairStatsEntry ::= SEQUENCE {
                        oc3APSPairStatsId                Integer32,
                        oc3APSPairWorkingSFDuration        Integer32,
                        oc3APSPairWorkingSDDuration        Integer32,
                        oc3APSPairProtectionSFDuration        Integer32,
                        oc3APSPairProtectionSDDuration        Integer32,
                        oc3APSPairTransmitK1K2Bytes        OCTET STRING,
                        oc3APSPairReceiveK1K2Bytes        OCTET STRING,
                        oc3APSPairSwitchOverCount        Integer32
                        }

oc3APSPairStatsId        OBJECT-TYPE
                SYNTAX Integer32
                MAX-ACCESS not-accessible
                STATUS current
                DESCRIPTION "Working Port ID - Slot/Port (SSPP)"
                ::= { oc3APSPairStatsEntry 1 }

oc3APSPairWorkingSFDuration OBJECT-TYPE
                SYNTAX Integer32
                MAX-ACCESS read-only
                STATUS current
                DESCRIPTION "Duration in seconds for which the Work port
                             has been in Signal Failure state "
                ::= { oc3APSPairStatsEntry 2 }

oc3APSPairWorkingSDDuration OBJECT-TYPE
                SYNTAX Integer32
                MAX-ACCESS read-only
                STATUS current
                DESCRIPTION "Duration in seconds for which the Work port
                             has been in Signal Degradation state "
                ::= { oc3APSPairStatsEntry 3 }

oc3APSPairProtectionSFDuration OBJECT-TYPE
                SYNTAX Integer32
                MAX-ACCESS read-only
                STATUS current
                DESCRIPTION "Duration in seconds for which the Prot
                             port has been in Signal Failure state "
                ::= { oc3APSPairStatsEntry 4 }

oc3APSPairProtectionSDDuration OBJECT-TYPE
                SYNTAX Integer32
                MAX-ACCESS read-only
                STATUS current
                DESCRIPTION "Duration in seconds for which
                          the Prot port has been in Signal Degradation state"
                ::= { oc3APSPairStatsEntry 5 }

oc3APSPairTransmitK1K2Bytes OBJECT-TYPE
                SYNTAX OCTET STRING (SIZE(2))
                MAX-ACCESS read-only
                STATUS current
                DESCRIPTION "The k1 / k2 bytes being transmitted by the prot
                             port to the remote port. "
                ::= { oc3APSPairStatsEntry 6 }

oc3APSPairReceiveK1K2Bytes OBJECT-TYPE
                SYNTAX OCTET STRING (SIZE(2))
                MAX-ACCESS read-only
                STATUS current
                DESCRIPTION "k1 / k2 bytes from the received SONET header
                             on the protection port. k1 / k2 are used for
                             the APS communication protocol. "
                ::= { oc3APSPairStatsEntry 7 }

oc3APSPairSwitchOverCount OBJECT-TYPE
                SYNTAX Integer32
                MAX-ACCESS read-only
                STATUS current
                DESCRIPTION "Number of times the APS pair has switched over
                             since last configuration."
                ::= { oc3APSPairStatsEntry 8 }

twoWireSourcePortConfigTable OBJECT-TYPE
                SYNTAX SEQUENCE OF TwoWireSourcePortConfigEntry
                MAX-ACCESS not-accessible
                STATUS current
                DESCRIPTION "Table of common physical Port attributes"
                ::= { equipConfig 7 }
 
twoWireSourcePortConfigEntry OBJECT-TYPE
                SYNTAX TwoWireSourcePortConfigEntry
                MAX-ACCESS not-accessible
                STATUS current
                DESCRIPTION "Row definition for common physical
                             port attributes"
                INDEX { twoWireSourcePortId }
                ::= { twoWireSourcePortConfigTable 1 }
 
TwoWireSourcePortConfigEntry ::= SEQUENCE {
                twoWireSourcePortId               Integer32,
                twoWireSourceLoopDetection          INTEGER,
                twoWireSourceDialMode             INTEGER,
                twoWireSourceLoopBackConfig     INTEGER,
                twoWireSourceLineStatus           INTEGER,
                twoWireSourceSignalingBits             INTEGER,
                twoWireSourceRingCadence             INTEGER,
                twoWireSourceSignalingState           INTEGER,
                twoWireSourceTestMode                  INTEGER
                }
 
twoWireSourcePortId      OBJECT-TYPE
                SYNTAX Integer32
                MAX-ACCESS not-accessible
                STATUS current
                DESCRIPTION "interface index - SSPP"
                ::= { twoWireSourcePortConfigEntry 1 }
 
twoWireSourceLoopDetection OBJECT-TYPE
                SYNTAX INTEGER  {
                                loopStart(1),
                                groundStart(2)
                                }
                MAX-ACCESS read-only
                STATUS current
                DESCRIPTION "This field selects terminal equipment loop circuit
                             detection mode."
                DEFVAL { loopStart }
                ::= { twoWireSourcePortConfigEntry 2 }
 
twoWireSourceDialMode OBJECT-TYPE
                SYNTAX INTEGER  {
                                dtmf(1),
                                dialPulse(2)
                                }
                MAX-ACCESS read-only
                STATUS current
                DESCRIPTION "This field configures twoWireSource card to 
                             support communication terminal equipment."
                DEFVAL { dtmf }
                ::= { twoWireSourcePortConfigEntry 3 }
 
twoWireSourceLoopBackConfig OBJECT-TYPE
                SYNTAX INTEGER  {
                                noLoopback(1),
                                facilityLoopback(2)
                                }
                MAX-ACCESS read-only
                STATUS current
                DESCRIPTION " Configuration of 2W Source LoopBack."  
                DEFVAL { noLoopback }
                ::= { twoWireSourcePortConfigEntry 4 }

twoWireSourceLineStatus  OBJECT-TYPE
                SYNTAX INTEGER (1..1023)
                MAX-ACCESS read-only
                STATUS current
                DESCRIPTION "twoWireSource line status:
                1:  NoAlarm: No alarm present
                2:  SignalingFailureState
                4:  FacilityLoopBack
                8:  Maintenance
                16: Out Of Service
                32: OtherFailure  "
                DEFVAL { 1 }
                ::= { twoWireSourcePortConfigEntry 5 }
 
twoWireSourceSignalingBits OBJECT-TYPE
                SYNTAX INTEGER  {
                                ab(1),
                                abcd(2)
                                }
                MAX-ACCESS read-only
                STATUS current
                DESCRIPTION "This field selects the signaling bits as seen in
                             DS1 signal, ab or abcd."
                DEFVAL { ab }
                ::= { twoWireSourcePortConfigEntry 6 }

twoWireSourceRingCadence OBJECT-TYPE
                SYNTAX INTEGER  {
                                oneOnThreeOff(1)
                                }
                MAX-ACCESS read-only
                STATUS current
                DESCRIPTION "This field selects ring On/Off pattern."
                DEFVAL { oneOnThreeOff }
                ::= { twoWireSourcePortConfigEntry 7 }

twoWireSourceSignalingState OBJECT-TYPE
                SYNTAX INTEGER  {
                                idle(1),
                                dtmf(2),
                                ringBack(3),
                                connect(4),
                                onHook(5),
                                ringTrip(6),
                                nearEndDisconnect(7),
                                farEndDisconnect(8)
                                }
                MAX-ACCESS read-only
                STATUS current
                DESCRIPTION "This field reflects the current signaling state."
                DEFVAL { idle }
                ::= { twoWireSourcePortConfigEntry 8 }

twoWireSourceTestMode OBJECT-TYPE
                SYNTAX INTEGER  {
                                off(1),
                                quietTime(2),
                                f-1004Hz(3)
                                }
                MAX-ACCESS read-write
                STATUS current
                DESCRIPTION "This field selects line test mode.  For normal
                             operation, this field should be OFF."
                DEFVAL { off }
                ::= { twoWireSourcePortConfigEntry 9 }

highSpeedPortConfigTable OBJECT-TYPE
                SYNTAX SEQUENCE OF HighSpeedPortConfigEntry
                MAX-ACCESS not-accessible
                STATUS current
                DESCRIPTION "Table of common physical Port attributes"
                ::= { equipConfig 8 }

highSpeedPortConfigEntry OBJECT-TYPE
                SYNTAX HighSpeedPortConfigEntry
                MAX-ACCESS not-accessible
                STATUS current
                DESCRIPTION "Row definition for common physical
                             port attributes"
                INDEX { highSpeedPortId }
                ::= { highSpeedPortConfigTable 1 }

HighSpeedPortConfigEntry ::= SEQUENCE {
                highSpeedPortId          Integer32,
                highSpeedPortInputRate   Integer32,
                highSpeedPortOutputRate  Integer32
                }

highSpeedPortId      OBJECT-TYPE
                SYNTAX Integer32
                MAX-ACCESS not-accessible
                STATUS current
                DESCRIPTION "interface index - SSPP"
                ::= { highSpeedPortConfigEntry 1 }

highSpeedPortInputRate OBJECT-TYPE
                SYNTAX Integer32
                MAX-ACCESS read-write
                STATUS current
                DESCRIPTION "Port input rate"
                ::= { highSpeedPortConfigEntry 2 }

highSpeedPortOutputRate OBJECT-TYPE
                SYNTAX Integer32
                MAX-ACCESS read-write
                STATUS current
                DESCRIPTION "Port output rate"
                ::= { highSpeedPortConfigEntry 3 }

dspPortConfigTable OBJECT-TYPE
                SYNTAX SEQUENCE OF DspPortConfigEntry
                MAX-ACCESS not-accessible
                STATUS current
                DESCRIPTION "Table of common physical Port attributes"
                ::= { equipConfig 9 }
 
dspPortConfigEntry OBJECT-TYPE
                SYNTAX DspPortConfigEntry
                MAX-ACCESS not-accessible
                STATUS current
                DESCRIPTION "Row definition for common physical
                             port attributes"
                INDEX { dspPortId }
                ::= { dspPortConfigTable 1 }
 
DspPortConfigEntry ::= SEQUENCE {
                dspPortId       Integer32
                }
 
dspPortId      OBJECT-TYPE
                SYNTAX Integer32
                MAX-ACCESS read-only
                STATUS current
                DESCRIPTION "interface index - SSPP"
                ::= { dspPortConfigEntry 1 }
 
twoWireSinkPortConfigTable OBJECT-TYPE
                SYNTAX SEQUENCE OF TwoWireSinkPortConfigEntry
                MAX-ACCESS not-accessible
                STATUS current
                DESCRIPTION "Table of common physical Port attributes"
                ::= { equipConfig 10 }
 
twoWireSinkPortConfigEntry OBJECT-TYPE
                SYNTAX TwoWireSinkPortConfigEntry
                MAX-ACCESS not-accessible
                STATUS current
                DESCRIPTION "Row definition for common physical
                             port attributes"
                INDEX { twoWireSinkPortId }
                ::= { twoWireSinkPortConfigTable 1 }
 
TwoWireSinkPortConfigEntry ::= SEQUENCE {
                twoWireSinkPortId               Integer32,
                twoWireSinkLoopDetection        INTEGER,
                twoWireSinkDialMode             INTEGER,
                twoWireSinkLineStatus           INTEGER,
                twoWireSinkSignalingBits        INTEGER,
                twoWireSinkSignalingState       INTEGER,
                twoWireSinkTestMode             INTEGER
                }
 
twoWireSinkPortId OBJECT-TYPE
                SYNTAX Integer32
                MAX-ACCESS not-accessible
                STATUS current
                DESCRIPTION "interface index - SSPP"
                ::= { twoWireSinkPortConfigEntry 1 }
 
twoWireSinkLoopDetection OBJECT-TYPE
                SYNTAX INTEGER  {
                                loopStart(1),
                                groundStart(2)
                                }
                MAX-ACCESS read-only
                STATUS current
                DESCRIPTION " Types of loop detection.  "
                DEFVAL { loopStart }
                ::= { twoWireSinkPortConfigEntry 2 }
 
twoWireSinkDialMode OBJECT-TYPE
                SYNTAX INTEGER  {
                                dtmf(1),
                                dialPulse(2)
                                }
                MAX-ACCESS read-only
                STATUS current
                DESCRIPTION "This field selects subscribed dial mode."
                DEFVAL { dtmf }
                ::= { twoWireSinkPortConfigEntry 3 }
 
twoWireSinkLineStatus OBJECT-TYPE
                SYNTAX INTEGER (1..1023)
                MAX-ACCESS read-only
                STATUS current
                DESCRIPTION "twoWireSink line status:
                1:  NoAlarm: No alarm present
                2:  SignalingFailureState
                4:  FacilityLoopBack
                8:  Maintenance
                16: Out Of Service
                32: OtherFailure  "
                DEFVAL { 1 }
                ::= { twoWireSinkPortConfigEntry 4 }
 
twoWireSinkSignalingBits OBJECT-TYPE
                SYNTAX INTEGER  {
                                ab(1),
                                abcd(2)
                                }
                MAX-ACCESS read-only
                STATUS current
                DESCRIPTION "This field selects the signaling bits as seen in
                             DS1 signal, ab or abcd."
                DEFVAL { ab }
                ::= { twoWireSinkPortConfigEntry 5 }

twoWireSinkSignalingState OBJECT-TYPE
                SYNTAX INTEGER  {
                                idle(1),
                                connect(2),
                                onHook(3),
                                ringTrip(4),
                                nearEndDisconnect(5),
                                farEndDisconnect(6)
                                }
                MAX-ACCESS read-only
                STATUS current
                DESCRIPTION "This field reflects the current signaling state."
                DEFVAL { idle }
                ::= { twoWireSinkPortConfigEntry 6 }

twoWireSinkTestMode OBJECT-TYPE
                SYNTAX INTEGER  {
                                off(1),
                                quietTime(2),
                                f-1004Hz(3)
                                }
                MAX-ACCESS read-write
                STATUS current
                DESCRIPTION "This field selects line test mode.  For normal
                             operation, this field should be OFF."
                DEFVAL { off }
                ::= { twoWireSinkPortConfigEntry 7 }

e3PortConfigTable  OBJECT-TYPE
                SYNTAX SEQUENCE OF E3PortConfigEntry
                MAX-ACCESS not-accessible
                STATUS current
                DESCRIPTION "Table of e3 specific port attributes"
                ::= { equipConfig 11 }

e3PortConfigEntry  OBJECT-TYPE
                SYNTAX E3PortConfigEntry
                MAX-ACCESS not-accessible
                STATUS current
                DESCRIPTION "Row definition for e3 specific
                             port attributes"
                INDEX { e3PortId }
                ::= { e3PortConfigTable 1 }

E3PortConfigEntry  ::= SEQUENCE {
                e3PortId                       Integer32,
                e3LineType                     INTEGER,
                e3LineCoding                   INTEGER,
                e3LoopbackConfig               INTEGER,
                e3TransmitClockSource          INTEGER,
                e3LineStatus                   INTEGER,
                e3LineBuildOut                 INTEGER,
                e3LineScramble                 INTEGER,
                e3CellMapping                  INTEGER
                }
                
 
e3PortId        OBJECT-TYPE
                SYNTAX Integer32 
                MAX-ACCESS not-accessible
                STATUS current
                DESCRIPTION "slot/port: SSPP"
                ::= { e3PortConfigEntry 1 }
 
e3LineType      OBJECT-TYPE
                SYNTAX INTEGER  {
                                g832(1),
                                g751(2)
                                }
                MAX-ACCESS read-write
                STATUS current
                DESCRIPTION "This variable indicates the basic frame structure
                                  supported in this E3 port. The rate of E3 is
                                   34.368 Mbps.
                                   TITLE:            SPECIFICATION:
                                   G.832             ITU-T G.832 1993.
                                   G.751             ITU-T G.751 1998"
                DEFVAL { g832 }
                ::= { e3PortConfigEntry 2 }
 
e3LineCoding    OBJECT-TYPE
                SYNTAX INTEGER  {
                                hdb3(1)
                                }
                MAX-ACCESS read-only
                STATUS current
                DESCRIPTION "The line code supported for the E3 port.
                                   The High Density Bipolar of order 3 (hdb3)
                                   as specified in section 8.1 of ITU-T G.703."
                DEFVAL { hdb3 }
                ::= { e3PortConfigEntry 3 }

e3LoopbackConfig       OBJECT-TYPE
                SYNTAX INTEGER  {
                                noLoop(1),
                                localLoop(2),
                                lineLoop(3),
                                payloadLoop(4)
                                }
                MAX-ACCESS read-write
                STATUS current
                DESCRIPTION "This variable represents the loopback 
                                    configuration of the E3 interface.

                                    See above diagrams for explanations of loops."
                DEFVAL { noLoop }
                ::= { e3PortConfigEntry 4 }
 
e3TransmitClockSource  OBJECT-TYPE
                SYNTAX INTEGER  {
                                loopTiming(1),
                                localTiming(2),
                                adaptiveTiming(3) 
                                }
                MAX-ACCESS read-write
                STATUS current
                DESCRIPTION "The source of Tranmit Clock.
                               'loopTiming' indicates that the recovered  re-
                             ceive clock is used as the transmit clock.
                               'localTiming' indicates  that  a  local  clock
                             source is used.
                             'adaptiveTiming'  indicates that the adaptive clocking
                              mechanism is used."
                DEFVAL { localTiming }
                ::= { e3PortConfigEntry 5 }

e3LineStatus  OBJECT-TYPE
                SYNTAX INTEGER (1..1023)
                MAX-ACCESS read-only
                STATUS current
                DESCRIPTION "e3 line status:
                1: e3NoAlarm: No alarm present
                2: e3RcvRAIFailure: Receiving Yellow/Remote Alarm Indication
                4: e3XmitRAIAlarm: Transmitting Yellow/Remote Alarm Indication
                8: e3RcvAIS: Receiving AIS failure state
                16: e3XmitAIS: Transmitting AIS failure statue
                32: e3LOF: Receiving LOF failure state
                64: e3LOS: Reveiving LOS failure state
                128: e3LoopbackState: Looping the received signal
                256: e3RcvTestCode: Receiving a Test Pattern
                512: e3OtherFailure: any line status not defined "
                DEFVAL { 1 }
                ::= { e3PortConfigEntry 6 }

e3LineBuildOut  OBJECT-TYPE
                SYNTAX INTEGER  {
                                short(1),
                                long(2)
                                }
                MAX-ACCESS read-only
                STATUS current
                DESCRIPTION "e3 line build out"
                DEFVAL { long }
                ::= { e3PortConfigEntry 7 }

e3LineScramble  OBJECT-TYPE
                SYNTAX INTEGER  {
                                enabled(1),
                                disabled(2)
                                }
                MAX-ACCESS read-write
                STATUS current
                DESCRIPTION "e3 line scramble"
                DEFVAL { enabled }
                ::= { e3PortConfigEntry 8 }

e3CellMapping   OBJECT-TYPE
                SYNTAX INTEGER  {
                                directMapping(1),
                                plcp(2)
                                }
                MAX-ACCESS read-write
                STATUS current
                DESCRIPTION "e3 cell mapping method"
                DEFVAL { directMapping }
                ::= { e3PortConfigEntry 9 }

e1PortConfigTable  OBJECT-TYPE
                SYNTAX SEQUENCE OF E1PortConfigEntry
                MAX-ACCESS not-accessible
                STATUS current
                DESCRIPTION "Table of e1 specific port attributes"
                ::= { equipConfig 12 }

e1PortConfigEntry  OBJECT-TYPE
                SYNTAX E1PortConfigEntry
                MAX-ACCESS not-accessible
                STATUS current
                DESCRIPTION "Row definition for e1 specific port attributes"
                INDEX { e1PortId }
                ::= { e1PortConfigTable 1 }

E1PortConfigEntry  ::= SEQUENCE {
                e1PortId                       Integer32,
                e1Channelization        INTEGER,
                e1LineType                     INTEGER,
                e1LineCoding                   INTEGER,
                e1LoopbackConfig        INTEGER,
                e1TransmitClockSource   INTEGER,
                e1LineNationalBits         INTEGER,
                e1LineStatus                INTEGER,



                e1TS16                        INTEGER,
                e1DataTransferType        INTEGER,
                e1CRC4                        INTEGER,
                e1OamInterworkingType        INTEGER,

                e1EnhanceFeatureSet1        INTEGER ,
                e1ConnGatewayFeature    INTEGER

}

e1PortId        OBJECT-TYPE
                SYNTAX Integer32 
                MAX-ACCESS not-accessible
                STATUS current
                DESCRIPTION "interface index - slot/port: SSPP"
                ::= { e1PortConfigEntry 1 }
 
e1Channelization        OBJECT-TYPE
                SYNTAX INTEGER  {
                                 disabled(1),
                                 enabled(2)
                                }
                MAX-ACCESS read-write
                STATUS current
                DESCRIPTION "e1 interface type"
                DEFVAL { disabled }
                ::= { e1PortConfigEntry 2 }
 
e1LineType      OBJECT-TYPE
                SYNTAX INTEGER  {
                                crc-mf(1)
                                }
                MAX-ACCESS read-only
                STATUS current
                DESCRIPTION "E1 interface type.
                             The rate of E1 is 2.048 Mbps"
                DEFVAL { crc-mf }
                ::= { e1PortConfigEntry 3 }
 
e1LineCoding    OBJECT-TYPE
                SYNTAX INTEGER  {
                                hdb3(1)
                                }
                MAX-ACCESS read-only
                STATUS current
                DESCRIPTION "e1 interface type"
                DEFVAL { hdb3 }
                ::= { e1PortConfigEntry 4 }
   
e1LoopbackConfig       OBJECT-TYPE
                SYNTAX INTEGER  {
                                noLoop(1),
                                localLoop(2),
                                lineLoop(3)
                                }
                MAX-ACCESS read-write
                STATUS current
                DESCRIPTION "This variable represents the loopback
                               configuration of the e1 interface
 
                                    See above diagrams for explanations of loops."
                DEFVAL { noLoop }
                ::= { e1PortConfigEntry 5 }
 
e1TransmitClockSource  OBJECT-TYPE
                SYNTAX INTEGER  {
                                loopTiming(1),
                                localTiming(2),
                                adaptive(3)
                                }
                MAX-ACCESS read-write
                STATUS current
                DESCRIPTION "e1 timing source"
                DEFVAL { localTiming }
                ::= { e1PortConfigEntry 6 }

e1LineNationalBits  OBJECT-TYPE
                SYNTAX INTEGER  {
                                b00000(1),
                                b00001(2),
                                b00010(3),
                                b00011(4),
                                b00100(5),
                                b00101(6),
                                b00110(7),
                                b00111(8),
                                b01000(9),
                                b01001(10),
                                b01010(11),
                                b01011(12),
                                b01100(13),
                                b01101(14),
                                b01110(15),
                                b01111(16),
                                b10000(17),
                                b10001(18),
                                b10010(19),
                                b10011(20),
                                b10100(21),
                                b10101(22),
                                b10110(23),
                                b10111(24),
                                b11000(25),
                                b11001(26),
                                b11010(27),
                                b11011(28),
                                b11100(29),
                                b11101(30),
                                b11110(31),
                                b11111(32)
                                }
                MAX-ACCESS read-write
                STATUS current
                DESCRIPTION "e1 line country specific code"
                ::= { e1PortConfigEntry 7 }

e1LineStatus    OBJECT-TYPE
                SYNTAX INTEGER (1..8191)
                MAX-ACCESS read-only
                STATUS current
                DESCRIPTION "This variable indicates the Line Status of the
                             interface. It contains loopback, failure, re-
                             ceived 'alarm' and transmitted 'alarm' infor-
                             mation.

                                  The e1LineStatus is a bit map represented  
                             as a sum, therefore, it can represent multiple 
                             failures (alarms) and a LoopbackState 
                             simultaneously.

                                  e1NoAlarm should be set if and only if no other 
                             flag is set.

                                  If the e1LoopbackState bit is set, the loopback
                             in effect can be determined from the 
                             e1LoopbackConfig object.

                     The various bit positions are:
                  1:       e1NoAlarm:          No Alarm Present
                  2:       e1RcvFarEndLOF:     Far end LOF (a.k.a., Yellow 
                                             Alarm)
                  4:       e1XmtFarEndLOF:     Near end sending LOF Indication
                  8:       e1RcvAIS:           Far end sending AIS
                 16:      e1XmtAIS:           Near end sending AIS
                 32:      e1LossOfFrame:      Near end LOF (a.k.a., Red Alarm)
                 64:      e1LossOfSignal:     Near end Loss Of Signal
                128:     e1LoopbackState:    Near end is looped
                256:     e1T16AIS:           E1 TS16 AIS
                512:     e1RcvFarEndLOMF:    Far End Sending TS16 LOMF
                       1024:    e1XmtFarEndLOMF:    Near End Sending TS16 LOMF
                       2048:    e1RcvTestCode:      Near End detects a test code
                       4096:    e1OtherFailure:     any line status not defined 
                                             here"
                DEFVAL { 1 }
                ::= { e1PortConfigEntry 8 }




e1TS16                OBJECT-TYPE
                SYNTAX INTEGER {
                                cas(1),
                                ccs(2)
                                }
                MAX-ACCESS read-write
                STATUS current
                DESCRIPTION "Time slot 16 is configurable for channel 
                             associated signaling (CAS) or data.

                             cas: 'ABCD' signaling will be extracted in time
                             slot 16 if channel is configured for circuit
                             emulation.
                             ccs: time slot 16 will not carry any e1 channel
                             signaling information, instead, it will be used
                             for data."
                DEFVAL { ccs }
                ::= { e1PortConfigEntry 10 }

e1DataTransferType OBJECT-TYPE
                SYNTAX INTEGER  {
                                structured(1),
                                unstructured(2)
                                }
                MAX-ACCESS read-write
                STATUS current
                DESCRIPTION "E1 data transfer type is only applicable in 
                             Circuit Emulation where unstructured CE packets 
                             entire T1 frame including the F-bit into the AAL1
                             for data tranfer, whereas, the structured CE 
                             packets the entire E1 frame except the Frame
                             alignment signal channel."
                DEFVAL { structured }
                ::= { e1PortConfigEntry 11 }
 
e1CRC4                OBJECT-TYPE
                SYNTAX INTEGER {
                                enabled(1),
                                disabled(2)
                                }
                MAX-ACCESS read-write
                STATUS current
                DESCRIPTION "Enable or disable transmission of CRC4 bits on 
                             bit 1 of each frame."
                DEFVAL { enabled }
                ::= { e1PortConfigEntry 12 }

e1OamInterworkingType OBJECT-TYPE
                SYNTAX INTEGER {
                        trunkCond(1),
                        unframed1s(2)
                        }
                MAX-ACCESS read-write
                STATUS current
                DESCRIPTION "Specifies whether the interworking is done 
                             by trunk conditioning or unframed1s"
                DEFVAL {trunkCond }
                ::= {e1PortConfigEntry 13 }


e1EnhanceFeatureSet1 OBJECT-TYPE
                SYNTAX INTEGER {
                        disabled(1),
                        enabled(2)
                        }
                MAX-ACCESS read-write
                STATUS current
                DESCRIPTION "To enable/disable a proprietary ab signaling
                             scheme, it applies to all DS0s in the port.
                             No individual DS0 signaling can be 
                             configured under the scheme."
                             
                DEFVAL { disabled }
                ::= {e1PortConfigEntry 14 }

e1ConnGatewayFeature OBJECT-TYPE
                SYNTAX INTEGER  {
                                disabled(1),
                                enabled(2)
                                }
                MAX-ACCESS read-write
                STATUS current
                DESCRIPTION "To enable/disable connection gateway
                                (Sapphire) API."
                DEFVAL { disabled }
                ::= { e1PortConfigEntry 15 }


ethernetPortConfigTable OBJECT-TYPE
                SYNTAX SEQUENCE OF EthernetPortConfigEntry
                MAX-ACCESS not-accessible
                STATUS current
                DESCRIPTION "Table of common physical Port attributes"
                ::= { equipConfig 13 }
 
ethernetPortConfigEntry OBJECT-TYPE
                SYNTAX EthernetPortConfigEntry
                MAX-ACCESS not-accessible
                STATUS current
                DESCRIPTION "Row definition for common physical
                             port attributes"
                INDEX { ethernetPortId }
                ::= { ethernetPortConfigTable 1 }
 
EthernetPortConfigEntry ::= SEQUENCE {
                ethernetPortId               Integer32,
                ethernetLinkType        INTEGER,
                ethernetPhysicalAddr        OCTET STRING,
                ethernetLineStatus        INTEGER,
                ethernetDuplexMode        INTEGER
                }
 
ethernetPortId        OBJECT-TYPE
                SYNTAX Integer32
                MAX-ACCESS not-accessible
                STATUS current
                DESCRIPTION "interface index - SSPP"
                ::= { ethernetPortConfigEntry 1 }
 
ethernetLinkType OBJECT-TYPE
                SYNTAX INTEGER  {
                                l-10BaseT(1),
                                l-100BaseT(2),
                                auto(3)
                                }
                MAX-ACCESS read-write
                STATUS current
                DESCRIPTION "The type of port can either be set to 10baseT or
                             100baseT for the first port on the ethernet card.
                             The other ports can only be set to 10baseT.  The
                             Auto mode will detect what LAN speed the port is
                             connected to."
                DEFVAL { l-10BaseT }
                ::= { ethernetPortConfigEntry 2 }
 
ethernetPhysicalAddr OBJECT-TYPE
                SYNTAX OCTET STRING (SIZE(6))
                MAX-ACCESS read-write
                STATUS current
                DESCRIPTION "The MAC address used by this bridge when it must
                             be referred to in a unique fashion.  It is 
                             recommended that this be the numerically smallest
                             MAC address of all ports that belong to this
                             bridge.  However it is only required to be unique.
                             When concatenated with dot1dSprPriority a unique
                             Bridgeidentifier is formed which is used in the
                             Spanning Tree Protocol."
                REFERENCE "IEEE 802.1D-1990: Sections 6.4.1.1.3 and 3.12.5"
                ::= { ethernetPortConfigEntry 3 }

ethernetLineStatus OBJECT-TYPE
                SYNTAX INTEGER (1..31)
                MAX-ACCESS read-only
                STATUS current
                DESCRIPTION "ethernet line status:
                        1: Down
                        2: 10baseT-FullDuplex
                        4: 10baseT-HalfDuplex
                        8: 100baseT-FullDuplex
                       16: 100baseT-HalfDuplex  "
                DEFVAL { 1 }
                ::= { ethernetPortConfigEntry 4 }
 
ethernetDuplexMode OBJECT-TYPE
                SYNTAX INTEGER  {
                                full(1),
                                half(2),
                                auto(3)
                                }
                MAX-ACCESS read-write
                STATUS current
                DESCRIPTION "Set the port to either be in full or half duplex.
                             You can also set the port to auto detect the mode
                             it is connected to."
                DEFVAL { full }
                ::= { ethernetPortConfigEntry 5 }


dsp2PortConfigTable OBJECT-TYPE
                SYNTAX SEQUENCE OF Dsp2PortConfigEntry
                MAX-ACCESS not-accessible
                STATUS current
                DESCRIPTION "Table of common physical Port attributes"
                ::= { equipConfig 14 }
 
dsp2PortConfigEntry OBJECT-TYPE
                SYNTAX Dsp2PortConfigEntry
                MAX-ACCESS not-accessible
                STATUS current
                DESCRIPTION "Row definition for common physical
                             port attributes"
                INDEX { dsp2PortId }
                ::= { dsp2PortConfigTable 1 }
 
Dsp2PortConfigEntry ::= SEQUENCE {
                dsp2PortId       Integer32
                }
 
dsp2PortId      OBJECT-TYPE
                SYNTAX Integer32
                MAX-ACCESS read-only
                STATUS current
                DESCRIPTION "interface index - SSPP"
                ::= { dsp2PortConfigEntry 1 }
 
imaPortConfigTable  OBJECT-TYPE
                SYNTAX SEQUENCE OF ImaPortConfigEntry
                MAX-ACCESS not-accessible
                STATUS current
                DESCRIPTION "Table used for the IMA virtual port on cards that
                             have physical interfaces configured as atmIma.
                             Corresponds to port 7 on DS1 and E1."
                ::= { equipConfig 15 }

imaPortConfigEntry  OBJECT-TYPE
                SYNTAX ImaPortConfigEntry
                MAX-ACCESS not-accessible
                STATUS current
                DESCRIPTION "Row definition for ima specific
                             port attributes"
                INDEX { imaPortId }
                ::= { imaPortConfigTable 1 }

ImaPortConfigEntry  ::= SEQUENCE {
                imaPortId               Integer32
                }
 
imaPortId       OBJECT-TYPE
                SYNTAX Integer32 
                MAX-ACCESS read-only
                STATUS current
                DESCRIPTION "interface index - slot/port: SSPP"
                ::= { imaPortConfigEntry 1 }


--
-- STS1 Port Config Table
--
sts1PortConfigTable  OBJECT-TYPE
                SYNTAX SEQUENCE OF Sts1PortConfigEntry
                MAX-ACCESS not-accessible
                STATUS current
                DESCRIPTION "Table of sts-1 specific port attributes"
                ::= { equipConfig 17 }

sts1PortConfigEntry  OBJECT-TYPE
                SYNTAX Sts1PortConfigEntry
                MAX-ACCESS not-accessible
                STATUS current
                DESCRIPTION "Row definition for sts-1 specific
                             port attributes"
                INDEX { sts1PortId }
                ::= { sts1PortConfigTable 1 }

Sts1PortConfigEntry  ::= SEQUENCE {
                sts1PortId              IntfIndex,
                sts1LineCoding          INTEGER,
                sts1LoopbackConfig      INTEGER,
                sts1TransmitClockSource INTEGER,
                sts1LineBuildOut        INTEGER,
                sts1LineStatus          INTEGER,
                sts1StsPointers         INTEGER,
                sts1VtPointers          INTEGER
                }
 
sts1PortId      OBJECT-TYPE
                SYNTAX IntfIndex
                MAX-ACCESS not-accessible
                STATUS current
                DESCRIPTION "slot/port: SSPP"
                ::= { sts1PortConfigEntry 1 }
 
sts1LineCoding  OBJECT-TYPE
                SYNTAX INTEGER  {
                                b3zs(1)
                                }
                MAX-ACCESS read-only
                STATUS current
                DESCRIPTION "This variable describes the variety of Zero Code
                             Suppression used on this interface, which in turn
                             affects a number of its characteristics.
                             B3ZS refers to the use of specified
                             patterns of normal bits and bipolar violations
                             which are used to replace sequences of zero bits
                             of a specified length."
                DEFVAL { b3zs }
                ::= { sts1PortConfigEntry 2 }

sts1LoopbackConfig OBJECT-TYPE
                SYNTAX INTEGER  {
                                noLoop(1),
                                localLoop(2),
                                lineLoop(3),
                                payloadLoop(4)
                                }
                MAX-ACCESS read-write
                STATUS current
                DESCRIPTION "This variable represents the loopback 
                             configuration of the sts-1 interface.

                             See above diagrams for explanations of loops."
                DEFVAL { noLoop }
                ::= { sts1PortConfigEntry 3 }
 
sts1TransmitClockSource  OBJECT-TYPE
                SYNTAX INTEGER  {
                                loopTiming(1),
                                localTiming(2),
                                cardFreeRun(3)
                                }
                MAX-ACCESS read-write
                STATUS current
                DESCRIPTION "The source of Tranmit Clock.
                             'loopTiming' indicates that the recovered  re-
                               ceive clock is used as the transmit clock.
                             'localTiming' indicates that a local clock
                               source is used.
                             'cardFreeRun' indicates that a local oscillator on 
                               the I/O card is used as the transmit clock."
                DEFVAL { localTiming }
                ::= { sts1PortConfigEntry 4 }

sts1LineBuildOut  OBJECT-TYPE
                SYNTAX INTEGER  {
                                short(1),
                                long(2)
                                }
                MAX-ACCESS read-write
                STATUS current
                DESCRIPTION "sts-1 line build out"
                DEFVAL { short }
                ::= { sts1PortConfigEntry 5 }

sts1LineStatus  OBJECT-TYPE
                SYNTAX INTEGER (1..32767)
                MAX-ACCESS read-only
                STATUS current    
                DESCRIPTION "sts-1 line status:
                1: dsx3NoAlarm: No alarm present
                2: dsx3RcvRAIFailure: Receiving Yellow/Remote Alarm Indication
                4: dsx3XmitRAIAlarm: Transmitting Yellow/Remote Alarm Indication                8: dsx3RcvAIS: Receiving AIS failure state
                16: dsx3XmitAIS: Transmitting AIS failure statue
                32: dsx3LOF: Receiving LOF failure state
                64: dsx3LOS: Reveiving LOS failure state
                128: dsx3LoopbackState: Looping the received signal
                256: dsx3RcvTestCode: Receiving a Test Pattern
                512: dsx3OtherFailure: any line status not defined
                1024: dsx3RcvRmtAIS:
                2048: dsx3RcvRmtOOF:
                4096: dsx3RcvRmtLOS:
                8192: dsx3RcvRmtIdle:
                16384: dsx3RmtLoopback: Far end remote loopback"
                DEFVAL { 1 }
                ::= { sts1PortConfigEntry 6 }

sts1StsPointers OBJECT-TYPE
                SYNTAX INTEGER  {
                                locked(1),
                                floating(2)
                                }
                MAX-ACCESS read-write
                STATUS current
                DESCRIPTION "status of the sts-1 sts pointers"
                DEFVAL { locked }
                ::= { sts1PortConfigEntry 7 }

sts1VtPointers  OBJECT-TYPE
                SYNTAX INTEGER  {
                                locked(1),
                                floating(2)
                                }
                MAX-ACCESS read-write
                STATUS current
                DESCRIPTION "status of the sts-1 vt pointers"
                DEFVAL { locked }
                ::= { sts1PortConfigEntry 8 }

-- Port Configuration for the tasm

tasmPortConfigTable OBJECT-TYPE
                SYNTAX SEQUENCE OF TasmPortConfigEntry
                MAX-ACCESS not-accessible
                STATUS current
                DESCRIPTION "Table of common physical Port attributes"
                ::= { equipConfig 18 }

tasmPortConfigEntry OBJECT-TYPE
                SYNTAX TasmPortConfigEntry
                MAX-ACCESS not-accessible
                STATUS current
                DESCRIPTION "Row definition for common physical
                             port attributes"
                INDEX { tasmPortId }
                ::= { tasmPortConfigTable 1 }

TasmPortConfigEntry ::= SEQUENCE {
                tasmPortId              Integer32
                }

tasmPortId      OBJECT-TYPE
                SYNTAX Integer32
                MAX-ACCESS read-only
                STATUS current
                DESCRIPTION "interface index - SSPP"
                ::= { tasmPortConfigEntry 1 }


protectionGroupConfigTable   OBJECT-TYPE
                         SYNTAX SEQUENCE OF ProtectionGroupConfigEntry
                         MAX-ACCESS not-accessible
                         STATUS current
                         DESCRIPTION "This table gives the list of Slot 
                             Protection Groups in the System. Slot protection 
                             group in one in which there are n cards being
                             protected by 1 standby card."
                ::= { equipConfig 19 }

protectionGroupConfigEntry   OBJECT-TYPE
                         SYNTAX ProtectionGroupConfigEntry
                         MAX-ACCESS not-accessible
                         STATUS current
                         DESCRIPTION "Row Definition for the Protection Group 
                             Tables"
                         INDEX { protectionSlotId }
                ::= { protectionGroupConfigTable 1 }

ProtectionGroupConfigEntry ::= SEQUENCE {
               protectionSlotId          INTEGER,
               workingSlotBitmap         INTEGER,
               protectionCommand         INTEGER,
               protectionCommandSlotId   INTEGER,
               protectionGroupStatus     INTEGER,
               workingSlotId             INTEGER,
               workingFailedBitmap       INTEGER,
               protectionActiveCounter   Integer32,
               protectionOOSCounter      Integer32
                                }

protectionSlotId             OBJECT-TYPE
                         SYNTAX INTEGER (1..15)
                         MAX-ACCESS not-accessible
                         STATUS current
                         DESCRIPTION "Protection Group Index. Index is the 
                             slot id of the Slot Configured as Protection."
                ::= { protectionGroupConfigEntry 1 }

workingSlotBitmap            OBJECT-TYPE
                         SYNTAX INTEGER (0..65535)
                         MAX-ACCESS read-write
                         STATUS current
                         DESCRIPTION "Working Slot Bitmap which the protection 
                             slot will monitor"
                         DEFVAL { 0 }
                ::= { protectionGroupConfigEntry 2 }

protectionCommand            OBJECT-TYPE
                         SYNTAX INTEGER {
                                clear(1),
                                forcedSwitchOverToProtection(2)
                             }
                         MAX-ACCESS read-write
                         STATUS current
                         DESCRIPTION "List of commands which can be executed 
                             on a protection Group.
                             Clear : This command is used to clear any previous
                                     commands which may have been and get back 
                                     to normal nto1 operation
                             Forced SwitchOver To Protection : Switchover to 
                                     Protection card even if the working card 
                                     is in service active
                             These commands to used in conjunction with 
                             the working slot id."
                          DEFVAL { clear }
                ::= { protectionGroupConfigEntry 3 }


protectionCommandSlotId      OBJECT-TYPE
                         SYNTAX INTEGER (1..15)
                         MAX-ACCESS read-write
                         STATUS current
                         DESCRIPTION "This is the working Slot to which command
                             has to be applied"
                         DEFVAL { 0 }
                ::= { protectionGroupConfigEntry 4}

protectionGroupStatus         OBJECT-TYPE
                         SYNTAX INTEGER  {
                                none(1),
                                inservice-Active(2),
                                inservice-Standby(3),
                                outOfService-Active(4),
                                outOfService-Standby(5)
                               }
                         MAX-ACCESS read-only
                         STATUS current
                         DESCRIPTION "Protection Status of a Protection Card. 
                             Inservice and OutofService indicates if the card 
                             has failed or still operational. Active or Standby
                             state indicates if it is carrying active traffic
                             or not."
                          DEFVAL { none }
                ::= { protectionGroupConfigEntry 5 }

workingSlotId                 OBJECT-TYPE
                          SYNTAX INTEGER (0..15)
                          MAX-ACCESS read-only
                          STATUS current
                          DESCRIPTION "If protection group status is active, 
                              this field will give the slot which is being 
                              working. In case it is in standby mode this
                              field will show 0"
                          DEFVAL { 0 }
                ::= { protectionGroupConfigEntry 6 }

workingFailedBitmap           OBJECT-TYPE
                          SYNTAX INTEGER (0..65535)
                          MAX-ACCESS read-only
                          STATUS current
                          DESCRIPTION "Gives Bitmap of the Failed Working Slots.
                              Subset of the Working Slot Bitmap."
                           DEFVAL { 0 }
                ::= { protectionGroupConfigEntry 7 }

protectionActiveCounter       OBJECT-TYPE
                          SYNTAX Integer32
                          MAX-ACCESS read-only
                          STATUS current
                          DESCRIPTION "Give the Number of Times a Protection 
                              has gone to active."
                ::= { protectionGroupConfigEntry 8 }

protectionOOSCounter          OBJECT-TYPE
                          SYNTAX Integer32
                          MAX-ACCESS read-only
                          STATUS current
                          DESCRIPTION "Give the Number of Times a Protection 
                              Card has failed."
                ::= { protectionGroupConfigEntry 9 }


-- The Channel Configuration Group

taxiChannelConfigTable OBJECT-TYPE
                SYNTAX SEQUENCE OF TaxiChannelConfigEntry
                MAX-ACCESS not-accessible
                STATUS current
                DESCRIPTION "Table of common physical Port attributes"
                ::= { channelConfig 1 }

taxiChannelConfigEntry OBJECT-TYPE
                SYNTAX TaxiChannelConfigEntry
                MAX-ACCESS not-accessible
                STATUS current
                DESCRIPTION "Row definition for common physical
                             port attributes"
                INDEX { taxiChannelId }
                ::= { taxiChannelConfigTable 1 }

TaxiChannelConfigEntry ::= SEQUENCE {
                taxiChannelId                IntfIndex,
                taxiChannelIfType        INTEGER,
                taxiChannelSecuFeature        INTEGER
                }

taxiChannelId       OBJECT-TYPE
                SYNTAX IntfIndex
                MAX-ACCESS not-accessible
                STATUS current
                DESCRIPTION "interface index - SSPPCC"
                ::= { taxiChannelConfigEntry 1 }

taxiChannelIfType OBJECT-TYPE
                SYNTAX INTEGER  {
                                unconfigured(1),
                                atmUni3-0(2),
                                atmUni3-1(3),

                                iispUser(4),
                                iispNetwork(5),

                                atmUni4-0(6)
                                }
                MAX-ACCESS read-write
                STATUS current
                DESCRIPTION " UNI or NNI type"
                DEFVAL { unconfigured }
                ::= { taxiChannelConfigEntry 2 }

taxiChannelSecuFeature OBJECT-TYPE
                SYNTAX INTEGER {
                                unsecurable(1),
                                secured(2),
                                securable(3)
                                }
                MAX-ACCESS read-write
                STATUS current
                DESCRIPTION " enhancement feature"
                DEFVAL { unsecurable }
                ::= { taxiChannelConfigEntry 3 }

ds3ChannelConfigTable OBJECT-TYPE
                SYNTAX SEQUENCE OF Ds3ChannelConfigEntry
                MAX-ACCESS not-accessible
                STATUS current
                DESCRIPTION "Table of common physical channel attributes"
                ::= { channelConfig 2 }

ds3ChannelConfigEntry OBJECT-TYPE
                SYNTAX Ds3ChannelConfigEntry
                MAX-ACCESS not-accessible
                STATUS current
                DESCRIPTION "Row definition for common physical
                             channel attributes"
                INDEX { ds3ChannelId }
                ::= { ds3ChannelConfigTable 1 }

Ds3ChannelConfigEntry ::= SEQUENCE {
                ds3ChannelId                 IntfIndex,
                ds3ChannelIfType         INTEGER,
                ds3ChannelSecuFeature         INTEGER
                }

ds3ChannelId       OBJECT-TYPE
                SYNTAX IntfIndex
                MAX-ACCESS not-accessible
                STATUS current
                DESCRIPTION "interface index - SSPPCCC"
                ::= { ds3ChannelConfigEntry 1 }

ds3ChannelIfType OBJECT-TYPE
                SYNTAX INTEGER  {
                                unconfigured(1),
                                atmUni3-0(2),
                                atmUni3-1(3),

                                iispUser(4),
                                iispNetwork(5),

                                frameRelayUni(6),
                                frameRelayNni(7),

                                atmPnni1-0(8),

                                atmUni4-0(9),
                                circuitEmulation(10)
                }
                MAX-ACCESS read-write
                STATUS current
                DESCRIPTION " UNI or NNI type,"
                DEFVAL { unconfigured }
                ::= { ds3ChannelConfigEntry 2 }

ds3ChannelSecuFeature OBJECT-TYPE
                SYNTAX INTEGER {
                                unsecurable(1),
                                secured(2),
                                securable(3)
                                }
                MAX-ACCESS read-write
                STATUS current
                DESCRIPTION " Interface type configured on DS3 channel "
                DEFVAL { unsecurable }
                ::= { ds3ChannelConfigEntry 3 }

ds1ChannelConfigTable OBJECT-TYPE
                SYNTAX SEQUENCE OF Ds1ChannelConfigEntry
                MAX-ACCESS not-accessible
                STATUS current
                DESCRIPTION "Table of common physical Port attributes"
                ::= { channelConfig 3 }

ds1ChannelConfigEntry OBJECT-TYPE
                SYNTAX Ds1ChannelConfigEntry
                MAX-ACCESS not-accessible
                STATUS current
                DESCRIPTION "Row definition for common physical
                             port attributes"
                INDEX { ds1ChannelId }
                ::= { ds1ChannelConfigTable 1 }

Ds1ChannelConfigEntry ::= SEQUENCE {
                ds1ChannelId                         IntfIndex,
                ds1ChannelIfType                 INTEGER,
                ds1ChannelDs0Map                 OCTET STRING,
                ds1ChannelCellMapping                 INTEGER,
                ds1ChannelInputCodingRule         INTEGER,
                ds1ChannelSecuFeature                 INTEGER,
                ds1ChannelSignaling                INTEGER,
                ds1ChannelCellScramble                INTEGER
                }

ds1ChannelId       OBJECT-TYPE
                SYNTAX IntfIndex
                MAX-ACCESS not-accessible
                STATUS current
                DESCRIPTION "interface index - SSPPCCC"
                ::= { ds1ChannelConfigEntry 1 }

ds1ChannelIfType OBJECT-TYPE
                SYNTAX INTEGER  {
                                unconfigured(1),
                                atmUni3-0(2),
                                atmUni3-1(3),

                                iispUser(4),
                                iispNetwork(5),

                                circuitEmulation(6),
                                frameRelayUni(7),
                                hdlcPassThrough(8),

                                pri-isdn-network(9),

                                dbCirEm(10),
                                frameRelayNni(11),

                                pri-isdn-user(12),

                                atmIma(13),

                                atmPnni1-0(14),

                                casTrunkLine(15),
                                atmUni4-0(16),
                gr303 (17)
                                }
                MAX-ACCESS read-write
                STATUS current
                DESCRIPTION "UNI or NNI type for ATM ,Frame Relay, or 
                             ISDN service interface type for channel"
                DEFVAL { unconfigured }
                ::= { ds1ChannelConfigEntry 2 }

ds1ChannelDs0Map OBJECT-TYPE
                SYNTAX OCTET STRING (SIZE(3))
                MAX-ACCESS read-write
                STATUS current
                DESCRIPTION "bit map of DS0 in channel"
                ::= { ds1ChannelConfigEntry 3 }

ds1ChannelCellMapping OBJECT-TYPE
                SYNTAX INTEGER  {
                                 directMapping(1),
                                 none(2)
                                }
                MAX-ACCESS read-write
                STATUS current
                DESCRIPTION "cell delineation mode for ATM cell bearing 
                             services"
                DEFVAL { directMapping }
                ::= { ds1ChannelConfigEntry 4 }

ds1ChannelInputCodingRule OBJECT-TYPE
                SYNTAX INTEGER {
                                none(1),
                                muLawPCM(2),
                                aLawPCM(3),
                                digital(4)
                                }
                MAX-ACCESS read-write
                STATUS current
                DESCRIPTION "enhancement feature"
                DEFVAL { none }
                ::= { ds1ChannelConfigEntry 5 }

ds1ChannelSecuFeature OBJECT-TYPE
                SYNTAX INTEGER {
                                unsecurable(1),
                                secured(2),
                                securable(3)
                                }
                MAX-ACCESS read-write
                STATUS current
                DESCRIPTION "enhancement feature"
                DEFVAL { unsecurable }
                ::= { ds1ChannelConfigEntry 6 }

ds1ChannelSignaling OBJECT-TYPE
                SYNTAX INTEGER {
                                disabled(1),
                                enabled(2)
                                }
                MAX-ACCESS read-write
                STATUS current
                DESCRIPTION "refers to robbed-bit signaling in 
                             circuitEmulation interfaces."
                DEFVAL { disabled }
                ::= { ds1ChannelConfigEntry 7 }

ds1ChannelCellScramble OBJECT-TYPE
                SYNTAX INTEGER {
                                disabled(1),
                                enabled(2)
                                }
                MAX-ACCESS read-write
                STATUS current
                DESCRIPTION "refers to enabling/disabling cell scrambling on
                             ATM interface."
                DEFVAL { disabled }
                ::= { ds1ChannelConfigEntry 8 }

msChannelConfigTable OBJECT-TYPE
                SYNTAX SEQUENCE OF MsChannelConfigEntry
                MAX-ACCESS not-accessible
                STATUS current
                DESCRIPTION "Channel configuration table for multi-serial 
                             ports."
                ::= { channelConfig 4 }

msChannelConfigEntry OBJECT-TYPE
                SYNTAX MsChannelConfigEntry
                MAX-ACCESS not-accessible
                STATUS current
                DESCRIPTION "Row definition for multi-serial channel config. "
                INDEX { msChannelId }
                ::= { msChannelConfigTable 1 }

MsChannelConfigEntry ::= SEQUENCE
                                 {
                                  msChannelId                        IntfIndex,
                                  msChannelIfType                INTEGER,
                                  msChannelCellBearingMode        INTEGER,
                                  msChannelCellBearingAddrMode  INTEGER,
                                  msChannelCellBearingPayloadFec INTEGER,
                                  msChannelSecuFeature                INTEGER
                                 }

msChannelId        OBJECT-TYPE
                SYNTAX IntfIndex
                MAX-ACCESS not-accessible
                STATUS current
                DESCRIPTION "interface index - SSPPCCC"
                ::= { msChannelConfigEntry 1 }

msChannelIfType OBJECT-TYPE
                SYNTAX INTEGER {
                                unconfigured(1),
                                atmUni3-0(2),
                                atmUni3-1(3),

                                iispUser(4),
                                iispNetwork(5),

                                circuitEmulation(6),
                                terminalEmulation(7),
                                frameRelayUni(8),
                                hdlcPassThrough(9),
                                frameRelayNni(10),

                                atmPnni1-0(11),

                                atmUni4-0(12)
                               }
                MAX-ACCESS read-write
                STATUS current
                DESCRIPTION "interface type for multi-serial port"
                DEFVAL { unconfigured }
                ::= { msChannelConfigEntry 2 }

msChannelCellBearingMode OBJECT-TYPE
                SYNTAX INTEGER {
                                lanet(1),
                                ccittDirectMapping(2),
                                none(3)
                               }
                MAX-ACCESS read-write
                STATUS current
                DESCRIPTION "The cell delineation mode is either LANET or
                                CCITT based"
                DEFVAL { lanet }
                ::= { msChannelConfigEntry 3 }

msChannelCellBearingAddrMode OBJECT-TYPE
                SYNTAX INTEGER {
                                standard(1),
                                noiseTolerant(2)
                               }
                MAX-ACCESS read-write
                STATUS current
                DESCRIPTION "standard - ATM Forum UNI 3.0/3.1
                             noiseTolerant - A proprietary noise tolerant
                             address mapping scheme"
                DEFVAL { standard }
                ::= { msChannelConfigEntry 4 }

msChannelCellBearingPayloadFec OBJECT-TYPE
                SYNTAX INTEGER {
                                dynamic(1),
                                threeEighthsRate(2),
                                oneQuarterRate(3),
                                oneEighthRate(4)
                               }
                MAX-ACCESS read-only
                STATUS current
                DESCRIPTION "payload error correction scheme"
                DEFVAL { dynamic }
                ::= { msChannelConfigEntry 5 }

msChannelSecuFeature OBJECT-TYPE
                SYNTAX INTEGER {
                                unsecurable(1),
                                secured(2),
                                securable(3)
                                }
                MAX-ACCESS read-write
                STATUS current
                DESCRIPTION "enhancement feature"
                DEFVAL { unsecurable }
                ::= { msChannelConfigEntry 6 }

oc3ChannelConfigTable OBJECT-TYPE
                SYNTAX SEQUENCE OF Oc3ChannelConfigEntry
                MAX-ACCESS not-accessible
                STATUS current
                DESCRIPTION "Table of common physical Port attributes"
                ::= { channelConfig 5 }
 
oc3ChannelConfigEntry OBJECT-TYPE
                SYNTAX Oc3ChannelConfigEntry
                MAX-ACCESS not-accessible
                STATUS current
                DESCRIPTION "Row definition for common physical
                             port attributes"
                INDEX { oc3ChannelId }
                ::= { oc3ChannelConfigTable 1 }
 
Oc3ChannelConfigEntry ::= SEQUENCE {
                oc3ChannelId                IntfIndex,
                oc3ChannelIfType        INTEGER,
                oc3ChannelSecuFeature        INTEGER
                }
 
oc3ChannelId       OBJECT-TYPE
                SYNTAX IntfIndex
                MAX-ACCESS not-accessible
                STATUS current
                DESCRIPTION "interface index - SSPPCC"
                ::= { oc3ChannelConfigEntry 1 }
 
oc3ChannelIfType OBJECT-TYPE
                SYNTAX INTEGER  {
                                unconfigured(1),
                                atmUni3-0(2),
                                atmUni3-1(3),

                                iispUser(4),
                                iispNetwork(5),


                                atmPnni1-0(6),

                                atmUni4-0(7)

                                ,atmVnnUni3-1(8)

                                }
                MAX-ACCESS read-write
                STATUS current
                DESCRIPTION " UNI or NNI type"
                DEFVAL { unconfigured }
                ::= { oc3ChannelConfigEntry 2 }
 
oc3ChannelSecuFeature OBJECT-TYPE
                SYNTAX INTEGER {
                                unsecurable(1),
                                secured(2),
                                securable(3)
                                }
                MAX-ACCESS read-write
                STATUS current
                DESCRIPTION " enhancement feature"
                DEFVAL { unsecurable }
                ::= { oc3ChannelConfigEntry 3 }


twoWireSourceChannelConfigTable OBJECT-TYPE
                SYNTAX SEQUENCE OF TwoWireSourceChannelConfigEntry
                MAX-ACCESS not-accessible
                STATUS current
                DESCRIPTION "Table of common physical Port attributes"
                ::= { channelConfig 6 }
 
twoWireSourceChannelConfigEntry OBJECT-TYPE
                SYNTAX TwoWireSourceChannelConfigEntry
                MAX-ACCESS not-accessible
                STATUS current
                DESCRIPTION "Row definition for common physical
                             port attributes"
                INDEX { twoWireSourceChannelId }
                ::= { twoWireSourceChannelConfigTable 1 }
 
TwoWireSourceChannelConfigEntry ::= SEQUENCE {
                twoWireSourceChannelId                         IntfIndex,
                twoWireSourceChannelIfType                 INTEGER,
                twoWireSourceChannelConnectionType        INTEGER,
                twoWireSourceChannelCompandingLaw         INTEGER,
                twoWireSourceChannelSecuFeature         INTEGER,
                twoWireSourceChannelVoiceCompression         INTEGER,
                twoWireSourceChannelEchoCancellation         INTEGER,
                twoWireSourceChannelSilenceSupression         INTEGER,
                twoWireSourceChannelEncapsulationAal         INTEGER,
                twoWireSourceChannelSubscriberService        INTEGER
                }
 
twoWireSourceChannelId       OBJECT-TYPE
                SYNTAX IntfIndex
                MAX-ACCESS not-accessible
                STATUS current
                DESCRIPTION "interface index - SSPPCC"
                ::= { twoWireSourceChannelConfigEntry 1 }
 
twoWireSourceChannelIfType OBJECT-TYPE
                SYNTAX INTEGER  {
                                unconfigured(1),
                                circuitEmulation(2)
                                }
                MAX-ACCESS read-write
                STATUS current
                DESCRIPTION " Interface types of 2W station(source) channel. "
                DEFVAL { unconfigured }
                ::= { twoWireSourceChannelConfigEntry 2 }
 
twoWireSourceChannelConnectionType OBJECT-TYPE
                SYNTAX INTEGER  {
                                pvc(1),
                                svc(2)
                                }
                MAX-ACCESS read-write
                STATUS current
                DESCRIPTION "This field selects ATM virtual circuit connection
                             type, PVC or SVC."
                DEFVAL { pvc }
                ::= { twoWireSourceChannelConfigEntry 3 }
 
twoWireSourceChannelCompandingLaw OBJECT-TYPE
                SYNTAX INTEGER  {
                                muLawPCM(1),
                                aLawPCM(2)
                                }
                MAX-ACCESS read-only
                STATUS current
                DESCRIPTION "This field selects channel encoding/decoding
                             quantization interval, muLaw or aLaw."
                DEFVAL { muLawPCM }
                ::= { twoWireSourceChannelConfigEntry 4 }

twoWireSourceChannelSecuFeature OBJECT-TYPE
                SYNTAX INTEGER {
                                unsecurable(1),
                                secured(2),
                                securable(3)
                                }
                MAX-ACCESS read-only
                STATUS current
                DESCRIPTION "enhancement feature"
                DEFVAL { unsecurable }
                ::= { twoWireSourceChannelConfigEntry 5 }
 
twoWireSourceChannelVoiceCompression OBJECT-TYPE
                SYNTAX INTEGER  {
                                disabled(1),
                                adpcm32k(2),
                                adpcm16k(3),
                                adpcm8k(4)
                                }
                MAX-ACCESS read-only
                STATUS current
                DESCRIPTION "voice compression scheme"
                DEFVAL { disabled }
                ::= { twoWireSourceChannelConfigEntry 6 }
 
twoWireSourceChannelEchoCancellation OBJECT-TYPE
                SYNTAX INTEGER  {
                                disabled(1),
                                enabled(2)
                                }
                MAX-ACCESS read-only
                STATUS current
                DESCRIPTION "This field disables/enables twoWireSource card
                             echo cancellation function."
                DEFVAL { disabled }
                ::= { twoWireSourceChannelConfigEntry 7 }
 
twoWireSourceChannelSilenceSupression OBJECT-TYPE
                SYNTAX INTEGER  {
                                disabled(1),
                                enabled(2)
                                }
                MAX-ACCESS read-only
                STATUS current
                DESCRIPTION "This field disables/enables twoWireSource card
                             silence suppression."
                DEFVAL { disabled }
                ::= { twoWireSourceChannelConfigEntry 8 }
 
twoWireSourceChannelEncapsulationAal OBJECT-TYPE
                SYNTAX INTEGER  {
                                aal1(1),
                                lucent(2)
                                }
                MAX-ACCESS read-only
                STATUS current
                DESCRIPTION "This field selects ATM cell payload format.
                             Aal1 - ATM Adaption Layer Type 1.
                             Yurie - A proprietary specific ATM cell payload 
                                format for compressed data."
                DEFVAL { aal1 }
                ::= { twoWireSourceChannelConfigEntry 9 }

twoWireSourceChannelSubscriberService OBJECT-TYPE
                SYNTAX INTEGER  {
                                plar(1),
                                fxs(2),
                                s-signaling(3)
                                }
                MAX-ACCESS read-write
                STATUS current
                DESCRIPTION "This field selects subscribed channel service 
                             types.
                             plar - Private Line Automatic Ring
                             fxs - Foreign Exchange Subscriber End
                             s-signaling - A proprietary specific signaling 
                                type based on AIN model."
                DEFVAL { plar }
                ::= { twoWireSourceChannelConfigEntry 10 }


highSpeedChannelConfigTable OBJECT-TYPE
                SYNTAX SEQUENCE OF HighSpeedChannelConfigEntry
                MAX-ACCESS not-accessible
                STATUS current
                DESCRIPTION "Table of common physical Port attributes"
                ::= { channelConfig 7 }

highSpeedChannelConfigEntry OBJECT-TYPE
                SYNTAX HighSpeedChannelConfigEntry
                MAX-ACCESS not-accessible
                STATUS current
                DESCRIPTION "Row definition for common physical
                             port attributes"
                INDEX { highSpeedChannelId }
                ::= { highSpeedChannelConfigTable 1 }

HighSpeedChannelConfigEntry ::= SEQUENCE {
                highSpeedChannelId        IntfIndex,
                highSpeedChannelIfType        INTEGER
                }

highSpeedChannelId       OBJECT-TYPE
                SYNTAX IntfIndex
                MAX-ACCESS not-accessible
                STATUS current
                DESCRIPTION "interface index - SSPPCC"
                ::= { highSpeedChannelConfigEntry 1 }

highSpeedChannelIfType OBJECT-TYPE
                SYNTAX INTEGER  {
                                unconfigured(1),
                                atmUni3-0(2),
                                atmUni3-1(3),

                                iispUser(4),
                                iispNetwork(5),

                                circuitEmulation(6),
                                atmUni4-0(7)
                                }
                MAX-ACCESS read-write
                STATUS current
                DESCRIPTION " UNI or NNI type"
                DEFVAL { unconfigured }
                ::= { highSpeedChannelConfigEntry 2 } 

dspChannelConfigTable OBJECT-TYPE
                SYNTAX SEQUENCE OF DspChannelConfigEntry
                MAX-ACCESS not-accessible
                STATUS current
                DESCRIPTION "Table of common physical Port attributes"
                ::= { channelConfig 8 }
 
dspChannelConfigEntry OBJECT-TYPE
                SYNTAX DspChannelConfigEntry
                MAX-ACCESS not-accessible
                STATUS current
                DESCRIPTION "Row definition for common physical
                             port attributes"
                INDEX { dspChannelId }
                ::= { dspChannelConfigTable 1 }
 
DspChannelConfigEntry ::= SEQUENCE {
                dspChannelId                        IntfIndex,
                dspChannelIfType                INTEGER,
                dspChannelInputCodingRule        INTEGER,
                dspChannelVoiceCompression        INTEGER,
                dspChannelEchoCancellation        INTEGER,
                dspChannelSilenceSupression        INTEGER
                }
 
dspChannelId       OBJECT-TYPE
                SYNTAX IntfIndex
                MAX-ACCESS not-accessible
                STATUS current
                DESCRIPTION "interface index - SSPPCC"
                ::= { dspChannelConfigEntry 1 }
 
dspChannelIfType OBJECT-TYPE
                SYNTAX INTEGER  {
                                unconfigured(1),
                                dsp(2)
                                }
                MAX-ACCESS read-write
                STATUS current
                DESCRIPTION "Channel Interface Type"
                DEFVAL { unconfigured }
                ::= { dspChannelConfigEntry 2 }
 
dspChannelInputCodingRule OBJECT-TYPE
                SYNTAX INTEGER  {
                                muLawPCM(1)
                                }
                MAX-ACCESS read-only
                STATUS current
                DESCRIPTION "Input Coding Rule "
                DEFVAL { muLawPCM }
                ::= { dspChannelConfigEntry 3 }

dspChannelVoiceCompression OBJECT-TYPE
                SYNTAX INTEGER  {
                                adpcm32k(1),
                                adpcm16k(2)
                                }
                MAX-ACCESS read-write
                STATUS current
                DESCRIPTION "voice compression scheme"
                DEFVAL { adpcm32k }
                ::= { dspChannelConfigEntry 4 }
 
dspChannelEchoCancellation OBJECT-TYPE
                SYNTAX INTEGER  {
                                enabled(1)
                                }
                MAX-ACCESS read-only
                STATUS current
                DESCRIPTION "voice compression scheme"
                DEFVAL { enabled }
                ::= { dspChannelConfigEntry 5 }
 
dspChannelSilenceSupression OBJECT-TYPE
                SYNTAX INTEGER  {
                                enabled(1)
                                }
                MAX-ACCESS read-only
                STATUS current
                DESCRIPTION "voice compression scheme"
                DEFVAL { enabled }
                ::= { dspChannelConfigEntry 6 }
 

twoWireSinkChannelConfigTable OBJECT-TYPE
                SYNTAX SEQUENCE OF TwoWireSinkChannelConfigEntry
                MAX-ACCESS not-accessible
                STATUS current
                DESCRIPTION "Table of common physical Port attributes"
                ::= { channelConfig 9 }
 
twoWireSinkChannelConfigEntry OBJECT-TYPE
                SYNTAX TwoWireSinkChannelConfigEntry
                MAX-ACCESS not-accessible
                STATUS current
                DESCRIPTION "Row definition for common physical
                             port attributes"
                INDEX { twoWireSinkChannelId }
                ::= { twoWireSinkChannelConfigTable 1 }
 
TwoWireSinkChannelConfigEntry ::= SEQUENCE {
                twoWireSinkChannelId                         IntfIndex,
                twoWireSinkChannelIfType                 INTEGER,
                twoWireSinkChannelConnectionType        INTEGER,
                twoWireSinkChannelCompandingLaw         INTEGER,
                twoWireSinkChannelVoiceCompression         INTEGER,
                twoWireSinkChannelEchoCancellation         INTEGER,
                twoWireSinkChannelSilenceSupression         INTEGER,
                twoWireSinkChannelEncapsulationAal         INTEGER,
                twoWireSinkChannelSubscriberService        INTEGER
                }
 
twoWireSinkChannelId OBJECT-TYPE
                SYNTAX IntfIndex
                MAX-ACCESS not-accessible
                STATUS current
                DESCRIPTION "interface index - SSPPCC"
                ::= { twoWireSinkChannelConfigEntry 1 }
 
twoWireSinkChannelIfType OBJECT-TYPE
                SYNTAX INTEGER  {
                                unconfigured(1),
                                circuitEmulation(2)
                                }
                MAX-ACCESS read-write
                STATUS current
                DESCRIPTION " Interface types. "
                DEFVAL { unconfigured }
                ::= { twoWireSinkChannelConfigEntry 2 }
 
twoWireSinkChannelConnectionType OBJECT-TYPE
                SYNTAX INTEGER  {
                                pvc(1),
                                svc(2)
                                }
                MAX-ACCESS read-only
                STATUS current
                DESCRIPTION "This field selects ATM virtual circuit connection
                             type, PVC or SVC."
                DEFVAL { pvc }
                ::= { twoWireSinkChannelConfigEntry 3 }
 
twoWireSinkChannelCompandingLaw OBJECT-TYPE
                SYNTAX INTEGER  {
                                muLawPCM(1),
                                aLawPCM(2)
                                }
                MAX-ACCESS read-only
                STATUS current
                DESCRIPTION "This field selects channel encoding/decoding
                             quantization interval, muLaw or aLaw."
                DEFVAL { muLawPCM }
                ::= { twoWireSinkChannelConfigEntry 4 }

twoWireSinkChannelVoiceCompression OBJECT-TYPE
                SYNTAX INTEGER  {
                                disabled(1),
                                adpcm32k(2),
                                adpcm16k(3),
                                adpcm8k(4)
                                }
                MAX-ACCESS read-only
                STATUS current
                DESCRIPTION "voice compression scheme"
                DEFVAL { disabled }
                ::= { twoWireSinkChannelConfigEntry 5 }
 
twoWireSinkChannelEchoCancellation OBJECT-TYPE
                SYNTAX INTEGER  {
                                disabled(1),
                                enabled(2)
                                }
                MAX-ACCESS read-only
                STATUS current
                DESCRIPTION "This field disables/enables twoWireSink card
                             echo cancellation function."
                DEFVAL { disabled }
                ::= { twoWireSinkChannelConfigEntry 6 }
 
twoWireSinkChannelSilenceSupression OBJECT-TYPE
                SYNTAX INTEGER  {
                                disabled(1),
                                enabled(2)
                                }
                MAX-ACCESS read-only
                STATUS current
                DESCRIPTION "This field disables/enables twoWireSink card
                             silence suppression."
                DEFVAL { disabled }
                ::= { twoWireSinkChannelConfigEntry 7 }
 
twoWireSinkChannelEncapsulationAal OBJECT-TYPE
                SYNTAX INTEGER  {
                                aal1(1),
                                lucent(2)
                                }
                MAX-ACCESS read-only
                STATUS current
                DESCRIPTION "This field selects ATM cell payload format.
                             Aal1 - ATM Adaption Layer Type 1.
                             Yurie - A proprietary specific ATM cell payload 
                                format for compressed data."
                DEFVAL { aal1 }
                ::= { twoWireSinkChannelConfigEntry 8 }

twoWireSinkChannelSubscriberService OBJECT-TYPE
                SYNTAX INTEGER  {
                                fxo(1)
                                }
                MAX-ACCESS read-only
                STATUS current
                DESCRIPTION "The only available service type for twoWireSink
                             card is Foreign Exchange Office End (fxo)."
                DEFVAL { fxo }
                ::= { twoWireSinkChannelConfigEntry 9 }
 

e3ChannelConfigTable OBJECT-TYPE
                SYNTAX SEQUENCE OF E3ChannelConfigEntry
                MAX-ACCESS not-accessible
                STATUS current
                DESCRIPTION "Table of common physical channel attributes"
                ::= { channelConfig 10 }

e3ChannelConfigEntry OBJECT-TYPE
                SYNTAX E3ChannelConfigEntry
                MAX-ACCESS not-accessible
                STATUS current
                DESCRIPTION "Row definition for common physical
                             channel attributes"
                INDEX { e3ChannelId }
                ::= { e3ChannelConfigTable 1 }

E3ChannelConfigEntry ::= SEQUENCE {
                e3ChannelId                 IntfIndex,
                e3ChannelIfType         INTEGER,
                e3ChannelSecuFeature         INTEGER
                }

e3ChannelId       OBJECT-TYPE
                SYNTAX IntfIndex
                MAX-ACCESS not-accessible
                STATUS current
                DESCRIPTION "interface index - SSPPCCC"
                ::= { e3ChannelConfigEntry 1 }

e3ChannelIfType OBJECT-TYPE
                SYNTAX INTEGER  {
                                unconfigured(1),
                                atmUni3-0(2),
                                atmUni3-1(3),

                                iispUser(4),
                                iispNetwork(5),


                                atmPnni1-0(6),

                                atmUni4-0(7),
                                circuitEmulation(8)                                
                                }
                MAX-ACCESS read-write
                STATUS current
                DESCRIPTION " Interface type configured on E3 channel "
                DEFVAL { unconfigured }
                ::= { e3ChannelConfigEntry 2 }

e3ChannelSecuFeature OBJECT-TYPE
                SYNTAX INTEGER {
                                unsecurable(1),
                                secured(2),
                                securable(3)
                                }
                MAX-ACCESS read-write
                STATUS current
                DESCRIPTION " enhancement feature"
                DEFVAL { unsecurable }
                ::= { e3ChannelConfigEntry 3 }

e1ChannelConfigTable OBJECT-TYPE
                SYNTAX SEQUENCE OF E1ChannelConfigEntry
                MAX-ACCESS not-accessible
                STATUS current
                DESCRIPTION "Table of common physical Port attributes"
                ::= { channelConfig 11 }

e1ChannelConfigEntry OBJECT-TYPE
                SYNTAX E1ChannelConfigEntry
                MAX-ACCESS not-accessible
                STATUS current
                DESCRIPTION "Row definition for common physical
                             port attributes"
                INDEX { e1ChannelId }
                ::= { e1ChannelConfigTable 1 }

E1ChannelConfigEntry ::= SEQUENCE {
                e1ChannelId                         IntfIndex,
                e1ChannelIfType                 INTEGER,
                e1ChannelDs0Map                 OCTET STRING,
                e1ChannelCellMapping                 INTEGER,
                e1ChannelInputCodingRule         INTEGER,
                e1ChannelSecuFeature                 INTEGER

                ,
                e1ChannelSignaling                 INTEGER

                }

e1ChannelId       OBJECT-TYPE
                SYNTAX IntfIndex
                MAX-ACCESS not-accessible
                STATUS current
                DESCRIPTION "interface index - SSPPCCC"
                ::= { e1ChannelConfigEntry 1 }

e1ChannelIfType OBJECT-TYPE
                SYNTAX INTEGER  {
                                unconfigured(1),
                                atmUni3-0(2),
                                atmUni3-1(3),

                                iispUser(4),
                                iispNetwork(5),

                                circuitEmulation(6),
                                frameRelayUni(7),
                                hdlcPassThrough(8),
                                frameRelayNni(9),
                                atmIma(10),

                                atmPnni1-0(11),



                                pri-isdn-network(12),
                                pri-isdn-user(13),

                                casTrunkLine(14),
                                atmUni4-0(15)
                                }
                MAX-ACCESS read-write
                STATUS current
                DESCRIPTION "UNI or NNI type for ATM ,Frame Relay, or 
                             ISDN serviceinterface type for channel"
                DEFVAL { unconfigured }
                ::= { e1ChannelConfigEntry 2 }

e1ChannelDs0Map OBJECT-TYPE
                SYNTAX OCTET STRING (SIZE(4))
                MAX-ACCESS read-write
                STATUS current
                DESCRIPTION "bit map of DS0 in channel"
                ::= { e1ChannelConfigEntry 3 }

e1ChannelCellMapping OBJECT-TYPE
                SYNTAX INTEGER  {
                                 directMapping(1),
                                 none(2)
                                }
                MAX-ACCESS read-write
                STATUS current
                DESCRIPTION "cell delineation mode for ATM cell bearing 
                             services"
                DEFVAL { directMapping }
                ::= { e1ChannelConfigEntry 4 }

e1ChannelInputCodingRule OBJECT-TYPE
                SYNTAX INTEGER {
                                none(1),
                                muLawPCM(2),
                                aLawPCM(3),
                                digital(4)
                                }
                MAX-ACCESS read-write
                STATUS current
                DESCRIPTION "enhancement feature"
                DEFVAL { none }
                ::= { e1ChannelConfigEntry 5 }

e1ChannelSecuFeature OBJECT-TYPE
                SYNTAX INTEGER {
                                unsecurable(1),
                                secured(2),
                                securable(3)
                                }
                MAX-ACCESS read-write
                STATUS current
                DESCRIPTION "enhancement feature"
                DEFVAL { unsecurable }
                ::= { e1ChannelConfigEntry 6 }


e1ChannelSignaling OBJECT-TYPE
                SYNTAX INTEGER {
                                disabled(1),
                                enabled(2)
                                }
                MAX-ACCESS read-write
                STATUS current
                DESCRIPTION "Refers to robbed-bit singaling in 
                             circuitEmulation interface."
                DEFVAL { disabled }
                ::= { e1ChannelConfigEntry 7 }



ethernetChannelConfigTable OBJECT-TYPE
                SYNTAX SEQUENCE OF EthernetChannelConfigEntry
                MAX-ACCESS not-accessible
                STATUS current
                DESCRIPTION "Table used for enthernet channel
                             configuration."
                ::= { channelConfig 12 }
 
ethernetChannelConfigEntry OBJECT-TYPE
                SYNTAX EthernetChannelConfigEntry
                MAX-ACCESS not-accessible
                STATUS current
                DESCRIPTION "Row definition for enthernet channel
                             attributes. "
                INDEX { ethernetChannelId }
                ::= { ethernetChannelConfigTable 1 }
 
EthernetChannelConfigEntry ::= SEQUENCE {
                ethernetChannelId                 Integer32,
                ethernetChannelIfType                 INTEGER
                }
 
ethernetChannelId OBJECT-TYPE
                SYNTAX Integer32
                MAX-ACCESS not-accessible
                STATUS current
                DESCRIPTION "Interface index"
                ::= { ethernetChannelConfigEntry 1 }
 
ethernetChannelIfType OBJECT-TYPE
                SYNTAX INTEGER  {
                                unconfigured(1),
                                bridge(2),
                                routing(3)
                                }
                MAX-ACCESS read-write
                STATUS current
                DESCRIPTION "   Types of ethernet interface.
                                There are two types of bridging
                                interface(channel):bridge and routing. "
                DEFVAL { unconfigured }
                ::= { ethernetChannelConfigEntry 2 }
 

dsp2Channel     OBJECT IDENTIFIER ::= { channelConfig 13 }

dsp2ChannelConfigTable OBJECT-TYPE
                SYNTAX SEQUENCE OF Dsp2ChannelConfigEntry
                MAX-ACCESS not-accessible
                STATUS current
                DESCRIPTION "Table of Channel attributes"
                ::= { dsp2Channel 1 }

dsp2ChannelConfigEntry OBJECT-TYPE
                SYNTAX Dsp2ChannelConfigEntry
                MAX-ACCESS not-accessible
                STATUS current
                DESCRIPTION "Row definition for common physical
                             port attributes"
                INDEX { dsp2ChannelId }
                ::= { dsp2ChannelConfigTable 1 }

Dsp2ChannelConfigEntry ::= SEQUENCE {
                dsp2ChannelId                        IntfIndex,
                dsp2ChannelIfType                INTEGER,
                dsp2ChannelAlarmType                  INTEGER,
                dsp2ChannelModeConfig                  INTEGER
                }
 
dsp2ChannelId       OBJECT-TYPE
                SYNTAX IntfIndex
                MAX-ACCESS not-accessible
                STATUS current
                DESCRIPTION "interface index - SSPPCC"
                ::= { dsp2ChannelConfigEntry 1 }
 
dsp2ChannelIfType OBJECT-TYPE
                SYNTAX INTEGER  {
                                unconfigured(1),
                                dsp2(2)
                                }
                MAX-ACCESS read-write
                STATUS current
                DESCRIPTION "Channel Interface Type"
                DEFVAL { unconfigured }
                ::= { dsp2ChannelConfigEntry 2 }
 
dsp2ChannelAlarmType OBJECT-TYPE
                SYNTAX INTEGER  {
                                noAlarm(1),
                                dspFailure(2)
                                }
                MAX-ACCESS read-only
                STATUS current
                DESCRIPTION "This field is a read only failure which
                        gives the status of a dsp.When the status
                        is dspFailure the Operational Status at the 
                        interface level will go OOS"
                DEFVAL { noAlarm }
                ::= { dsp2ChannelConfigEntry 3 }

dsp2ChannelModeConfig OBJECT-TYPE
                SYNTAX INTEGER  {
                                algoSet1(1),
                                algoSet2(2),
                                algoSet3(3),
                                algoSet4(4),
                                algoSet5(5),
                                algoSet6(6)           
                                }
                MAX-ACCESS read-write
                STATUS current
                DESCRIPTION "This field is used to configure the mode of 
                             the DSP card. Each mode corresponds to a set
                             of algorithms supported by the IO card. 
                             The complete list of enumerations of supported 
                             algorithms is given in the dsp2AlgorithmTable.
                             The following description outlines the algorithms 
                             supported in each corresponding AlgoSet.
                               algoSet1 :     g168-echo-cancellation128ms

                               algoSet2 :     g726-voice-compression, 
                                              g165-echo-cancellation, 
                                              generic-silence-suppression,
                                              fax-modem-tone-detection,
                                              g168-echo-cancellation64ms.

                               algoSet3 :     g729a-voice-compression,
                                              g165-echo-cancellation,
                                              g729b-silence-suppression,
                                              fax-modem-tone-detection,
                                              g168-echo-cancellation64ms.

                               algoSet4 :     v17-fax-algorithm-upto-14400-bps, 
                                              v29-fax-algorithm-upto-9600-bps,
                                             v27ter-fax-algorithm-upto-2400-bps,
                                              v21-fax-algorithm-upto-300-bps.

                               algoSet5 :     g168-echo-cancellation64ms.

                               algoSet6 :     g726-voice-compression,
                                              g729a-voice-compression,
                                              g729b-silence-suppression,
                                              g168-echo-cancellation64ms,
                                              v17-fax-algorithm-upto-14400-bps, 
                                              v29-fax-algorithm-upto-9600-bps,
                                             v27ter-fax-algorithm-upto-2400-bps,
                                              v21-fax-algorithm-upto-300-bps.
                                  " 
                    DEFVAL { algoSet2 } 
                    ::= { dsp2ChannelConfigEntry 4 }

dsp2AlgorithmTable OBJECT-TYPE
                SYNTAX SEQUENCE OF Dsp2AlgorithmEntry
                MAX-ACCESS not-accessible
                STATUS current
                DESCRIPTION "Table of dsp2 algorithms assigned to interface."
                ::= { dsp2Channel 2 }

dsp2AlgorithmEntry OBJECT-TYPE
                SYNTAX Dsp2AlgorithmEntry
                MAX-ACCESS not-accessible
                STATUS current
                DESCRIPTION "Row definition for dsp2 algorithms assigned to
                             interfaces."
                INDEX { dsp2AlgorithmId, dsp2AlgorithmType }
                ::= { dsp2AlgorithmTable 1 }

Dsp2AlgorithmEntry ::= SEQUENCE {
                dsp2AlgorithmId         IntfIndex,
                dsp2AlgorithmType       INTEGER
                }

dsp2AlgorithmId OBJECT-TYPE
                SYNTAX IntfIndex
                MAX-ACCESS not-accessible
                STATUS current
                DESCRIPTION "interface index - SSPPCC"
                ::= { dsp2AlgorithmEntry 1 }

dsp2AlgorithmType OBJECT-TYPE
                SYNTAX INTEGER  {
                                g726-voice-compression(1),
                                g165-echo-cancellation(2),
                                generic-silence-suppression(3),
                                fax-modem-tone-detection(4),
                                g729a-voice-compression(5),
                                g729b-silence-suppression(6),
                                g168-echo-cancellation64ms(7),
                                g168-echo-cancellation128ms(8),
                                v17-fax-algorithm-upto-14400-bps(9),
                                v29-fax-algorithm-upto-9600-bps(10),
                                v27ter-fax-algorithm-upto-2400-bps(11),
                                v21-fax-algorithm-upto-300-bps(12)
                                }
                MAX-ACCESS read-only
                STATUS current
                DESCRIPTION "DSP Algorithm type."
                DEFVAL { g726-voice-compression }
                ::= { dsp2AlgorithmEntry 2 }


imaGrpChannelConfigTable  OBJECT-TYPE
                SYNTAX SEQUENCE OF ImaGrpChannelConfigEntry
                MAX-ACCESS not-accessible
                STATUS current
                DESCRIPTION "Table used for the IMA virtual channel (group)
                             configuration on cards that have physical 
                             interfaces configured as atmIma. Represents three
                             channels that can be configured as IMA groups on
                             port 7 of DS1 and E1 cards."
                ::= { channelConfig 14 }

imaGrpChannelConfigEntry OBJECT-TYPE
                SYNTAX ImaGrpChannelConfigEntry
                MAX-ACCESS not-accessible
                STATUS current
                DESCRIPTION "Row definition for common physical
                             port attributes"
                INDEX { imaGrpChannelId }
                ::= { imaGrpChannelConfigTable 1 }

ImaGrpChannelConfigEntry ::= SEQUENCE {
                imaGrpChannelId                    IntfIndex,
                imaGrpChannelIfType                INTEGER,
                imaGrpChannelPortMap               Integer32,
                imaGrpChannelNeState               ImaGrpChannelEndState,
                imaGrpChannelFeState               ImaGrpChannelEndState,
                imaGrpChannelFailureStatus         INTEGER,
                imaGrpChannelSymmetry              INTEGER,
                imaGrpChannelMinNumTxLinks         INTEGER,
                imaGrpChannelMinNumRxLinks         INTEGER,
                imaGrpChannelNeTxClkMode           INTEGER,
                imaGrpChannelFeTxClkMode           INTEGER,
                imaGrpChannelTxImaId               INTEGER,
                imaGrpChannelRxImaId               INTEGER,
                imaGrpChannelTxFrameLength         INTEGER,
                imaGrpChannelRxFrameLength         INTEGER,
                imaGrpChannelDiffLinkDelayMax      Integer32,
                imaGrpChannelLeastDelayLink        IntfIndex,
                imaGrpChannelDiffDelayMaxObs       Integer32,
                imaGrpChannelAlphaValue            INTEGER,
                imaGrpChannelBetaValue             INTEGER,
                imaGrpChannelGammaValue            INTEGER,
                imaGrpChannelStatsNeNumFailures    Integer32,
                imaGrpChannelStatsFeNumFailures    Integer32,
                imaGrpChannelStatsNumTxActLnks     Integer32,
                imaGrpChannelStatsNumRxActLnks     Integer32,
                imaGrpChannelStatsTimer            Integer32,
                imaGrpChannelCompatMode                   INTEGER
                }

imaGrpChannelId OBJECT-TYPE
                SYNTAX IntfIndex
                MAX-ACCESS not-accessible
                STATUS current
                DESCRIPTION "interface index - SSPPCCC"
                ::= { imaGrpChannelConfigEntry 1 }

imaGrpChannelIfType OBJECT-TYPE
                SYNTAX INTEGER  {
                                unconfigured(1),
                                atmUni3-0(2),
                                atmUni3-1(3),
                                iispUser(4),
                                iispNetwork(5),
                                atmPnni1-0(6),
                                atmUni4-0(7)
                                }
                MAX-ACCESS read-write
                STATUS current
                DESCRIPTION "interface type "
                DEFVAL { unconfigured }
                ::= { imaGrpChannelConfigEntry 2 }

imaGrpChannelPortMap OBJECT-TYPE
                SYNTAX Integer32
                MAX-ACCESS read-write
                STATUS current
                DESCRIPTION "A bitmap that identifies the physical IMA
                             interfaces in this group. The least significant 
                             bit represents port 1."
                ::= { imaGrpChannelConfigEntry 3 }

imaGrpChannelNeState OBJECT-TYPE
                SYNTAX ImaGrpChannelEndState 
                MAX-ACCESS read-only
                STATUS current
                DESCRIPTION "The current operational state of the near-end IMA 
                             Group State Machine."
                ::= {imaGrpChannelConfigEntry 4 }

imaGrpChannelFeState OBJECT-TYPE
                SYNTAX ImaGrpChannelEndState 
                MAX-ACCESS read-only
                STATUS current
                DESCRIPTION "The current operational state of the far-end IMA 
                             Group State Machine."
                ::= { imaGrpChannelConfigEntry 5 }

imaGrpChannelFailureStatus OBJECT-TYPE
                SYNTAX INTEGER { 
                        noFailure(1), 
                        startUpNe(2),
                        startUpFe(3), 
                        invalidMValueNe(4),
                        invalidMValueFe(5),
                        failedAssymetricNe(6),
                        failedAssymetricFe(7),
                        insuffLinksNe(8),
                        insuffLinksFe(9),
                        blockedNe(10),
                        blockedFe(11),
                        otherFailure(12)
                      } 
                MAX-ACCESS read-only
                STATUS current
                DESCRIPTION "The current failure status of the IMA group
                             (the reason why the GTSM is in the down state).
                        noFailure(1)          no failure
                        startUpNe(2)          near-end is in the state of start-up
                        startUpFe(3)          far-end  is in the state of start-up
                        invalidMValueNe(4)    near-end has invalid frame length
                        invalidMValueFe(5)    far-end  has invalid frame length
                        failedAssymetricNe(6) near-end failed due to incompatable
                                              symmetry
                        failedAssymetricFe(7) far-end  failed due to incompatable
                                              symmetry
                        insuffLinksNe(8)      Near-end reported less than the min
                                              number of Tx links are active or
                                              less than the min number
                                              of Rx links are active
                        insuffLinksFe(9)      Far-end reported less than the min
                                              number of Rx links are active or less
                                              than thenmin number of Tx links are
                                              active
                        blockedNe(10)         Near-end is administratively
                                              out-of-service
                        blockedFe(11)         Far-end  is administratively
                                              out-of-service
                        otherFailure(12)      other failures"
                ::= { imaGrpChannelConfigEntry 6 }   

imaGrpChannelSymmetry OBJECT-TYPE
                SYNTAX INTEGER { 
                        symOperation(1),
                        asymOperation(2),
                        asymConfiguration(3)
                      }
                MAX-ACCESS read-only
                STATUS current
                DESCRIPTION "Symmetry of the IMA group.
                        Symmetric configuration: all ports of IMA group are
                        configured as full-duplex.  With symmetric configuration,
                        operation is symmetric if no links failes; is asymmetric
                        if a link fails so that the active forward and backward
                        links between far-end and near-end are asymmetric.  If
                        the configuration is asymmetric, the operation can never
                        be symmetric."
                DEFVAL { symOperation }
                ::= {imaGrpChannelConfigEntry 7 }

imaGrpChannelMinNumTxLinks OBJECT-TYPE
                SYNTAX INTEGER (1..32)
                MAX-ACCESS read-write
                STATUS current
                DESCRIPTION "Minimum number of transmit links required to be 
                             Active for the IMA group to be in the Up state."
                ::= { imaGrpChannelConfigEntry 8 }

imaGrpChannelMinNumRxLinks OBJECT-TYPE
                SYNTAX INTEGER (1..32)
                MAX-ACCESS read-write
                STATUS current
                DESCRIPTION "Minimum number of receive links required to be 
                             Active for the IMA group to be in the Up state."
                ::= { imaGrpChannelConfigEntry 9 }

imaGrpChannelNeTxClkMode OBJECT-TYPE
                SYNTAX INTEGER {
                        ctc(1),
                        itc(2)
                      }
                MAX-ACCESS read-write
                STATUS current
                DESCRIPTION "Transmit clocking mode used by the near-end IMA 
                  group. There are two possible modes: the Common Transmit 
                  Clock (CTC) and the Independent Transmit Clock (ITC). The 
                  CTC mode corresponds to the case when the transmit clock of 
                  all IMA links are derived from the same source. The ITC 
                  configuration corresponds to the case where there is at 
                  least one IMA link whose transmit clock is derived from a 
                  source different than at least another link transmit clock. 
                  The underlying clock configuration must be set up by the 
                  user to ensure operation in the selected mode."
                DEFVAL { ctc }
                ::= { imaGrpChannelConfigEntry 10 }

imaGrpChannelFeTxClkMode OBJECT-TYPE
                SYNTAX INTEGER {
                        ctc(1),
                        itc(2)
                      }
                MAX-ACCESS read-only
                STATUS current
                DESCRIPTION
                  "Transmit clocking mode used by the far-end IMA group.
                  There are two possible modes: the Common Transmit 
                  Clock (CTC) and the Independent Transmit Clock (ITC). 
                  The CTC mode corresponds to the case when the transmit clock 
                  of all IMA links are derived from the same source. The ITC 
                  configuration corresponds to the case where there is at least
                  one IMA link whose transmit clock is derived from a source 
                  different than at least another link transmit clock."
                ::= { imaGrpChannelConfigEntry 11 }

imaGrpChannelTxImaId OBJECT-TYPE
                SYNTAX INTEGER (0..255)
                MAX-ACCESS read-write
                STATUS current
                DESCRIPTION "The IMA ID currently in use by the near-end IMA 
                            function."
                ::= {imaGrpChannelConfigEntry 12 }

imaGrpChannelRxImaId OBJECT-TYPE
                SYNTAX INTEGER (0..255)
                MAX-ACCESS  read-only
                STATUS current
                DESCRIPTION "The IMA ID currently in use by the far-end IMA 
                             function."
                ::= { imaGrpChannelConfigEntry 13 }

imaGrpChannelTxFrameLength OBJECT-TYPE
                SYNTAX INTEGER {
                        m32(32),
                        m64(64),
                        m128(128),
                        m256(256)
                      }
                MAX-ACCESS read-write
                STATUS current
                DESCRIPTION
                 "The frame length to be used by the IMA group in the transmit 
                  direction. Can only be set when the IMA group is startup."
                DEFVAL { m128 }
                ::= { imaGrpChannelConfigEntry 14 }

imaGrpChannelRxFrameLength OBJECT-TYPE
                SYNTAX INTEGER {
                        m32(32),
                        m64(64),
                        m128(128),
                        m256(256)
                      }
                MAX-ACCESS read-only
                STATUS current
                DESCRIPTION "Value of IMA frame length as received from 
                             remote IMA function."
                ::= { imaGrpChannelConfigEntry 15 }

imaGrpChannelDiffLinkDelayMax OBJECT-TYPE
                SYNTAX INTEGER (1..200)
                MAX-ACCESS read-write
                STATUS current
                DESCRIPTION
                "The maximum number of milliseconds of delay differential among
                 the links that will be tolerated on this interface."
                DEFVAL { 25 }
                ::= { imaGrpChannelConfigEntry 16 }

imaGrpChannelLeastDelayLink OBJECT-TYPE
                SYNTAX IntfIndex
                MAX-ACCESS read-only
                STATUS current
                DESCRIPTION
                 "The Interface Index of the link configured in the IMA 
                  group which has the smallest link propagation delay. This 
                  value has meaning only if at least 1 link has been configured
                  in the IMA group."
                ::= { imaGrpChannelConfigEntry 17 }
      
imaGrpChannelDiffDelayMaxObs OBJECT-TYPE
                SYNTAX Integer32
                MAX-ACCESS read-only 
                STATUS current
                DESCRIPTION
                 "The latest maximum differential delay observed (in 
                  milliseconds), i.e. between the links having the least and 
                  most link propagation delay, among the receive links that 
                  are currently configured in the IMA group."
                ::= { imaGrpChannelConfigEntry 18 }

imaGrpChannelAlphaValue OBJECT-TYPE
                SYNTAX INTEGER (1..2)
                MAX-ACCESS read-write
                STATUS current
                DESCRIPTION
                 "This indicates the 'alpha' value used to specify the 
                  number of consecutive invalid ICP cells to be detected 
                  before moving to the IMA HUNT state."
                DEFVAL { 2 }
                ::= { imaGrpChannelConfigEntry 19 }

imaGrpChannelBetaValue OBJECT-TYPE
                SYNTAX INTEGER (1..5)
                MAX-ACCESS read-write
                STATUS current
                DESCRIPTION
                 "This indicates the 'beta' value used to specify the 
                  number of consecutive errored ICP cells to be detected 
                  before moving to the IMA HUNT state."
                DEFVAL { 2 }
                ::= { imaGrpChannelConfigEntry 20 }

imaGrpChannelGammaValue OBJECT-TYPE
                SYNTAX INTEGER (1..5)
                MAX-ACCESS read-write
                STATUS current
                DESCRIPTION
                 "This indicates the 'gamma' value used to specify the 
                  number of consecutive valid ICP cells to be detected before 
                  moving to the IMA SYNC state from the PRESYNC state."
                DEFVAL { 1 }
                ::= { imaGrpChannelConfigEntry 21 }

imaGrpChannelStatsNeNumFailures OBJECT-TYPE
                SYNTAX Integer32
                MAX-ACCESS read-only
                STATUS current
                DESCRIPTION
                 "The number of times a near-end group failure (Config-Abort,
                  Insufficient-Links) has been reported."
                ::= { imaGrpChannelConfigEntry 22 }

imaGrpChannelStatsFeNumFailures OBJECT-TYPE
                SYNTAX Integer32
                MAX-ACCESS read-only
                STATUS current
                DESCRIPTION
                 "The number of times a far-end group failure (Config-Abort-FE,
                  Insufficient-Links-FE, Blocked-FE) has been reported."
                ::= { imaGrpChannelConfigEntry 23 }

imaGrpChannelStatsNumTxActLnks OBJECT-TYPE
                SYNTAX Integer32
                MAX-ACCESS read-only
                STATUS current
                DESCRIPTION
                 "The number of links which are configured to transmit and are
                  currently Active in this IMA group."
                ::= { imaGrpChannelConfigEntry 24 }
 
imaGrpChannelStatsNumRxActLnks OBJECT-TYPE
                SYNTAX Integer32
                MAX-ACCESS read-only
                STATUS current
                DESCRIPTION
                 "The number of links which are configured to receive and are
                  currently Active in this IMA group."
                ::= { imaGrpChannelConfigEntry 25 }

imaGrpChannelStatsTimer OBJECT-TYPE
                SYNTAX Integer32
                MAX-ACCESS read-only
                STATUS current
                DESCRIPTION " Time, in seconds, since last reset."
                ::= { imaGrpChannelConfigEntry 26 }

imaGrpChannelCompatMode OBJECT-TYPE
                SYNTAX INTEGER {
                        no(1),
                        yes(2)
                }
                MAX-ACCESS read-write
                STATUS current
                DESCRIPTION 
                 "This is used to indicate interoperability mode to the I/O
                 card in terms of reporting the link status at the correct
                 location in the IMA Control Protocol (ICP) cell"
                DEFVAL {no}
                ::= { imaGrpChannelConfigEntry 27 }

--
-- Channel Configuration for the new card
--

tasmChannelConfigTable OBJECT-TYPE
                SYNTAX SEQUENCE OF TasmChannelConfigEntry
                MAX-ACCESS not-accessible
                STATUS current
                DESCRIPTION "Table of common physical Channel attributes"
                ::= { channelConfig 15 }

tasmChannelConfigEntry OBJECT-TYPE
                SYNTAX TasmChannelConfigEntry
                MAX-ACCESS not-accessible
                STATUS current
                DESCRIPTION "Row definition for common physical
                             channel attributes"
                INDEX { tasmChannelId }
                ::= { tasmChannelConfigTable 1 }

TasmChannelConfigEntry ::= SEQUENCE {
                tasmChannelId                   IntfIndex,
                tasmChannelIfType               INTEGER,
                tasmChannelAlarmType            INTEGER,
                tasmChannelModeConfig                INTEGER
                }

tasmChannelId       OBJECT-TYPE
                SYNTAX IntfIndex
                MAX-ACCESS not-accessible
                STATUS current
                DESCRIPTION "Interface index - SSPPCC"
                ::= { tasmChannelConfigEntry 1 }

tasmChannelIfType OBJECT-TYPE
                SYNTAX INTEGER  {
                                unconfigured(1),
                                toneAnnce(2)
                                }
                MAX-ACCESS read-write
                STATUS current
                DESCRIPTION "Channel Interface Type"
                DEFVAL { unconfigured }
                ::= { tasmChannelConfigEntry 2 }

tasmChannelAlarmType OBJECT-TYPE
                SYNTAX INTEGER  {
                                noAlarm(1),
                                tasmFailure(2)
                                }
                MAX-ACCESS read-only
                STATUS current
                DESCRIPTION "This field is a read only failure which
                        gives the status of a DSP in the TASM card.When
                        the status is tasmFailure the Operational Status
                        at the interface level will go OOS"
                DEFVAL { noAlarm }
                ::= { tasmChannelConfigEntry 3 }

tasmChannelModeConfig OBJECT-TYPE
                SYNTAX INTEGER {
                                casMode(1),
                                tasMode(2)
                                     }
                MAX-ACCESS read-write
                STATUS current
                DESCRIPTION "This field is used to configure the mdoe in which
                        a TASM DSP will be used asd a resource. The modes are
                        explained as follows:
                        casMode: DSP resource is used for DTMF/MF
                                tone detection/generation and running the
                                Type 100, 105, and 108 tests.
                        tasMode: DSP resource is used for playing/compressing
                                announcement."
                DEFVAL { casMode }
                ::= {tasmChannelConfigEntry 4 }


-- The Interface Configuration Group

atmUniConfigTable        OBJECT-TYPE
                SYNTAX SEQUENCE OF AtmUniConfigEntry
                MAX-ACCESS not-accessible
                STATUS current
                DESCRIPTION "Table of atm user to network interface (UNI)"
                ::= { intfConfig 1 }

atmUniConfigEntry        OBJECT-TYPE
                SYNTAX AtmUniConfigEntry
                MAX-ACCESS not-accessible
                STATUS current
                DESCRIPTION "Row definition of atm UNI"
                INDEX { atmUniIfIndex } 
                ::= { atmUniConfigTable 1 }

AtmUniConfigEntry        ::= SEQUENCE {
                atmUniIfIndex                        IntfIndex,
                atmUniAddrType                        INTEGER,
                atmUniSvcMinVpi                        INTEGER,
                atmUniSvcMaxVpi                        INTEGER,
                atmUniSvcMinVci                        INTEGER,
                atmUniSvcMaxVci                        INTEGER,
                atmUniAdminStatus                INTEGER,
                atmUniOperStatus                INTEGER,
                atmUniOverSubscription                INTEGER,
                atmUniNwPrefix1                        OCTET STRING,
                atmUniT303                        Integer32,
                atmUniT308                        Integer32,
                atmUniT309                        Integer32,
                atmUniT310                        Integer32,
                atmUniT313                        Integer32,
                atmUniT316                        Integer32,
                atmUniT317                        Integer32,
                atmUniT322                        Integer32,
                atmUniT398                        Integer32,
                atmUniT399                        Integer32,
                atmUniMyNeighborIpAddress        IpAddress,
                atmUniMyNeighborIfName                DisplayString,
                atmUniVpiSig                        INTEGER,
                atmUniVciSig                        INTEGER,
                atmUniVpiIlmi                        INTEGER,
                atmUniVciIlmi                        INTEGER,
                atmUniAtmSignalingStatus        INTEGER,



                atmUniMyIfName                        DisplayString,
                atmUniIlmiProtocolStatus        INTEGER,
                atmUniIlmiOperStatus                INTEGER,
                atmUniIlmiConfigProc                INTEGER,
                atmUniIlmiConnectProc                INTEGER,
                atmUniIlmiAttachPtProc                INTEGER,
                atmUniIlmiSecureLinkProc        INTEGER,
                atmUniIlmiAddrRegProc                INTEGER,
                atmUniIlmiTimerS                Integer32,
                atmUniIlmiTimerT                Integer32,
                atmUniIlmiRetryK                Integer32,
                atmUniIntfType                        INTEGER,
                atmUniUserAddress                OCTET STRING,
                atmUniViSuppFlag                INTEGER,
                atmUniUPCSupp                         INTEGER,
                atmUniUbrLoadBalSupp                 INTEGER,
                atmUniAvailBwIgr                   Integer32,
                atmUniAvailBwEgr                  Integer32,

        atmUniVUNISuppFlag     INTEGER,
        atmUniUserAddrOrgScope  INTEGER,

                atmUniSscopRxWndSz              INTEGER,
                atmUniConnTrafficShapingFlag    INTEGER
                }

atmUniIfIndex        OBJECT-TYPE
                SYNTAX IntfIndex
                MAX-ACCESS not-accessible
                STATUS current
                DESCRIPTION "interface index (slot/port/channel) SSPPCCC"
                ::= { atmUniConfigEntry 1 }

atmUniAddrType        OBJECT-TYPE
                SYNTAX INTEGER  {
                                nsap(1),
                                e164(2),
                                private(3)
                                }
                MAX-ACCESS read-write
                STATUS current
                DESCRIPTION "atm address type"
                DEFVAL { nsap }
                ::= { atmUniConfigEntry 2 }

atmUniSvcMinVpi        OBJECT-TYPE
                SYNTAX INTEGER (0..255)
                MAX-ACCESS read-write
                STATUS current
                DESCRIPTION "The lower bound of the VPI for SVC connections."
                DEFVAL { 0 }
                ::= { atmUniConfigEntry 3 }

atmUniSvcMaxVpi        OBJECT-TYPE
                SYNTAX INTEGER (0..255)
                MAX-ACCESS read-write
                STATUS current
                DESCRIPTION "The upper bound of the VPI for SVC connections."
                DEFVAL { 0 }
                ::= { atmUniConfigEntry 4 }

atmUniSvcMinVci        OBJECT-TYPE
                SYNTAX INTEGER (0..65535)
                MAX-ACCESS read-write
                STATUS current
                DESCRIPTION "The lower bound of the VCI for SVC connections."



                DEFVAL { 32 }

                ::= { atmUniConfigEntry 5 }

atmUniSvcMaxVci        OBJECT-TYPE
                SYNTAX INTEGER (0..65535)
                MAX-ACCESS read-write
                STATUS current
                DESCRIPTION "The upper bound of the VCI for SVC connections."



                DEFVAL { 255 }

                ::= { atmUniConfigEntry 6 }

atmUniAdminStatus        OBJECT-TYPE
                SYNTAX INTEGER  {
                                outOfService(1),
                                inService(2),
                                delete(3)
                                }
                MAX-ACCESS read-write
                STATUS current
                DESCRIPTION "The administrative action:
                             'outOfService' means take the UNI out of service
                             'inService'    means take the UNI in service
                             'delete'       remove/deconfigure the UNI."
                DEFVAL { outOfService }
                ::= { atmUniConfigEntry 7 }

atmUniOperStatus        OBJECT-TYPE
                SYNTAX INTEGER  {
                                outOfService(1),
                                inService(2)
                                }
                MAX-ACCESS read-only
                STATUS current
                DESCRIPTION "The operational status of the UNI:
                             'outOfService' means the UNI is out of service
                             'inService'    means the UNI is in service"
                DEFVAL { outOfService }
                ::= { atmUniConfigEntry 8 }

atmUniNwPrefix1        OBJECT-TYPE
                SYNTAX OCTET STRING (SIZE(13))
                MAX-ACCESS read-write
                STATUS current
                DESCRIPTION "ATM Network Prefix 1"
                ::= { atmUniConfigEntry 9 }

atmUniOverSubscription        OBJECT-TYPE
                SYNTAX INTEGER (1..100)
                MAX-ACCESS read-write
                STATUS current
                DESCRIPTION "Over subscription factor"
                DEFVAL { 10 }
                ::= { atmUniConfigEntry 10 }

atmUniT303        OBJECT-TYPE
                SYNTAX Integer32
                MAX-ACCESS read-write
                STATUS current
                DESCRIPTION "Timer T303 value - seconds"
                DEFVAL { 4 }
                ::= { atmUniConfigEntry 11 }

atmUniT308        OBJECT-TYPE
                SYNTAX Integer32
                MAX-ACCESS read-write
                STATUS current
                DESCRIPTION "Timer T308 value - seconds"
                DEFVAL { 30 }
                ::= { atmUniConfigEntry 12 }

atmUniT309        OBJECT-TYPE
                SYNTAX Integer32
                MAX-ACCESS read-write
                STATUS current
                DESCRIPTION "Timer T309 value - seconds"
                DEFVAL { 10 }
                ::= { atmUniConfigEntry 13 }

atmUniT310        OBJECT-TYPE
                SYNTAX Integer32
                MAX-ACCESS read-write
                STATUS current
                DESCRIPTION "Timer T310 value - seconds"
                DEFVAL { 10 }
                ::= { atmUniConfigEntry 14 }

atmUniT313        OBJECT-TYPE
                SYNTAX Integer32
                MAX-ACCESS read-write
                STATUS current
                DESCRIPTION "Timer T313 value - User side only - seconds"
                DEFVAL { 4 }
                ::= { atmUniConfigEntry 15 }

atmUniT316        OBJECT-TYPE
                SYNTAX Integer32
                MAX-ACCESS read-write
                STATUS current
                DESCRIPTION "Timer T316 value - seconds"
                DEFVAL { 120 }
                ::= { atmUniConfigEntry 16 }

atmUniT317        OBJECT-TYPE
                SYNTAX Integer32
                MAX-ACCESS read-write
                STATUS current
                DESCRIPTION "Timer T317 value - seconds"
                DEFVAL { 60 }
                ::= { atmUniConfigEntry 17 }

atmUniT322        OBJECT-TYPE
                SYNTAX Integer32
                MAX-ACCESS read-write
                STATUS current
                DESCRIPTION "Timer T322 value - seconds"
                DEFVAL { 4 }
                ::= { atmUniConfigEntry 18}

atmUniT398        OBJECT-TYPE
                SYNTAX Integer32
                MAX-ACCESS read-write
                STATUS current
                DESCRIPTION "Timer T398 value - seconds"
                DEFVAL { 4 }
                ::= { atmUniConfigEntry 19 }

atmUniT399        OBJECT-TYPE
                SYNTAX Integer32
                MAX-ACCESS read-write
                STATUS current
                DESCRIPTION "Timer T399 value - seconds"
                DEFVAL { 14 }
                ::= { atmUniConfigEntry 20 }

atmUniMyNeighborIpAddress OBJECT-TYPE
                SYNTAX IpAddress
                MAX-ACCESS read-write
                STATUS current
                DESCRIPTION "The IP address of the neighbor system connected to
                             the far end of this interface, to which a Network
                             Management Station can send SNMP messages, as IP
                             datagrams sent to UDP port 161, in order to access
                             network management information concerning the 
                             operation of that system.  Note that the value
                             of this object can currently only be obtained 
                             by manual configuration."
                ::= { atmUniConfigEntry 21 }
 
atmUniMyNeighborIfName OBJECT-TYPE
                SYNTAX DisplayString (SIZE(20))
                MAX-ACCESS read-write
                STATUS current
                DESCRIPTION "The textual name of the interface on the neighbor
                             system on the far end of this interface, and to
                             which this interface connects.  If the neighbor
                             system is manageable through SNMP and supports
                             the object ifName, the value of this object must
                             be identical with that of ifName for the ifEntry
                             of the lowest level physical interface for this 
                             port.  If this interface does not have a
                             textual name, the value of this object is a zero
                             length string.  Note that the value of this object
                             can currently only be obtained by manual
                             configuration."
                ::= { atmUniConfigEntry 22 }
 
atmUniVpiSig        OBJECT-TYPE
                SYNTAX INTEGER (0..255)
                MAX-ACCESS read-write
                STATUS current
                DESCRIPTION "VPI value for the signalling channel for the UNI
                             interface."
                DEFVAL { 0 }
                ::= { atmUniConfigEntry 23 }

atmUniVciSig        OBJECT-TYPE
                SYNTAX INTEGER (0..31)
                MAX-ACCESS read-write
                STATUS current
                DESCRIPTION "VCI value for the signalling channel for the UNI
                             interface."
                DEFVAL { 5 }
                ::= { atmUniConfigEntry 24 }

atmUniVpiIlmi        OBJECT-TYPE
                SYNTAX INTEGER (0..255)
                MAX-ACCESS read-write
                STATUS current
                DESCRIPTION "VPI value for the ilmi channel for the UNI
                             interface."
                DEFVAL { 0 }
                ::= { atmUniConfigEntry 25 }

atmUniVciIlmi        OBJECT-TYPE
                SYNTAX INTEGER (0..31)
                MAX-ACCESS read-write
                STATUS current
                DESCRIPTION "VCI value for the ilmi channel for the UNI
                             interface."
                DEFVAL { 16 }
                ::= { atmUniConfigEntry 26 }

atmUniAtmSignalingStatus OBJECT-TYPE
                SYNTAX INTEGER  {
                                enabled(1),
                                disabled(2)
                                }
                MAX-ACCESS read-write
                STATUS current
                DESCRIPTION "Indicates if atm signaling is enabled or disabled
                             for this interface."



                DEFVAL { disabled }

                ::= { atmUniConfigEntry 27 }



atmUniMyIfName        OBJECT-TYPE
                SYNTAX DisplayString (SIZE(20))
                MAX-ACCESS read-write
                STATUS current
                DESCRIPTION "A textual name of this interface.  If this system
                             is manageable manageable through SNMP and supports
                             the object ifName, the value of this object must
                             be identical with that of ifName for the ifEntry
                             of the lowest level physical interface for this 
                             port.  This interface must be uniquely named on 
                             this system to distinguish parallel links with a 
                             neighboring system.  If this interface does not 
                             have a textual name, the value of this object is a 
                             zero length string."
                ::= { atmUniConfigEntry 29 }
 
atmUniIlmiProtocolStatus OBJECT-TYPE
                SYNTAX INTEGER  {
                                enabled(1),
                                disabled(2)
                                }
                MAX-ACCESS read-write
                STATUS current
                DESCRIPTION "The administrative status:
                             'enabled'  - ILMI protocol enabled on UNI
                             'disabled' - ILMI protocol disabled on UNI."
                DEFVAL { disabled }
                ::= { atmUniConfigEntry 30 }

atmUniIlmiOperStatus OBJECT-TYPE
                SYNTAX INTEGER  {
                                outOfService(1),
                                inService(2)
                                }
                MAX-ACCESS read-only
                STATUS current
                DESCRIPTION "The operational status:
                             'outOfService' - ILMI connectivity is down
                             'inService'    - ILMI connectivity is up."
                DEFVAL { outOfService }
                ::= { atmUniConfigEntry 31 }

atmUniIlmiConfigProc OBJECT-TYPE
                SYNTAX INTEGER  {
                                enabled(1),
                                disabled(2)
                                }
                MAX-ACCESS read-write
                STATUS current
                DESCRIPTION "ILMI Configuration Procedure status."
                DEFVAL { disabled }
                ::= { atmUniConfigEntry 32 }

atmUniIlmiConnectProc OBJECT-TYPE
                SYNTAX INTEGER  {
                                enabled(1),
                                disabled(2)
                                }
                MAX-ACCESS read-write
                STATUS current
                DESCRIPTION "ILMI Connectivity Procedure status."
                DEFVAL { disabled }
                ::= { atmUniConfigEntry 33 }

atmUniIlmiAttachPtProc OBJECT-TYPE
                SYNTAX INTEGER  {
                                enabled(1),
                                disabled(2)
                                }
                MAX-ACCESS read-write
                STATUS current
                DESCRIPTION "ILMI Attachment Point Procedure status."
                DEFVAL { disabled }
                ::= { atmUniConfigEntry 34 }

atmUniIlmiSecureLinkProc OBJECT-TYPE
                SYNTAX INTEGER  {
                                enabled(1),
                                disabled(2)
                                }
                MAX-ACCESS read-write
                STATUS current
                DESCRIPTION "ILMI Secure Link Procedure status.  Can be enabled
                             only if Attachment Point Procedure is enabled."
                DEFVAL { disabled }
                ::= { atmUniConfigEntry 35 }

atmUniIlmiAddrRegProc OBJECT-TYPE
                SYNTAX INTEGER  {
                                enabled(1),
                                disabled(2)
                                }
                MAX-ACCESS read-write
                STATUS current
                DESCRIPTION "ILMI Address Registration Procedure status."
                DEFVAL { disabled }
                ::= { atmUniConfigEntry 36 }

atmUniIlmiTimerS OBJECT-TYPE
                SYNTAX Integer32
                MAX-ACCESS read-write
                STATUS current
                DESCRIPTION "Timer S (secs).  Used to poll peer when link is
                             down."
                DEFVAL { 1 }
                ::= { atmUniConfigEntry 37 }

atmUniIlmiTimerT OBJECT-TYPE
                SYNTAX Integer32
                MAX-ACCESS read-write
                STATUS current
                DESCRIPTION "Timer T (secs).  Used to poll peer when link is
                             up."
                DEFVAL { 5 }
                ::= { atmUniConfigEntry 38 }

atmUniIlmiRetryK OBJECT-TYPE
                SYNTAX Integer32
                MAX-ACCESS read-write
                STATUS current
                DESCRIPTION "Retry K - number of timeouts before link is 
                             declared down."
                DEFVAL { 4 }
                ::= { atmUniConfigEntry 39 }

atmUniIntfType  OBJECT-TYPE
                SYNTAX INTEGER  {
                                user(1),
                                network(2)
                                }
                MAX-ACCESS read-write
                STATUS current
                DESCRIPTION "atm interface type"
                DEFVAL { network }
                ::= { atmUniConfigEntry 40 }

atmUniUserAddress OBJECT-TYPE
                SYNTAX OCTET STRING (SIZE(7))
                MAX-ACCESS read-write
                STATUS current
                DESCRIPTION "ATM User Address"
                ::= { atmUniConfigEntry 41 }

atmUniViSuppFlag OBJECT-TYPE
                SYNTAX INTEGER  {
                                disabled(1),
                                enabled(2)
                                }
                MAX-ACCESS read-write
                STATUS current
                DESCRIPTION "virtual interface supp off/on"
                DEFVAL { disabled }
                ::= { atmUniConfigEntry 42 }

atmUniUPCSupp OBJECT-TYPE
                SYNTAX INTEGER  {
                                disabled(1),
                                enabled(2)
                                }
                MAX-ACCESS read-write
                STATUS current
                DESCRIPTION "upc supp off/on"
                DEFVAL { disabled }
                ::= { atmUniConfigEntry 43 }

atmUniUbrLoadBalSupp OBJECT-TYPE
                SYNTAX INTEGER  {
                                disabled(1),
                                enabled(2)
                                }
                MAX-ACCESS read-write
                STATUS current
                DESCRIPTION "load balancing supp for ubr conns off/on"
                DEFVAL { disabled }
                ::= { atmUniConfigEntry 44 }


atmUniAvailBwIgr OBJECT-TYPE
                  SYNTAX Integer32
                  MAX-ACCESS read-only
                  STATUS current
                  DESCRIPTION "The Avail Bandwidth for that interface in
                                cells per sec. Bandwidth for UBR conns
                                will not be accounted for"
                 DEFVAL { 0 }
                 ::= { atmUniConfigEntry 45 }

atmUniAvailBwEgr OBJECT-TYPE
                SYNTAX Integer32
                MAX-ACCESS read-only
                STATUS current
                DESCRIPTION "The Avail Bandwidth for that interface in
                          cells per sec which can go out of the
                          interface. Bandwidth for UBR conns
                          will not be accounted for"
                DEFVAL { 0 }
                ::= { atmUniConfigEntry 46 }


atmUniVUNISuppFlag OBJECT-TYPE
                SYNTAX INTEGER  {
                                disabled(1),
                                enabled(2)
                                }
                MAX-ACCESS read-write
                STATUS current
                DESCRIPTION "virtual UNI interface supp off/on"
                DEFVAL { disabled }
                ::= { atmUniConfigEntry 47 }

atmUniUserAddrOrgScope OBJECT-TYPE
                SYNTAX INTEGER  {
                                localNetwork(1),
                                localNetworkPlusOne(2),
                                localNetworkPlusTwo(3),
                                siteMinusOne(4),
                                intraSite(5),
                                sitePlusOne(6),
                                organizationMinusOne(7),
                                intraOrganization(8),
                                organizationPlusOne(9),
                                communityMinusOne(10),
                                intraCommunity(11),
                                communityPlusOne(12),
                                regional(13),
                                interRegional(14),
                                global(15)
                                }
                MAX-ACCESS read-write
                STATUS current
                DESCRIPTION "ATM User Address Organizational scope"
                DEFVAL { global }
                ::= { atmUniConfigEntry 48 }


atmUniSscopRxWndSz OBJECT-TYPE
                SYNTAX INTEGER (8..256)
                MAX-ACCESS read-write
                STATUS current
                DESCRIPTION "The receive window size for the SSCOP layer"
                DEFVAL { 32 }
                ::= { atmUniConfigEntry 49 }

atmUniConnTrafficShapingFlag OBJECT-TYPE
                SYNTAX INTEGER  {
                                 disabled(1),
                                 enabled(2)
                                }
                MAX-ACCESS read-write
                STATUS current
                DESCRIPTION "Traffic Shaping for Conn was enabled
                             primarily because the core would lose
                             cells since we were non-conformant cells.
                             Therefore the hardware added traffic
                             shaping per connection. But condition is
                             VI should not be enabled if this feature
                             is enabled."
                DEFVAL { disabled }
                ::= { atmUniConfigEntry 50 }

atmIispConfigTable OBJECT-TYPE
                SYNTAX SEQUENCE OF AtmIispConfigEntry
                MAX-ACCESS not-accessible
                STATUS current
                DESCRIPTION "Table of atm iisp interface"
                ::= { intfConfig 2 }

atmIispConfigEntry OBJECT-TYPE
                SYNTAX AtmIispConfigEntry
                MAX-ACCESS not-accessible
                STATUS current
                DESCRIPTION "Row definition of atm iisp interface"
                INDEX { atmIispIfIndex } 
                ::= { atmIispConfigTable 1 }

AtmIispConfigEntry ::= SEQUENCE {
                atmIispIfIndex                        IntfIndex,
                atmIispSvcMinVpi                INTEGER,
                atmIispSvcMaxVpi                INTEGER,
                atmIispSvcMinVci                INTEGER,
                atmIispSvcMaxVci                INTEGER,
                atmIispAdminStatus                INTEGER,
                atmIispOperStatus                INTEGER,
                atmIispOverSubscription                INTEGER,
                atmIispT303                        Integer32,
                atmIispT308                        Integer32,
                atmIispT309                        Integer32,
                atmIispT310                        Integer32,
                atmIispT316                        Integer32,
                atmIispT317                        Integer32,
                atmIispT322                        Integer32,
                atmIispT398                        Integer32,
                atmIispT399                        Integer32,
                atmIispAtmSignalingStatus        INTEGER,
                atmIispAvailBwIgr                   Integer32,
                atmIispAvailBwEgr                   Integer32,
                atmIispUPCSupp                         INTEGER,
                atmIispUbrLoadBalSupp                 INTEGER,
                atmIispSscopRxWndSz             INTEGER,
                atmIispConnTrafficShapingFlag    INTEGER
                }

atmIispIfIndex        OBJECT-TYPE
                SYNTAX IntfIndex
                MAX-ACCESS not-accessible
                STATUS current
                DESCRIPTION "interface index (slot/port/channel) SSPPCCC"
                ::= { atmIispConfigEntry 1 }

atmIispSvcMinVpi        OBJECT-TYPE
                SYNTAX INTEGER (0..4095)
                MAX-ACCESS read-write
                STATUS current
                DESCRIPTION "The lower bound of the VPI for SVC connections."
                DEFVAL { 0 }
                ::= { atmIispConfigEntry 2 }

atmIispSvcMaxVpi        OBJECT-TYPE
                SYNTAX INTEGER (0..4095)
                MAX-ACCESS read-write
                STATUS current
                DESCRIPTION "The upper bound of the VPI for SVC connections."
                DEFVAL { 0 }
                ::= { atmIispConfigEntry 3 }

atmIispSvcMinVci        OBJECT-TYPE
                SYNTAX INTEGER (0..65535)
                MAX-ACCESS read-write
                STATUS current
                DESCRIPTION "The lower bound of the VCI for SVC connections."
                DEFVAL { 32 }
                ::= { atmIispConfigEntry 4 }

atmIispSvcMaxVci        OBJECT-TYPE
                SYNTAX INTEGER (0..65535)
                MAX-ACCESS read-write
                STATUS current
                DESCRIPTION "The upper bound of the VCI for SVC connections. "
                DEFVAL { 255 }
                ::= { atmIispConfigEntry 5 }

atmIispAdminStatus        OBJECT-TYPE
                SYNTAX INTEGER  {
                                outOfService(1),
                                inService(2),
                                delete(3)
                                }
                MAX-ACCESS read-write
                STATUS current
                DESCRIPTION "The administrative action:
                             'outOfService' means take the UNI out of service
                             'inService'    means take the UNI in service
                             'delete'       remove/deconfigure the UNI."
                DEFVAL { outOfService }
                ::= { atmIispConfigEntry 6 }

atmIispOperStatus        OBJECT-TYPE
                SYNTAX INTEGER  {
                                outOfService(1),
                                inService(2)
                                }
                MAX-ACCESS read-only
                STATUS current
                DESCRIPTION "The operational status of the UNI:
                             'outOfService' means the UNI is out of service
                             'inService'    means the UNI is in service"
                DEFVAL { outOfService }
                ::= { atmIispConfigEntry 7 }

atmIispOverSubscription OBJECT-TYPE
                SYNTAX INTEGER (1..100)
                MAX-ACCESS read-write
                STATUS current
                DESCRIPTION "Over subscription factor"
                DEFVAL { 10 }
                ::= { atmIispConfigEntry 8 }

atmIispT303        OBJECT-TYPE
                SYNTAX Integer32
                MAX-ACCESS read-write
                STATUS current
                DESCRIPTION "Timer value - seconds"
                DEFVAL { 4 }
                ::= { atmIispConfigEntry 9 }

atmIispT308        OBJECT-TYPE
                SYNTAX Integer32
                MAX-ACCESS read-write
                STATUS current
                DESCRIPTION "Timer value - seconds"
                DEFVAL { 30 }
                ::= { atmIispConfigEntry 10 }

atmIispT309        OBJECT-TYPE
                SYNTAX Integer32
                MAX-ACCESS read-write
                STATUS current
                DESCRIPTION "Timer value - seconds"
                DEFVAL { 10 }
                ::= { atmIispConfigEntry 11 }

atmIispT310        OBJECT-TYPE
                SYNTAX Integer32
                MAX-ACCESS read-write
                STATUS current
                DESCRIPTION "Timer value - seconds"
                DEFVAL { 10 }
                ::= { atmIispConfigEntry 12 }

atmIispT316        OBJECT-TYPE
                SYNTAX Integer32
                MAX-ACCESS read-write
                STATUS current
                DESCRIPTION "Timer value - seconds"
                DEFVAL { 120 }
                ::= { atmIispConfigEntry 13 }

atmIispT317        OBJECT-TYPE
                SYNTAX Integer32
                MAX-ACCESS read-write
                STATUS current
                DESCRIPTION "Timer value - seconds"
                DEFVAL { 60 }
                ::= { atmIispConfigEntry 14 }

atmIispT322        OBJECT-TYPE
                SYNTAX Integer32
                MAX-ACCESS read-write
                STATUS current
                DESCRIPTION "Timer value - seconds"
                DEFVAL { 4 }
                ::= { atmIispConfigEntry 15 }

atmIispT398        OBJECT-TYPE
                SYNTAX Integer32
                MAX-ACCESS read-write
                STATUS current
                DESCRIPTION "Timer value - seconds"
                DEFVAL { 4 }
                ::= { atmIispConfigEntry 16 }

atmIispT399        OBJECT-TYPE
                SYNTAX Integer32
                MAX-ACCESS read-write
                STATUS current
                DESCRIPTION "Timer value - seconds"
                DEFVAL { 14 }
                ::= { atmIispConfigEntry 17 }

atmIispAtmSignalingStatus OBJECT-TYPE
                SYNTAX INTEGER  {
                                enabled(1),
                                disabled(2)
                                }
                MAX-ACCESS read-write
                STATUS current
                DESCRIPTION "Indicates if atm signaling is enabled or disabled
                             for this interface."
                DEFVAL { disabled }
                ::= { atmIispConfigEntry 18 }

atmIispAvailBwIgr OBJECT-TYPE
                  SYNTAX Integer32
                MAX-ACCESS read-only
                STATUS current
                DESCRIPTION "The Avail Bandwidth for that interface in
                        cells per sec. Bandwidth for UBR conns
                        will not be accounted for."
                DEFVAL { 0 }
                ::= { atmIispConfigEntry 19 }

atmIispAvailBwEgr OBJECT-TYPE
                  SYNTAX Integer32
                MAX-ACCESS read-only
                STATUS current
                DESCRIPTION "The Avail Bandwidth for that interface in
                        cells per sec. Bandwidth for UBR conns
                        will not be accounted for."
                DEFVAL { 0 }
                ::= { atmIispConfigEntry 20 }

atmIispUPCSupp OBJECT-TYPE
                  SYNTAX INTEGER  {
                                disabled(1),
                                enabled(2)
                                }
                MAX-ACCESS read-write
                STATUS current
                DESCRIPTION "upc supp off/on"
                DEFVAL { disabled }
                ::= { atmIispConfigEntry 21 }

atmIispUbrLoadBalSupp OBJECT-TYPE
                SYNTAX INTEGER  {
                                disabled(1),
                                enabled(2)
                                }
                MAX-ACCESS read-write
                STATUS current
                DESCRIPTION "load balancing supp for ubr conns off/on"
                DEFVAL { disabled }
                ::= { atmIispConfigEntry 22 }

atmIispSscopRxWndSz OBJECT-TYPE
                SYNTAX INTEGER (8..256)
                MAX-ACCESS read-write
                STATUS current
                DESCRIPTION "The receive window size for the SSCOP layer"
                DEFVAL { 32 }
                ::= { atmIispConfigEntry 23 }

atmIispConnTrafficShapingFlag OBJECT-TYPE
                SYNTAX INTEGER  {
                                 disabled(1),
                                 enabled(2)
                                }
                MAX-ACCESS read-write
                STATUS current
                DESCRIPTION "Traffic Shaping for Conn was enabled
                             primarily because the core would lose
                             cells since we were non-conformant cells.
                             Therefore the hardware added traffic
                             shaping per connection. But condition is
                             VI should not be enabled if this feature
                             is enabled."
                DEFVAL { disabled }
                ::= { atmIispConfigEntry 24 }

atmCirEmConfigTable OBJECT-TYPE
                SYNTAX SEQUENCE OF AtmCirEmConfigEntry
                MAX-ACCESS not-accessible
                STATUS current
                DESCRIPTION "Table for ATM Circuit Emulation Interface"
                ::= { intfConfig 3 }

atmCirEmConfigEntry OBJECT-TYPE
                SYNTAX AtmCirEmConfigEntry
                MAX-ACCESS not-accessible
                STATUS current
                DESCRIPTION "Row definition for ATM Circuit Emulation 
                             interface"
                INDEX { atmCirEmIfIndex } 
                ::= { atmCirEmConfigTable 1 }

AtmCirEmConfigEntry ::= SEQUENCE {
                                  atmCirEmIfIndex                IntfIndex,
                                  atmCirEmAdminStatus           INTEGER,
                                  atmCirEmOperStatus            INTEGER,
                                  atmCirEmCASIdleAbcdPattern         INTEGER,
                                  atmCirEmCASBusyAbcdPattern         INTEGER,
                                  atmCirEmAlarmDataPattern        INTEGER,
                                  atmCirEmTCPattern                INTEGER,
                                  atmCirEmDownStInterworking    INTEGER
                                 }

atmCirEmIfIndex        OBJECT-TYPE
                SYNTAX IntfIndex
                MAX-ACCESS not-accessible
                STATUS current
                DESCRIPTION "interface index (slot/port/channel) SSPPCCC"
                ::= { atmCirEmConfigEntry 1 }

atmCirEmAdminStatus        OBJECT-TYPE
                SYNTAX INTEGER {
                                outOfService(1),
                                inService(2),
                                delete(3)
                               }
                MAX-ACCESS read-write
                STATUS current
                DESCRIPTION "The administrative action:
                             'outOfService'  take the interface out of service
                             'inService'     take the interface in service
                             'delete'        remove/deconfigure the interface."
                DEFVAL { outOfService }
                ::= { atmCirEmConfigEntry 2 }

atmCirEmOperStatus        OBJECT-TYPE
                SYNTAX INTEGER {
                                outOfService(1),
                                inService(2)
                               }
                MAX-ACCESS read-only
                STATUS current
                DESCRIPTION "The operational status of the interface:
                             'outOfService' interface is out of service
                                 'inService'    interface is in service"
                DEFVAL { outOfService }
                ::= { atmCirEmConfigEntry 3 }

atmCirEmCASIdleAbcdPattern OBJECT-TYPE
                SYNTAX INTEGER (0..15)
                MAX-ACCESS read-write
                STATUS current
                DESCRIPTION "abcd bit pattern for cirEm AIS"
                DEFVAL { 0 }
                ::= { atmCirEmConfigEntry 4 }

atmCirEmCASBusyAbcdPattern OBJECT-TYPE
                SYNTAX INTEGER (0..15)
                MAX-ACCESS read-write
                STATUS current
                DESCRIPTION "abcd bit pattern for cirEm RDI"
                DEFVAL { 15 }
                ::= { atmCirEmConfigEntry 5 }

atmCirEmAlarmDataPattern OBJECT-TYPE
                SYNTAX INTEGER (0..255)
                MAX-ACCESS read-write
                STATUS current
                DESCRIPTION "data pattern for cirEm AIS"
                DEFVAL { 127 }
                ::= { atmCirEmConfigEntry 6 }

atmCirEmTCPattern OBJECT-TYPE
                SYNTAX INTEGER {
                                casIdle(1),
                                casBusy(2)
                               }
                MAX-ACCESS read-write
                STATUS current
                DESCRIPTION "Should abcd bits be toggled after 2.5 Secs."
                DEFVAL { casBusy }
                ::= { atmCirEmConfigEntry 7 }

atmCirEmDownStInterworking OBJECT-TYPE
                SYNTAX INTEGER {
                                unSupp(1),
                                oAM(2),
                                trunkCond(3)
                                }
                MAX-ACCESS read-write
                STATUS current
                DESCRIPTION "This field will be used to select 
                             the type of interworking to be 
                             done in the down stream direction."
                DEFVAL { trunkCond }
                ::= { atmCirEmConfigEntry 8 }

atmTermEmConfigTable OBJECT-TYPE
                SYNTAX SEQUENCE OF AtmTermEmConfigEntry
                MAX-ACCESS not-accessible
                STATUS current
                DESCRIPTION "Table for ATM Terminal Emulation Interface"
                ::= { intfConfig 4 }

atmTermEmConfigEntry OBJECT-TYPE
                SYNTAX AtmTermEmConfigEntry
                MAX-ACCESS not-accessible
                STATUS current
                DESCRIPTION "Row definition for ATM Terminal Emulation 
                             interface"
                INDEX { atmTermEmIfIndex } 
                ::= { atmTermEmConfigTable 1 }

AtmTermEmConfigEntry ::= SEQUENCE {
                                  atmTermEmIfIndex        IntfIndex,
                                  atmTermEmRxTimeOut        INTEGER,
                                  atmTermEmAdminStatus  INTEGER,
                                  atmTermEmOperStatus   INTEGER
                                 }

atmTermEmIfIndex OBJECT-TYPE
                SYNTAX IntfIndex
                MAX-ACCESS not-accessible
                STATUS current
                DESCRIPTION "interface index (slot/port/channel) SSPPCCC"
                ::= { atmTermEmConfigEntry 1 }

atmTermEmRxTimeOut OBJECT-TYPE
                SYNTAX INTEGER (7..10)
                MAX-ACCESS read-write
                STATUS current
                DESCRIPTION "receive timeout value in tenths of seconds."
                ::= { atmTermEmConfigEntry 2 }

atmTermEmAdminStatus        OBJECT-TYPE
                SYNTAX INTEGER {
                                outOfService(1),
                                inService(2),
                                delete(3)
                               }
                MAX-ACCESS read-write
                STATUS current
                DESCRIPTION "The administrative action:
                             'outOfService' take the interface out of service
                             'inService'    take the interface in service
                             'delete'       remove/deconfigure the interface."
                DEFVAL { outOfService }
                ::= { atmTermEmConfigEntry 3 }

atmTermEmOperStatus        OBJECT-TYPE
                SYNTAX INTEGER {
                                outOfService(1),
                                inService(2)
                               }
                MAX-ACCESS read-only
                STATUS current
                DESCRIPTION "The operational status of the interface:
                             'outOfService' interface is out of service
                             'inService'    interface is in service"
                DEFVAL { outOfService }
                ::= { atmTermEmConfigEntry 4 }

hdlcConfigTable OBJECT-TYPE
                SYNTAX SEQUENCE OF HdlcConfigEntry
                MAX-ACCESS not-accessible
                STATUS current
                DESCRIPTION "Table for an HDLC Pass Through Interface"
                ::= { intfConfig 5 }

hdlcConfigEntry OBJECT-TYPE
                SYNTAX HdlcConfigEntry
                MAX-ACCESS not-accessible
                STATUS current
                DESCRIPTION "Row definition for an HDLC Pass Through interface"
                INDEX { hdlcIfIndex } 
                ::= { hdlcConfigTable 1 }

HdlcConfigEntry ::= SEQUENCE {
                                hdlcIfIndex       IntfIndex,
                                hdlcAdminStatus   INTEGER,
                                hdlcOperStatus    INTEGER,
                                hdlcThroughPut    INTEGER,
                                hdlcDataInversion INTEGER
                             }

hdlcIfIndex        OBJECT-TYPE
                SYNTAX IntfIndex
                MAX-ACCESS not-accessible
                STATUS current
                DESCRIPTION "interface index (slot/port/channel) SSPPCCC"
                ::= { hdlcConfigEntry 1 }

hdlcAdminStatus        OBJECT-TYPE
                SYNTAX INTEGER {
                                outOfService(1),
                                inService(2),
                                delete(3) 
                                }
                MAX-ACCESS read-write
                STATUS current
                DESCRIPTION "The administrative action:
                        'outOfService' means take the interface out of service
                        'inService'    means take the interface in service
                        'delete'       remove/deconfigure the interface."
                DEFVAL { outOfService }
                ::= { hdlcConfigEntry 2 }

hdlcOperStatus        OBJECT-TYPE
                SYNTAX INTEGER {
                                outOfService(1),
                                inService(2)
                               }
                MAX-ACCESS read-only
                STATUS current
                DESCRIPTION "The operational status of the interface:
                        'outOfService' means the interface is out of service
                        'inService'    means the interface is in service"
                DEFVAL { outOfService }
                ::= { hdlcConfigEntry 3 }

hdlcThroughPut  OBJECT-TYPE
                SYNTAX INTEGER {
                                k64(1),
                                k56(2)
                                }
                MAX-ACCESS read-write
                STATUS current
                DESCRIPTION "The throughput bandwidth of the interface:
                        'k64' means a throughput of 64 kb
                        'k56' means a throughput of 56 kb"
                DEFVAL { k64 }
                ::= { hdlcConfigEntry 4 }

hdlcDataInversion OBJECT-TYPE
                SYNTAX INTEGER {
                                disabled(1),
                                enabled(2)
                               }
                MAX-ACCESS read-write
                STATUS current
                DESCRIPTION "Flag indicating whether data inversion is 
                         performed by the IO card for this interface."
                DEFVAL { disabled }
                ::= { hdlcConfigEntry 5 }




frUniConfigTable OBJECT-TYPE
                SYNTAX SEQUENCE OF FrUniConfigEntry
                MAX-ACCESS not-accessible
                STATUS current
                DESCRIPTION "Table for Frame Realy UNI Interface"
                ::= { intfConfig 6 }

frUniConfigEntry OBJECT-TYPE
                SYNTAX FrUniConfigEntry
                MAX-ACCESS not-accessible
                STATUS current
                DESCRIPTION "Row definition for Frame Relay interface"
                INDEX { frUniIfIndex } 
                ::= { frUniConfigTable 1 }

FrUniConfigEntry ::= SEQUENCE {
                                  frUniIfIndex                  IntfIndex,
                                  frUniAddrDlciLen              INTEGER,
                                  frUniDlcmiState               INTEGER,
                                  frUniAdminStatus              INTEGER,
                                  frUniOperStatus               INTEGER,
                                  frUniOverSubscription         INTEGER,
                                  frUniLmiProtocol              INTEGER,
                                  frUniInterworkingType         INTEGER,
                                  frUniN391                     INTEGER,
                                  frUniN392                     INTEGER,
                                  frUniN393                     INTEGER,
                                  frUniT391                     INTEGER,
                                  frUniT392                     INTEGER,
                                  frUniAsyncLmi                 INTEGER,
                                  frLmiOperStatus               INTEGER,
                                  frUniNT3                      INTEGER,
                                  frUniThroughPut               INTEGER
                                 }

frUniIfIndex     OBJECT-TYPE
                SYNTAX IntfIndex
                MAX-ACCESS not-accessible
                STATUS current
                DESCRIPTION "interface index (slot/port/channel) SSPPCCC"
                ::= { frUniConfigEntry 1 }

frUniAddrDlciLen OBJECT-TYPE
                SYNTAX INTEGER {
                                twoOctets10Bits(1)
                               }
                MAX-ACCESS read-only
                STATUS current
                DESCRIPTION "Length of Data Link connection identify of
                             frame relay UNI address"
                DEFVAL { twoOctets10Bits }
                ::= { frUniConfigEntry 2 }

frUniDlcmiState OBJECT-TYPE
                SYNTAX INTEGER {
                                noLmi(1),
                                lmiDte(2),
                                lmiDce(3),
                                lmiNni(4)
                               }
                MAX-ACCESS read-write
                STATUS current
                DESCRIPTION "The state of Data Link Connection Management
                             Indentify of frame relay UNI. "
                DEFVAL { noLmi }
                ::= { frUniConfigEntry 3 }

frUniAdminStatus OBJECT-TYPE
                SYNTAX INTEGER {
                                outOfService(1),
                                inService(2),
                                delete(3)
                               }
                MAX-ACCESS read-write
                STATUS current
                DESCRIPTION "The administrative action:
                             'outOfService' take the interface out of service
                             'inService'    take the interface in service
                             'delete'       remove/deconfigure the interface."
                DEFVAL { outOfService }
                ::= { frUniConfigEntry 4 }

frUniOperStatus        OBJECT-TYPE
                SYNTAX INTEGER {
                                outOfService(1),
                                inService(2)
                               }
                MAX-ACCESS read-only
                STATUS current
                DESCRIPTION "The operational status of the interface:
                             'outOfService' interface is out of service
                             'inService'    interface is in service"
                DEFVAL { outOfService }
                ::= { frUniConfigEntry 5 }

frUniOverSubscription OBJECT-TYPE
                SYNTAX INTEGER (1..10)
                MAX-ACCESS read-write
                STATUS current
                DESCRIPTION " Allow for the 'reserved' bandwidth allocated
                              to oversubscribe the line by up to a factor
                              of 10 . Generally, a figure of between 1 and 4
                              is normally a safe bet, although higher levels
                              are often acceptable."
                DEFVAL { 10 }
                ::= { frUniConfigEntry 6 }

frUniLmiProtocol OBJECT-TYPE
                SYNTAX INTEGER {
                                none(1),
                                ccitt(2),
                                ansi(3),
                                att(4)
                               }
                MAX-ACCESS read-write
                STATUS current
                DESCRIPTION " Lmi protocol to run"
                DEFVAL { ccitt }
                ::= { frUniConfigEntry 7 }

frUniInterworkingType OBJECT-TYPE
                SYNTAX INTEGER {
                                frf5(1)

                                ,
                                frf8(2)

                               }
                MAX-ACCESS read-write
                STATUS current
                DESCRIPTION " frf5 - fr/atm network interworking
                              frf8 - fr/atm service interworking"



                DEFVAL { frf8 }

                ::= { frUniConfigEntry 8 }

frUniN391 OBJECT-TYPE
                SYNTAX INTEGER (1..255)
                MAX-ACCESS read-write
                STATUS current
                DESCRIPTION " full status polling counter.
                              DTE:Mandatory, DCE:N/A"
                DEFVAL { 6 }
                ::= { frUniConfigEntry 9 }

frUniN392 OBJECT-TYPE
                SYNTAX INTEGER (1..10)
                MAX-ACCESS read-write
                STATUS current
                DESCRIPTION " error threshold. DTE:Mandatory, DCE:Mandatory"
                DEFVAL { 3 }
                ::= { frUniConfigEntry 10 }

frUniN393 OBJECT-TYPE
                SYNTAX INTEGER (1..10)
                MAX-ACCESS read-write
                STATUS current
                DESCRIPTION "Monitored event count. DTE:Mandatory,
                                                    DCE:N/A"
                DEFVAL { 4 }
                ::= { frUniConfigEntry 11 }

frUniT391 OBJECT-TYPE
                SYNTAX INTEGER (5..30)
                MAX-ACCESS read-write
                STATUS current
                DESCRIPTION "Link integrity verification timer.
                                        DTE:Mandatory, DCE:N/A"
                DEFVAL { 10 }
                ::= { frUniConfigEntry 12 }

frUniT392 OBJECT-TYPE
                SYNTAX INTEGER (5..30)
                MAX-ACCESS read-write
                STATUS current
                DESCRIPTION "Polling verification timer.
                                        DTE:N/A, DCE:Mandatory"
                DEFVAL { 15 }
                ::= { frUniConfigEntry 13 }

frUniAsyncLmi OBJECT-TYPE
                SYNTAX INTEGER {
                                enabled(1),
                                disabled(2)
                               }
                MAX-ACCESS read-write
                STATUS current
                DESCRIPTION " Async PVC status messages"
                DEFVAL { enabled }
                ::= { frUniConfigEntry 14 }

frLmiOperStatus        OBJECT-TYPE
                SYNTAX INTEGER {
                                outOfService(1),
                                inService(2)
                               }
                MAX-ACCESS read-only
                STATUS current
                DESCRIPTION "The operational status of the lmi protocol:
                             'outOfService'    interface is out of service
                             'inService' interface is in service"
                DEFVAL { outOfService }
                ::= { frUniConfigEntry 15 }

frUniNT3        OBJECT-TYPE
                SYNTAX INTEGER (5..30)
                MAX-ACCESS read-write
                STATUS current
                DESCRIPTION "Message frequency timer relevant for ATT LMI only."
                DEFVAL { 10 }
                ::= { frUniConfigEntry 16 }

frUniThroughPut  OBJECT-TYPE
                SYNTAX INTEGER {
                                k64(1),
                                k56(2)
                                }
                MAX-ACCESS read-write
                STATUS current
                DESCRIPTION "The throughput bandwidth of the interface:
                        'k64' means a throughput of 64 kb
                        'k56' means a throughput of 56 kb"
                DEFVAL { k64 }
                ::= { frUniConfigEntry 17 }


dspConfigTable OBJECT-TYPE
                SYNTAX SEQUENCE OF DspConfigEntry
                MAX-ACCESS not-accessible
                STATUS current
                DESCRIPTION "Table for Dsp Interface"
                ::= { intfConfig 7 }

dspConfigEntry OBJECT-TYPE
                SYNTAX DspConfigEntry
                MAX-ACCESS not-accessible
                STATUS current
                DESCRIPTION "Row definition for Dsp interface"
                INDEX { dspIfIndex } 
                ::= { dspConfigTable 1 }

DspConfigEntry ::= SEQUENCE {
                            dspIfIndex                     IntfIndex,
                            dspAdminStatus           INTEGER,
                            dspOperStatus            INTEGER
                            }

dspIfIndex        OBJECT-TYPE
                SYNTAX IntfIndex
                MAX-ACCESS not-accessible
                STATUS current
                DESCRIPTION "interface index (slot/port/channel) SSPPCCC"
                ::= { dspConfigEntry 1 }

dspAdminStatus OBJECT-TYPE
                SYNTAX INTEGER {
                                outOfService(1),
                                inService(2),
                                delete(3)
                               }
                MAX-ACCESS read-write
                STATUS current
                DESCRIPTION "The administrative action:
                             'outOfService' take the interface out of service
                             'inService'    take the interface in service
                             'delete'       remove/deconfigure the interface."
                DEFVAL { outOfService }
                ::= { dspConfigEntry 2 }

dspOperStatus        OBJECT-TYPE
                SYNTAX INTEGER {
                                outOfService(1),
                                inService(2)
                               }
                MAX-ACCESS read-only
                STATUS current
                DESCRIPTION "The operational status of the interface:
                             'outOfService' interface is out of service
                             'inService'    interface is in service"
                DEFVAL { outOfService }
                ::= { dspConfigEntry 3 }


bridgeConfigTable OBJECT-TYPE
                SYNTAX SEQUENCE OF BridgeConfigEntry
                MAX-ACCESS not-accessible
                STATUS current
                DESCRIPTION "Table which hold Config Entries
                              for all bridges."
                ::= { intfConfig 8 }

bridgeConfigEntry OBJECT-TYPE
                SYNTAX BridgeConfigEntry
                MAX-ACCESS not-accessible
                STATUS current
                DESCRIPTION "Row definition for bridge entries"
                INDEX { bridgeIfIndex } 
                ::= { bridgeConfigTable 1 }

BridgeConfigEntry ::= SEQUENCE {
                            bridgeIfIndex                     Integer32,
                            bridgeAdminStatus           INTEGER,
                            bridgeOperStatus            INTEGER,
                            bridgeNumber                INTEGER,
                            bridgePortPriority                INTEGER,
                            bridgePathCost                INTEGER,
                            bridgeConnectionType        INTEGER
                            }

bridgeIfIndex        OBJECT-TYPE
                SYNTAX Integer32
                MAX-ACCESS not-accessible
                STATUS current
                DESCRIPTION "interface index (slot/port/channel) SSPPCCC"
                ::= { bridgeConfigEntry 1 }

bridgeAdminStatus OBJECT-TYPE
                SYNTAX INTEGER {
                                outOfService(1),
                                inService(2),
                                delete(3)
                               }
                MAX-ACCESS read-write
                STATUS current
                DESCRIPTION "The administrative action:
                             'outOfService' take the interface out of service
                             'inService'    take the interface in service
                             'delete'       remove/deconfigure the interface."
                DEFVAL { outOfService }
                ::= { bridgeConfigEntry 2 }

bridgeOperStatus OBJECT-TYPE
                SYNTAX INTEGER {
                                outOfService(1),
                                inService(2)
                               }
                MAX-ACCESS read-only
                STATUS current
                DESCRIPTION "The operational status of the interface:
                             'outOfService' interface is out of service
                             'inService'    interface is in service"
                DEFVAL { outOfService }
                ::= { bridgeConfigEntry 3 }

bridgeNumber        OBJECT-TYPE
                SYNTAX INTEGER (0..999)
                MAX-ACCESS read-write
                STATUS current
                DESCRIPTION "The number of bridges"
                DEFVAL { 0 }
                ::= { bridgeConfigEntry 4 }

bridgePortPriority OBJECT-TYPE
                SYNTAX INTEGER (0..255)
                MAX-ACCESS read-write
                STATUS current
                DESCRIPTION "The value of the priority field which is
                             contained in the first (in network byte order)
                             octet of the (2 octet long) Port ID.  The other
                             octet of the Port ID is given by the value of
                             dot1dStpPort."
                REFERENCE "IEEE 802.1D-1990: Section 4.5.5.1"
                DEFVAL { 0 }
                ::= { bridgeConfigEntry 5 }

bridgePathCost        OBJECT-TYPE
                SYNTAX INTEGER (0..65535)
                MAX-ACCESS read-write
                STATUS current
                DESCRIPTION "The contribution of this port to the path cost of
                             paths towards the spanning tree root which include
                             this port.  802-1D-1990 recommends that the 
                             default value of this parameter be in inverse
                             proportion to the speed of the attached LAN."
                REFERENCE "IEEE 802.1D-1990: Section 4.5.5.3"
                DEFVAL { 1 }
                ::= { bridgeConfigEntry 6 }

bridgeConnectionType OBJECT-TYPE
                SYNTAX INTEGER {
                                vc(1),
                                llc(2)
                               }
                MAX-ACCESS read-write
                STATUS current
                DESCRIPTION "Connection types"
                DEFVAL { vc }
                ::= { bridgeConfigEntry 7 }


bridgeDomainTable OBJECT-TYPE
                SYNTAX SEQUENCE OF BridgeDomainEntry
                MAX-ACCESS not-accessible
                STATUS current
                DESCRIPTION "A table which holds the bridgeDomainEntry data"
                ::= { intfConfig 9 }

bridgeDomainEntry OBJECT-TYPE
                SYNTAX BridgeDomainEntry
                MAX-ACCESS not-accessible
                STATUS current
                DESCRIPTION "A table entry for a Bridge Domain on 
                             an ethernet card"
                INDEX { bridgeDomainNumber } 
                ::= { bridgeDomainTable 1 }

BridgeDomainEntry ::= SEQUENCE {
                        bridgeDomainNumber                        Integer32,
                        bridgeDomainAdminStatus                        INTEGER,
                        bridgeDomainOperStatus                        INTEGER,
                        bridgeDomainPriority                        INTEGER,
                        bridgeDomainTimeSinceTopologyChange        TimeTicks,
                        bridgeDomainDesignatedRoot                OCTET STRING,
                        bridgeDomainRootCost                        Integer32,
                        bridgeDomainRootPort                        Integer32,
                        bridgeDomainMaxMessageAge                Integer32,
                        bridgeDomainHelloTime                        Integer32,
                        bridgeDomainHoldTime                        Integer32,
                        bridgeDomainForwardDelay                Integer32,
                        bridgeDomainMaxBridgeAge                INTEGER,
                        bridgeDomainBridgeHelloTime                INTEGER,
                        bridgeDomainBridgeForwardDelay                INTEGER,
                        bridgeDomainAgingTime                        INTEGER,
                        bridgeDomainSpanningTree                INTEGER,
                        bridgeDomainTopologyChanges                Integer32,
                        bridgeDomainLearnedEntryDiscards        Integer32,
                        bridgeDomainTimer                        Integer32,
                        bridgeDomainDefaultGateway                IpAddress,
                        bridgeDomainPortStatusBitmap                OCTET STRING
                        }

bridgeDomainNumber OBJECT-TYPE
                SYNTAX Integer32
                MAX-ACCESS not-accessible
                STATUS current
                DESCRIPTION "The bridge number of the bridge which this 
                             interface is a part of.  If the interface is
                             currently not associated with any bridge this 
                             will be set to none."
                ::= { bridgeDomainEntry 1 }

bridgeDomainAdminStatus OBJECT-TYPE
                SYNTAX INTEGER {
                                outOfService(1),
                                inService(2)
                               }
                MAX-ACCESS read-write
                STATUS current
                DESCRIPTION "The administrative action:
                             'outOfService' take the interface out of service
                             'inService'    take the interface in service"
                DEFVAL { outOfService }
                ::= { bridgeDomainEntry 2 }

bridgeDomainOperStatus OBJECT-TYPE
                SYNTAX INTEGER {
                                outOfService(1),
                                inService(2)
                               }
                MAX-ACCESS read-only
                STATUS current
                DESCRIPTION "The operational status of the interface:
                             'outOfService' interface is out of service
                             'inService'    interface is in service"
                DEFVAL { outOfService }
                ::= { bridgeDomainEntry 3 }

bridgeDomainPriority OBJECT-TYPE
                SYNTAX INTEGER (0..65535)
                MAX-ACCESS read-write
                STATUS current
                DESCRIPTION "The value of the writeable portion of the Bridge
                             ID, i.e., the first two octets of the (8 octet
                             long) Bridge ID.  The other (last) 6 octets of the
                             Bridge ID are given by the value of 
                             dot1dBaseBridgeAddress."
                REFERENCE "IEEE 802.1D-1990: Section 4.5.3.7"
                DEFVAL { 0 }
                ::= { bridgeDomainEntry 4 }

bridgeDomainTimeSinceTopologyChange OBJECT-TYPE
                SYNTAX TimeTicks
                MAX-ACCESS read-only
                STATUS current
                DESCRIPTION "The time (in hundredths of a second) since the 
                             last time a topology change was detedted by the
                             bridge entity."
                REFERENCE "IEEE 802.1D-1990: Section 6.8.1.1.3"
                ::= { bridgeDomainEntry 5 }

bridgeDomainDesignatedRoot OBJECT-TYPE
                SYNTAX OCTET STRING (SIZE(6))
                MAX-ACCESS read-only
                STATUS current
                DESCRIPTION "The bridge identifier of the root of the spanning
                             tree as determined by the Spanning Tree Protocol
                             as executed by this node.  This value is used as
                             the Root Identifier parameter in all Configuration
                             Bridge PDUs originated by this node."
                REFERENCE "IEEE 802.1D-1990: Section 4.5.3.1"
                ::= { bridgeDomainEntry 6 }

bridgeDomainRootCost OBJECT-TYPE
                SYNTAX Integer32
                MAX-ACCESS read-only
                STATUS current
                DESCRIPTION "The cost of the path to the root as seen from
                             this bridge."
                REFERENCE "IEEE 802.1D-1990: Section 4.5.3.2"
                ::= { bridgeDomainEntry 7 }

bridgeDomainRootPort OBJECT-TYPE
                SYNTAX Integer32
                MAX-ACCESS read-only
                STATUS current
                DESCRIPTION "The port number of the port which offers the 
                             lowest cost path from this bridge to the root
                             bridge."
                REFERENCE "IEEE 802.1D-1990: Section 4.5.3.3"
                ::= { bridgeDomainEntry 8 }

bridgeDomainMaxMessageAge OBJECT-TYPE
                SYNTAX Integer32
                MAX-ACCESS read-only
                STATUS current
                DESCRIPTION "The maximum age of Spanning Tree Protocol
                             information learned from the network on any port
                             before it is discarded, in units of hundredths of
                             a second.  This is the actual value that this 
                             bridge is currently using."
                REFERENCE "IEEE 802.1D-1990: Section 4.5.3.4"
                ::= { bridgeDomainEntry 9 }

bridgeDomainHelloTime OBJECT-TYPE
                SYNTAX Integer32
                MAX-ACCESS read-only
                STATUS current
                DESCRIPTION "The amount of time between the transmission of
                             Configuration bridge PDUs by this node on any port
                             when it is the root of the spanning tree or trying
                             to become so, in units of hundredths of a second.
                             This is the actual value that this bridge is
                             currently using."
                REFERENCE "IEEE 802.1D-1990: Section 4.5.3.5"
                ::= { bridgeDomainEntry 10 }

bridgeDomainHoldTime OBJECT-TYPE
                SYNTAX Integer32
                MAX-ACCESS read-only
                STATUS current
                DESCRIPTION "This time value determines the interval length
                             during which no more than two Configuration bridge
                             PDUs shall be transmitted by this node, in units
                             of hundredths of a second."
                REFERENCE "IEEE 802.1D-1990: Section 4.5.3.14"
                ::= { bridgeDomainEntry 11 }

bridgeDomainForwardDelay OBJECT-TYPE
                SYNTAX Integer32
                MAX-ACCESS read-only
                STATUS current
                DESCRIPTION "This time value, measured in units of hundredths
                             of a second, controls how fast a port changes its
                             state.  The value determines how long the port
                             stays in each of the Listening and Learning states,
                             which precede the Forwarding state.  This value is
                             also used, when a topology change has been detected
                             and is underway, to age all dynamic entries in the
                             Forwarding Database.  [Note that this value is the
                             one that this bridge is currently using, in 
                             contrast to bridgeDomainBridgeForwardDelay which is
                             the value that this bridge and all others would 
                             start using if/when this bridge were to become
                             the root.]"
                REFERENCE "IEEE 802.1D-1990: Section 4.5.3.6"
                ::= { bridgeDomainEntry 12 }

bridgeDomainMaxBridgeAge OBJECT-TYPE
                SYNTAX INTEGER (6..40)
                MAX-ACCESS read-write
                STATUS current
                DESCRIPTION "The value that all bridges use for MaxAge when
                             this bridge is acting as the root.  Note that
                             802.1D-1990 specifies that the range for this
                             parameter is related to the value of 
                             bridgeDomainBridgeHelloTime.  The granularity of
                             this timer is specified by 802.1D-1990 to be 1
                             second.  An agent may return a badValue error if a
                             set is attempted to a value which is not a whole
                             number of seconds."
                REFERENCE "IEEE 802.1D-1990: Section 4.5.3.8"
                DEFVAL { 20 }
                ::= { bridgeDomainEntry 13 }

bridgeDomainBridgeHelloTime OBJECT-TYPE
                SYNTAX INTEGER (1..10)
                MAX-ACCESS read-write
                STATUS current
                DESCRIPTION "The value that all bridges use for HelloTime when
                             this bridge is acting as the root.  The 
                             granularity of this timer is specified by 802.1D-
                             1990 to be 1 second.  An agent may return a 
                             badValue error if a set is attempted to a value
                             which is not a whole number of seconds."
                REFERENCE "IEEE 802.1D-1990: Section 4.5.3.9"
                DEFVAL { 2 }
                ::= { bridgeDomainEntry 14 }

bridgeDomainBridgeForwardDelay OBJECT-TYPE
                SYNTAX INTEGER (4..30)
                MAX-ACCESS read-write
                STATUS current
                DESCRIPTION "The value that  all bridges user for ForwardDelay
                             when this bridge is acting as the root.  Note that
                             802.1D-1990 specifies that the range for this
                             parameter is related to the value of 
                             bridgeDomainMaxBridgeAge.  The granularity of this
                             timer is specified by 802.1D-1990 to be 1 second.
                             An agent may return a badValue error if a set is
                             attempted to a value which is not a whole number
                             of seconds."
                REFERENCE "IEEE 802.1D-1990: Section 4.5.3.10"
                DEFVAL { 15 }
                ::= { bridgeDomainEntry 15 }

bridgeDomainAgingTime OBJECT-TYPE
                SYNTAX INTEGER (10..1000000)
                MAX-ACCESS read-write
                STATUS current
                DESCRIPTION "The timeout period in seconds for aging out
                             dynamically learned forwarding information.
                             802.1D-1990 recommends a default of 300 seconds."
                REFERENCE "IEEE 802.1D-1990: Section 6.7.1.1.3"
                DEFVAL { 300 }
                ::= { bridgeDomainEntry 16 }

bridgeDomainSpanningTree OBJECT-TYPE
                SYNTAX INTEGER  {
                                enabled(1),
                                disabled(2)
                                }
                MAX-ACCESS read-write
                STATUS current
                DESCRIPTION "Allows the bridge to be configured to run 
                             without the spanning tree algorithm."
                DEFVAL { enabled }
                ::= { bridgeDomainEntry 17 }

bridgeDomainTopologyChanges OBJECT-TYPE
                SYNTAX Integer32
                MAX-ACCESS read-only
                STATUS current
                DESCRIPTION "The total number of topology changes detected by
                             this bridge since the management entity was last
                             reset or initialized."
                REFERENCE "IEEE 802.1D-1990: Section 6.8.1.1.3"
                ::= { bridgeDomainEntry 18 }

bridgeDomainLearnedEntryDiscards OBJECT-TYPE
                SYNTAX Integer32
                MAX-ACCESS read-only
                STATUS current
                DESCRIPTION "The total number of Forwarding Database entries,
                             which have been or would have been learnt, but
                             have been discarded due to a lack of space to
                             store them in the Forwarding Database.  If this
                             counter is increasing, it indicates that the
                             Forwarding Database is regularly becoming full (a
                             condition which has unpleasant performance effects
                             on the subnetwork).  If this counter has a 
                             significant value but is not presently increasing,
                             it indicates that the problem has been occurring
                             but is not persistent."
                REFERENCE "IEEE 802.1D-1990: Section 6.7.1.1.3"
                ::= { bridgeDomainEntry 19 }

bridgeDomainTimer OBJECT-TYPE
                SYNTAX Integer32
                MAX-ACCESS read-only
                STATUS current
                DESCRIPTION "Number of seconds elapsed since 
                             the last reset of bridge group statistics"
                ::= { bridgeDomainEntry 20 }

bridgeDomainDefaultGateway OBJECT-TYPE
                SYNTAX IpAddress
                MAX-ACCESS read-write
                STATUS current
                DESCRIPTION "The default gateway for this bridge domain. 
                             This is now an obsolete entry"
                ::= { bridgeDomainEntry 21 }
 
bridgeDomainPortStatusBitmap OBJECT-TYPE
                SYNTAX OCTET STRING (SIZE(30))
                MAX-ACCESS read-only
                STATUS current
                DESCRIPTION " A bit map describing which ports 
                             in a bridge group are up or down"
                ::= { bridgeDomainEntry 22 }


routerConfigTable OBJECT-TYPE
                SYNTAX SEQUENCE OF RouterConfigEntry
                MAX-ACCESS not-accessible
                STATUS current
                DESCRIPTION " Table which hold Config Entries 
                              for all routers (VPNs)"
                ::= { intfConfig 10 }

routerConfigEntry OBJECT-TYPE
                SYNTAX RouterConfigEntry
                MAX-ACCESS not-accessible
                STATUS current
                DESCRIPTION " config data for a router (VPN) "
                INDEX { routerIfIndex } 
                ::= { routerConfigTable 1 }

RouterConfigEntry ::= SEQUENCE {
                            routerIfIndex                     Integer32,
                            routerAdminStatus           INTEGER,
                            routerOperStatus            INTEGER,
                            routerIpAddress                IpAddress,
                            routerIpNetworkMask         IpAddress,
                            routerNumber                INTEGER,
                            routerEthernetIpAddress        IpAddress
                            }

routerIfIndex        OBJECT-TYPE
                SYNTAX Integer32
                MAX-ACCESS not-accessible
                STATUS current
                DESCRIPTION " A scalar number which identifies an IP 
                              interface within a given router (VPN)"
                ::= { routerConfigEntry 1 }

routerAdminStatus OBJECT-TYPE
                SYNTAX INTEGER {
                                outOfService(1),
                                inService(2),
                                delete(3)
                               }
                MAX-ACCESS read-write
                STATUS current
                DESCRIPTION "The administrative action:
                             'outOfService' take the interface out of service
                             'inService'    take the interface in service
                             'delete'       remove/deconfigure the interface."
                DEFVAL { outOfService }
                ::= { routerConfigEntry 2 }

routerOperStatus OBJECT-TYPE
                SYNTAX INTEGER {
                                outOfService(1),
                                inService(2)
                               }
                MAX-ACCESS read-only
                STATUS current
                DESCRIPTION "The operational status of the interface:
                             'outOfService' interface is out of service
                             'inService'    interface is in service"
                DEFVAL { outOfService }
                ::= { routerConfigEntry 3 }

routerIpAddress OBJECT-TYPE
                SYNTAX IpAddress
                MAX-ACCESS read-write
                STATUS current
                DESCRIPTION "router ATM IP Address."
                ::= { routerConfigEntry 4 }
 
routerIpNetworkMask OBJECT-TYPE
                SYNTAX IpAddress
                MAX-ACCESS read-write
                STATUS current
                DESCRIPTION " An IP network mask for an IP interface 
                              within a given router (VPN)"
                ::= { routerConfigEntry 5 }
 
routerNumber        OBJECT-TYPE
                SYNTAX INTEGER (0..999)
                MAX-ACCESS read-write
                STATUS current
                DESCRIPTION " A scalar number which identifies 
                              a given router (VPN)"
                DEFVAL { 0 }
                ::= { routerConfigEntry 6 }

routerEthernetIpAddress OBJECT-TYPE
                SYNTAX IpAddress
                MAX-ACCESS read-write
                STATUS current
                DESCRIPTION "router Ethernet IP Address."
                ::= { routerConfigEntry 7 }
 


isdnConfig             OBJECT IDENTIFIER ::=   { intfConfig 11 }

isdnIntfConfigTable OBJECT-TYPE
                SYNTAX SEQUENCE OF IsdnIntfConfigEntry
                MAX-ACCESS not-accessible
                STATUS current
                DESCRIPTION "Table of ISDN interface configuration attriburtes"
                ::= { isdnConfig 1 }

isdnIntfConfigEntry OBJECT-TYPE
                SYNTAX IsdnIntfConfigEntry
                MAX-ACCESS not-accessible
                STATUS current
                DESCRIPTION "Row definition for ISDN  interface configuration
                                            table"
                INDEX { isdnIntfId }
                ::= { isdnIntfConfigTable 1 }

IsdnIntfConfigEntry ::= SEQUENCE {
                isdnIntfId                Integer32,
                isdnIntfDChanId                Integer32,
                isdnIntfAdminStatus INTEGER,
                isdnIntfOperStatus INTEGER,
                isdnIntfSwitchType INTEGER
        }

isdnIntfId        OBJECT-TYPE
                SYNTAX Integer32
                MAX-ACCESS not-accessible
                STATUS current
                DESCRIPTION "Interface ID (SSPPCCC)"
                ::= { isdnIntfConfigEntry 1 }

isdnIntfDChanId        OBJECT-TYPE
                SYNTAX Integer32 (0..24)
                MAX-ACCESS read-write
                STATUS current
                DESCRIPTION "D-Channel Number - if the Dchannel no.
                        is 0 no LAPD will run on this PRI-ISDN interface"
                DEFVAL { 0 }
                ::= { isdnIntfConfigEntry 2 }

isdnIntfAdminStatus        OBJECT-TYPE
                SYNTAX INTEGER   {
                        outOfService (1),
                        inService (2),
                        delete (3)

                    }
                MAX-ACCESS read-write
                STATUS current
                DESCRIPTION "ISDN interface admin status"
                ::= { isdnIntfConfigEntry 3 }

isdnIntfOperStatus        OBJECT-TYPE
                SYNTAX INTEGER   {
                        outOfService (1),
                        inService    (2)
                    }
                MAX-ACCESS read-write
                STATUS current
                DESCRIPTION "ISDN interface operational status"
                ::= { isdnIntfConfigEntry 4 }

isdnIntfSwitchType        OBJECT-TYPE
                SYNTAX INTEGER   {
                                    pri-ni2 (1),
                        pri-net5 (2),
                        pri-1tr6 (3),
                        pri-4ess (4),
                        pri-5ess (5),
                        pri-dass2  (6),
                        pri-dms100  (7),
                        pri-kdd  (8),
                        pri-ntt  (9),
                        pri-net5sw  (10),
                        pri-ts014  (11),
                        pri-vn  (12)
                    }
                MAX-ACCESS read-write
                STATUS current
                DESCRIPTION "ISDN interface Switch Type"
                        DEFVAL { pri-ni2 }
                ::= { isdnIntfConfigEntry 5 }

-- LAPD configuration table

isdnL2ConfigTable OBJECT-TYPE
                SYNTAX SEQUENCE OF IsdnL2ConfigEntry
                MAX-ACCESS not-accessible
                STATUS current
                DESCRIPTION "Table of Layer 2 (LAPD) attributes"
                ::= { isdnConfig 2 }

isdnL2ConfigEntry OBJECT-TYPE
                SYNTAX IsdnL2ConfigEntry
                MAX-ACCESS not-accessible
                STATUS current
                DESCRIPTION "Row definition for ISDN LAPD parameters"
                INDEX { isdnL2IntfId }
                ::= { isdnL2ConfigTable 1 }

IsdnL2ConfigEntry ::= SEQUENCE {
                isdnL2IntfId                INTEGER,
                isdnT200                INTEGER,
                isdnT203                INTEGER,
                isdnN200                INTEGER,
                isdnN201                INTEGER,
                isdnK                        INTEGER,
                isdnL2OperStatus        INTEGER,
                isdnL2CurrentState        INTEGER
                }

isdnL2IntfId      OBJECT-TYPE
                SYNTAX Integer32
                MAX-ACCESS not-accessible
                STATUS current
                DESCRIPTION "Interface index (SSPPCCC)"
                ::= { isdnL2ConfigEntry 1 }

isdnT200        OBJECT-TYPE
                SYNTAX INTEGER (1..100)
                MAX-ACCESS read-write
                STATUS current
                DESCRIPTION "value of L2 T200 timer in 1/10 seconds"
                DEFVAL { 10 }
                ::= { isdnL2ConfigEntry 2 }

isdnT203        OBJECT-TYPE
                SYNTAX INTEGER (1..60)
                MAX-ACCESS read-write
                STATUS current
                DESCRIPTION "value of L2 T203 timer in seconds"
                DEFVAL { 10 }
                ::= { isdnL2ConfigEntry 3 }

isdnN200        OBJECT-TYPE
                SYNTAX INTEGER (1..5)
                MAX-ACCESS read-write
                STATUS current
                DESCRIPTION "Maximum number of retransmissions before
                             the LAPD Link is declared as down"
                DEFVAL { 3 }
                ::= { isdnL2ConfigEntry 4 }

isdnN201        OBJECT-TYPE
                SYNTAX INTEGER (1..300)
                MAX-ACCESS read-write
                STATUS current
                DESCRIPTION "Maximum number of octets in an information 
                                field - Maximum value of this parameter
                                will be 300 bytes."
                DEFVAL { 260 }
                ::= { isdnL2ConfigEntry 5 }

isdnK           OBJECT-TYPE
                SYNTAX INTEGER (1..127) 
                MAX-ACCESS read-write
                STATUS current
                DESCRIPTION "Maximum number of outstanding I frames -
                             L2 - window size."
                DEFVAL { 7 }
                ::= { isdnL2ConfigEntry 6 }

isdnL2OperStatus    OBJECT-TYPE
                    SYNTAX INTEGER  {
                           not-initiated (1) ,
                           up (2),
                           down (3)
                }
                MAX-ACCESS read-only
                STATUS current
                DESCRIPTION "ISDN Layer 2 operational status  - 
                             not-initiated means that first SETUP message 
                             has not been transmitted and L2 estalishment 
                             procedure has not been initiated yet"
               ::= { isdnL2ConfigEntry 7}

isdnL2CurrentState    OBJECT-TYPE
                    SYNTAX INTEGER  {
                           tei-unassigned(1),
                           tei-assigned (4),
                           awaiting-establishment (5),
                           awaiting-release (6),
                           multiple-frame-established (7),
                           timer-recovery (8)
                }
                MAX-ACCESS read-only
                STATUS current
                DESCRIPTION "ISDN Layer 2 protocol's current state" 
               ::= { isdnL2ConfigEntry 8}

-- ISDN B Channel Table

isdnBChanConfigTable OBJECT-TYPE
                SYNTAX SEQUENCE OF IsdnBChanConfigEntry
                MAX-ACCESS not-accessible
                STATUS current
                DESCRIPTION "Table of ISDN B Channel configuration attriburtes"
                ::= { isdnConfig 3 }

isdnBChanConfigEntry OBJECT-TYPE
                SYNTAX IsdnBChanConfigEntry
                MAX-ACCESS not-accessible
                STATUS current
                DESCRIPTION "Row definition for ISDN  B Channel configuration
                                            table"
                INDEX { isdnBChanId }
                ::= { isdnBChanConfigTable 1 }

IsdnBChanConfigEntry ::= SEQUENCE {
                isdnBChanId                INTEGER,
                isdnBChanAdminStatus INTEGER,
                isdnBChanOperStatus INTEGER
        }

isdnBChanId        OBJECT-TYPE
                SYNTAX Integer32
                MAX-ACCESS not-accessible
                STATUS current
                DESCRIPTION "B Chan ID (SSPPCCC)"
                ::= { isdnBChanConfigEntry 1 }

isdnBChanAdminStatus        OBJECT-TYPE
                SYNTAX INTEGER   {
                       outOfService (1),
                       inService (2)
                    }
                MAX-ACCESS read-write
                STATUS current
                DESCRIPTION "ISDN B Chan admin status"
                ::= { isdnBChanConfigEntry 2 }

isdnBChanOperStatus        OBJECT-TYPE
                SYNTAX INTEGER   {
                        outOfService (1),
                        inService (2)
                    }
                MAX-ACCESS read-write
                STATUS current
                DESCRIPTION "ISDN B Chan operational status"
                ::= { isdnBChanConfigEntry 3 }




atmDbCirEmConfigTable OBJECT-TYPE
                SYNTAX SEQUENCE OF AtmDbCirEmConfigEntry
                MAX-ACCESS not-accessible
                STATUS current
                DESCRIPTION "Table for ATM DBCES Interface"
                ::= { intfConfig 12 }

atmDbCirEmConfigEntry OBJECT-TYPE
                SYNTAX AtmDbCirEmConfigEntry
                MAX-ACCESS not-accessible
                STATUS current
                DESCRIPTION "Row definition for ATM Dynamic Bandwidth Circuit
                             Emulation interface."
                INDEX { atmDbCirEmIfIndex } 
                ::= { atmDbCirEmConfigTable 1 }

AtmDbCirEmConfigEntry ::= SEQUENCE {
                            atmDbCirEmIfIndex                     IntfIndex,
                            atmDbCirEmAdminStatus           INTEGER,
                            atmDbCirEmOperStatus            INTEGER,
                            atmDbCirEmIdlePattern        Integer32,
                            atmDbCirEmServiceType        INTEGER,
                            atmDbCirEmDbcesType                INTEGER,
                            atmDbCirEmIntegrationTime        INTEGER
                            }

atmDbCirEmIfIndex OBJECT-TYPE
                SYNTAX IntfIndex
                MAX-ACCESS not-accessible
                STATUS current
                DESCRIPTION "Interface index (slot/port/channel) SSPPCCC."
                ::= { atmDbCirEmConfigEntry 1 }

atmDbCirEmAdminStatus OBJECT-TYPE
                SYNTAX INTEGER {
                                outOfService(1),
                                inService(2),
                                delete(3)
                               }
                MAX-ACCESS read-write
                STATUS current
                DESCRIPTION "The administrative action:
                             'outOfService' take the interface out of service
                             'inService'    take the interface in service
                             'delete'       remove/deconfigure the interface."
                DEFVAL { outOfService }
                ::= { atmDbCirEmConfigEntry 2 }

atmDbCirEmOperStatus OBJECT-TYPE
                SYNTAX INTEGER {
                                outOfService(1),
                                inService(2)
                               }
                MAX-ACCESS read-only
                STATUS current
                DESCRIPTION "The operational status of the interface:
                             'outOfService' interface is out of service
                             'inService'    interface is in service"
                DEFVAL { outOfService }
                ::= { atmDbCirEmConfigEntry 3 }



atmDbCirEmIdlePattern OBJECT-TYPE
                SYNTAX Integer32
                MAX-ACCESS read-write
                STATUS current
                DESCRIPTION "Idle pattern for idle data."
                DEFVAL { 127 }
                ::= { atmDbCirEmConfigEntry 7 }

atmDbCirEmServiceType OBJECT-TYPE
                SYNTAX INTEGER  {
                                plar(1),
                                fxo-loopstart(2),
                                fxs-loopstart(3),
                                fxo-groundstart(4),
                                fxs-groundstart(5)
                                }
                MAX-ACCESS read-write
                STATUS current
                DESCRIPTION "Service type to be used.  Affects the ABCD 
                             Signaling."
                DEFVAL { plar }
                ::= { atmDbCirEmConfigEntry 8 }

atmDbCirEmDbcesType OBJECT-TYPE
                SYNTAX INTEGER  {
                                lucent(1)
                                }
                MAX-ACCESS read-write
                STATUS current
                DESCRIPTION "The type of dbces used.
                             yurie:  Yurie proprietary specific."
                DEFVAL { lucent }
                ::= { atmDbCirEmConfigEntry 9 }

atmDbCirEmIntegrationTime OBJECT-TYPE
                SYNTAX INTEGER (1..65535)
                MAX-ACCESS read-write
                STATUS current
                DESCRIPTION "This specifies the time to wait after receiving 
                             idle pattern to change state.  The unit is in 
                             seconds."
                DEFVAL { 1 }
                ::= { atmDbCirEmConfigEntry 10 }


lmiDlciConfigTable OBJECT-TYPE
                SYNTAX SEQUENCE OF LmiDlciConfigEntry
                MAX-ACCESS not-accessible
                STATUS current
                DESCRIPTION "Table for Lmi DLCI Interface."
                ::= { intfConfig 13 }

lmiDlciConfigEntry OBJECT-TYPE
                SYNTAX LmiDlciConfigEntry
                MAX-ACCESS not-accessible
                STATUS current
                DESCRIPTION "Row definition for Lmi DLCI Interface."
                INDEX { lmiDlciIfIndex, lmiDlci } 
                ::= { lmiDlciConfigTable 1 }

LmiDlciConfigEntry ::= SEQUENCE {
                            lmiDlciIfIndex        IntfIndex,
                            lmiDlci                Integer32,
                            lmiDlciOperStatus        INTEGER,
                            lmiDlciStatusTime        Integer32
                            }

lmiDlciIfIndex        OBJECT-TYPE
                SYNTAX IntfIndex
                MAX-ACCESS not-accessible
                STATUS current
                DESCRIPTION "Interface index (slot/port/channel) SSPPCCC."
                ::= { lmiDlciConfigEntry 1 }

lmiDlci                OBJECT-TYPE
                SYNTAX Integer32
                MAX-ACCESS not-accessible
                STATUS current
                DESCRIPTION "dlci."
                ::= { lmiDlciConfigEntry 2 }

lmiDlciOperStatus OBJECT-TYPE
                SYNTAX INTEGER {
                                outOfService(1),
                                inService(2)
                               }
                MAX-ACCESS read-only
                STATUS current
                DESCRIPTION "The operational status of the lmi protocol:
                             'outOfService' protocol is out of service
                             'inService'    protocol is in service"
                DEFVAL { outOfService }
                ::= { lmiDlciConfigEntry 3 }

lmiDlciStatusTime OBJECT-TYPE
                SYNTAX Integer32
                MAX-ACCESS read-only
                STATUS current
                DESCRIPTION "Time since last status transition occurred."
                ::= { lmiDlciConfigEntry 4 }


dsp2ConfigTable OBJECT-TYPE
                SYNTAX SEQUENCE OF Dsp2ConfigEntry
                MAX-ACCESS not-accessible
                STATUS current
                DESCRIPTION "Table for Dsp2 Interface"
                ::= { intfConfig 14 }

dsp2ConfigEntry OBJECT-TYPE
                SYNTAX Dsp2ConfigEntry
                MAX-ACCESS not-accessible
                STATUS current
                DESCRIPTION "Row definition for Dsp2 interface"
                INDEX { dsp2IfIndex } 
                ::= { dsp2ConfigTable 1 }

Dsp2ConfigEntry ::= SEQUENCE {
                            dsp2IfIndex                     IntfIndex,
                            dsp2AdminStatus           INTEGER,
                            dsp2OperStatus            INTEGER,
                            dsp2LoadCount       Integer32,
                            dsp2AalMode         INTEGER
                             }

dsp2IfIndex        OBJECT-TYPE
                SYNTAX IntfIndex
                MAX-ACCESS not-accessible
                STATUS current
                DESCRIPTION "interface index (slot/port/channel) SSPPCCC"
                ::= { dsp2ConfigEntry 1 }

dsp2AdminStatus OBJECT-TYPE
                SYNTAX INTEGER {
                           outOfService(1),
                           inService(2),
                           delete(3)
                               }
                MAX-ACCESS read-write
                STATUS current
                DESCRIPTION "The administrative action:
                            'outOfService' take the interface out of service
                            'inService'    take the interface in service
                            'delete'       remove/deconfigure the interface."
                DEFVAL { outOfService }
                ::= { dsp2ConfigEntry 2 }

dsp2OperStatus        OBJECT-TYPE
                SYNTAX INTEGER {
                           outOfService(1),
                           inService(2)
                               }
                MAX-ACCESS read-only
                STATUS current
                DESCRIPTION "The operational status of the interface:
                'outOfService' interface is out of service
                'inService'    interface is in service"
                DEFVAL { outOfService }
                ::= { dsp2ConfigEntry 3 }

dsp2LoadCount OBJECT-TYPE
                SYNTAX Integer32
                MAX-ACCESS read-only
                STATUS current
                DESCRIPTION "Gives the number of calls going through that dsp.
                This will be of use in case of deletion of
                dsp interface. When no calls are going through
                the dsp this value will be 0"
                ::= { dsp2ConfigEntry 4 }

dsp2AalMode OBJECT-TYPE
                SYNTAX INTEGER {
                        aal2-non-multiplexed(1),
                        aal2-standard(2),
                        aal1(3)
                               }
                MAX-ACCESS read-write
                STATUS current
                DESCRIPTION "aal2-non-multiplexed : Does not support 
                             multiplexing of multiple channels with one trunk
                             aal2-standard: Support Standard Aal2 Multiplexing
                             aal1:Support Aal1 mode.
                            "
                DEFVAL { aal2-non-multiplexed }
                ::= { dsp2ConfigEntry 5 }


atmImaConfigTable OBJECT-TYPE
                SYNTAX SEQUENCE OF AtmImaConfigEntry
                MAX-ACCESS not-accessible
                STATUS current
                DESCRIPTION "Inverse Multiplexing interface table."
                ::= { intfConfig 15 }

atmImaConfigEntry OBJECT-TYPE
                SYNTAX AtmImaConfigEntry
                MAX-ACCESS not-accessible
                STATUS current
                DESCRIPTION "Row definition for Inverse Multiplexing
                              attributes"
                INDEX { atmImaIntfIndex } 
                ::= { atmImaConfigTable 1 }

AtmImaConfigEntry ::= SEQUENCE {
                        atmImaIntfIndex        IntfIndex,
                        atmImaNeTxState        INTEGER,
                        atmImaNeRxState        INTEGER,
                        atmImaFeTxState        INTEGER,
                        atmImaFeRxState        INTEGER,
                        atmImaNeRxDefect       INTEGER,
                        atmImaFeRxDefect       INTEGER,
                        atmImaAdminStatus      INTEGER,
                        atmImaOperStatus       INTEGER
                        }

atmImaIntfIndex OBJECT-TYPE
                SYNTAX Integer32
                MAX-ACCESS not-accessible
                STATUS current
                DESCRIPTION "interface index (slot/port/channel) SSPPCCC"
                ::= { atmImaConfigEntry 1 }

atmImaNeTxState OBJECT-TYPE
                SYNTAX INTEGER {
                        notInGroup(1), 
                        unusableNoReason(2), 
                        unusableFault(3),
                        unusableMisconnected(4),
                        unusableInhibited(5),
                        unusableFailed(6),
                        usable(7), 
                        active(8)
                        }
                MAX-ACCESS read-only
                STATUS current
                DESCRIPTION "The near-end transmit state.
                 notInGroup            -- Interface is not assigned to group
                 unusableNoReason      -- Doesn't work; Don't know why.
                 unusableFailed        -- Check the Defect value 
                 usable                -- Interface is ready to go.
                 active                -- Interface is in use."
                DEFVAL { notInGroup }
                ::= { atmImaConfigEntry 2 }

atmImaNeRxState OBJECT-TYPE
                SYNTAX INTEGER {
                        notInGroup(1), 
                        unusableNoReason(2), 
                        unusableFault(3),
                        unusableMisconnected(4),
                        unusableInhibited(5),
                        unusableFailed(6),
                        usable(7), 
                        active(8)
                       }
                MAX-ACCESS read-only
                STATUS current
                DESCRIPTION "The near-end receive state.
                 notInGroup            -- Interface is not assigned to group
                 unusableNoReason      -- Doesn't work; Don't know why.
                 unusableFailed        -- Check the Defect value 
                 usable                -- Interface is ready to go.
                 active                -- Interface is in use."
                DEFVAL { notInGroup }
                ::= { atmImaConfigEntry 3 }

atmImaFeTxState OBJECT-TYPE
                SYNTAX INTEGER {
                        notInGroup(1), 
                        unusableNoReason(2), 
                        unusableFault(3),
                        unusableMisconnected(4),
                        unusableInhibited(5),
                        unusableFailed(6),
                        usable(7), 
                        active(8)
                        }
                MAX-ACCESS read-only
                STATUS current
                DESCRIPTION "The far-end transmit state.
                 notInGroup            -- Interface is not assigned to group
                 unusableNoReason      -- Doesn't work; Don't know why.
                 unusableFailed        -- Check the Defect value 
                 usable                -- Interface is ready to go.
                 active                -- Interface is in use."
                DEFVAL { notInGroup }
                ::= { atmImaConfigEntry 4 }

atmImaFeRxState OBJECT-TYPE
                SYNTAX INTEGER {
                        notInGroup(1), 
                        unusableNoReason(2), 
                        unusableFault(3),
                        unusableMisconnected(4),
                        unusableInhibited(5),
                        unusableFailed(6),
                        usable(7), 
                        active(8)
                       }
                MAX-ACCESS read-only
                STATUS current
                DESCRIPTION "The far-end receive state.
                 notInGroup            -- Interface is not assigned to group
                 unusableNoReason      -- Doesn't work; Don't know why.
                 unusableFailed        -- Check the Defect value 
                 usable                -- Interface is ready to go.
                 active                -- Interface is in use."
                DEFVAL { notInGroup }
                ::= { atmImaConfigEntry 5 }

atmImaNeRxDefect OBJECT-TYPE
                SYNTAX INTEGER {
                        noDefect(1),
                        linkFailure(2),
                        lif(3),
                        lods(4)
                      }
                MAX-ACCESS read-only
                STATUS current
                DESCRIPTION "The near-end receive defect.
                 noDefect             -- No link defect exists
                 linkFailure          -- Physical failure/ Loss of signal
                 lifDefect            -- Persistence of LIF defect at near-end 
                                         (Loss of IMA Frame)
                 lodsDefect           -- Persistence of LODS defect at near-end
                                         (Link Out of Delay Synchronization)"
                DEFVAL { noDefect }
                ::= { atmImaConfigEntry 6 }

atmImaFeRxDefect OBJECT-TYPE
                SYNTAX INTEGER {
                        noDefect(1),
                        linkFailure(2),
                        lif(3),
                        lods(4)
                        }
                MAX-ACCESS read-only
                STATUS current
                DESCRIPTION "The far-end receive defect.
                 noDefect             -- No link defect exists
                 linkFailure          -- Physical failure/ Loss of signal
                 lifDefect            -- Persistence of LIF defect at near-end 
                                         (Loss of IMA Frame)
                 lodsDefect           -- Persistence of LODS defect at near-end
                                         (Link Out of Delay Synchronization)"
                DEFVAL { noDefect }
                ::= { atmImaConfigEntry 7 }

atmImaAdminStatus OBJECT-TYPE
                SYNTAX INTEGER {
                                outOfService(1),
                                inService(2),
                                delete(3)
                               }
                MAX-ACCESS read-write
                STATUS current
                DESCRIPTION "The administrative action:
                             'outOfService' take the interface out of service
                             'inService'    take the interface in service
                             'delete'       remove/deconfigure the interface."
                DEFVAL { outOfService }
                ::= { atmImaConfigEntry 8 }

atmImaOperStatus OBJECT-TYPE
                SYNTAX INTEGER {
                                outOfService(1),
                                inService(2)
                               }
                MAX-ACCESS read-only
                STATUS current
                DESCRIPTION "The operational status of the interface:
                             'outOfService' interface is out of service
                             'inService'    interface is in service"
                DEFVAL { outOfService }
                ::= { atmImaConfigEntry 9 }

atmPnniConfigTable  OBJECT-TYPE
                    SYNTAX SEQUENCE OF AtmPnniConfigEntry
                    MAX-ACCESS not-accessible
                    STATUS current
                    DESCRIPTION "Table of atm PNNI Configuration"
                    ::= { intfConfig 16 }

atmPnniConfigEntry  OBJECT-TYPE
                    SYNTAX AtmPnniConfigEntry
                    MAX-ACCESS not-accessible
                    STATUS current
                    DESCRIPTION "Row definition of PNNI Configuration"
                    INDEX { atmPnniIfIndex }
                    ::= { atmPnniConfigTable 1 }

AtmPnniConfigEntry      ::= SEQUENCE {
                        atmPnniIfIndex                            IntfIndex,
                        atmPnniSvcMinVpi                       INTEGER,
                        atmPnniSvcMaxVpi                       INTEGER,
                        atmPnniSvcMinVci                       INTEGER,
                        atmPnniSvcMaxVci                       INTEGER,
                        atmPnniAdminStatus                       INTEGER,
                        atmPnniOperStatus                       INTEGER,
                        atmPnniT303                               Integer32,
                        atmPnniT308                               Integer32,
                        atmPnniT309                               Integer32,
                        atmPnniT310                               Integer32,
                        atmPnniT313                               Integer32,
                        atmPnniT316                               Integer32,
                        atmPnniT317                               Integer32,
                        atmPnniT322                               Integer32,
                        atmPnniT397                               Integer32,
                        atmPnniT398                               Integer32,
                        atmPnniT399                               Integer32,
                        atmPnniCbrServCatSupp                       INTEGER,
                             atmPnniCbrGcacClpEqualZero               INTEGER,
                          atmPnniCbrMaxCellRate                        Integer32,
                        atmPnniCbrAvailCellRate                       Integer32,
                        atmPnniCbrCellXerDelay                       Integer32,
                        atmPnniCbrCellLossRatioZero               Integer32,
                        atmPnniCbrCellLossRatioZeroPlusOne     Integer32,
                        atmPnniCbrCellDelayVar                       Integer32,
                        atmPnniRtVbrServCatSupp                       INTEGER,
                        atmPnniRtVbrGcacClpEqualZero               INTEGER,
                        atmPnniRtVbrMaxCellRate                       Integer32,
                        atmPnniRtVbrAvailCellRate               Integer32,
                        atmPnniRtVbrCellXerDelay               Integer32,
                        atmPnniRtVbrCellLossRatioZero               Integer32,
                        atmPnniRtVbrCellLossRatioZeroPlusOne   Integer32,
                        atmPnniRtVbrCellDelayVar               Integer32,
                        atmPnniRtVbrGcacPresent                       INTEGER,
                        atmPnniRtVbrCellRateMargin               Integer32,
                        atmPnniRtVbrVarianceFactor               Integer32,
                        atmPnniNrtVbrServCatSupp               Integer32,
                        atmPnniNrtVbrGcacClpEqualZero               Integer32,
                        atmPnniNrtVbrMaxCellRate               Integer32,
                        atmPnniNrtVbrAvailCellRate               Integer32,
                        atmPnniNrtVbrCellXerDelay               Integer32,
                        atmPnniNrtVbrCellLossRatioZero               Integer32,
                        atmPnniNrtVbrCellLossRatioZeroPlusOne  Integer32,
                        atmPnniNrtVbrGcacPresent               INTEGER,
                        atmPnniNrtVbrCellRateMargin               Integer32,
                        atmPnniNrtVbrVarianceFactor               Integer32,
                        atmPnniAbrServCatSupp                       Integer32,
                        atmPnniAbrMaxCellRate                       Integer32,
                        atmPnniAbrAvailCellRate                       Integer32,
                        atmPnniUbrServCatSupp                       Integer32,
                        atmPnniUbrMaxCellRate                       Integer32,
                        atmPnniOverSubscription                INTEGER,
                        atmPnniSgnlEnabled                     INTEGER,
                        atmPnniVpiSig                               INTEGER,
                        atmPnniVciSig                                      INTEGER,
                        atmPnniAvailBwIgr                         Integer32,
                        atmPnniAvailBwEgr                         Integer32,
                        atmPnniUPCSupp                                INTEGER,
                        atmPnniUbrLoadBalSupp                        INTEGER,
                        atmPnniSscopRxWndSz                       INTEGER,
                        atmPnniRemoteSvcMinVpi                       INTEGER,
                        atmPnniRemoteSvcMaxVpi                       INTEGER,
                        atmPnniRemoteSvcMinVci                 INTEGER,
                        atmPnniRemoteSvcMaxVci                 INTEGER,
                        atmPnniVpiIlmi                               INTEGER,
                        atmPnniVciIlmi                               INTEGER,
                        atmPnniIlmiProtocolStatus              INTEGER,
                        atmPnniIlmiOperStatus                        INTEGER,
                        atmPnniIlmiConfigProc                       INTEGER,
                        atmPnniIlmiConnectProc                 INTEGER,
                        atmPnniIlmiAttachPtProc                INTEGER,
                        atmPnniIlmiSecureLinkProc               INTEGER,
                        atmPnniIlmiAddrRegProc                 INTEGER,
                        atmPnniIlmiTimerS                       Integer32,
                        atmPnniIlmiTimerT                       Integer32,
                        atmPnniIlmiRetryK                       Integer32,
                        atmPnniConnTrafficShapingFlag          INTEGER
                    }                        

atmPnniIfIndex        OBJECT-TYPE
                SYNTAX IntfIndex
                MAX-ACCESS not-accessible
                STATUS current
                DESCRIPTION "interface index (slot/port/channel) SSPPCCC"
                ::= { atmPnniConfigEntry 1 }

atmPnniSvcMinVpi        OBJECT-TYPE
                        SYNTAX INTEGER (0..4095)
                        MAX-ACCESS read-write
                        STATUS current
                        DESCRIPTION "The lower bound of the VPI for SVC connections."
                        DEFVAL { 0 }
                        ::= { atmPnniConfigEntry 2 }

atmPnniSvcMaxVpi        OBJECT-TYPE
                        SYNTAX INTEGER (0..4095)
                        MAX-ACCESS read-write
                        STATUS current
                        DESCRIPTION "The upper bound of the VPI for SVC connections."
                        DEFVAL { 0 }
                        ::= { atmPnniConfigEntry 3 }

atmPnniSvcMinVci        OBJECT-TYPE
                        SYNTAX INTEGER (0..65535)
                        MAX-ACCESS read-write
                        STATUS current
                        DESCRIPTION "The lower bound of the VCI for SVC connections."
                        DEFVAL { 512 }
                        ::= { atmPnniConfigEntry 4 }

atmPnniSvcMaxVci        OBJECT-TYPE
                        SYNTAX INTEGER (0..65535)
                        MAX-ACCESS read-write
                        STATUS current
                        DESCRIPTION "The upper bound of the VCI for SVC connections."
                        DEFVAL { 512 }
                        ::= { atmPnniConfigEntry 5 }

atmPnniAdminStatus        OBJECT-TYPE
                        SYNTAX INTEGER  {
                                outOfService(1),
                                inService(2),
                                delete(3)
                                }
                        MAX-ACCESS read-write
                        STATUS current
                        DESCRIPTION "The administrative action:
                             'outOfService' means take the PNNI out of service
                             'inService'    means take the PNNI in service
                             'delete'       remove/deconfigure the PNNI."
                        DEFVAL { outOfService }
                        ::= { atmPnniConfigEntry 6 }

atmPnniOperStatus        OBJECT-TYPE
                        SYNTAX INTEGER  {
                                outOfService(1),
                                inService(2)
                                }
                        MAX-ACCESS read-only
                        STATUS current
                        DESCRIPTION "The operational status of the PNNI:
                             'outOfService' means the PNNI is out of service
                             'inService'    means the PNNI is in service"
                        DEFVAL { outOfService }
                        ::= { atmPnniConfigEntry 7 }

atmPnniT303        OBJECT-TYPE
                SYNTAX Integer32
                MAX-ACCESS read-write
                STATUS current
                DESCRIPTION "Timer T303 value - seconds"
                DEFVAL { 4 }
                ::= { atmPnniConfigEntry 8 }

atmPnniT308        OBJECT-TYPE
                SYNTAX Integer32
                MAX-ACCESS read-write
                STATUS current
                DESCRIPTION "Timer T308 value - seconds"
                DEFVAL { 30 }
                ::= { atmPnniConfigEntry 9 }

atmPnniT309        OBJECT-TYPE
                SYNTAX Integer32
                MAX-ACCESS read-write
                STATUS current
                DESCRIPTION "Timer T309 value - seconds"
                DEFVAL { 10 }
                ::= { atmPnniConfigEntry 10 }

atmPnniT310        OBJECT-TYPE
                SYNTAX Integer32
                MAX-ACCESS read-write
                STATUS current
                DESCRIPTION "Timer T310 value - seconds"
                DEFVAL { 10 }
                ::= { atmPnniConfigEntry 11 }

atmPnniT313        OBJECT-TYPE
                SYNTAX Integer32
                MAX-ACCESS read-write
                STATUS current
                DESCRIPTION "Timer T313 value - User side only - seconds"
                DEFVAL { 4 }
                ::= { atmPnniConfigEntry 12 }

atmPnniT316        OBJECT-TYPE
                SYNTAX Integer32
                MAX-ACCESS read-write
                STATUS current
                DESCRIPTION "Timer T316 value - seconds"
                DEFVAL { 120 }
                ::= { atmPnniConfigEntry 13 }

atmPnniT317        OBJECT-TYPE
                SYNTAX Integer32
                MAX-ACCESS read-write
                STATUS current
                DESCRIPTION "Timer T317 value - seconds"
                DEFVAL { 60 }
                ::= { atmPnniConfigEntry 14 }

atmPnniT322        OBJECT-TYPE
                SYNTAX Integer32
                MAX-ACCESS read-write
                STATUS current
                DESCRIPTION "Timer T322 value - seconds"
                DEFVAL { 4 }
                ::= { atmPnniConfigEntry 15}

atmPnniT397        OBJECT-TYPE
                SYNTAX Integer32
                MAX-ACCESS read-write
                STATUS current
                DESCRIPTION "Timer T397 value - seconds"
                DEFVAL { 4 }
                ::= { atmPnniConfigEntry 16 }

atmPnniT398        OBJECT-TYPE
                SYNTAX Integer32
                MAX-ACCESS read-write
                STATUS current
                DESCRIPTION "Timer T398 value - seconds"
                DEFVAL { 4 }
                ::= { atmPnniConfigEntry 17 }

atmPnniT399        OBJECT-TYPE
                SYNTAX Integer32
                MAX-ACCESS read-write
                STATUS current
                DESCRIPTION "Timer T399 value - seconds"
                DEFVAL { 14 }
                ::= { atmPnniConfigEntry 18 }

atmPnniCbrServCatSupp        OBJECT-TYPE
                        SYNTAX INTEGER  {
                                enabled(1),
                                disabled(2)
                        }
                        MAX-ACCESS read-write
                        STATUS current
                        DESCRIPTION "If CBR category is supported"
                        DEFVAL { enabled }
                        ::= { atmPnniConfigEntry 19 }

atmPnniCbrGcacClpEqualZero        OBJECT-TYPE
                                SYNTAX INTEGER  {
                                        enabled(1),
                                        disabled(2)
                                }
                                MAX-ACCESS read-write
                                STATUS current
                                DESCRIPTION "If the advertised GCAC parameters apply for CLP=0 or CLP=0+1 traffic"
                                DEFVAL { disabled }
                                ::= { atmPnniConfigEntry 20 }

atmPnniCbrMaxCellRate        OBJECT-TYPE
                        SYNTAX  Integer32
                        MAX-ACCESS read-write
                        STATUS current
                        DESCRIPTION "CBR category Maximum Cell Rate"
                        DEFVAL { 0 }
                        ::= { atmPnniConfigEntry 21 }

atmPnniCbrAvailCellRate        OBJECT-TYPE
                        SYNTAX Integer32
                        MAX-ACCESS read-write
                        STATUS current
                        DESCRIPTION "CBR category Available Cell Rate"
                        DEFVAL { 0 }
                        ::= { atmPnniConfigEntry 22 }

atmPnniCbrCellXerDelay        OBJECT-TYPE
                        SYNTAX Integer32
                        MAX-ACCESS read-write
                        STATUS current
                        DESCRIPTION "CBR category Cell Transfer Delay"
                        DEFVAL { 0 }
                        ::= { atmPnniConfigEntry 23 }

atmPnniCbrCellLossRatioZero        OBJECT-TYPE
                                SYNTAX Integer32
                                MAX-ACCESS read-write
                                STATUS current
                                DESCRIPTION "CBR category Cell Loss Ratio for CLP=0 traffic"
                                DEFVAL { 0 }
                                ::= { atmPnniConfigEntry 24 }

atmPnniCbrCellLossRatioZeroPlusOne        OBJECT-TYPE
                                SYNTAX Integer32
                                MAX-ACCESS read-write
                                STATUS current
                                DESCRIPTION "CBR category Cell Loss Ratio for CLP=0+1 traffic"
                                DEFVAL { 0 }
                                ::= { atmPnniConfigEntry 25 }

atmPnniCbrCellDelayVar        OBJECT-TYPE
                        SYNTAX Integer32
                        MAX-ACCESS read-write
                        STATUS current
                        DESCRIPTION "CBR category Cell Delay Variation"
                        DEFVAL { 0 }
                        ::= { atmPnniConfigEntry 26 }

atmPnniRtVbrServCatSupp        OBJECT-TYPE
                        SYNTAX INTEGER  {
                                enabled(1),
                                disabled(2)
                        }
                        MAX-ACCESS read-write
                        STATUS current
                        DESCRIPTION "If RT VBR category is supported"
                        DEFVAL { enabled }
                        ::= { atmPnniConfigEntry 27 }

atmPnniRtVbrGcacClpEqualZero        OBJECT-TYPE
                                SYNTAX INTEGER  {
                                        enabled(1),
                                        disabled(2)
                                }
                                MAX-ACCESS read-write
                                STATUS current
                                DESCRIPTION "If the advertised GCAC parameters apply for CLP=0 or CLP=0+1 traffic"
                                DEFVAL { disabled }
                                ::= { atmPnniConfigEntry 28 }

atmPnniRtVbrMaxCellRate        OBJECT-TYPE
                        SYNTAX  Integer32
                        MAX-ACCESS read-write
                        STATUS current
                        DESCRIPTION "RT VBR category Maximum Cell Rate"
                        DEFVAL { 0 }
                        ::= { atmPnniConfigEntry 29 }

atmPnniRtVbrAvailCellRate        OBJECT-TYPE
                                SYNTAX Integer32
                                MAX-ACCESS read-write
                                STATUS current
                                DESCRIPTION "RT VBR category Available Cell Rate"
                                DEFVAL { 0 }
                                ::= { atmPnniConfigEntry 30 }

atmPnniRtVbrCellXerDelay        OBJECT-TYPE
                                SYNTAX Integer32
                                MAX-ACCESS read-write
                                STATUS current
                                DESCRIPTION "RT VBR category Cell Transfer Delay"
                                DEFVAL { 0 }
                                ::= { atmPnniConfigEntry 31 }

atmPnniRtVbrCellLossRatioZero        OBJECT-TYPE
                                SYNTAX Integer32
                                MAX-ACCESS read-write
                                STATUS current
                                DESCRIPTION "RT VBR category Cell Loss Ratio for CLP=0 traffic"
                                DEFVAL { 0 }
                                ::= { atmPnniConfigEntry 32 }

atmPnniRtVbrCellLossRatioZeroPlusOne        OBJECT-TYPE
                                        SYNTAX Integer32
                                        MAX-ACCESS read-write
                                        STATUS current
                                        DESCRIPTION "RT VBR category Cell Loss Ratio for CLP=0+1 traffic"
                                        DEFVAL { 0 }
                                        ::= { atmPnniConfigEntry 33 }

atmPnniRtVbrCellDelayVar        OBJECT-TYPE
                                SYNTAX Integer32
                                MAX-ACCESS read-write
                                STATUS current
                                DESCRIPTION "RT VBR category Cell Delay Variation"
                                DEFVAL { 0 }
                                ::= { atmPnniConfigEntry 34 }

atmPnniRtVbrGcacPresent        OBJECT-TYPE
                        SYNTAX INTEGER  {
                                enabled(1),
                                disabled(2)
                        }
                        MAX-ACCESS read-write
                        STATUS current
                        DESCRIPTION "If RT VBR category GCAC Parameters present"
                        DEFVAL { disabled }
                        ::= { atmPnniConfigEntry 35 }

atmPnniRtVbrCellRateMargin        OBJECT-TYPE
                                SYNTAX INTEGER (0..255)
                                MAX-ACCESS read-write
                                STATUS current
                                DESCRIPTION "RT VBR category Cell Rate Margin"
                                DEFVAL { 0 }
                                ::= { atmPnniConfigEntry 36 }

atmPnniRtVbrVarianceFactor        OBJECT-TYPE
                                SYNTAX INTEGER (0..255)
                                MAX-ACCESS read-write
                                STATUS current
                                DESCRIPTION "RT VBR category Variance Factor"
                                DEFVAL { 0 }
                                ::= { atmPnniConfigEntry 37 }

atmPnniNrtVbrServCatSupp        OBJECT-TYPE
                                SYNTAX INTEGER  {
                                        enabled(1),
                                        disabled(2)
                                }
                                MAX-ACCESS read-write
                                STATUS current
                                DESCRIPTION "If NRT VBR category is supported"
                                DEFVAL { enabled }
                                ::= { atmPnniConfigEntry 38 }

atmPnniNrtVbrGcacClpEqualZero        OBJECT-TYPE
                                SYNTAX INTEGER  {
                                        enabled(1),
                                        disabled(2)
                                }
                                MAX-ACCESS read-write
                                STATUS current
                                DESCRIPTION "If the advertised GCAC parameters apply for CLP=0 or CLP=0+1 traffic"
                                DEFVAL { disabled }
                                ::= { atmPnniConfigEntry 39 }

atmPnniNrtVbrMaxCellRate        OBJECT-TYPE
                                SYNTAX  Integer32
                                MAX-ACCESS read-write
                                STATUS current
                                DESCRIPTION "NRT VBR category Maximum Cell Rate"
                                DEFVAL { 0 }
                                ::= { atmPnniConfigEntry 40 }

atmPnniNrtVbrAvailCellRate        OBJECT-TYPE
                                SYNTAX Integer32
                                MAX-ACCESS read-write
                                STATUS current
                                DESCRIPTION "NRT VBR category Available Cell Rate"
                                DEFVAL { 0 }
                                ::= { atmPnniConfigEntry 41 }

atmPnniNrtVbrCellXerDelay        OBJECT-TYPE
                                SYNTAX Integer32
                                MAX-ACCESS read-write
                                STATUS current
                                DESCRIPTION "NRT VBR category Cell Transfer Delay"
                                DEFVAL { 0 }
                                ::= { atmPnniConfigEntry 42 }

atmPnniNrtVbrCellLossRatioZero        OBJECT-TYPE
                                SYNTAX Integer32
                                MAX-ACCESS read-write
                                STATUS current
                                DESCRIPTION "NRT VBR category Cell Loss Ratio for CLP=0 traffic"
                                DEFVAL { 0 }
                                ::= { atmPnniConfigEntry 43 }

atmPnniNrtVbrCellLossRatioZeroPlusOne        OBJECT-TYPE
                                        SYNTAX Integer32
                                        MAX-ACCESS read-write
                                        STATUS current
                                        DESCRIPTION "NRT VBR category Cell Loss Ratio for CLP=0+1 traffic"
                                        DEFVAL { 0 }
                                        ::= { atmPnniConfigEntry 44 }

atmPnniNrtVbrGcacPresent        OBJECT-TYPE
                                SYNTAX INTEGER  {
                                        enabled(1),
                                        disabled(2)
                                }
                                MAX-ACCESS read-write
                                STATUS current
                                DESCRIPTION "If NRT VBR category GCAC Parameters present"
                                DEFVAL { disabled }
                                ::= { atmPnniConfigEntry 45 }

atmPnniNrtVbrCellRateMargin        OBJECT-TYPE
                                SYNTAX INTEGER (0..255)
                                MAX-ACCESS read-write
                                STATUS current
                                DESCRIPTION "NRT VBR category Cell Rate Margin"
                                DEFVAL { 0 }
                                ::= { atmPnniConfigEntry 46 }

atmPnniNrtVbrVarianceFactor        OBJECT-TYPE
                                SYNTAX INTEGER (0..255)
                                MAX-ACCESS read-write
                                STATUS current
                                DESCRIPTION "NRT VBR category Variance Factor"
                                DEFVAL { 0 }
                                ::= { atmPnniConfigEntry 47 }

atmPnniAbrServCatSupp        OBJECT-TYPE
                        SYNTAX INTEGER  {
                                enabled(1),
                                disabled(2)
                        }
                        MAX-ACCESS read-write
                        STATUS current
                        DESCRIPTION "If ABR category is supported"
                        DEFVAL { disabled }
                        ::= { atmPnniConfigEntry 48 }


atmPnniAbrMaxCellRate        OBJECT-TYPE
                        SYNTAX  Integer32
                        MAX-ACCESS read-write
                        STATUS current
                        DESCRIPTION "ABR category Maximum Cell Rate"
                        DEFVAL { 0 }
                        ::= { atmPnniConfigEntry 49 }

atmPnniAbrAvailCellRate        OBJECT-TYPE
                        SYNTAX Integer32
                        MAX-ACCESS read-write
                        STATUS current
                        DESCRIPTION "ABR category Available Cell Rate"
                        DEFVAL { 0 }
                        ::= { atmPnniConfigEntry 50 }

atmPnniUbrServCatSupp        OBJECT-TYPE
                        SYNTAX INTEGER  {
                                enabled(1),
                                disabled(2)
                        }
                        MAX-ACCESS read-write
                        STATUS current
                        DESCRIPTION "UBR category Cell Transfer Delay"
                        DEFVAL { enabled }
                        ::= { atmPnniConfigEntry 51 }

atmPnniUbrMaxCellRate        OBJECT-TYPE
                        SYNTAX Integer32
                        MAX-ACCESS read-write
                        STATUS current
                        DESCRIPTION "NRT VBR category Cell Loss Ratio for CLP=0 traffic"
                        DEFVAL { 0 }
                        ::= { atmPnniConfigEntry 52 }

atmPnniOverSubscription OBJECT-TYPE
                        SYNTAX INTEGER (1..100)
                        MAX-ACCESS read-write
                        STATUS current
                        DESCRIPTION "Over subscription factor for PNNI Intf."
                        DEFVAL { 10 }
                        ::= { atmPnniConfigEntry 53 }

atmPnniSgnlEnabled OBJECT-TYPE
                SYNTAX INTEGER  {
                                enabled(1),
                                disabled(2)
                                }
                MAX-ACCESS read-write
                STATUS current
                DESCRIPTION "Indicates if atm signaling is enabled or disabled
                             for this PNNI interface."
                DEFVAL { enabled }
                ::= { atmPnniConfigEntry 54 }

atmPnniVpiSig        OBJECT-TYPE
                SYNTAX INTEGER (0..4095)
                MAX-ACCESS read-write
                STATUS current
                DESCRIPTION "VPI value for the signalling channel for the PNNI
                             interface."
                DEFVAL { 0 }
                ::= { atmPnniConfigEntry 55 }

atmPnniVciSig        OBJECT-TYPE
                SYNTAX INTEGER (0..31)
                MAX-ACCESS read-write
                STATUS current
                DESCRIPTION "VCI value for the signalling channel for the PNNI
                             interface."
                DEFVAL { 5 }
                ::= { atmPnniConfigEntry 56 }

atmPnniAvailBwIgr OBJECT-TYPE
                  SYNTAX Integer32
                MAX-ACCESS read-only
                STATUS current
                DESCRIPTION "The Avail Bandwidth for that interface in
                        cells per sec. Bandwidth for UBR conns
                        will not be accounted for."
                 DEFVAL { 0 }
                 ::= { atmPnniConfigEntry 57 }

atmPnniAvailBwEgr OBJECT-TYPE
                  SYNTAX Integer32
                MAX-ACCESS read-only
                STATUS current
                DESCRIPTION "The Avail Bandwidth for that interface in
                        cells per sec. Bandwidth for UBR conns
                        will not be accounted for."
                 DEFVAL { 0 }
                 ::= { atmPnniConfigEntry 58 }

atmPnniUPCSupp OBJECT-TYPE
                SYNTAX INTEGER  {
                                disabled(1),
                                enabled(2)
                                }
                MAX-ACCESS read-write
                STATUS current
                DESCRIPTION "upc supp off/on"
                DEFVAL { disabled }
                ::= { atmPnniConfigEntry 59 }

atmPnniUbrLoadBalSupp OBJECT-TYPE
                SYNTAX INTEGER  {
                                disabled(1),
                                enabled(2)
                                }
                MAX-ACCESS read-write
                STATUS current
                DESCRIPTION "load balancing supp for ubr conns off/on"
                DEFVAL { disabled }
                ::= { atmPnniConfigEntry 60 }

atmPnniSscopRxWndSz OBJECT-TYPE
                SYNTAX INTEGER (8..256)
                MAX-ACCESS read-write
                STATUS current
                DESCRIPTION "The receive window size for the SSCOP layer"
                DEFVAL { 32 }
                ::= { atmPnniConfigEntry 61 }

atmPnniRemoteSvcMinVpi OBJECT-TYPE
                   SYNTAX INTEGER (0..4095)
                MAX-ACCESS read-only
                STATUS current
                DESCRIPTION "The lower bound of the actual VPI 
                        for SVC connections."
                DEFVAL { 0 }
                ::= { atmPnniConfigEntry 62 }   

atmPnniRemoteSvcMaxVpi OBJECT-TYPE
                   SYNTAX INTEGER (0..4095)
                MAX-ACCESS read-only
                STATUS current
                DESCRIPTION "The Upper bound of the actual VPI 
                        for SVC connections."
                DEFVAL { 0 } 
                ::= { atmPnniConfigEntry 63 }

atmPnniRemoteSvcMinVci OBJECT-TYPE
                SYNTAX INTEGER (32..65535)
                MAX-ACCESS read-only
                STATUS current
                DESCRIPTION "The lower bound of the actual VCI for 
                        SVC connections."
                DEFVAL { 32 }
                   ::= { atmPnniConfigEntry 64}

atmPnniRemoteSvcMaxVci OBJECT-TYPE
                SYNTAX INTEGER (32..65535)
                MAX-ACCESS read-only
                STATUS current
                DESCRIPTION "The Upper bound of the actual VCI for 
                        SVC connections."
                DEFVAL { 65535 }
                   ::= { atmPnniConfigEntry 65 }

atmPnniVpiIlmi OBJECT-TYPE
                   SYNTAX INTEGER (0..255)
                MAX-ACCESS read-write
                STATUS current
                DESCRIPTION "VPI value for the ilmi channel for 
                        the PNNI interface."
                DEFVAL {  0 }
                ::= { atmPnniConfigEntry 66 }

atmPnniVciIlmi  OBJECT-TYPE
                SYNTAX INTEGER (0..31)
                MAX-ACCESS read-write
                STATUS current
                DESCRIPTION "VCI value for the ilmi channel for 
                        the PNNI interface."
                DEFVAL { 16 }
                   ::= { atmPnniConfigEntry 67}

atmPnniIlmiProtocolStatus OBJECT-TYPE
                   SYNTAX INTEGER {
                                enabled(1),
                                disabled(2)
                                }   
                MAX-ACCESS read-write
                STATUS current
                DESCRIPTION "The administrative status:
                        'enabled'  - ILMI protocol enabled on PNNI
                        'disabled' - ILMI protocol disabled on PNNI ."
                DEFVAL { disabled }
                ::= { atmPnniConfigEntry 68 }

atmPnniIlmiOperStatus OBJECT-TYPE
                SYNTAX INTEGER {
                                outOfService(1),
                                inService(2)
                                }
                MAX-ACCESS read-only
                STATUS current
                DESCRIPTION "The operational status:
                        'outOfService' - ILMI connectivity is down
                        'inService'    - ILMI connectivity is up."
                DEFVAL { outOfService }
                ::= { atmPnniConfigEntry 69 }

atmPnniIlmiConfigProc OBJECT-TYPE
                   SYNTAX INTEGER {
                                enabled(1),
                                disabled(2)
                                }
                MAX-ACCESS read-write
                STATUS current
                DESCRIPTION "ILMI Configuration Procedure status."
                DEFVAL { disabled }
                ::= { atmPnniConfigEntry 70 }

atmPnniIlmiConnectProc OBJECT-TYPE 
                SYNTAX INTEGER {
                                enabled(1),
                                disabled(2)
                                }
                MAX-ACCESS read-write
                STATUS current
                DESCRIPTION "ILMI Connectivity Procedure  status."
                DEFVAL { disabled }
                ::= { atmPnniConfigEntry 71 }

atmPnniIlmiAttachPtProc OBJECT-TYPE
                SYNTAX INTEGER {
                                enabled(1),
                                disabled(2)
                                }
                MAX-ACCESS read-write   
                STATUS current
                DESCRIPTION "ILMI Attachment Point Procedure  status."
                DEFVAL { disabled }
                ::= { atmPnniConfigEntry 72 }

atmPnniIlmiSecureLinkProc OBJECT-TYPE
                SYNTAX INTEGER {
                                enabled(1),
                                disabled(2)
                                }
                MAX-ACCESS read-write
                STATUS current
                DESCRIPTION "ILMI Secure Link Procedure  status. 
                        Can be enabled only if Attachment Point
                        Procedure is enabled."
                DEFVAL { disabled }
                ::= { atmPnniConfigEntry 73 }

atmPnniIlmiAddrRegProc OBJECT-TYPE
                SYNTAX INTEGER {
                                enabled(1),
                                disabled(2)
                                }
                   MAX-ACCESS read-write
                STATUS current
                DESCRIPTION "ILMI Address Registration Procedure  status."
                DEFVAL { disabled }
                ::= { atmPnniConfigEntry 74 }

atmPnniIlmiTimerS OBJECT-TYPE
                   SYNTAX Integer32
                MAX-ACCESS read-write
                STATUS current
                DESCRIPTION "Timer S (secs). Used to poll peer when 
                        link is down."
                DEFVAL {  1 } 
                ::= { atmPnniConfigEntry 75 }

atmPnniIlmiTimerT OBJECT-TYPE
                SYNTAX Integer32
                MAX-ACCESS read-write
                STATUS current
                DESCRIPTION "Timer T (secs). Used to poll peer when 
                                link is up."
                DEFVAL {  5 }
                ::= { atmPnniConfigEntry 76 }

atmPnniIlmiRetryK OBJECT-TYPE
                   SYNTAX Integer32
                MAX-ACCESS read-write
                STATUS current
                DESCRIPTION "Retry K - number of timeouts of before 
                        link is declared down." 
                DEFVAL {  4 }
                ::= { atmPnniConfigEntry 77}

atmPnniConnTrafficShapingFlag OBJECT-TYPE
                SYNTAX INTEGER  {
                                 disabled(1),
                                 enabled(2)
                                }
                MAX-ACCESS read-write
                STATUS current
                DESCRIPTION "Traffic Shaping for Conn was enabled
                             primarily because the core would lose
                             cells since we were non-conformant cells.
                             Therefore the hardware added traffic
                             shaping per connection. But condition is
                             VI should not be enabled if this feature
                             is enabled."
                DEFVAL { disabled }
                ::= { atmPnniConfigEntry 78 }


-- End of 1  MIB Table Entries



-- The 1  Interface Configuration Group

atmVnnConfigTable OBJECT-TYPE
        SYNTAX SEQUENCE OF AtmVnnConfigEntry
        MAX-ACCESS not-accessible
        STATUS current
        DESCRIPTION "Table of atm user to network interface (UNI)"
        ::= { intfConfig 17 }

atmVnnConfigEntry OBJECT-TYPE
        SYNTAX AtmVnnConfigEntry
        MAX-ACCESS not-accessible
        STATUS current
        DESCRIPTION "Row definition of atm UNI"
        INDEX { atmVnnIfIndex } 
        ::= { atmVnnConfigTable 1 }

AtmVnnConfigEntry ::= SEQUENCE {
        atmVnnIfIndex               IntfIndex,
        atmVnnAddrType              INTEGER,
        atmVnnSvcMinVpi             INTEGER,
        atmVnnSvcMaxVpi             INTEGER,
        atmVnnSvcMinVci             INTEGER,
        atmVnnSvcMaxVci             INTEGER,
        atmVnnAdminStatus           INTEGER,
        atmVnnOperStatus            INTEGER,
        atmVnnOverSubscription      INTEGER,
        atmVnnNwPrefix1             OCTET STRING,
        atmVnnT303                  Integer32,
        atmVnnT308                  Integer32,
        atmVnnT309                  Integer32,
        atmVnnT310                  Integer32,
        atmVnnT313                  Integer32,
        atmVnnT316                  Integer32,
        atmVnnT317                  Integer32,
        atmVnnT322                  Integer32,
        atmVnnT398                  Integer32,
        atmVnnT399                  Integer32,
        atmVnnMyNeighborIpAddress   IpAddress,
        atmVnnMyNeighborIfName      DisplayString,
        atmVnnVpiSig                INTEGER,
        atmVnnVciSig                INTEGER,
        atmVnnVpiIlmi               INTEGER,
        atmVnnVciIlmi               INTEGER,
        atmVnnAtmSignalingStatus    INTEGER,
        atmVnnMyIfName              DisplayString,
        atmVnnIlmiProtocolStatus    INTEGER,
        atmVnnIlmiOperStatus        INTEGER,
        atmVnnIlmiConfigProc        INTEGER,
        atmVnnIlmiConnectProc       INTEGER,
        atmVnnIlmiAttachPtProc      INTEGER,
        atmVnnIlmiSecureLinkProc    INTEGER,
        atmVnnIlmiAddrRegProc       INTEGER,
        atmVnnIlmiTimerS            Integer32,
        atmVnnIlmiTimerT            Integer32,
        atmVnnIlmiRetryK            Integer32,
        atmVnnAvailBwIgr            Integer32,
        atmVnnAvailBwEgr            Integer32,
        atmVnnUPCSupp                     INTEGER,
        atmVnnUbrLoadBalSupp        INTEGER,
        atmVnnSscopRxWndSz          INTEGER
        }

atmVnnIfIndex OBJECT-TYPE
        SYNTAX IntfIndex
        MAX-ACCESS not-accessible
        STATUS current
        DESCRIPTION "interface index (slot/port/channel) SSPPCCC"
        ::= { atmVnnConfigEntry 1 }

atmVnnAddrType OBJECT-TYPE
        SYNTAX INTEGER  {
                nsap(1),
                e164(2),
                private(3)
                }
        MAX-ACCESS read-write
        STATUS current
        DESCRIPTION "atm address type"
        DEFVAL { nsap }
        ::= { atmVnnConfigEntry 2 }

atmVnnSvcMinVpi OBJECT-TYPE
        SYNTAX INTEGER (0..255)
        MAX-ACCESS read-write
        STATUS current
        DESCRIPTION "The lower bound of the VPI for SVC connections."
        DEFVAL { 0 }
        ::= { atmVnnConfigEntry 3 }

atmVnnSvcMaxVpi OBJECT-TYPE
        SYNTAX INTEGER (0..255)
        MAX-ACCESS read-write
        STATUS current
        DESCRIPTION "The upper bound of the VPI for SVC connections."
        DEFVAL { 0 }
        ::= { atmVnnConfigEntry 4 }

atmVnnSvcMinVci OBJECT-TYPE
        SYNTAX INTEGER (0..65535)
        MAX-ACCESS read-write
        STATUS current
        DESCRIPTION "The lower bound of the VCI for SVC connections."
        DEFVAL { 32 }
        ::= { atmVnnConfigEntry 5 }

atmVnnSvcMaxVci OBJECT-TYPE
        SYNTAX INTEGER (0..65535)
        MAX-ACCESS read-write
        STATUS current
        DESCRIPTION "The upper bound of the VCI for SVC connections."
        DEFVAL { 255 }
        ::= { atmVnnConfigEntry 6 }

atmVnnAdminStatus OBJECT-TYPE
        SYNTAX INTEGER  {
                outOfService(1),
                inService(2),
                delete(3)
                }
        MAX-ACCESS read-write
        STATUS current
        DESCRIPTION "The administrative action:
                 'outOfService' means take the UNI out of service
                 'inService'    means take the UNI in service
                 'delete'       remove/deconfigure the UNI."
        DEFVAL { outOfService }
        ::= { atmVnnConfigEntry 7 }

atmVnnOperStatus OBJECT-TYPE
        SYNTAX INTEGER  {
                outOfService(1),
                inService(2)
                }
        MAX-ACCESS read-only
        STATUS current
        DESCRIPTION "The operational status of the UNI:
                 'outOfService' means the UNI is out of service
                 'inService'    means the UNI is in service"
        DEFVAL { outOfService }
        ::= { atmVnnConfigEntry 8 }

atmVnnOverSubscription OBJECT-TYPE
        SYNTAX INTEGER (1..100)
        MAX-ACCESS read-write
        STATUS current
        DESCRIPTION "Over subscription factor"
        DEFVAL { 10 }
        ::= { atmVnnConfigEntry 9 }

atmVnnNwPrefix1 OBJECT-TYPE
        SYNTAX OCTET STRING (SIZE(13))
        MAX-ACCESS read-only
        STATUS current
        DESCRIPTION "ATM Network Prefix 1"
        ::= { atmVnnConfigEntry 10 }

atmVnnT303 OBJECT-TYPE
        SYNTAX Integer32
        MAX-ACCESS read-write
        STATUS current
        DESCRIPTION "Timer T303 value - seconds"
        DEFVAL { 4 }
        ::= { atmVnnConfigEntry 11 }

atmVnnT308 OBJECT-TYPE
        SYNTAX Integer32
        MAX-ACCESS read-write
        STATUS current
        DESCRIPTION "Timer T308 value - seconds"
        DEFVAL { 30 }
        ::= { atmVnnConfigEntry 12 }

atmVnnT309 OBJECT-TYPE
        SYNTAX Integer32
        MAX-ACCESS read-write
        STATUS current
        DESCRIPTION "Timer T309 value - seconds"
        DEFVAL { 10 }
        ::= { atmVnnConfigEntry 13 }

atmVnnT310 OBJECT-TYPE
        SYNTAX Integer32
        MAX-ACCESS read-write
        STATUS current
        DESCRIPTION "Timer T310 value - seconds"
        DEFVAL { 10 }
        ::= { atmVnnConfigEntry 14 }

atmVnnT313 OBJECT-TYPE
        SYNTAX Integer32
        MAX-ACCESS read-write
        STATUS current
        DESCRIPTION "Timer T313 value - User side only - seconds"
        DEFVAL { 4 }
        ::= { atmVnnConfigEntry 15 }

atmVnnT316 OBJECT-TYPE
        SYNTAX Integer32
        MAX-ACCESS read-write
        STATUS current
        DESCRIPTION "Timer T316 value - seconds"
        DEFVAL { 120 }
        ::= { atmVnnConfigEntry 16 }

atmVnnT317 OBJECT-TYPE
        SYNTAX Integer32
        MAX-ACCESS read-write
        STATUS current
        DESCRIPTION "Timer T317 value - seconds"
        DEFVAL { 60 }
        ::= { atmVnnConfigEntry 17 }

atmVnnT322 OBJECT-TYPE
        SYNTAX Integer32
        MAX-ACCESS read-write
        STATUS current
        DESCRIPTION "Timer T322 value - seconds"
        DEFVAL { 4 }
        ::= { atmVnnConfigEntry 18}

atmVnnT398 OBJECT-TYPE
        SYNTAX Integer32
        MAX-ACCESS read-write
        STATUS current
        DESCRIPTION "Timer T398 value - seconds"
        DEFVAL { 4 }
        ::= { atmVnnConfigEntry 19 }

atmVnnT399 OBJECT-TYPE
        SYNTAX Integer32
        MAX-ACCESS read-write
        STATUS current
        DESCRIPTION "Timer T399 value - seconds"
        DEFVAL { 14 }
        ::= { atmVnnConfigEntry 20 }

atmVnnMyNeighborIpAddress OBJECT-TYPE
        SYNTAX IpAddress
        MAX-ACCESS read-write
        STATUS current
        DESCRIPTION "The IP address of the neighbor system connected to
            the far end of this interface, to which a Network
            Management Station can send SNMP messages, as IP
            datagrams sent to UDP port 161, in order to access
            network management information concerning the 
            operation of that system.  Note that the value
            of this object can currently only be obtained 
            by manual configuration."
        ::= { atmVnnConfigEntry 21 }
 
atmVnnMyNeighborIfName OBJECT-TYPE
        SYNTAX DisplayString (SIZE(20))
        MAX-ACCESS read-write
        STATUS current
        DESCRIPTION "The textual name of the interface on the neighbor
            system on the far end of this interface, and to
            which this interface connects.  If the neighbor
            system is manageable through SNMP and supports
            the object ifName, the value of this object must
            be identical with that of ifName for the ifEntry
            of the lowest level physical interface for this 
            port.  If this interface does not have a
            textual name, the value of this object is a zero
            length string.  Note that the value of this object
            can currently only be obtained by manual
            configuration."
        ::= { atmVnnConfigEntry 22 }
 
atmVnnVpiSig OBJECT-TYPE
        SYNTAX INTEGER (0..255)
        MAX-ACCESS read-write
        STATUS current
        DESCRIPTION "VPI value for the signalling channel for the UNI
                 interface."
        DEFVAL { 0 }
        ::= { atmVnnConfigEntry 23 }

atmVnnVciSig OBJECT-TYPE
        SYNTAX INTEGER (0..31)
        MAX-ACCESS read-write
        STATUS current
        DESCRIPTION "VCI value for the signalling channel for the UNI
                 interface."
        DEFVAL { 5 }
        ::= { atmVnnConfigEntry 24 }

atmVnnVpiIlmi OBJECT-TYPE
        SYNTAX INTEGER (0..255)
        MAX-ACCESS read-write
        STATUS current
        DESCRIPTION "VPI value for the ilmi channel for the UNI
                 interface."
        DEFVAL { 0 }
        ::= { atmVnnConfigEntry 25 }

atmVnnVciIlmi OBJECT-TYPE
        SYNTAX INTEGER (0..31)
        MAX-ACCESS read-write
        STATUS current
        DESCRIPTION "VCI value for the ilmi channel for the UNI
                 interface."
        DEFVAL { 16 }
        ::= { atmVnnConfigEntry 26 }

atmVnnAtmSignalingStatus OBJECT-TYPE
        SYNTAX INTEGER  {
                enabled(1)
                }
        MAX-ACCESS read-only
        STATUS current
        DESCRIPTION "Indicates if atm signaling is enabled or disabled
                 for this interface. Consistent with other AC interfaces"
        ::= { atmVnnConfigEntry 27 }

atmVnnMyIfName OBJECT-TYPE
        SYNTAX DisplayString (SIZE(20))
        MAX-ACCESS read-write
        STATUS current
        DESCRIPTION "A textual name of this interface.  If this system
            is manageable manageable through SNMP and supports
            the object ifName, the value of this object must
            be identical with that of ifName for the ifEntry
            of the lowest level physical interface for this 
            port.  This interface must be uniquely named on 
            this system to distinguish parallel links with a 
            neighboring system.  If this interface does not 
            have a textual name, the value of this object is a 
            zero length string."
        ::= { atmVnnConfigEntry 28 }
 
atmVnnIlmiProtocolStatus OBJECT-TYPE
        SYNTAX INTEGER  {
                enabled(1)
                }
        MAX-ACCESS read-only
        STATUS current
        DESCRIPTION "The administrative status:
                 'enabled'  - ILMI protocol enabled on UNI."
        ::= { atmVnnConfigEntry 29 }

atmVnnIlmiOperStatus OBJECT-TYPE
        SYNTAX INTEGER  {
                outOfService(1),
                inService(2)
                }
        MAX-ACCESS read-only
        STATUS current
        DESCRIPTION "The operational status:
                 'outOfService' - ILMI connectivity is down
                 'inService'    - ILMI connectivity is up."
        DEFVAL { outOfService }
        ::= { atmVnnConfigEntry 30 }

atmVnnIlmiConfigProc OBJECT-TYPE
        SYNTAX INTEGER  {
                disabled(2)
                }
        MAX-ACCESS read-only
        STATUS current
        DESCRIPTION "ILMI Configuration Procedure status."
        ::= { atmVnnConfigEntry 31 }

atmVnnIlmiConnectProc OBJECT-TYPE
        SYNTAX INTEGER  {
                enabled(1)
                }
        MAX-ACCESS read-only
        STATUS current
        DESCRIPTION "ILMI Connectivity Procedure status."
        ::= { atmVnnConfigEntry 32 }

atmVnnIlmiAttachPtProc OBJECT-TYPE
        SYNTAX INTEGER  {
                disabled(2)
                }
        MAX-ACCESS read-only
        STATUS current
        DESCRIPTION "ILMI Attachment Point Procedure status."
        ::= { atmVnnConfigEntry 33 }

atmVnnIlmiSecureLinkProc OBJECT-TYPE
        SYNTAX INTEGER  {
                disabled(2)
                }
        MAX-ACCESS read-only
        STATUS current
        DESCRIPTION "ILMI Secure Link Procedure status.  Can be enabled
                 only if Attachment Point Procedure is enabled."
        ::= { atmVnnConfigEntry 34 }

atmVnnIlmiAddrRegProc OBJECT-TYPE
        SYNTAX INTEGER  {
                enabled(1)
                }
        MAX-ACCESS read-only
        STATUS current
        DESCRIPTION "ILMI Address Registration Procedure status."
        ::= { atmVnnConfigEntry 35 }

atmVnnIlmiTimerS OBJECT-TYPE
        SYNTAX Integer32
        MAX-ACCESS read-write
        STATUS current
        DESCRIPTION "Timer S (secs).  Used to poll peer when link is
                 down."
        DEFVAL { 1 }
        ::= { atmVnnConfigEntry 36 }

atmVnnIlmiTimerT OBJECT-TYPE
        SYNTAX Integer32
        MAX-ACCESS read-write
        STATUS current
        DESCRIPTION "Timer T (secs).  Used to poll peer when link is
                 up."
        DEFVAL { 5 }
        ::= { atmVnnConfigEntry 37 }

atmVnnIlmiRetryK OBJECT-TYPE
        SYNTAX Integer32
        MAX-ACCESS read-write
        STATUS current
        DESCRIPTION "Retry K - number of timeouts before link is 
                 declared down."
        DEFVAL { 4 }
        ::= { atmVnnConfigEntry 38 }

atmVnnAvailBwIgr OBJECT-TYPE
          SYNTAX Integer32
            MAX-ACCESS read-only
              STATUS current
        DESCRIPTION "The Avail Bandwidth for that interface in
                cells per sec. Bandwidth for UBR conns
                will not be accounted for."
        DEFVAL { 0 }
        ::= { atmVnnConfigEntry 39 }

atmVnnAvailBwEgr OBJECT-TYPE
          SYNTAX Integer32
            MAX-ACCESS read-only
              STATUS current
        DESCRIPTION "The Avail Bandwidth for that interface in
                cells per sec. Bandwidth for UBR conns
                will not be accounted for."
        DEFVAL { 0 }
        ::= { atmVnnConfigEntry 40 }

atmVnnUPCSupp OBJECT-TYPE
          SYNTAX INTEGER  {
                        disabled(1),
                        enabled(2)
                        }
        MAX-ACCESS read-write
        STATUS current
        DESCRIPTION "upc supp off/on " 
        DEFVAL { disabled }
        ::= { atmVnnConfigEntry 41 }

atmVnnUbrLoadBalSupp OBJECT-TYPE
        SYNTAX INTEGER  {
                        disabled(1),
                        enabled(2)
                        }
        MAX-ACCESS read-write
        STATUS current
        DESCRIPTION "load balancing supp for ubr conns off/on" 
        DEFVAL { disabled }
        ::= { atmVnnConfigEntry 42 }

atmVnnSscopRxWndSz OBJECT-TYPE
        SYNTAX INTEGER (8..256)
        MAX-ACCESS read-write
        STATUS current
        DESCRIPTION "The receive window size for the SSCOP layer"
        DEFVAL { 32 }
        ::= { atmVnnConfigEntry 43 }

-- End of 1  Interface Configuration Group




virtualIntfConfigTable        OBJECT-TYPE
                SYNTAX SEQUENCE OF VirtualIntfConfigEntry
                MAX-ACCESS not-accessible
                STATUS current
                DESCRIPTION "Table of Virtual Interfaces Configurations"
                ::= { intfConfig 18 }

virtualIntfConfigEntry        OBJECT-TYPE
                SYNTAX VirtualIntfConfigEntry
                MAX-ACCESS not-accessible
                STATUS current
                DESCRIPTION "Index is the Interface and the Virutal Interface"
                INDEX { virtualIntfConfigIf, virtualIntfConfigVi }
                ::= { virtualIntfConfigTable 1 }

VirtualIntfConfigEntry        ::= SEQUENCE {
                virtualIntfConfigIf                      IntfIndex,
                virtualIntfConfigVi                      INTEGER,
                virtualIntfConfigCellRate                Integer32,
                virtualIntfConfigOverSubs                Integer32,
                virtualIntfConfigRowStatus               RowStatus,
                virtualIntfConfigUPCSupp                 INTEGER,
                virtualIntfAvailBwEgr                    Integer32
                }

virtualIntfConfigIf        OBJECT-TYPE
                SYNTAX IntfIndex
                MAX-ACCESS not-accessible
                STATUS current
                DESCRIPTION "Interface index for side A of an ATM-to-ATM PVC VCC
                             connection.  Number value is interpreted as an
                             interface of the form, SSPPCCC, where SS is the 
                             card slot, PP is the port number, and CCC is the 
                             channel number."
                ::= { virtualIntfConfigEntry 1 }

virtualIntfConfigVi        OBJECT-TYPE
                SYNTAX INTEGER (0..1024)
                MAX-ACCESS not-accessible
                STATUS current
                DESCRIPTION "VI value. Def Val is 1 because 0 cannot be 
                             configured"
                DEFVAL { 1 }
                ::= { virtualIntfConfigEntry 2 }

virtualIntfConfigCellRate        OBJECT-TYPE
                SYNTAX Integer32
                MAX-ACCESS read-write
                STATUS current
                DESCRIPTION " Bandwidth assigned for the VI. 
                              The unit is cells per sec.
                              Total Bandwidth of all VI's 
                              cannot exceed bandwidth of the 
                              main interface. CAC will be supported per VI."
                ::= { virtualIntfConfigEntry 3 }

virtualIntfConfigOverSubs       OBJECT-TYPE
                SYNTAX Integer32
                MAX-ACCESS read-write
                STATUS current
                DESCRIPTION " Over Subscription rate for VI "
                ::= { virtualIntfConfigEntry 4 }

virtualIntfConfigRowStatus        OBJECT-TYPE
                SYNTAX RowStatus
                MAX-ACCESS read-write
                STATUS current
                DESCRIPTION "row status"
                ::= { virtualIntfConfigEntry 5 }

virtualIntfConfigUPCSupp OBJECT-TYPE
                SYNTAX INTEGER  {
                                disabled(1),
                                enabled(2)
                                }
                MAX-ACCESS read-write
                STATUS current
                DESCRIPTION "virtual interface upc supp off/on
                        If this is changed then all the connections
                        on this interface will be replayed."
                DEFVAL { disabled }
                ::= { virtualIntfConfigEntry 6 }

virtualIntfAvailBwEgr   OBJECT-TYPE
                SYNTAX Integer32
                MAX-ACCESS read-only
                STATUS current
                DESCRIPTION " Avail Bw for that VI in cells per sec in the
                              Egress Direction or the direction away
                              from back plane."
                ::= { virtualIntfConfigEntry 7 }





-- Virtual UNI configuration table 

virtualUNIConfigTable        OBJECT-TYPE
                SYNTAX SEQUENCE OF VirtualUNIConfigEntry
                MAX-ACCESS not-accessible
                STATUS current
                DESCRIPTION "Table of Virtual UNI Interfaces Configurations"
                ::= { intfConfig 19 }

virtualUNIConfigEntry        OBJECT-TYPE
                SYNTAX VirtualUNIConfigEntry
                MAX-ACCESS not-accessible
                STATUS current
                DESCRIPTION "Index is the Interface and the Virutal UNI  Interface"
                INDEX { virtualUNIIfIndex, virtualUNIVUNIId }
                ::= { virtualUNIConfigTable 1 }

VirtualUNIConfigEntry        ::= SEQUENCE {
                virtualUNIIfIndex           IntfIndex,
                virtualUNIVUNIId            INTEGER,
                virtualUNIVISupport         INTEGER,
                virtualUNIMinVpi            INTEGER,
                virtualUNIMaxVpi            INTEGER,
                virtualUNIConfigRowStatus   RowStatus,
                virtualUNIAddrType          INTEGER,
                virtualUNISvcMinVpi         INTEGER,
                virtualUNISvcMaxVpi         INTEGER,
                virtualUNISvcMinVci         INTEGER,
                virtualUNISvcMaxVci         INTEGER,
                virtualUNIAdminStatus       INTEGER,
                virtualUNIOperStatus        INTEGER,
                virtualUNINwPrefix1         OCTET STRING,
                virtualUNIT303              Integer32,
                virtualUNIT308                        Integer32,
                virtualUNIT309                        Integer32,
                virtualUNIT310                        Integer32,
                virtualUNIT313                        Integer32,
                virtualUNIT316                        Integer32,
                virtualUNIT317                        Integer32,
                virtualUNIT322                        Integer32,
                virtualUNIT398                        Integer32,
                virtualUNIT399                        Integer32,
                virtualUNIMyNeighborIpAddress        IpAddress,
                virtualUNIMyNeighborIfName                DisplayString,
                virtualUNIVpiSig                        INTEGER,
                virtualUNIVciSig                        INTEGER,
                virtualUNISignalingAdminStatus   INTEGER,
                virtualUNISignalingOperStatus    INTEGER,
                virtualUNIVpiIlmi                        INTEGER,
                virtualUNIVciIlmi                        INTEGER,
                virtualUNIMyIfName                        DisplayString,
                virtualUNIIlmiProtocolStatus        INTEGER,
                virtualUNIIlmiOperStatus                INTEGER,
                virtualUNIIlmiConfigProc                INTEGER,
                virtualUNIIlmiConnectProc                INTEGER,
                virtualUNIIlmiAttachPtProc                INTEGER,
                virtualUNIIlmiSecureLinkProc        INTEGER,
                virtualUNIIlmiAddrRegProc                INTEGER,
                virtualUNIIlmiTimerS                Integer32,
                virtualUNIIlmiTimerT                Integer32,
                virtualUNIIlmiRetryK                Integer32,
                virtualUNIIntfType                        INTEGER,
                virtualUNIUserAddress                OCTET STRING,
                virtualUNIUserAddrOrgScope        INTEGER ,
                virtualUNISscopRxWndSz          INTEGER
                }

virtualUNIIfIndex        OBJECT-TYPE
                SYNTAX IntfIndex
                MAX-ACCESS not-accessible
                STATUS current
                DESCRIPTION "This is the first  index to the Virtual UNI 
                Interface table. Interface index will be of the form SSPPCCC, 
                where SS is the card slot, PP is the port number, and CCC 
                is the channel number."
                ::= { virtualUNIConfigEntry 1 }

virtualUNIVUNIId        OBJECT-TYPE
                SYNTAX INTEGER (1..255)
                MAX-ACCESS not-accessible
                STATUS current
                DESCRIPTION "Virtual UNI number, second index to access the virtual
                     UNI interface."
                DEFVAL { 1 }
                ::= { virtualUNIConfigEntry 2 }

virtualUNIVISupport        OBJECT-TYPE
                SYNTAX INTEGER  {
                                enabled(1),
                                disabled(2)
                                }
                MAX-ACCESS read-write
                STATUS current
                DESCRIPTION "Virtual Interface (Traffic Shaping) is enabled or
        disabled on this VUNI. A Virtual Interface should already be
        configured befaore the traffic shaping can be enabled on this VUNI. If
        VISupport is disabled then all the connections on the VUNI can only be
        configured as UBR connections if this VUNI interface is on a VI enabled 
        physical interface"
                DEFVAL { disabled }
                ::= { virtualUNIConfigEntry 3 }

virtualUNIMinVpi        OBJECT-TYPE
                SYNTAX INTEGER (0..255)
                MAX-ACCESS read-write
                STATUS current
                DESCRIPTION "Lower value of the VPI range for this VUNI"
                ::= { virtualUNIConfigEntry 4 }

virtualUNIMaxVpi        OBJECT-TYPE
                SYNTAX INTEGER (0..255)
                MAX-ACCESS read-write
                STATUS current
                DESCRIPTION "Upper value of the VPI range for this VUNI"
                ::= { virtualUNIConfigEntry 5 }

virtualUNIConfigRowStatus        OBJECT-TYPE
                SYNTAX RowStatus
                MAX-ACCESS read-write
                STATUS current
                DESCRIPTION "row status"
                ::= { virtualUNIConfigEntry 6 }

virtualUNIAddrType        OBJECT-TYPE
                SYNTAX INTEGER  {
                                nsap(1),
                                e164(2),
                                private(3)
                                }
                MAX-ACCESS read-write
                STATUS current
                DESCRIPTION "atm address type"
                DEFVAL { nsap }
                ::= { virtualUNIConfigEntry 7 }

virtualUNISvcMinVpi        OBJECT-TYPE
                SYNTAX INTEGER (0..255)
                MAX-ACCESS read-write
                STATUS current
                DESCRIPTION "The lower bound of the VPI for SVC connections."
                DEFVAL { 0 }
                ::= { virtualUNIConfigEntry 8 }

virtualUNISvcMaxVpi        OBJECT-TYPE
                SYNTAX INTEGER (0..255)
                MAX-ACCESS read-write
                STATUS current
                DESCRIPTION "The upper bound of the VPI for SVC connections."
                DEFVAL { 0 }
                ::= { virtualUNIConfigEntry 9 }

virtualUNISvcMinVci        OBJECT-TYPE
                SYNTAX INTEGER (0..65535)
                MAX-ACCESS read-write
                STATUS current
                DESCRIPTION "The lower bound of the VCI for SVC connections."
                DEFVAL { 32 }
                ::= { virtualUNIConfigEntry 10 }

virtualUNISvcMaxVci        OBJECT-TYPE
                SYNTAX INTEGER (0..65535)
                MAX-ACCESS read-write
                STATUS current
                DESCRIPTION "The upper bound of the VCI for SVC connections."
                DEFVAL { 255 }
                ::= { virtualUNIConfigEntry 11 }

virtualUNIAdminStatus        OBJECT-TYPE
                        SYNTAX INTEGER  {
                                outOfService(1),
                                inService(2)
                                }
                        MAX-ACCESS read-write
                        STATUS current
                        DESCRIPTION "The administrative action:
                             'outOfService' means take the VUNI out of service
                             'inService'    means take the VUNI in service"
                        DEFVAL { outOfService }
                        ::= { virtualUNIConfigEntry 12 }

virtualUNIOperStatus        OBJECT-TYPE
                        SYNTAX INTEGER  {
                                outOfService(1),
                                inService(2)
                                }
                        MAX-ACCESS read-only
                        STATUS current
                        DESCRIPTION "The operational status of the VUNI:
                             'outOfService' means the VUNI is out of service
                             'inService'    means the VUNI is in service"
                        DEFVAL { outOfService }
                        ::= { virtualUNIConfigEntry 13 }

virtualUNINwPrefix1        OBJECT-TYPE
                SYNTAX OCTET STRING (SIZE(13))
                MAX-ACCESS read-write
                STATUS current
                DESCRIPTION "ATM Network Prefix 1"
                ::= { virtualUNIConfigEntry 14 }


virtualUNIT303        OBJECT-TYPE
                SYNTAX Integer32
                MAX-ACCESS read-write
                STATUS current
                DESCRIPTION "Timer T303 value - seconds"
                DEFVAL { 4 }
                ::= { virtualUNIConfigEntry 15 }

virtualUNIT308        OBJECT-TYPE
                SYNTAX Integer32
                MAX-ACCESS read-write
                STATUS current
                DESCRIPTION "Timer T308 value - seconds"
                DEFVAL { 30 }
                ::= { virtualUNIConfigEntry 16 }

virtualUNIT309        OBJECT-TYPE
                SYNTAX Integer32
                MAX-ACCESS read-write
                STATUS current
                DESCRIPTION "Timer T309 value - seconds"
                DEFVAL { 10 }
                ::= { virtualUNIConfigEntry 17 }

virtualUNIT310        OBJECT-TYPE
                SYNTAX Integer32
                MAX-ACCESS read-write
                STATUS current
                DESCRIPTION "Timer T310 value - seconds"
                DEFVAL { 10 }
                ::= { virtualUNIConfigEntry 18 }

virtualUNIT313        OBJECT-TYPE
                SYNTAX Integer32
                MAX-ACCESS read-write
                STATUS current
                DESCRIPTION "Timer T313 value - User side only - seconds"
                DEFVAL { 4 }
                ::= { virtualUNIConfigEntry 19 }

virtualUNIT316        OBJECT-TYPE
                SYNTAX Integer32
                MAX-ACCESS read-write
                STATUS current
                DESCRIPTION "Timer T316 value - seconds"
                DEFVAL { 120 }
                ::= { virtualUNIConfigEntry 20 }

virtualUNIT317        OBJECT-TYPE
                SYNTAX Integer32
                MAX-ACCESS read-write
                STATUS current
                DESCRIPTION "Timer T317 value - seconds"
                DEFVAL { 60 }
                ::= { virtualUNIConfigEntry 21 }

virtualUNIT322        OBJECT-TYPE
                SYNTAX Integer32
                MAX-ACCESS read-write
                STATUS current
                DESCRIPTION "Timer T322 value - seconds"
                DEFVAL { 4 }
                ::= { virtualUNIConfigEntry 22}

virtualUNIT398        OBJECT-TYPE
                SYNTAX Integer32
                MAX-ACCESS read-write
                STATUS current
                DESCRIPTION "Timer T398 value - seconds"
                DEFVAL { 4 }
                ::= { virtualUNIConfigEntry 23 }

virtualUNIT399        OBJECT-TYPE
                SYNTAX Integer32
                MAX-ACCESS read-write
                STATUS current
                DESCRIPTION "Timer T399 value - seconds"
                DEFVAL { 14 }
                ::= { virtualUNIConfigEntry 24 }

virtualUNIMyNeighborIpAddress OBJECT-TYPE
                SYNTAX IpAddress
                MAX-ACCESS read-write
                STATUS current
                DESCRIPTION "The IP address of the neighbor system connected to
                             the far end of this interface, to which a Network
                             Management Station can send SNMP messages, as IP
                             datagrams sent to UDP port 161, in order to access
                             network management information concerning the 
                             operation of that system.  Note that the value
                             of this object can currently only be obtained 
                             by manual configuration."
                ::= { virtualUNIConfigEntry 25 }
 
virtualUNIMyNeighborIfName OBJECT-TYPE
                SYNTAX DisplayString (SIZE(20))
                MAX-ACCESS read-write
                STATUS current
                DESCRIPTION "The textual name of the interface on the neighbor
                             system on the far end of this interface, and to
                             which this interface connects.  If the neighbor
                             system is manageable through SNMP and supports
                             the object ifName, the value of this object must
                             be identical with that of ifName for the ifEntry
                             of the lowest level physical interface for this 
                             port.  If this interface does not have a
                             textual name, the value of this object is a zero
                             length string.  Note that the value of this object
                             can currently only be obtained by manual
                             configuration."
                ::= { virtualUNIConfigEntry 27 }
 
virtualUNIVpiSig        OBJECT-TYPE
                SYNTAX INTEGER (0..255)
                MAX-ACCESS read-write
                STATUS current
                DESCRIPTION "VPI value for the signalling channel for the UNI
                             interface."
                DEFVAL { 0 }
                ::= { virtualUNIConfigEntry 28 }

virtualUNIVciSig        OBJECT-TYPE
                SYNTAX INTEGER (0..31)
                MAX-ACCESS read-write
                STATUS current
                DESCRIPTION "VCI value for the signalling channel for the UNI
                             interface."
                DEFVAL { 5 }
                ::= { virtualUNIConfigEntry 29 }

virtualUNISignalingAdminStatus OBJECT-TYPE
                SYNTAX INTEGER  {
                                enabled(1),
                                disabled(2)
                                }
                MAX-ACCESS read-write
                STATUS current
                DESCRIPTION "Indicates if atm signaling is enabled or disabled
                             for this VUNI interface."
                ::= { virtualUNIConfigEntry 30 }

virtualUNISignalingOperStatus OBJECT-TYPE
                SYNTAX INTEGER  {
                                inService(1),
                                outOfService(2)
                                }
                MAX-ACCESS read-only
                STATUS current
                DESCRIPTION "The protocol operational status of the UNI:
                             'outOfService' means the UNI is out of service
                             'inService'    means the UNI is in service"
                DEFVAL { outOfService }
                ::= { virtualUNIConfigEntry 31 }

virtualUNIVpiIlmi        OBJECT-TYPE
                SYNTAX INTEGER (0..255)
                MAX-ACCESS read-write
                STATUS current
                DESCRIPTION "VPI value for the ilmi channel for the UNI
                             interface."
                DEFVAL { 0 }
                ::= { virtualUNIConfigEntry 32 }

virtualUNIVciIlmi        OBJECT-TYPE
                SYNTAX INTEGER (0..31)
                MAX-ACCESS read-write
                STATUS current
                DESCRIPTION "VCI value for the ilmi channel for the UNI
                             interface."
                DEFVAL { 16 }
                ::= { virtualUNIConfigEntry 33 }


virtualUNIMyIfName        OBJECT-TYPE
                SYNTAX DisplayString (SIZE(20))
                MAX-ACCESS read-write
                STATUS current
                DESCRIPTION "A textual name of this interface.  If this system
                             is manageable manageable through SNMP and supports
                             the object ifName, the value of this object must
                             be identical with that of ifName for the ifEntry
                             of the lowest level physical interface for this 
                             port.  This interface must be uniquely named on 
                             this system to distinguish parallel links with a 
                             neighboring system.  If this interface does not 
                             have a textual name, the value of this object is a 
                             zero length string."
                ::= { virtualUNIConfigEntry 34 }
 
virtualUNIIlmiProtocolStatus OBJECT-TYPE
                SYNTAX INTEGER  {
                                enabled(1),
                                disabled(2)
                                }
                MAX-ACCESS read-write
                STATUS current
                DESCRIPTION "The administrative status:
                             'enabled'  - ILMI protocol enabled on UNI
                             'disabled' - ILMI protocol disabled on UNI."
                DEFVAL { disabled }
                ::= { virtualUNIConfigEntry 35 }

virtualUNIIlmiOperStatus OBJECT-TYPE
                SYNTAX INTEGER  {
                                outOfService(1),
                                inService(2)
                                }
                MAX-ACCESS read-only
                STATUS current
                DESCRIPTION "The operational status:
                             'outOfService' - ILMI connectivity is down
                             'inService'    - ILMI connectivity is up."
                DEFVAL { outOfService }
                ::= { virtualUNIConfigEntry 36 }

virtualUNIIlmiConfigProc OBJECT-TYPE
                SYNTAX INTEGER  {
                                enabled(1),
                                disabled(2)
                                }
                MAX-ACCESS read-write
                STATUS current
                DESCRIPTION "ILMI Configuration Procedure status."
                DEFVAL { disabled }
                ::= { virtualUNIConfigEntry 37 }

virtualUNIIlmiConnectProc OBJECT-TYPE
                SYNTAX INTEGER  {
                                enabled(1),
                                disabled(2)
                                }
                MAX-ACCESS read-write
                STATUS current
                DESCRIPTION "ILMI Connectivity Procedure status."
                DEFVAL { disabled }
                ::= { virtualUNIConfigEntry 38 }

virtualUNIIlmiAttachPtProc OBJECT-TYPE
                SYNTAX INTEGER  {
                                enabled(1),
                                disabled(2)
                                }
                MAX-ACCESS read-write
                STATUS current
                DESCRIPTION "ILMI Attachment Point Procedure status."
                DEFVAL { disabled }
                ::= { virtualUNIConfigEntry 39 }

virtualUNIIlmiSecureLinkProc OBJECT-TYPE
                SYNTAX INTEGER  {
                                enabled(1),
                                disabled(2)
                                }
                MAX-ACCESS read-write
                STATUS current
                DESCRIPTION "ILMI Secure Link Procedure status.  Can be enabled
                             only if Attachment Point Procedure is enabled."
                DEFVAL { disabled }
                ::= { virtualUNIConfigEntry 40 }

virtualUNIIlmiAddrRegProc OBJECT-TYPE
                SYNTAX INTEGER  {
                                enabled(1),
                                disabled(2)
                                }
                MAX-ACCESS read-write
                STATUS current
                DESCRIPTION "ILMI Address Registration Procedure status."
                DEFVAL { disabled }
                ::= { virtualUNIConfigEntry 41 }

virtualUNIIlmiTimerS OBJECT-TYPE
                SYNTAX Integer32
                MAX-ACCESS read-write
                STATUS current
                DESCRIPTION "Timer S (secs).  Used to poll peer when link is
                             down."
                DEFVAL { 1 }
                ::= { virtualUNIConfigEntry 42 }

virtualUNIIlmiTimerT OBJECT-TYPE
                SYNTAX Integer32
                MAX-ACCESS read-write
                STATUS current
                DESCRIPTION "Timer T (secs).  Used to poll peer when link is
                             up."
                DEFVAL { 5 }
                ::= { virtualUNIConfigEntry 43 }

virtualUNIIlmiRetryK OBJECT-TYPE
                SYNTAX Integer32
                MAX-ACCESS read-write
                STATUS current
                DESCRIPTION "Retry K - number of timeouts before link is 
                             declared down."
                DEFVAL { 4 }
                ::= { virtualUNIConfigEntry 44 }

virtualUNIIntfType  OBJECT-TYPE
                SYNTAX INTEGER  {
                                user(1),
                                network(2)
                                }
                MAX-ACCESS read-write
                STATUS current
                DESCRIPTION "atm interface type"
                DEFVAL { network }
                ::= { virtualUNIConfigEntry 45 }

virtualUNIUserAddress OBJECT-TYPE
                SYNTAX OCTET STRING (SIZE(7))
                MAX-ACCESS read-write
                STATUS current
                DESCRIPTION "ATM User Address"
                ::= { virtualUNIConfigEntry 46 }

virtualUNIUserAddrOrgScope OBJECT-TYPE
                SYNTAX INTEGER  {
                                localNetwork(1),
                                localNetworkPlusOne(2),
                                localNetworkPlusTwo(3),
                                siteMinusOne(4),
                                intraSite(5),
                                sitePlusOne(6),
                                organizationMinusOne(7),
                                intraOrganization(8),
                                organizationPlusOne(9),
                                communityMinusOne(10),
                                intraCommunity(11),
                                communityPlusOne(12),
                                regional(13),
                                interRegional(14),
                                global(15)
                                }
                MAX-ACCESS read-write
                STATUS current
                DESCRIPTION "ATM User Address Organizational scope"
                ::= { virtualUNIConfigEntry 47 }

virtualUNISscopRxWndSz OBJECT-TYPE
                SYNTAX INTEGER (8..256)
                MAX-ACCESS read-write
                STATUS current
                DESCRIPTION "The receive window size for the SSCOP layer"
                DEFVAL { 32 }
                ::= { virtualUNIConfigEntry 48 }





casConfig      OBJECT IDENTIFIER ::=   { intfConfig 20 }

casConfigTable  OBJECT-TYPE
                  SYNTAX SEQUENCE OF CasConfigEntry 
                MAX-ACCESS not-accessible
                STATUS current
                DESCRIPTION "Table for CAS trunk/line configuration."
                ::= { casConfig 1 }

casConfigEntry  OBJECT-TYPE
                SYNTAX CasConfigEntry
                MAX-ACCESS not-accessible
                STATUS current
                DESCRIPTION "Row definition for CAS trunk/line configuration."
                INDEX { casIfIndex } 
                ::= { casConfigTable 1 }

CasConfigEntry ::= SEQUENCE {
                            casIfIndex          IntfIndex,
                            casAdminStatus            INTEGER,
                            casOperStatus              INTEGER,
                            casProtocolType           INTEGER,
                            casDirection          INTEGER,
                            casAddressingType         INTEGER,
                            casBitPatternType         INTEGER,
                            casGroupId          INTEGER
                            }

casIfIndex OBJECT-TYPE
                  SYNTAX IntfIndex
                MAX-ACCESS not-accessible
                STATUS current
                DESCRIPTION "The channel ID (slot/port/channel) in SSPPCCC 
                        format associated with the CAS trunk/line."
                  ::= { casConfigEntry 1 }

casAdminStatus  OBJECT-TYPE
                  SYNTAX INTEGER {
                                outOfService(1),
                                inService(2),
                                delete(3)
                                }
                MAX-ACCESS read-write
                STATUS current
                DESCRIPTION "The administrative action:
                        outOfService-take the CAS trunk/line out of service, 
                        inService-take the CAS trunk/line in service,
                         delete-remove/deconfigure the CAS trunk/line."
                  DEFVAL { outOfService }
                ::= { casConfigEntry 2 }

casOperStatus OBJECT-TYPE
                SYNTAX INTEGER {
                                outOfService(1),
                                inService(2)
                                }
                  MAX-ACCESS read-only
                STATUS current
                DESCRIPTION "The operational status of the CAS trunk/line:
                        outOfService-the CAS trunk/line is out of service,
                        inService-the CAS trunk/line is in service."
                DEFVAL { outOfService }
                  ::= { casConfigEntry 3 }

casProtocolType OBJECT-TYPE
                  SYNTAX INTEGER {
                                wink-start(1),
                                loop-start-network(2),
                                loop-start-user(3),
                                ground-start-network(4),
                                ground-start-user(5),
                                itu-t-r2(6)
                                }
                  MAX-ACCESS read-write
                STATUS current
                DESCRIPTION "The type of CAS protocol to be used. 
                        The protocol must match the one used on the 
                        other end of the trunk/line."
                DEFVAL { wink-start }
                  ::= { casConfigEntry 4 }

casDirection  OBJECT-TYPE
                SYNTAX INTEGER {
                                both(1), 
                                incoming(2),
                                outgoing(3)
                                }
                  MAX-ACCESS read-write
                  STATUS current
                  DESCRIPTION "The direction of traffic flow on this CAS
                        trunk/line."
                DEFVAL { both }
                  ::= { casConfigEntry 5 }

casAddressingType OBJECT-TYPE
                SYNTAX INTEGER {
                                dtmf(1), 
                                r1-mf(2),
                                r2-mf(3) 
                                }
                  MAX-ACCESS read-write
                  STATUS current
                  DESCRIPTION "The addressing type used for the CAS trunk/line.
                                dtmf  -- dual tone multifrequency
                                r1-mf -- R1 multifrequency,
                                r2-mf -- R2 multifrequency.
                            Type of 're-mf' is valid only when casProtocolType 
                            is 'wink start', while 'r2-mf' is valid only when
                            casProtocolType is 'itu-t r2' ."
                  DEFVAL { dtmf }
                  ::= { casConfigEntry 6 }

casBitPatternType OBJECT-TYPE
                  SYNTAX INTEGER {
                                ab(1),
                                abcd(2)
                                }
                  MAX-ACCESS read-only
                STATUS current
                DESCRIPTION "The type of bit pattern used for supervisory 
                         signaling. The value is AB when SF framing is
                              used, ABCD when ESF framing is used for DS1.
                        In case of E1, the value is always ABCD."
                  ::= { casConfigEntry 7 }

casGroupId OBJECT-TYPE
                  SYNTAX INTEGER (0..255)
                MAX-ACCESS read-write
                STATUS current
                DESCRIPTION "The identifier to associate a group of CAS
                        trunks/lines which have same reachability.
                        When SG is disabled, it must be specified with a
                        non-zero value. When SG is enabled, the value should
                        be set to zero which indicate no routing performed
                        based on the value."
                DEFVAL { 0 }
                ::= { casConfigEntry 8 }


--
-- tone announcement server configuration table
--
toneAnnceConfigTable OBJECT-TYPE
                SYNTAX SEQUENCE OF ToneAnnceConfigEntry
                MAX-ACCESS not-accessible
                STATUS current
                DESCRIPTION "Table for the Tone Announcement Interface"
                ::= { intfConfig 21 }

toneAnnceConfigEntry OBJECT-TYPE
                SYNTAX ToneAnnceConfigEntry
                MAX-ACCESS not-accessible
                STATUS current
                DESCRIPTION "Row definition for Tone Announcement interface"
                INDEX { toneAnnceIfIndex }
                ::= { toneAnnceConfigTable 1 }


ToneAnnceConfigEntry ::= SEQUENCE {
                toneAnnceIfIndex       IntfIndex,
                toneAnnceAdminStatus   INTEGER,
                toneAnnceOperStatus    INTEGER
                }

toneAnnceIfIndex     OBJECT-TYPE
                SYNTAX IntfIndex
                MAX-ACCESS not-accessible
                STATUS current
                DESCRIPTION "interface index (slot/port/channel) SSPPCCC"
                ::= { toneAnnceConfigEntry 1 }

toneAnnceAdminStatus OBJECT-TYPE
                SYNTAX INTEGER {
                                outOfService(1),
                                inService(2),
                                delete(3)
                                }
                MAX-ACCESS read-write
                STATUS current
                DESCRIPTION "The administrative action:
                        'outOfService' means take the interface out of service
                        'inService'    means take the interface in service
                        'delete'       remove/deconfigure the interface."
                DEFVAL { outOfService }
                ::= { toneAnnceConfigEntry 2 }

toneAnnceOperStatus  OBJECT-TYPE
                SYNTAX INTEGER {
                                outOfService(1),
                                inService(2)
                               }
                MAX-ACCESS read-only
                STATUS current
                DESCRIPTION "The operational status of the interface:
                        'outOfService' means the interface is out of service 
                        'inService'    means the interface is in service"
                DEFVAL { outOfService }
                ::= { toneAnnceConfigEntry 3 }





-- GR303 Interface table 
gr303IntfConfig             OBJECT IDENTIFIER ::=   { intfConfig 22 }

gr303IntfConfigTable OBJECT-TYPE
                SYNTAX SEQUENCE OF Gr303IntfConfigEntry
                MAX-ACCESS not-accessible
                STATUS current
                DESCRIPTION "Table of GR303 interface configuration attributes"
                ::= { gr303IntfConfig 1 }

gr303IntfConfigEntry OBJECT-TYPE
                SYNTAX Gr303IntfConfigEntry
                MAX-ACCESS not-accessible
                STATUS current
                DESCRIPTION "Row definition for GR303  interface configuration
                                            table"
                INDEX { gr303IntfId }
                ::= { gr303IntfConfigTable 1 }

Gr303IntfConfigEntry ::= SEQUENCE {
                gr303IntfId                Integer32,
                gr303TMCChannelId  Integer32,      
                gr303EOCChannelId  Integer32,      
                gr303IntfAdminStatus INTEGER,
                gr303IntfOperStatus INTEGER
        }

gr303IntfId        OBJECT-TYPE
                SYNTAX Integer32
                MAX-ACCESS not-accessible
                STATUS current
                DESCRIPTION "Interface ID (SSPPCCC)"
                ::= { gr303IntfConfigEntry 1 }

gr303TMCChannelId        OBJECT-TYPE
                SYNTAX Integer32 (0..24)
                MAX-ACCESS read-write
                STATUS current
                DESCRIPTION "TMC-Channel Number. If TMC Channel is set to 0
                             there will be no  TMC channel on the
                             corresponding DS1. Generally the TMC channel
                             should be specified on the one of the DS1's in a
                             GR303 interface group and should be on DS0 no.
                             24"
                DEFVAL { 0 }
                ::= { gr303IntfConfigEntry 2 }

gr303EOCChannelId        OBJECT-TYPE
                SYNTAX Integer32 (0..24)
                MAX-ACCESS read-write
                STATUS current
                DESCRIPTION "EOC-Channel Number. If EOC Channel is set to 0
                             there will be no  EOC channel on the
                             corresponding DS1. Generally the TMC channel
                             should be specified on the one of the DS1's in a
                             GR303 interface group and should be on DS0 no.
                             12"
                DEFVAL { 0 }
                ::= { gr303IntfConfigEntry 3 }
gr303IntfAdminStatus        OBJECT-TYPE
                SYNTAX INTEGER   {
                        outOfService (1),
                        inService (2),
                        delete (3)

                    }
                MAX-ACCESS read-write
                STATUS current
                DESCRIPTION "GR303 interface admin status"
                ::= { gr303IntfConfigEntry 4 }

gr303IntfOperStatus        OBJECT-TYPE
                SYNTAX INTEGER   {
                                    outOfService (1),
                        inService    (2)
                    }
                MAX-ACCESS read-write
                STATUS current
                DESCRIPTION "GR303 interface operational status"
                ::= { gr303IntfConfigEntry 5 }


-- GR303 DS0 Channel Table

gr303Ds0ChanConfigTable OBJECT-TYPE
                SYNTAX SEQUENCE OF Gr303Ds0ChanConfigEntry
                MAX-ACCESS not-accessible
                STATUS current
                DESCRIPTION "Table of GR303 DS0 Channel configuration attriburtes"
                ::= { gr303IntfConfig 2 }

gr303Ds0ChanConfigEntry OBJECT-TYPE
                SYNTAX Gr303Ds0ChanConfigEntry
                MAX-ACCESS not-accessible
                STATUS current
                DESCRIPTION "Row definition for GR303 DS0  Channel configuration
                                            table"
                INDEX { gr303Ds0ChanId }
                ::= { gr303Ds0ChanConfigTable 1 }

Gr303Ds0ChanConfigEntry::= SEQUENCE {
                gr303Ds0ChanId                INTEGER,
                gr303Ds0ChanAdminStatus INTEGER,
                gr303Ds0ChanOperStatus INTEGER
        }

gr303Ds0ChanId        OBJECT-TYPE
                SYNTAX Integer32
                MAX-ACCESS not-accessible
                STATUS current
                DESCRIPTION "GR303 DS0  Chan ID (SSPPCCC)"
                ::= { gr303Ds0ChanConfigEntry 1 }

gr303Ds0ChanAdminStatus        OBJECT-TYPE
                SYNTAX INTEGER   {
                                        outOfService (1),
                            inService  (2)
                    }
                MAX-ACCESS read-write
                STATUS current
                DESCRIPTION "GR303 Ds0 Chan admin status"
                ::= { gr303Ds0ChanConfigEntry 2 }

gr303Ds0ChanOperStatus        OBJECT-TYPE
                SYNTAX INTEGER   {
                                        outOfService (1),
                            inService  (2)
                    }
                MAX-ACCESS read-write
                STATUS current
                DESCRIPTION "GR303  Ds0 Chan operational status"
                ::= { gr303Ds0ChanConfigEntry 3 }

-- GR303 Interface Group Table (GR303IG)

gr303IgConfig                 OBJECT IDENTIFIER ::=   { gr303Config 1}

gr303IgConfigTable OBJECT-TYPE
                SYNTAX SEQUENCE OF Gr303IgConfigEntry
                MAX-ACCESS not-accessible
                STATUS current
                DESCRIPTION "Table of GR303 group configuration"
                ::= { gr303IgConfig 1 }

gr303IgConfigEntry OBJECT-TYPE
                SYNTAX Gr303IgConfigEntry
                MAX-ACCESS not-accessible
                STATUS current
                DESCRIPTION "Row definition for GR303 group configuration"
                INDEX { gr303IgId }
                ::= { gr303IgConfigTable 1 }

Gr303IgConfigEntry::= SEQUENCE {
            gr303IgId                        INTEGER,
            gr303IgRowStatus            RowStatus,       
                gr303IgAdminStatus          INTEGER,
                gr303IgPrimaryTMCChanIntfId  IntfIndex,
                gr303IgPrimaryEOCChanIntfId  IntfIndex,
                gr303IgBackupTMCChanIntfId  IntfIndex,
                gr303IgBackupEOCChanIntfId  IntfIndex,
            gr303IgPrimaryTMCStatus      INTEGER,
            gr303IgPrimaryEOCStatus      INTEGER,
            gr303IgBackupTMCStatus      INTEGER,
            gr303IgBackupEOCStatus      INTEGER,
            gr303IgTMCProtSwitchProvState INTEGER,
            gr303IgEOCProtSwitchProvState INTEGER,
            gr303IgTMCProtSwitchCommand INTEGER,
            gr303IgEOCProtSwitchCommand INTEGER,
            gr303IgLocalDigitalSwitchType INTEGER,
            gr303IgLocalDigitalSwitchVersion INTEGER
           }
 
gr303IgId      OBJECT-TYPE
                SYNTAX INTEGER (1..84)
                MAX-ACCESS not-accessible
                STATUS current
                DESCRIPTION "This is used as an index into GR303IG table which
                recognizes GR303 Interface Group"
                ::= { gr303IgConfigEntry 1 }

gr303IgRowStatus          OBJECT-TYPE
                             SYNTAX RowStatus
                             MAX-ACCESS read-write
                             STATUS current
                             DESCRIPTION "GR303IG config entry row status"
                             ::= { gr303IgConfigEntry 2 }

gr303IgAdminStatus      OBJECT-TYPE
                SYNTAX INTEGER  {
                        inService (1),
                            outOfService (2)
                }
                MAX-ACCESS read-write
                STATUS current
                DESCRIPTION "Administrative status of the GR303IG"
                DEFVAL { outOfService }
                ::= { gr303IgConfigEntry 3 }

gr303IgPrimaryTMCChanIntfId      OBJECT-TYPE
                             SYNTAX IntfIndex 
                             MAX-ACCESS read-write
                             STATUS current
                             DESCRIPTION "Primary TMC  channel Interface Id
                                          in SSPPCCC format"
                             ::= { gr303IgConfigEntry 4 }           
 
gr303IgPrimaryEOCChanIntfId      OBJECT-TYPE
                             SYNTAX IntfIndex
                             MAX-ACCESS read-write
                             STATUS current
                             DESCRIPTION "Primary EOC channel Interface Id in
                             SSPPCCC format"
                             ::= { gr303IgConfigEntry 5 }           


gr303IgBackupTMCChanIntfId      OBJECT-TYPE
                             SYNTAX IntfIndex 
                             MAX-ACCESS read-write
                             STATUS current
                             DESCRIPTION "Backup TMC  channel Interface Id
                                          in SSPPCCC format "
                             ::= { gr303IgConfigEntry 6 }           

gr303IgBackupEOCChanIntfId      OBJECT-TYPE
                             SYNTAX IntfIndex
                             MAX-ACCESS read-write
                             STATUS current
                             DESCRIPTION "Backup EOC channel Interface Id in
                             SSPPCCC format"
                             ::= { gr303IgConfigEntry 7 }           

gr303IgPrimaryTMCStatus      OBJECT-TYPE
                             SYNTAX INTEGER {
                                         standby-OutOfService (1),
                                         standby-InService (2),
                                         active-OutOfService (3),
                                         active-InService (4)
                             }
                             MAX-ACCESS read-only
                             STATUS current
                             DESCRIPTION "Primary TMC channel Status"
                             ::= { gr303IgConfigEntry 8 }


gr303IgPrimaryEOCStatus      OBJECT-TYPE
                             SYNTAX INTEGER {
                                         standby-OutOfService (1),
                                         standby-InService (2),
                                         active-OutOfService (3),
                                         active-InService (4)
                             }
                             MAX-ACCESS read-only
                             STATUS current
                             DESCRIPTION "Primary EOC channel Status"
                             ::= { gr303IgConfigEntry 9 }

gr303IgBackupTMCStatus      OBJECT-TYPE
                             SYNTAX INTEGER {
                                         standby-OutOfService (1),
                                         standby-InService (2),
                                         active-OutOfService (3),
                                         active-InService (4),
                                         null (5)
                             }
                             MAX-ACCESS read-only
                             STATUS current
                             DESCRIPTION "Backup TMC channel Status.Value
                             null(5) Indicates that the Backup TMC has not
                             been configured."
                             ::= { gr303IgConfigEntry 10 }


gr303IgBackupEOCStatus      OBJECT-TYPE
                             SYNTAX INTEGER {
                                         standby-OutOfService (1),
                                         standby-InService (2),
                                         active-OutOfService (3),
                                         active-InService (4),
                                         null (5)
                             }
                             MAX-ACCESS read-only
                             STATUS current
                             DESCRIPTION "Backup EOC channel Status.Value
                             null(5) Indicates that the Backup EOC has not
                             been configured."
                             ::= { gr303IgConfigEntry 11 }

gr303IgTMCProtSwitchProvState OBJECT-TYPE 
                             SYNTAX INTEGER {
                                         pps-inhibit (1),
                                         pps-enable (2)
                             }
                             MAX-ACCESS read-write
                             STATUS current
                             DESCRIPTION "Lock/Unlock the protection switch" 
                             DEFVAL { pps-enable }
                             ::= { gr303IgConfigEntry 12 }

gr303IgEOCProtSwitchProvState OBJECT-TYPE 
                             SYNTAX INTEGER {
                                         pps-inhibit (1),
                                         pps-enable (2)
                             }
                             MAX-ACCESS read-write
                             STATUS current
                             DESCRIPTION "Lock/Unlock the protection switch" 
                             DEFVAL { pps-enable }
                             ::= { gr303IgConfigEntry 13 }

gr303IgTMCProtSwitchCommand OBJECT-TYPE 
                             SYNTAX INTEGER {
                             noAction (1),
                             normalSwitchToBackup (2),
                             normalSwitchToPrimary (3),
                             forcedSwitchToBackup (4),
                             forcedSwitchToPrimary (5)
                                }
                MAX-ACCESS read-write
                STATUS current
                DESCRIPTION "User command to do path protection switch"
                DEFVAL { noAction }
                ::= { gr303IgConfigEntry 14 }

gr303IgEOCProtSwitchCommand OBJECT-TYPE 
                             SYNTAX INTEGER {
                                noAction (1),
                                normalSwitchToBackup (2),
                                normalSwitchToPrimary (3),
                                forcedSwitchToBackup (4),
                                forcedSwitchToPrimary (5)
                                }
                MAX-ACCESS read-write
                STATUS current
                DESCRIPTION "User command to do path protection switch"
                DEFVAL { noAction }
                ::= { gr303IgConfigEntry 15 }

gr303IgLocalDigitalSwitchType OBJECT-TYPE 
                             SYNTAX INTEGER {
                             lucent-5ess (1),
                             nortel-dms (2)
                                }
                MAX-ACCESS read-write
                STATUS current
                DESCRIPTION "LDS (IDT) type"
                DEFVAL { lucent-5ess }
                ::= { gr303IgConfigEntry 16 }

gr303IgLocalDigitalSwitchVersion OBJECT-TYPE 
                             SYNTAX INTEGER {
                             lucent-5ess-version-1 (1),
                             nortel-dms-version-1 (2)
                                }
                MAX-ACCESS read-write
                STATUS current
                DESCRIPTION "LDS (IDT)Version"
                DEFVAL { lucent-5ess-version-1 }
                ::= { gr303IgConfigEntry 17 }

-- GR303 IG interface table (table of grouped interfaces)

gr303IgIntfConfigTable OBJECT-TYPE
                SYNTAX SEQUENCE OF Gr303IgIntfConfigEntry
                MAX-ACCESS not-accessible
                STATUS current
                DESCRIPTION "Table of interface attributes in an GR303IG"
                ::= { gr303IgConfig 2 }

gr303IgIntfConfigEntry OBJECT-TYPE
                SYNTAX Gr303IgIntfConfigEntry
                MAX-ACCESS not-accessible
                STATUS current
                DESCRIPTION "Row definition for GR303 Access Arrangement Interface configuration"
                INDEX { gr303IntfIgId , gr303IgIntfId}
                ::= { gr303IgIntfConfigTable 1 }

Gr303IgIntfConfigEntry::= SEQUENCE {
                gr303IntfIgId        INTEGER,
                gr303IgIntfId        INTEGER,
                gr303IgIntfPhysId INTEGER,
                gr303IgIntfNetId INTEGER,
                gr303IgIntfRowStatus RowStatus
           }
 
gr303IntfIgId OBJECT-TYPE
                SYNTAX INTEGER (1..84)
                MAX-ACCESS not-accessible
                STATUS current
                DESCRIPTION "This is used as an index into GR303Ig table which
                recognizes GR303 Interface Group. This is used as a first 
                index into this interface table."
                ::= { gr303IgIntfConfigEntry 1 }

gr303IgIntfId OBJECT-TYPE
                SYNTAX INTEGER (1..28)
                MAX-ACCESS not-accessible
                STATUS current
                DESCRIPTION "This is used as an index into IG interface table 
                which recognizes GR303 Ig interfaces. This is used as a 
                second index into this table"
                ::= { gr303IgIntfConfigEntry 2 }

gr303IgIntfPhysId   OBJECT-TYPE
                SYNTAX Integer32
                MAX-ACCESS read-write
                STATUS current
                DESCRIPTION "Interface's Physical  ID (SSPPCCC)"
                ::= { gr303IgIntfConfigEntry 3 }


gr303IgIntfNetId OBJECT-TYPE
                SYNTAX Integer32
                MAX-ACCESS read-only
                STATUS current
                DESCRIPTION "gr303Ig Interface (DS1) Net Id assigned by the network"
                ::= { gr303IgIntfConfigEntry 4 }

gr303IgIntfRowStatus OBJECT-TYPE
                SYNTAX RowStatus
                MAX-ACCESS read-write
                STATUS current
                DESCRIPTION "GR303IG interface entry row status - row status can not be made
                             active until all the values are set"
                ::= { gr303IgIntfConfigEntry 5 }


-- GR303 LAPD Table

gr303LapdConfigTable OBJECT-TYPE
                SYNTAX SEQUENCE OF Gr303LapdConfigEntry
                MAX-ACCESS not-accessible
                STATUS current
                DESCRIPTION "Table of LAPD attributes in an GR303IG"
                ::= { gr303IgConfig 4 }

gr303LapdConfigEntry OBJECT-TYPE
                SYNTAX Gr303LapdConfigEntry
                MAX-ACCESS not-accessible
                STATUS current
                DESCRIPTION "Row definition for LAPD attributes in a GR303IG"
                INDEX { gr303LapdIgId }
                ::= { gr303LapdConfigTable 1 }

Gr303LapdConfigEntry::= SEQUENCE {
                gr303LapdIgId          INTEGER,
                gr303T200          Integer32,
                        gr303T203          Integer32,
                        gr303N200           Integer32,
                        gr303K                  Integer32
                }

gr303LapdIgId      OBJECT-TYPE
                SYNTAX INTEGER (1..84)
                MAX-ACCESS not-accessible
                STATUS current
                DESCRIPTION "GR303IG Number index which recognizes GR303
                Interface group"
                ::= { gr303LapdConfigEntry 1 }

gr303T200        OBJECT-TYPE
                SYNTAX INTEGER(100..350)
                MAX-ACCESS read-write
                STATUS current
                DESCRIPTION "value of Lapd T200 timer in miliseconds in step
                size of 50 ms"
                DEFVAL { 150 }
                ::= { gr303LapdConfigEntry 2 }

gr303T203        OBJECT-TYPE
                SYNTAX INTEGER(10..300) 
                MAX-ACCESS read-write
                STATUS current
                DESCRIPTION "value of Lapd T203 timer in seconds"
                DEFVAL { 30 }
                ::= { gr303LapdConfigEntry 3 }

gr303N200        OBJECT-TYPE
                SYNTAX INTEGER(1..10) 
                MAX-ACCESS read-write
                STATUS current
                DESCRIPTION "Maximum number of retransmissions"
                DEFVAL { 3 }
                ::= { gr303LapdConfigEntry 4 }


gr303K           OBJECT-TYPE
                SYNTAX INTEGER(1..7) 
                MAX-ACCESS read-write
                STATUS current
                DESCRIPTION "Maximum number of outstanding I frames -
                             Lapd - window size."
                DEFVAL { 7 }
                ::= { gr303LapdConfigEntry 5 }


-- GR303 TMC Table

gr303TMCConfigTable OBJECT-TYPE
                SYNTAX SEQUENCE OF Gr303TMCConfigEntry
                MAX-ACCESS not-accessible
                STATUS current
                DESCRIPTION "Table of Layer 3 attributes in an GR303IG"
                ::= { gr303IgConfig 5 }

gr303TMCConfigEntry OBJECT-TYPE
                SYNTAX Gr303TMCConfigEntry
                MAX-ACCESS not-accessible
                STATUS current
                DESCRIPTION "Row definition for GR303 Access Arrangement 
                                Layer3 parameters configuration"
                INDEX { gr303TMCIgId }
                ::= { gr303TMCConfigTable 1 }

Gr303TMCConfigEntry::= SEQUENCE {
               gr303TMCIgId        INTEGER,
               gr303TMCT303        INTEGER,
               gr303TMCT396        INTEGER
}

gr303TMCIgId      OBJECT-TYPE
                SYNTAX INTEGER (1..84)
                MAX-ACCESS not-accessible
                STATUS current
                DESCRIPTION "GR303IG Number index which recognizes GR303
                Interface group"
                ::= { gr303TMCConfigEntry 1 }

gr303TMCT303        OBJECT-TYPE
                SYNTAX INTEGER(700..4700) 
                MAX-ACCESS read-write
                STATUS current
                DESCRIPTION "value of TMC T303 timer in miliseconds with a
                step size of 500 ms"
                DEFVAL { 700 }
                ::= { gr303TMCConfigEntry 2 }

gr303TMCT396        OBJECT-TYPE
                SYNTAX INTEGER(700..14700) 
                MAX-ACCESS read-write
                STATUS current
                DESCRIPTION "value of TMC T396 timer in miliseconds with a
                step size of 1000 ms"
                DEFVAL { 14700 }
                ::= { gr303TMCConfigEntry 3 }


-- GR303 IG stats table

gr303IgStats                 OBJECT IDENTIFIER ::=   { gr303Stats 1 }

gr303IgStatsTable OBJECT-TYPE
                SYNTAX SEQUENCE OF Gr303IgStatsEntry
                MAX-ACCESS not-accessible
                STATUS current
                DESCRIPTION "Table of GR303 GR303IG based stats attributes" 
                ::= { gr303IgStats 1 }

gr303IgStatsEntry OBJECT-TYPE
                SYNTAX Gr303IgStatsEntry
                MAX-ACCESS not-accessible
                STATUS current
                DESCRIPTION "Row definition for GR303  GR303IG based stats"
                INDEX { gr303IgStatsIgId }
                ::= { gr303IgStatsTable 1 }

Gr303IgStatsEntry    ::= SEQUENCE {
                         gr303IgStatsIgId                INTEGER,
                         gr303IgStatsCurrentInCalls         Integer32,
                         gr303IgStatsCurrentOutCalls         Integer32,
                         gr303IgStatsOutCallSuccessful        Integer32,
                         gr303IgStatsOutCallFailed        Integer32,
                         gr303IgStatsInCallSuccessful        Integer32,
                         gr303IgStatsInCallFailed        Integer32,
                         gr303IgStatsReset          INTEGER
                        }

gr303IgStatsIgId        OBJECT-TYPE
                       SYNTAX INTEGER (1..84)
                       MAX-ACCESS not-accessible
                       STATUS current
                       DESCRIPTION "This is used as an index into GR303 Ig
                       table which recognizes GR303 Interface Group
                       Interface group"
                       ::= { gr303IgStatsEntry 1 }

gr303IgStatsCurrentInCalls       OBJECT-TYPE
                                SYNTAX Integer32 
                                MAX-ACCESS read-only
                                STATUS current
                                DESCRIPTION "Total number of Currently 
                                                established incoming calls"
                                ::= { gr303IgStatsEntry 2 }

gr303IgStatsCurrentOutCalls       OBJECT-TYPE
                                SYNTAX Integer32 
                                MAX-ACCESS read-only
                                STATUS current
                                DESCRIPTION "Total number of Currently 
                                                established outgoing calls"
                                ::= { gr303IgStatsEntry 3 }

gr303IgStatsOutCallSuccessful       OBJECT-TYPE
                                    SYNTAX Integer32 
                                    MAX-ACCESS read-only
                                    STATUS current
                                    DESCRIPTION "Total number successful
                                                outgoing calls"
                                    ::= { gr303IgStatsEntry 4 }

gr303IgStatsOutCallFailed           OBJECT-TYPE
                                    SYNTAX Integer32 
                                    MAX-ACCESS read-only
                                    STATUS current
                                    DESCRIPTION "Total number of Failed
                                                outgoing calls"
                                    ::= { gr303IgStatsEntry 5 }

gr303IgStatsInCallSuccessful        OBJECT-TYPE
                                    SYNTAX Integer32 
                                    MAX-ACCESS read-only
                                    STATUS current
                                    DESCRIPTION "Total number successful
                                                incoming calls"
                                    ::= { gr303IgStatsEntry 6 }

gr303IgStatsInCallFailed            OBJECT-TYPE
                                    SYNTAX Integer32 
                                    MAX-ACCESS read-only
                                    STATUS current
                                    DESCRIPTION "Total number of Failed
                                                incoming calls"
                                    ::= { gr303IgStatsEntry 7 }


gr303IgStatsReset                   OBJECT-TYPE
                                    SYNTAX INTEGER {
                                        reset(1)
                                    }
                                    MAX-ACCESS read-write
                                    STATUS current
                                    DESCRIPTION "gr303Ig reset statistics
                                    button"
                                    ::= { gr303IgStatsEntry 8 }

-- The Connection Configuration Group connectionConfig

atmPvcVccTable        OBJECT-TYPE
                SYNTAX SEQUENCE OF AtmPvcVccEntry
                MAX-ACCESS not-accessible
                STATUS current
                DESCRIPTION "Table of PVC atm virtual channel connections"
                ::= { connectionConfig 1 }

atmPvcVccEntry        OBJECT-TYPE
                SYNTAX AtmPvcVccEntry
                MAX-ACCESS not-accessible
                STATUS current
                DESCRIPTION "Row definition of atm PVC VCC connections"
                INDEX { atmPvcVccIfA, atmPvcVccVpiA, atmPvcVccVciA, 
                        atmPvcVccIfB, atmPvcVccVpiB, atmPvcVccVciB }
                ::= { atmPvcVccTable 1 }

AtmPvcVccEntry        ::= SEQUENCE {
                atmPvcVccIfA                        IntfIndex,
                atmPvcVccVpiA                        INTEGER,
                atmPvcVccVciA                        INTEGER,
                atmPvcVccIfB                        IntfIndex,
                atmPvcVccVpiB                        INTEGER,
                atmPvcVccVciB                        INTEGER,
                atmPvcVccServiceTypeA2B                INTEGER,
                atmPvcVccSarTypeA2B                INTEGER,
                atmPvcVccPeakCellRateA2B        Integer32,
                atmPvcVccSusCellRateA2B                Integer32,
                atmPvcVccMaxBurstSizeA2B        Integer32,
                atmPvcVccServiceTypeB2A                INTEGER,
                atmPvcVccSarTypeB2A                INTEGER,
                atmPvcVccPeakCellRateB2A        Integer32,
                atmPvcVccSusCellRateB2A                Integer32,
                atmPvcVccMaxBurstSizeB2A        Integer32,
                atmPvcVccType                        INTEGER,
                atmPvcVccFlow                        INTEGER,
                atmPvcVccRowStatus                RowStatus,
                atmPvcVccFrwdErrCorrectionA2B        INTEGER,
                atmPvcVccFrwdErrCorrectionB2A        INTEGER,
                atmPvcVccConnectionStatus        INTEGER,
                atmPvcVccOamStatus                INTEGER,

                atmPvcVccDualHomed                INTEGER,

                atmPvcVccViA                    INTEGER,
                atmPvcVccViB                    INTEGER,
                atmPvcVccCnfrmTypeA2B           INTEGER,
                atmPvcVccCnfrmTypeB2A           INTEGER,

                atmPvcVccVUNIA                  INTEGER,
                atmPvcVccVUNIB                  INTEGER,

                atmPvcVccOamStatusB             INTEGER,
                atmPvcVccOAMConnEndPtStatusA    INTEGER,
                atmPvcVccOAMConnEndPtStatusB    INTEGER,
                atmPvcVccOAMConnSegEndPtStatusA INTEGER,
                atmPvcVccOAMConnSegEndPtStatusB INTEGER,
                atmPvcVccMfsA2B                 INTEGER,
                atmPvcVccMfsB2A                 INTEGER,
                atmPvcVccConnFailureCauseA      AtmConnFailureCause,
                atmPvcVccConnFailureCauseB      AtmConnFailureCause,
                atmPvcVccTrafficShapingA2B      INTEGER,
                atmPvcVccTrafficShapingB2A      INTEGER
 
                }

atmPvcVccIfA        OBJECT-TYPE
                SYNTAX IntfIndex
                MAX-ACCESS not-accessible
                STATUS current
                DESCRIPTION "Interface index for side A of an ATM-to-ATM PVC VCC
                             connection.  Number value is interpreted as an
                             interface of the form, SSPPCCC, where SS is the 
                             card slot, PP is the port number, and CCC is the 
                             channel number."
                ::= { atmPvcVccEntry 1 }

atmPvcVccVpiA        OBJECT-TYPE
                SYNTAX INTEGER (0..4095)
                MAX-ACCESS not-accessible
                STATUS current
                DESCRIPTION "VPI value for side A of an ATM-to-ATM PVC VCC 
                             connection.  Valid range is a number between 0 and 
                             4095."
                ::= { atmPvcVccEntry 2 }

atmPvcVccVciA        OBJECT-TYPE
                SYNTAX INTEGER (0..65535)
                MAX-ACCESS not-accessible
                STATUS current
                DESCRIPTION "VCI value for side A of an ATM-to-ATM PVC VCC 
                             connection.  Valid range is a number between 0 and 
                             65535."
                ::= { atmPvcVccEntry 3 }

atmPvcVccIfB        OBJECT-TYPE
                SYNTAX IntfIndex
                MAX-ACCESS not-accessible
                STATUS current
                DESCRIPTION "Interface index for side B of an ATM-to-ATM PVC VCC
                             connection.  Number value is interpreted as an
                             interface of the form, SSPPCCC, where SS is the 
                             card slot, PP is the port number, and CCC is the 
                             channel number."
                ::= { atmPvcVccEntry 4 }

atmPvcVccVpiB        OBJECT-TYPE
                SYNTAX INTEGER (0..4095)
                MAX-ACCESS not-accessible
                STATUS current
                DESCRIPTION "VPI value for side B of an ATM-to-ATM PVC VCC 
                             connection.  Valid range is a number between 0 and 
                             4095."
                ::= { atmPvcVccEntry 5 }

atmPvcVccVciB        OBJECT-TYPE
                SYNTAX INTEGER (0..65535)
                MAX-ACCESS not-accessible
                STATUS current
                DESCRIPTION "VCI value for side B of an ATM-to-ATM PVC VCC 
                             connection.  Valid range is a number between 0 and 
                             65535."
                ::= { atmPvcVccEntry 6 }

atmPvcVccServiceTypeA2B OBJECT-TYPE
                SYNTAX INTEGER  {
                                ubr(1),
                                vbr-nrt2(2),
                                vbr-nrt1(3),
                                vbr-rt2(4),
                                vbr-rt1(5),
                                vbr-express(6),
                                cbr4(7),
                                cbr3(8),
                                cbr2(9),
                                cbr1(10),
                                gfr2(11)
                                }
                MAX-ACCESS read-write
                STATUS current
                DESCRIPTION "service type"
                DEFVAL { ubr }
                ::= { atmPvcVccEntry 7 }

atmPvcVccSarTypeA2B OBJECT-TYPE
                SYNTAX INTEGER  {
                                aal5(1),
                                aal3-4(2),
                                aal2(3),
                                aal1(4),
                                null(5)
                                }
                MAX-ACCESS read-write
                STATUS current
                DESCRIPTION "SAR type used in atm adaption"
                DEFVAL { null }
                ::= { atmPvcVccEntry 8 }

atmPvcVccPeakCellRateA2B        OBJECT-TYPE
                SYNTAX Integer32
                MAX-ACCESS read-write
                STATUS current
                DESCRIPTION "peak cell rate - side A, in cell per second"
                DEFVAL { 1 }
                ::= { atmPvcVccEntry 10 }

atmPvcVccSusCellRateA2B        OBJECT-TYPE
                SYNTAX Integer32
                MAX-ACCESS read-write
                STATUS current
                DESCRIPTION "sustained rate - side A, in cell per second"
                DEFVAL { 1 }
                ::= { atmPvcVccEntry 11 }

atmPvcVccMaxBurstSizeA2B        OBJECT-TYPE
                SYNTAX Integer32
                MAX-ACCESS read-write
                STATUS current
                DESCRIPTION "maximum burst size - side A, in cells"
                DEFVAL { 1 }
                ::= { atmPvcVccEntry 12 }

atmPvcVccServiceTypeB2A OBJECT-TYPE
                SYNTAX INTEGER  {
                                ubr(1),
                                vbr-nrt2(2),
                                vbr-nrt1(3),
                                vbr-rt2(4),
                                vbr-rt1(5),
                                vbr-express(6),
                                cbr4(7),
                                cbr3(8),
                                cbr2(9),
                                cbr1(10),
                                gfr2(11)
                                }
                MAX-ACCESS read-write
                STATUS current
                DESCRIPTION "service type"
                DEFVAL { ubr }
                ::= { atmPvcVccEntry 13 }

atmPvcVccSarTypeB2A OBJECT-TYPE
                SYNTAX INTEGER  {
                                aal5(1),
                                aal3-4(2),
                                aal2(3),
                                aal1(4),
                                null(5)
                                }
                MAX-ACCESS read-write
                STATUS current
                DESCRIPTION "sar type used in atm adaption"
                DEFVAL { null }
                ::= { atmPvcVccEntry 14 }

atmPvcVccPeakCellRateB2A        OBJECT-TYPE
                SYNTAX Integer32
                MAX-ACCESS read-write
                STATUS current
                DESCRIPTION "peak rate - side B, in cell per second."
                DEFVAL { 1 }
                ::= { atmPvcVccEntry 16 }

atmPvcVccSusCellRateB2A        OBJECT-TYPE
                SYNTAX Integer32
                MAX-ACCESS read-write
                STATUS current
                DESCRIPTION "sustained rate - side B, in cell per second."
                DEFVAL { 1 }
                ::= { atmPvcVccEntry 17 }

atmPvcVccMaxBurstSizeB2A        OBJECT-TYPE
                SYNTAX Integer32
                MAX-ACCESS read-write
                STATUS current
                DESCRIPTION "maximum burst size - side B, in cells."
                DEFVAL { 1 }
                ::= { atmPvcVccEntry 18 }



atmPvcVccType        OBJECT-TYPE
                SYNTAX INTEGER  {
                                nonsecured(1),
                                secured(2)
                                }
                MAX-ACCESS read-write
                STATUS current
                DESCRIPTION "type of connection"
                DEFVAL { nonsecured }
                ::= { atmPvcVccEntry 20 }

atmPvcVccFlow        OBJECT-TYPE
                SYNTAX INTEGER  {
                                duplex(1),
                                simplexA2B(2),
                                pointToMultipointA2B(3)
                                }
                MAX-ACCESS read-write
                STATUS current
                DESCRIPTION "type of flow"
                DEFVAL { duplex }
                ::= { atmPvcVccEntry 21 }

atmPvcVccRowStatus        OBJECT-TYPE
                SYNTAX RowStatus
                MAX-ACCESS read-write
                STATUS current
                DESCRIPTION "row status"
                ::= { atmPvcVccEntry 22 }

atmPvcVccFrwdErrCorrectionA2B OBJECT-TYPE
                SYNTAX INTEGER {
                                none(1),
                                eighthRate(2),
                                quarterRate(3),
                                halfRate(4),
                                autoHiQ(5),
                                auto(6),
                                autoLoQ(7)
                               }
                MAX-ACCESS read-write
                STATUS current
                DESCRIPTION "Forward error correction scheme"
                DEFVAL { none }
                ::= { atmPvcVccEntry 23 }

atmPvcVccFrwdErrCorrectionB2A OBJECT-TYPE
                SYNTAX INTEGER {
                                none(1),
                                eighthRate(2),
                                quarterRate(3),
                                halfRate(4),
                                autoHiQ(5),
                                auto(6),
                                autoLoQ(7)
                               }
                MAX-ACCESS read-write
                STATUS current
                DESCRIPTION "Forward error correction scheme"
                DEFVAL { none }
                ::= { atmPvcVccEntry 24 }

atmPvcVccConnectionStatus OBJECT-TYPE
                SYNTAX INTEGER {
                                active(1),
                                inactive(2),
                                inactiveA2B-B2A(3),
                                inactiveA2B(4),
                                inactiveB2A(5)
                               }
                MAX-ACCESS read-only
                STATUS current
                DESCRIPTION "Indicates the current connections status.
                             Active:  All interfaces through which the 
                                      connection is going are in service.
                             Inactive:  One of the end interfaces of the 
                                        connection is not in service.

                             The rest of the states apply to connections going
                             through resource interfaces like DSP2 and FEC.  These
                             interfaces are dynamically allocated.

                             InactiveA2B-B2A:  Both the A2B and B2A resource
                                               interfaces are not in service.
                             InactiveA2B:  The A2B resource interface is not in 
                                           service.
                             InactiveB2A:  The B2A resource interface is not in 
                                           service.

                             If an end interface and the resource interfaces 
                             are out of service, the status will be inactive 
                             because the end interfaces take priority."
                DEFVAL { inactive }
                ::= { atmPvcVccEntry 25 }

atmPvcVccOamStatus OBJECT-TYPE
                SYNTAX INTEGER {
                                unsupp(1),
                                end-Pt(2),
                                seg-Pt(3),
                                end-Seg-Pt(4),
                                intermediate-Pt(5),
                                intra-Segment-Pt (6)
                               }
                MAX-ACCESS read-write
                STATUS current
                DESCRIPTION "Indicates the OAM monitoring status of side A.
                             The 5 possible states are:
                             Unsupp:  No monitoring enabled.
                             End-Pt:  A side is only an end point, therefore
                                it will respond to AIS/RDI.
                             Seg-Pt:  A side is only a segment point, therefore
                                it will only respond to maintenance OAM cells
                                and not fault cells.
                             End-Seg-Pt:  A side is both an end point and a
                                segment point.
                             Intermediate-Pt:  It will only generate AIS during
                                local failure.

                             For ATM-to-ATM connections the OAM status will be
                             symmetric on both sides of the connection."
                DEFVAL { unsupp }
                ::= { atmPvcVccEntry 26 }


atmPvcVccDualHomed OBJECT-TYPE
                SYNTAX INTEGER {
                                no(1),
                                yes(2)
                               }
                MAX-ACCESS read-only
                STATUS current
                DESCRIPTION "Does this PVC need a backup Dual homing PVC."
                DEFVAL { no }
                ::= { atmPvcVccEntry 27 }


atmPvcVccViA    OBJECT-TYPE
                SYNTAX INTEGER (0..1024)
                MAX-ACCESS read-write
                STATUS current
                DESCRIPTION "VI to associate the Egress part of the
                        B2A connection ."
                DEFVAL { 0 }
                ::= { atmPvcVccEntry 28 }

atmPvcVccViB    OBJECT-TYPE
                SYNTAX INTEGER (0..1024)
                MAX-ACCESS read-write
                STATUS current
                DESCRIPTION "VI to associate the Egress part of the
                        A2B connection ."
                DEFVAL { 0 }
                ::= { atmPvcVccEntry 29 }

atmPvcVccCnfrmTypeA2B    OBJECT-TYPE
                SYNTAX INTEGER {
                                best-effort(1),
                                one-bucket-notag-0plus1(2),
                                two-bucket-notag-0plus1-0plus1(3),
                                two-bucket-notag-0plus1-0(4),
                                two-bucket-tag-0plus1-0(5),
                                best-effort-tag(6)
                                }
                MAX-ACCESS read-write
                STATUS current
                DESCRIPTION "The following is the description of this field
                                This will be used in conjunction with the
                                service type field to get the correct
                                traffic behaviour. In the conformances the
                                the 0 or 0plus1 refers to the clp bit in the
                                cells. If 0plus1 is the bucket reference then
                                the clp bit is ignored. If 0 is specified for
                                the bucket then check only clp=0 cells.
                                1: Best Effort will try to send all cellsin a
                                best effort way. This will follow the
                                Aqueman Algorithm
                                2: one_bucket_notag_0plus1 will use 1 bucket
                                i.e is the PCR(0+1) bucket and drop all
                                cells in excess.
                                3: two_bucket_notag_0plus1_0plus1 uses 2 buckets.
                                The 2 buckets are pcr(0+1) and scr(0+1).
                                All cells conforming to both buckets will be
                                passed through. The rest will be dropped.
                                4: two_bucket_notag_0plus1_0 uses 2 buckets.
                                The 2 buckets are pcr(0+1) and scr(0) or
                                pcr(0). Cells which conform to both buckets
                                are passed through. The rest are dropped.
                                5: two_bucket_tag_0plus1_0 uses 2 buckets.
                                The 2 buckets are pcr(0+1) and scr(0) or
                                pcr(0). Cells which do not conform to the first
                                bucket are dropped. Cells which do not
                                conform to the 2nd bucket are tagged.
                                6: best_effort_tag. Tag all cells and then
                                do a best effort. "
                DEFVAL { best-effort }
                ::= { atmPvcVccEntry 30 }

atmPvcVccCnfrmTypeB2A    OBJECT-TYPE
                SYNTAX INTEGER {
                                    best-effort(1),
                                one-bucket-notag-0plus1(2),
                                two-bucket-notag-0plus1-0plus1(3),
                                two-bucket-notag-0plus1-0(4),
                                two-bucket-tag-0plus1-0(5),
                                best-effort-tag(6)
                                }
                MAX-ACCESS read-write
                STATUS current
                DESCRIPTION "The following is the description of this field
                                This will be used in conjunction with the
                                service type field to get the correct
                                traffic behaviour. In the conformances the
                                the 0 or 0plus1 refers to the clp bit in the
                                cells. If 0plus1 is the bucket reference then
                                the clp bit is ignored. If 0 is specified for
                                the bucket then check only clp=0 cells.
                                1: Best Effort will try to send all cellsin a
                                best effort way. This will follow the
                                Aqueman Algorithm
                                2: one_bucket_notag_0plus1 will use 1 bucket
                                i.e is the PCR(0+1) bucket and drop all
                                cells in excess.
                                3: two_bucket_notag_0plus1_0plus1 uses 2 buckets.
                                The 2 buckets are pcr(0+1) and scr(0+1).
                                All cells conforming to both buckets will be
                                passed through. The rest will be dropped.
                                4: two_bucket_notag_0plus1_0 uses 2 buckets.
                                The 2 buckets are pcr(0+1) and scr(0) or
                                pcr(0). Cells which conform to both buckets
                                are passed through. The rest are dropped.
                                5: two_bucket_tag_0plus1_0 uses 2 buckets.
                                The 2 buckets are pcr(0+1) and scr(0) or
                                pcr(0). Cells which do not conform to the first
                                bucket are dropped. Cells which do not
                                conform to the 2nd bucket are tagged.
                                6: best_effort_tag. Tag all cells and then
                                do a best effort. "
                DEFVAL { best-effort }
                ::= { atmPvcVccEntry 31 }


atmPvcVccVUNIA    OBJECT-TYPE
                SYNTAX INTEGER (0..255)
                MAX-ACCESS read-write
                STATUS current
                DESCRIPTION "VUNI to associate the Egress part of the
                        B2A connection ."
                ::= { atmPvcVccEntry 32 }

atmPvcVccVUNIB    OBJECT-TYPE
                SYNTAX INTEGER (0..255)
                MAX-ACCESS read-write
                STATUS current
                DESCRIPTION "VUNI to associate the Egress part of the
                        A2B connection ."
                ::= { atmPvcVccEntry 33 }



atmPvcVccOamStatusB OBJECT-TYPE
                 SYNTAX INTEGER {
                                unsupp(1),
                                end-Pt(2),
                                seg-Pt(3),
                                end-Seg-Pt(4),
                                intermediate-Pt(5),
                                intra-Segment-Pt (6)
                                }
                 MAX-ACCESS read-write
                STATUS current
                DESCRIPTION "Indicates the Oam monitoring status of side B 
                        of an internal connection. Refer to ITU I.610 and
                        Bellcore GR1248-CORE for definitions.
                        The 6 possible states are:
                        Unsupp:  No OAM cell monitoring or generation 
                                enabled. All OAM flows are transparently 
                                passed through.
                        End-Pt:  Connection endPoint, segment flows are 
                                discarded.
                        Seg-Pt:  Segment endPoint.
                        End-Seg-Pt: Connection endPoint that is also
                                a segment endPoint.  
                        Intermediate-Pt: Connecting point, that is 
                                outside any segment.  Generates only ete 
                                flows.
                        Intra-Segment-Pt: Connecting point with a segment.
                        Generates ete as well as segment flows."
                 DEFVAL { unsupp }
                 ::= { atmPvcVccEntry 34 }

atmPvcVccOAMConnEndPtStatusA    OBJECT-TYPE
                 SYNTAX INTEGER {
                                ete-active(1),
                                ete-ais-state(2),
                                ete-rdi-state(3),
                                ete-ais-rdi-state(4)
                                }
                MAX-ACCESS read-only
                STATUS current
                DESCRIPTION "Connection endpoint side A status. Valid only at 
                        connection endpoint."
                ::= { atmPvcVccEntry 35 }

atmPvcVccOAMConnEndPtStatusB    OBJECT-TYPE
                 SYNTAX INTEGER {
                                ete-active(1),
                                ete-ais-state(2),
                                ete-rdi-state(3),
                                ete-ais-rdi-state(4)
                                }
                MAX-ACCESS read-only
                STATUS current
                DESCRIPTION "Connection endpoint side B status. Valid only at 
                        connection endpoint."
                ::= { atmPvcVccEntry 36 }

atmPvcVccOAMConnSegEndPtStatusA    OBJECT-TYPE
                 SYNTAX INTEGER {
                                seg-active(1),
                                seg-ais-state(2),
                                seg-rdi-state(3),
                                seg-ais-rdi-state(4)
                                }
                MAX-ACCESS read-only
                STATUS current
                DESCRIPTION "Segment endpoint side A status. Valid only at 
                        segment endpoints."
                 ::= { atmPvcVccEntry 37 }

atmPvcVccOAMConnSegEndPtStatusB    OBJECT-TYPE
                 SYNTAX INTEGER {
                                seg-active(1),
                                seg-ais-state(2),
                                seg-rdi-state(3),
                                seg-ais-rdi-state(4)
                                }
                MAX-ACCESS read-only
                STATUS current
                DESCRIPTION "Segment endpoint side B status. Valid only at 
                        segment endpoints."
                ::= { atmPvcVccEntry 38 }

atmPvcVccMfsA2B OBJECT-TYPE
                SYNTAX INTEGER (1..65535)
                MAX-ACCESS read-write
                STATUS current
                DESCRIPTION "Maximum Frame Size for GFR traffic for A2B dir"
                DEFVAL { 1 }
                ::= { atmPvcVccEntry 39 }
                
atmPvcVccMfsB2A OBJECT-TYPE
                SYNTAX INTEGER (1..65535)
                MAX-ACCESS read-write
                STATUS current
                DESCRIPTION "Maximum Frame Size for GFR traffic for B2A dir"
                DEFVAL { 1 }
                ::= { atmPvcVccEntry 40 }

 atmPvcVccConnFailureCauseA    OBJECT-TYPE
                SYNTAX AtmConnFailureCause
                MAX-ACCESS read-only
                STATUS current
                DESCRIPTION " connestion status reason code"
                ::= { atmPvcVccEntry 41 }

atmPvcVccConnFailureCauseB    OBJECT-TYPE
                SYNTAX AtmConnFailureCause
                MAX-ACCESS read-only
                STATUS current
                DESCRIPTION "connection status reason code"
                ::= { atmPvcVccEntry 42 }

atmPvcVccTrafficShapingA2B      OBJECT-TYPE
                SYNTAX INTEGER {
                                disabled(1),
                                enabled(2)
                               }
                MAX-ACCESS read-write
                STATUS current
                DESCRIPTION "Traffic Shaping Support in the A2B direction."
                DEFVAL { disabled }
                ::= { atmPvcVccEntry 43 }

atmPvcVccTrafficShapingB2A      OBJECT-TYPE
		SYNTAX INTEGER {
                                disabled(1),
                                enabled(2)
                               }
                MAX-ACCESS read-write
                STATUS current
                DESCRIPTION "Traffic Shaping Support in the B2A direction."
                DEFVAL { disabled }
                ::= { atmPvcVccEntry 44 }

atmPvcVpcTable        OBJECT-TYPE
                SYNTAX SEQUENCE OF AtmPvcVpcEntry
                MAX-ACCESS not-accessible
                STATUS current
                DESCRIPTION "Table of PVC atm virtual path connections"
                ::= { connectionConfig 2 }

atmPvcVpcEntry        OBJECT-TYPE
                SYNTAX AtmPvcVpcEntry
                MAX-ACCESS not-accessible
                STATUS current
                DESCRIPTION "Row definition of atm connections"
                INDEX { atmPvcVpcIfA, atmPvcVpcVpiA, 
                        atmPvcVpcIfB, atmPvcVpcVpiB }
                ::= { atmPvcVpcTable 1 }

AtmPvcVpcEntry        ::= SEQUENCE {
                atmPvcVpcIfA                        IntfIndex,
                atmPvcVpcVpiA                        INTEGER,
                atmPvcVpcIfB                        IntfIndex,
                atmPvcVpcVpiB                        INTEGER,
                atmPvcVpcServiceTypeA2B                INTEGER,
                atmPvcVpcSarTypeA2B                INTEGER,
                atmPvcVpcPeakCellRateA2B        Integer32,
                atmPvcVpcSusCellRateA2B                Integer32,
                atmPvcVpcMaxBurstSizeA2B        Integer32,
                atmPvcVpcServiceTypeB2A                INTEGER,
                atmPvcVpcSarTypeB2A                INTEGER,
                atmPvcVpcPeakCellRateB2A        Integer32,
                atmPvcVpcSusCellRateB2A                Integer32,
                atmPvcVpcMaxBurstSizeB2A        Integer32,
                atmPvcVpcType                        INTEGER,
                atmPvcVpcFlow                        INTEGER,
                atmPvcVpcRowStatus                RowStatus,
                atmPvcVpcConnectionStatus        INTEGER,
                atmPvcVpcOamStatus                INTEGER,

                atmPvcVpcDualHomed                INTEGER,

                atmPvcVpcViA                    INTEGER,
                atmPvcVpcViB                    INTEGER,
                atmPvcVpcCnfrmTypeA2B           INTEGER,
                atmPvcVpcCnfrmTypeB2A           INTEGER,

                atmPvcVpcVUNIA                  INTEGER,
                atmPvcVpcVUNIB                  INTEGER,

                atmPvcVpcOamStatusB             INTEGER,
                atmPvcVpcOAMConnEndPtStatusA    INTEGER,
                atmPvcVpcOAMConnEndPtStatusB    INTEGER,
                atmPvcVpcOAMConnSegEndPtStatusA INTEGER,
                atmPvcVpcOAMConnSegEndPtStatusB INTEGER,
                atmPvcVpcConnFailureCauseA        AtmConnFailureCause,
                atmPvcVpcConnFailureCauseB        AtmConnFailureCause,
                atmPvcVpcTrafficShapingA2B      INTEGER,
		atmPvcVpcTrafficShapingB2A      INTEGER
                }

atmPvcVpcIfA        OBJECT-TYPE
                SYNTAX IntfIndex
                MAX-ACCESS not-accessible
                STATUS current
                DESCRIPTION "Interface index for side A of an ATM-to-ATM PVC VPC
                             connection.  Number value is interpreted as an
                             interface of the form, SSPPCCC, where SS is the 
                             card slot, PP is the port number, and CCC is the 
                             channel number."
                ::= { atmPvcVpcEntry 1 }

atmPvcVpcVpiA        OBJECT-TYPE
                SYNTAX INTEGER (0..4095)
                MAX-ACCESS not-accessible
                STATUS current
                DESCRIPTION "VPI value for side A of an ATM-to-ATM PVC VPC 
                             connection.  Valid range is a number between 0 and 
                             4095."
                ::= { atmPvcVpcEntry 2 }

atmPvcVpcIfB        OBJECT-TYPE
                SYNTAX IntfIndex
                MAX-ACCESS not-accessible
                STATUS current
                DESCRIPTION "Interface index for side B of an ATM-to-ATM PVC VPC
                             connection.  Number value is interpreted as an
                             interface of the form, SSPPCCC, where SS is the 
                             card slot, PP is the port number, and CCC is the 
                             channel number."
                ::= { atmPvcVpcEntry 3 }

atmPvcVpcVpiB        OBJECT-TYPE
                SYNTAX INTEGER (0..4095)
                MAX-ACCESS not-accessible
                STATUS current
                DESCRIPTION "VPI value for side B of an ATM-to-ATM PVC VPC 
                             connection.  Valid range is a number between 0 and 
                             4095."
                ::= { atmPvcVpcEntry 4 }

atmPvcVpcServiceTypeA2B        OBJECT-TYPE
                SYNTAX INTEGER  {
                                ubr(1),
                                vbr-nrt2(2),
                                vbr-nrt1(3),
                                vbr-rt2(4),
                                vbr-rt1(5),
                                vbr-express(6),
                                cbr4(7),
                                cbr3(8),
                                cbr2(9),
                                cbr1(10)
                                }
                MAX-ACCESS read-write
                STATUS current
                DESCRIPTION "service type"
                DEFVAL { ubr }
                ::= { atmPvcVpcEntry 5 }

atmPvcVpcSarTypeA2B OBJECT-TYPE
                SYNTAX INTEGER  {
                                aal5(1),
                                aal3-4(2),
                                aal2(3),
                                aal1(4),
                                null(5)
                                }
                MAX-ACCESS read-write
                STATUS current
                DESCRIPTION "SAR Type"
                DEFVAL { null }
                ::= { atmPvcVpcEntry 6 }

atmPvcVpcPeakCellRateA2B        OBJECT-TYPE
                SYNTAX Integer32
                MAX-ACCESS read-write
                STATUS current
                DESCRIPTION "peak rate - side A, in cell per second."
                DEFVAL { 1 }
                ::= { atmPvcVpcEntry 8 }

atmPvcVpcSusCellRateA2B        OBJECT-TYPE
                SYNTAX Integer32
                MAX-ACCESS read-write
                STATUS current
                DESCRIPTION "sustained rate - side A, in cell per second."
                DEFVAL { 1 }
                ::= { atmPvcVpcEntry 9 }

atmPvcVpcMaxBurstSizeA2B        OBJECT-TYPE
                SYNTAX Integer32
                MAX-ACCESS read-write
                STATUS current
                DESCRIPTION "maximum burst size - side A, in cell per second."
                DEFVAL { 1 }
                ::= { atmPvcVpcEntry 10 }

atmPvcVpcServiceTypeB2A        OBJECT-TYPE
                SYNTAX INTEGER  {
                                ubr(1),
                                vbr-nrt2(2),
                                vbr-nrt1(3),
                                vbr-rt2(4),
                                vbr-rt1(5),
                                vbr-express(6),
                                cbr4(7),
                                cbr3(8),
                                cbr2(9),
                                cbr1(10)
                                }
                MAX-ACCESS read-write
                STATUS current
                DESCRIPTION "service type"
                DEFVAL { ubr }
                ::= { atmPvcVpcEntry 11 }

atmPvcVpcSarTypeB2A OBJECT-TYPE
                SYNTAX INTEGER  {
                                aal5(1),
                                aal3-4(2),
                                aal2(3),
                                aal1(4),
                                null(5)
                                }
                MAX-ACCESS read-write
                STATUS current
                DESCRIPTION "SAR Type"
                DEFVAL { null }
                ::= { atmPvcVpcEntry 12 }

atmPvcVpcPeakCellRateB2A        OBJECT-TYPE
                SYNTAX Integer32
                MAX-ACCESS read-write
                STATUS current
                DESCRIPTION "peak rate - side B, in cell per second."
                DEFVAL { 1 }
                ::= { atmPvcVpcEntry 14 }

atmPvcVpcSusCellRateB2A        OBJECT-TYPE
                SYNTAX Integer32
                MAX-ACCESS read-write
                STATUS current
                DESCRIPTION "sustained rate - side B, in cell per second."
                DEFVAL { 1 }
                ::= { atmPvcVpcEntry 15 }

atmPvcVpcMaxBurstSizeB2A        OBJECT-TYPE
                SYNTAX Integer32
                MAX-ACCESS read-write
                STATUS current
                DESCRIPTION "maximum burst size - side B, in cell per second."
                DEFVAL { 1 }
                ::= { atmPvcVpcEntry 16 }

atmPvcVpcType        OBJECT-TYPE
                SYNTAX INTEGER {
                                nonsecured(1),
                                secured(2)
                               }
                MAX-ACCESS read-write
                STATUS current
                DESCRIPTION "security feature type"
                DEFVAL { nonsecured }
                ::= { atmPvcVpcEntry 17 }

atmPvcVpcFlow        OBJECT-TYPE
                SYNTAX INTEGER {
                                duplex(1),
                                simplexA2B(2),
                                pointToMultipointA2B(3)
                               }
                MAX-ACCESS read-write
                STATUS current
                DESCRIPTION "flow type"
                DEFVAL { duplex }
                ::= { atmPvcVpcEntry 18 }

atmPvcVpcRowStatus        OBJECT-TYPE
                SYNTAX RowStatus
                MAX-ACCESS read-write
                STATUS current
                DESCRIPTION "row status"
                ::= { atmPvcVpcEntry 19 }

atmPvcVpcConnectionStatus OBJECT-TYPE
                SYNTAX INTEGER {
                                active(1),
                                inactive(2),
                                inactiveA2B-B2A(3),
                                inactiveA2B(4),
                                inactiveB2A(5)
                               }
                MAX-ACCESS read-only
                STATUS current
                DESCRIPTION "Indicates the current connections status.
                             Active:  All interfaces through which the 
                                      connection is going are in service.
                             Inactive:  One of the end interfaces of the 
                                        connection is not in service.

                             The rest of the states apply to connections going
                             through resource interfaces like DSP2 and FEC.  These
                             interfaces are dynamically allocated.

                             InactiveA2B-B2A:  Both the A2B and B2A resource
                                               interfaces are not in service.
                             InactiveA2B:  The A2B resource interface is not in 
                                           service.
                             InactiveB2A:  The B2A resource interface is not in 
                                           service.

                             If an end interface and the resource interfaces 
                             are out of service, the status will be inactive 
                             because the end interfaces take priority."
                DEFVAL { inactive }
                ::= { atmPvcVpcEntry 20 }

atmPvcVpcOamStatus OBJECT-TYPE
                SYNTAX INTEGER {
                                unsupp(1),
                                end-Pt(2),
                                seg-Pt(3),
                                end-Seg-Pt(4),
                                intermediate-Pt(5),
                                intra-Segment-Pt(6)
                               }
                MAX-ACCESS read-write
                STATUS current
                DESCRIPTION "Indicates the OAM monitoring status of side A.
                             The 5 possible states are:
                             Unsupp:  No monitoring enabled.
                             End-Pt:  A side is only an end point, therefore
                                it will respond to AIS/RDI.
                             Seg-Pt:  A side is only a segment point, therefore
                                it will only respond to maintenance OAM cells
                                and not fault cells.
                             End-Seg-Pt:  A side is both an end point and a
                                segment point.
                             Intermediate-Pt:  It will only generate AIS during
                                local failure.

                             For ATM-to-ATM connections the OAM status will be
                             symmetric on both sides of the connection."
                DEFVAL { unsupp }
                ::= { atmPvcVpcEntry 21 }


atmPvcVpcDualHomed OBJECT-TYPE
                SYNTAX INTEGER {
                                no(1),
                                yes(2)
                               }
                MAX-ACCESS read-only
                STATUS current
                DESCRIPTION "Does this PVC need a backup Dual homing PVC."
                DEFVAL { no }
                ::= { atmPvcVpcEntry 22 }


atmPvcVpcViA        OBJECT-TYPE
                SYNTAX INTEGER (0..1024)
                MAX-ACCESS read-write
                STATUS current
                DESCRIPTION "VI to associate the Egress part of the 
                             B2A connection ."
                DEFVAL { 0 }
                ::= { atmPvcVpcEntry 23 }

atmPvcVpcViB        OBJECT-TYPE
                SYNTAX INTEGER (0..1024)
                MAX-ACCESS read-write
                STATUS current
                DESCRIPTION "VI to associate the Egress part of the 
                             A2B connection ."
                DEFVAL { 0 }
                ::= { atmPvcVpcEntry 24 }


atmPvcVpcCnfrmTypeA2B    OBJECT-TYPE
                SYNTAX INTEGER {
                                best-effort(1),
                                one-bucket-notag-0plus1(2),
                                two-bucket-notag-0plus1-0plus1(3),
                                two-bucket-notag-0plus1-0(4),
                                two-bucket-tag-0plus1-0(5),
                                best-effort-tag(6)
                               }
                MAX-ACCESS read-write
                STATUS current
                DESCRIPTION "The following is the description of this field
                        This will be used in conjunction with the
                        service type field to get the correct
                        traffic behaviour. In the conformances the 
                        the 0 or 0plus1 refers to the clp bit in the
                        cells. If 0plus1 is the bucket reference then
                        the clp bit is ignored. If 0 is specified for 
                        the bucket then check only clp=0 cells.
                        1: Best Effort will try to send all cellsin a 
                        best effort way. This will follow the 
                        Aqueman Algorithm
                        2: one-bucket-notag-0plus1 will use 1 bucket
                        i.e is the PCR(0+1) bucket and drop all
                        cells in excess.
                        3: two-bucket-notag-0plus1-0plus1 uses 2 buckets.
                        The 2 buckets are pcr(0+1) and scr(0+1).
                        All cells conforming to both buckets will be
                        passed through. The rest will be dropped.
                        4: two-bucket-notag-0plus1-0 uses 2 buckets.
                        The 2 buckets are pcr(0+1) and scr(0) or 
                        pcr(0). Cells which conform to both buckets
                        are passed through. The rest are dropped.
                        5: two-bucket-tag-0plus1-0 uses 2 buckets.
                        The 2 buckets are pcr(0+1) and scr(0) or 
                        pcr(0). Cells which do not conform to the first
                        bucket are dropped. Cells which do not 
                        conform to the 2nd bucket are tagged.
                        6: best-effort-tag. Tag all cells and then
                        do a best effort. "
    
                DEFVAL { best-effort }
                ::= { atmPvcVpcEntry 25 }

atmPvcVpcCnfrmTypeB2A    OBJECT-TYPE
                SYNTAX INTEGER {
                                    best-effort(1),
                                one-bucket-notag-0plus1(2),
                                two-bucket-notag-0plus1-0plus1(3),
                                two-bucket-notag-0plus1-0(4),
                                two-bucket-tag-0plus1-0(5),
                                best-effort-tag(6)
                               }
                MAX-ACCESS read-write
                STATUS current
                DESCRIPTION "The following is the description of this field
                        This will be used in conjunction with the
                        service type field to get the correct
                        traffic behaviour. In the conformances the 
                        the 0 or 0plus1 refers to the clp bit in the
                        cells. If 0plus1 is the bucket reference then
                        the clp bit is ignored. If 0 is specified for 
                        the bucket then check only clp=0 cells.
                        1: Best Effort will try to send all cellsin a 
                        best effort way. This will follow the 
                        Aqueman Algorithm
                        2: one-bucket-notag-0plus1 will use 1 bucket
                        i.e is the PCR(0+1) bucket and drop all
                        cells in excess.
                        3: two-bucket-notag-0plus1-0plus1 uses 2 buckets.
                        The 2 buckets are pcr(0+1) and scr(0+1).
                        All cells conforming to both buckets will be
                        passed through. The rest will be dropped.
                        4: two-bucket-notag-0plus1-0 uses 2 buckets.
                        The 2 buckets are pcr(0+1) and scr(0) or 
                        pcr(0). Cells which conform to both buckets
                        are passed through. The rest are dropped.
                        5: two-bucket-tag-0plus1-0 uses 2 buckets.
                        The 2 buckets are pcr(0+1) and scr(0) or 
                        pcr(0). Cells which do not conform to the first
                        bucket are dropped. Cells which do not 
                        conform to the 2nd bucket are tagged.
                        6: best-effort-tag. Tag all cells and then
                        do a best effort.  "
                DEFVAL { best-effort }
                ::= { atmPvcVpcEntry 26 }


atmPvcVpcVUNIA        OBJECT-TYPE
                SYNTAX INTEGER (0..255)
                MAX-ACCESS read-write
                STATUS current
                DESCRIPTION "VUNI Id to associate the Egress part of the 
                             B2A connection ."
                DEFVAL { 0 }
                ::= { atmPvcVpcEntry 27 }

atmPvcVpcVUNIB        OBJECT-TYPE
                SYNTAX INTEGER (0..255)
                MAX-ACCESS read-write
                STATUS current
                DESCRIPTION "VUNI Id to associate the Egress part of the 
                             A2B connection ."
                DEFVAL { 0 }
                ::= { atmPvcVpcEntry 28 }



atmPvcVpcOamStatusB OBJECT-TYPE
                SYNTAX INTEGER {
                                unsupp(1),
                                end-Pt(2),
                                seg-Pt(3),
                                end-Seg-Pt(4),
                                intermediate-Pt(5),
                                intra-Segment-Pt(6)
                                }
                MAX-ACCESS read-write
                STATUS current
                DESCRIPTION "Indicates the Oam monitoring status of side B
                        of an internal connection. Refer to ITU I.610 and
                        Bellcore GR1248-CORE for definitions.
                        The 6 possible states are:
                        Unsupp:  No OAM cell monitoring or generation 
                                enabled. All OAM flows are transparently 
                                passed through.
                        End-Pt:  Connection endPoint, segment flows are 
                                discarded.  
                        Seg-Pt:  Segment endPoint.
                              End-Seg-Pt: Connection endPoint that is also a 
                                segment endPoint.
                        Intermediate-Pt: Connecting point, that is outside 
                                any segment.  Generates only ete flows.  
                        Intra-Segment-Pt: Connecting point with a segment.
                                Generates ete as well as segment flows."
                 DEFVAL { unsupp }
                 ::= { atmPvcVpcEntry 29 }

atmPvcVpcOAMConnEndPtStatusA    OBJECT-TYPE
                 SYNTAX INTEGER {
                                ete-active(1),
                                ete-ais-state(2),
                                ete-rdi-state(3),
                                ete-ais-rdi-state(4)
                                }
                 MAX-ACCESS read-only
                STATUS current
                DESCRIPTION "Connection endpoint side A status. Valid only 
                        at connection endpoint."
                 ::= { atmPvcVpcEntry 30 }

atmPvcVpcOAMConnEndPtStatusB    OBJECT-TYPE
                 SYNTAX INTEGER {
                                ete-active(1),
                                ete-ais-state(2),
                                ete-rdi-state(3),
                                ete-ais-rdi-state(4)
                                }
                 MAX-ACCESS read-only
                STATUS current
                DESCRIPTION "Connection endpoint side B status. Valid only at 
                        connection endpoint."
                ::= { atmPvcVpcEntry 31 }

atmPvcVpcOAMConnSegEndPtStatusA    OBJECT-TYPE
                 SYNTAX INTEGER {
                                seg-active(1),
                                seg-ais-state(2),
                                seg-rdi-state(3),
                                seg-ais-rdi-state(4)
                                }
                MAX-ACCESS read-only
                STATUS current
                DESCRIPTION "Segment endpoint side A status. Valid only at 
                        segment/connection endpoints."
                ::= { atmPvcVpcEntry 32 }

atmPvcVpcOAMConnSegEndPtStatusB    OBJECT-TYPE
                 SYNTAX INTEGER {
                                seg-active(1),
                                seg-ais-state(2),
                                seg-rdi-state(3),
                                seg-ais-rdi-state(4)
                                }
                MAX-ACCESS read-only
                STATUS current
                 DESCRIPTION "Segment endpoint side B status. Valid only at 
                        segment/connection endpoints."
                 ::= { atmPvcVpcEntry 33 }

atmPvcVpcConnFailureCauseA    OBJECT-TYPE
                SYNTAX AtmConnFailureCause
                MAX-ACCESS read-only
                STATUS current
                DESCRIPTION " connestion status reason code"
                ::= { atmPvcVpcEntry 34 }

atmPvcVpcConnFailureCauseB    OBJECT-TYPE
                SYNTAX AtmConnFailureCause
                MAX-ACCESS read-only
                STATUS current
                DESCRIPTION "connection status reason code"
                ::= { atmPvcVpcEntry 35 }

atmPvcVpcTrafficShapingA2B     OBJECT-TYPE
          SYNTAX INTEGER {
                          disabled(1),
                          enabled(2)
                         }
                MAX-ACCESS read-write
                STATUS current
                DESCRIPTION "Traffic Shaping Support in the A2B direction."
                DEFVAL { disabled }
                ::= { atmPvcVpcEntry 36 }

atmPvcVpcTrafficShapingB2A     OBJECT-TYPE
                SYNTAX INTEGER {
                                disabled(1),
                                enabled(2)
                               }
                MAX-ACCESS read-write
                STATUS current
                DESCRIPTION "Traffic Shaping Support in the B2A direction."
                DEFVAL { disabled }
          ::= { atmPvcVpcEntry 37 }

atmSvcVccTable        OBJECT-TYPE
                SYNTAX SEQUENCE OF AtmSvcVccEntry
                MAX-ACCESS not-accessible
                STATUS current
                DESCRIPTION "Table of atm connections"
                ::= { connectionConfig 3 }

atmSvcVccEntry        OBJECT-TYPE
                SYNTAX AtmSvcVccEntry
                MAX-ACCESS not-accessible
                STATUS current
                DESCRIPTION "Row definition of atm connections"
                INDEX { atmSvcVccIfA, atmSvcVccVpiA, 
                        atmSvcVccVciA, atmSvcVccIfB, 
                        atmSvcVccVpiB, atmSvcVccVciB }
                ::= { atmSvcVccTable 1 }

AtmSvcVccEntry        ::= SEQUENCE {
                atmSvcVccIfA                        IntfIndex,
                atmSvcVccVpiA                       INTEGER,
                atmSvcVccVciA                       INTEGER,
                atmSvcVccIfB                        IntfIndex,
                atmSvcVccVpiB                       INTEGER,
                atmSvcVccVciB                       INTEGER,
                atmSvcVccServiceTypeA2B             INTEGER,
                atmSvcVccSarTypeA2B                 INTEGER,
                atmSvcVccPeakCellRateA2B            Integer32,
                atmSvcVccSusCellRateA2B             Integer32,
                atmSvcVccMaxBurstSizeA2B            Integer32,
                atmSvcVccServiceTypeB2A             INTEGER,
                atmSvcVccSarTypeB2A                 INTEGER,
                atmSvcVccPeakCellRateB2A            Integer32,
                atmSvcVccSusCellRateB2A             Integer32,
                atmSvcVccMaxBurstSizeB2A            Integer32,
                atmSvcVccFlow                       INTEGER,
                atmSvcVccType                       INTEGER,
                atmSvcVccConnectionStatus           INTEGER,
                atmSvcVccViA                        INTEGER,
                atmSvcVccViB                        INTEGER,
                atmSvcVccCnfrmTypeA2B               INTEGER,
                atmSvcVccCnfrmTypeB2A               INTEGER

                ,atmSvcVccVUNIA                     INTEGER,
                 atmSvcVccVUNIB                     INTEGER

                ,atmSvcVccTrafficShapingA2B         INTEGER,
                atmSvcVccTrafficShapingB2A          INTEGER

                }

atmSvcVccIfA        OBJECT-TYPE
                SYNTAX IntfIndex
                MAX-ACCESS not-accessible
                STATUS current
                DESCRIPTION "interface index (slot/port/channel) SSPPCCC"
                ::= { atmSvcVccEntry 1 }

atmSvcVccVpiA        OBJECT-TYPE
                SYNTAX INTEGER (0..4095)
                MAX-ACCESS not-accessible
                STATUS current
                DESCRIPTION "atm path identifier - side A"
                ::= { atmSvcVccEntry 2 }

atmSvcVccVciA        OBJECT-TYPE
                SYNTAX INTEGER (0..65535)
                MAX-ACCESS not-accessible
                STATUS current
                DESCRIPTION "atm channel identifier - side A"
                ::= { atmSvcVccEntry 3 }

atmSvcVccIfB        OBJECT-TYPE
                SYNTAX IntfIndex
                MAX-ACCESS not-accessible
                STATUS current
                DESCRIPTION "interface index (slot/port/channel) SSPPCCC"
                ::= { atmSvcVccEntry 4 }

atmSvcVccVpiB        OBJECT-TYPE
                SYNTAX INTEGER (0..4095)
                MAX-ACCESS not-accessible
                STATUS current
                DESCRIPTION "atm path identifier - side B"
                ::= { atmSvcVccEntry 5 }

atmSvcVccVciB        OBJECT-TYPE
                SYNTAX INTEGER (0..65535)
                MAX-ACCESS not-accessible
                STATUS current
                DESCRIPTION "atm channel identifier - side B"
                ::= { atmSvcVccEntry 6 }

atmSvcVccServiceTypeA2B        OBJECT-TYPE
                SYNTAX INTEGER  {
                                ubr(1),
                                vbr-nrt2(2),
                                vbr-nrt1(3),
                                vbr-rt2(4),
                                vbr-rt1(5),
                                vbr-express(6),
                                cbr4(7),
                                cbr3(8),
                                cbr2(9),
                                cbr1(10)
                                }
                MAX-ACCESS read-only
                STATUS current
                DESCRIPTION "service type"
                DEFVAL { ubr }
                ::= { atmSvcVccEntry 7 }

atmSvcVccSarTypeA2B OBJECT-TYPE
                SYNTAX INTEGER  {
                                aal5(1),
                                aal3-4(2),
                                aal2(3),
                                aal1(4),
                                null(5)
                                }
                MAX-ACCESS read-only
                STATUS current
                DESCRIPTION "sar type - A to B direction"
                DEFVAL { null }
                ::= { atmSvcVccEntry 8 }

atmSvcVccPeakCellRateA2B        OBJECT-TYPE
                SYNTAX Integer32
                MAX-ACCESS read-only
                STATUS current
                DESCRIPTION "peak rate - side A"
                DEFVAL { 1 }
                ::= { atmSvcVccEntry 10 }

atmSvcVccSusCellRateA2B        OBJECT-TYPE
                SYNTAX Integer32
                MAX-ACCESS read-only
                STATUS current
                DESCRIPTION "sustained rate - side A"
                DEFVAL { 1 }
                ::= { atmSvcVccEntry 11 }

atmSvcVccMaxBurstSizeA2B        OBJECT-TYPE
                SYNTAX Integer32
                MAX-ACCESS read-only
                STATUS current
                DESCRIPTION "maximum burst size - side A"
                DEFVAL { 1 }
                ::= { atmSvcVccEntry 12 }

atmSvcVccServiceTypeB2A        OBJECT-TYPE
                SYNTAX INTEGER  {
                                ubr(1),
                                vbr-nrt2(2),
                                vbr-nrt1(3),
                                vbr-rt2(4),
                                vbr-rt1(5),
                                vbr-express(6),
                                cbr4(7),
                                cbr3(8),
                                cbr2(9),
                                cbr1(10)
                                }
                MAX-ACCESS read-only
                STATUS current
                DESCRIPTION "service type"
                DEFVAL { ubr }
                ::= { atmSvcVccEntry 13 }

atmSvcVccSarTypeB2A OBJECT-TYPE
                SYNTAX INTEGER  {
                                aal5(1),
                                aal3-4(2),
                                aal2(3),
                                aal1(4),
                                null(5)
                                }
                MAX-ACCESS read-only
                STATUS current
                DESCRIPTION "sar type - B to A direction"
                DEFVAL { null }
                ::= { atmSvcVccEntry 14 }

atmSvcVccPeakCellRateB2A        OBJECT-TYPE
                SYNTAX Integer32
                MAX-ACCESS read-only
                STATUS current
                DESCRIPTION "peak rate - side B"
                DEFVAL { 1 }
                ::= { atmSvcVccEntry 16 }

atmSvcVccSusCellRateB2A        OBJECT-TYPE
                SYNTAX Integer32
                MAX-ACCESS read-only
                STATUS current
                DESCRIPTION "sustained rate - side B"
                DEFVAL { 1 }
                ::= { atmSvcVccEntry 17 }

atmSvcVccMaxBurstSizeB2A        OBJECT-TYPE
                SYNTAX Integer32
                MAX-ACCESS read-only
                STATUS current
                DESCRIPTION "maximum burst size - side B"
                DEFVAL { 1 }
                ::= { atmSvcVccEntry 18 }

atmSvcVccFlow        OBJECT-TYPE
                SYNTAX INTEGER        {
                                duplex(1),
                                pointToMultipoint(2)
                                }
                MAX-ACCESS read-only
                STATUS current
                DESCRIPTION "flow type"
                DEFVAL { duplex }
                ::= { atmSvcVccEntry 19 }

atmSvcVccType        OBJECT-TYPE
                SYNTAX INTEGER  {
                                nonsecured(1),
                                secured(2)
                                }
                MAX-ACCESS read-only
                STATUS current
                DESCRIPTION "type of connection"
                DEFVAL { nonsecured }
                ::= { atmSvcVccEntry 20 }

atmSvcVccConnectionStatus OBJECT-TYPE
                SYNTAX INTEGER {
                                active(1),
                                inactive(2),
                                inactiveA2B-B2A(3),
                                inactiveA2B(4),
                                inactiveB2A(5)
                               }
                MAX-ACCESS read-only
                STATUS current
                DESCRIPTION "Indicates the current connections status.
                             Active:  All interfaces through which the 
                                      connection is going are in service.
                             Inactive:  One of the end interfaces of the 
                                        connection is not in service.

                             The rest of the states apply to connections going
                             through resource interfaces like DSP2 and FEC.  These
                             interfaces are dynamically allocated.

                             InactiveA2B-B2A:  Both the A2B and B2A resource
                                               interfaces are not in service.
                             InactiveA2B:  The A2B resource interface is not in 
                                           service.
                             InactiveB2A:  The B2A resource interface is not in 
                                           service.

                             If an end interface and the resource interfaces 
                             are out of service, the status will be inactive 
                             because the end interfaces take priority."
                DEFVAL { inactive }
                ::= { atmSvcVccEntry 21 }

atmSvcVccViA    OBJECT-TYPE
                SYNTAX INTEGER (0..1024)
                MAX-ACCESS read-write
                STATUS current
                DESCRIPTION "VI to associate the Egress part of the
                        B2A connection ."
                DEFVAL { 0 }
                ::= { atmSvcVccEntry 22 }

atmSvcVccViB    OBJECT-TYPE
                SYNTAX INTEGER (0..1024) 
                MAX-ACCESS read-write
                STATUS current
                DESCRIPTION "VI to associate the Egress part of the
                        A2B connection ."
                DEFVAL { 0 }
                ::= { atmSvcVccEntry 23 }

        
atmSvcVccCnfrmTypeA2B    OBJECT-TYPE
                SYNTAX INTEGER {
                                    best-effort(1),
                                one-bucket-notag-0plus1(2),
                                two-bucket-notag-0plus1-0plus1(3),
                                two-bucket-notag-0plus1-0(4),
                                two-bucket-tag-0plus1-0(5),
                                best-effort-tag(6)
                               }
                MAX-ACCESS read-write
                STATUS current
                DESCRIPTION "The following is the description of this field
                        This will be used in conjunction with the
                        service type field to get the correct
                        traffic behaviour. In the conformances the 
                        the 0 or 0plus1 refers to the clp bit in the
                        cells. If 0plus1 is the bucket reference then
                        the clp bit is ignored. If 0 is specified for 
                        the bucket then check only clp=0 cells.
                        1: Best Effort will try to send all cellsin a 
                        best effort way. This will follow the 
                        Aqueman Algorithm
                        2: one-bucket-notag-0plus1 will use 1 bucket
                        i.e is the PCR(0+1) bucket and drop all
                        cells in excess.
                        3: two-bucket-notag-0plus1-0plus1 uses 2 buckets.
                        The 2 buckets are pcr(0+1) and scr(0+1).
                        All cells conforming to both buckets will be
                        passed through. The rest will be dropped.
                        4: two-bucket-notag-0plus1-0 uses 2 buckets.
                        The 2 buckets are pcr(0+1) and scr(0) or 
                        pcr(0). Cells which conform to both buckets
                        are passed through. The rest are dropped.
                        5: two-bucket-tag-0plus1-0 uses 2 buckets.
                        The 2 buckets are pcr(0+1) and scr(0) or 
                        pcr(0). Cells which do not conform to the first
                        bucket are dropped. Cells which do not 
                        conform to the 2nd bucket are tagged.
                        6: best-effort-tag. Tag all cells and then
                        do a best effort.  "
                DEFVAL { best-effort }
                ::= { atmSvcVccEntry 24 }


atmSvcVccCnfrmTypeB2A    OBJECT-TYPE
                SYNTAX INTEGER {
                                    best-effort(1),
                                one-bucket-notag-0plus1(2),
                                two-bucket-notag-0plus1-0plus1(3),
                                two-bucket-notag-0plus1-0(4),
                                two-bucket-tag-0plus1-0(5),
                                best-effort-tag(6)
                               }
                MAX-ACCESS read-write
                STATUS current
                DESCRIPTION "The following is the description of this field
                        This will be used in conjunction with the
                        service type field to get the correct
                        traffic behaviour. In the conformances the 
                        the 0 or 0plus1 refers to the clp bit in the
                        cells. If 0plus1 is the bucket reference then
                        the clp bit is ignored. If 0 is specified for 
                        the bucket then check only clp=0 cells.
                        1: Best Effort will try to send all cellsin a 
                        best effort way. This will follow the 
                        Aqueman Algorithm
                        2: one-bucket-notag-0plus1 will use 1 bucket
                        i.e is the PCR(0+1) bucket and drop all
                        cells in excess.
                        3: two-bucket-notag-0plus1-0plus1 uses 2 buckets.
                        The 2 buckets are pcr(0+1) and scr(0+1).
                        All cells conforming to both buckets will be
                        passed through. The rest will be dropped.
                        4: two-bucket-notag-0plus1-0 uses 2 buckets.
                        The 2 buckets are pcr(0+1) and scr(0) or 
                        pcr(0). Cells which conform to both buckets
                        are passed through. The rest are dropped.
                        5: two-bucket-tag-0plus1-0 uses 2 buckets.
                        The 2 buckets are pcr(0+1) and scr(0) or 
                        pcr(0). Cells which do not conform to the first
                        bucket are dropped. Cells which do not 
                        conform to the 2nd bucket are tagged.
                        6: best-effort-tag. Tag all cells and then
                        do a best effort.  "
                DEFVAL { best-effort }
                ::= { atmSvcVccEntry 25 }


atmSvcVccVUNIA    OBJECT-TYPE
                SYNTAX INTEGER (0..255)
                MAX-ACCESS read-write
                STATUS current
                DESCRIPTION "VUNI to associate the Egress part of the
                        B2A connection ."
                DEFVAL { 0 }
                ::= { atmSvcVccEntry 26 }

atmSvcVccVUNIB    OBJECT-TYPE
                SYNTAX INTEGER (0..255) 
                MAX-ACCESS read-write
                STATUS current
                DESCRIPTION "VUNI to associate the Egress part of the
                        A2B connection ."
                DEFVAL { 0 }
                ::= { atmSvcVccEntry 27 }


atmSvcVccTrafficShapingA2B     OBJECT-TYPE
                SYNTAX INTEGER {
                                disabled(1),
                                enabled(2)
                               }
                MAX-ACCESS read-write
                STATUS current
                DESCRIPTION "Traffic Shaping Support in the A2B direction."
                DEFVAL { disabled }
                ::= { atmSvcVccEntry 28 }

atmSvcVccTrafficShapingB2A     OBJECT-TYPE
                SYNTAX INTEGER {
                                disabled(1),
                                enabled(2)
                               }
                MAX-ACCESS read-write
                STATUS current
                DESCRIPTION "Traffic Shaping Support in the B2A direction."
                DEFVAL { disabled }
                ::= { atmSvcVccEntry 29 }


ipAtmAppPvcVccTable OBJECT-TYPE
                SYNTAX SEQUENCE OF IpAtmAppPvcVccEntry
                MAX-ACCESS not-accessible
                STATUS current
                DESCRIPTION "Table about in-band management atm connection
                             entries."
                ::= { connectionConfig 4 }

ipAtmAppPvcVccEntry OBJECT-TYPE
                SYNTAX IpAtmAppPvcVccEntry
                MAX-ACCESS not-accessible
                STATUS current
                DESCRIPTION "Row definition of in-band management
                             atm connection attribution."
                INDEX { ipAtmAppPvcVccDestAddrA, ipAtmAppPvcVccSubnetMaskA,
                        ipAtmAppPvcVccIfB, ipAtmAppPvcVccVpiB, 
                        ipAtmAppPvcVccVciB }
                ::= { ipAtmAppPvcVccTable 1 }

IpAtmAppPvcVccEntry ::= SEQUENCE {
                ipAtmAppPvcVccDestAddrA          IpAddress,
                ipAtmAppPvcVccSubnetMaskA        IpAddress,
                ipAtmAppPvcVccIfB                Integer32,
                ipAtmAppPvcVccVpiB               INTEGER,
                ipAtmAppPvcVccVciB               INTEGER,
                ipAtmAppPvcVccServiceTypeA2B     INTEGER,
                ipAtmAppPvcVccServiceTypeB2A     INTEGER,
                ipAtmAppPvcVccPeakCellRateB2A    Integer32,
                ipAtmAppPvcVccSusCellRateB2A     Integer32,
                ipAtmAppPvcVccMaxBurstSizeB2A    Integer32,
                ipAtmAppPvcVccType               INTEGER,
                ipAtmAppPvcVccRowStatus          RowStatus,
                ipAtmAppPvcVccConnectionStatus   INTEGER,

                ipAtmAppPvcVccDualHomed          INTEGER,

                ipAtmAppPvcVccViB                INTEGER,
                ipAtmAppPvcVccCnfrmTypeB2A       INTEGER,


                ipAtmAppPvcVccVUNIB              INTEGER,

                ipAtmAppPvcVccMfsB2A             INTEGER,
                ipAtmAppPvcVccConnFailureCauseB  AtmConnFailureCause,
                ipAtmAppPvcVccTrafficShapingA2B  INTEGER,
                ipAtmAppPvcVccOamStatus          INTEGER
                }

ipAtmAppPvcVccDestAddrA OBJECT-TYPE
                SYNTAX IpAddress
                MAX-ACCESS not-accessible
                STATUS current
                DESCRIPTION "Destination IP address of an in-band management-
                             atm connection.  Value is and IP address."
                ::= { ipAtmAppPvcVccEntry 1 }

ipAtmAppPvcVccSubnetMaskA OBJECT-TYPE
                SYNTAX IpAddress
                MAX-ACCESS not-accessible
                STATUS current
                DESCRIPTION "The subnet mask of the destination IP address.  
                             Value is an IP address."
                ::= { ipAtmAppPvcVccEntry 2 }

ipAtmAppPvcVccIfB OBJECT-TYPE
                SYNTAX Integer32
                MAX-ACCESS not-accessible
                STATUS current
                DESCRIPTION "Interface index for side B, the atm side, of an 
                             in-band management-atm connection.  Number value 
                             is interpreted as an interface of the form, 
                             SSPPCCC, where SS is the card slot, PP is the port
                              number, and CCC is the channel number."
                ::= { ipAtmAppPvcVccEntry 3 }

ipAtmAppPvcVccVpiB OBJECT-TYPE
                SYNTAX INTEGER (0..4095)
                MAX-ACCESS not-accessible
                STATUS current
                DESCRIPTION "VPI value for side B, the atm side, of an 
                             in-band management-atm connection.  Valid range
                             is a number between 0 and 4095."
                ::= { ipAtmAppPvcVccEntry 4 }

ipAtmAppPvcVccVciB OBJECT-TYPE
                SYNTAX INTEGER (0..65535)
                MAX-ACCESS not-accessible
                STATUS current
                DESCRIPTION "VCI value for side B, the atm side, of an 
                             in-band management-atm connection.  Valid range
                             is a number between 0 and 65535."
                ::= { ipAtmAppPvcVccEntry 5 }

ipAtmAppPvcVccServiceTypeA2B OBJECT-TYPE
                SYNTAX INTEGER  {
                                ubr(1),
                                vbr-express(2)
                                }
                MAX-ACCESS read-write
                STATUS current
                DESCRIPTION "Service type from side A to B"
                DEFVAL { ubr }
                ::= { ipAtmAppPvcVccEntry 6 }

ipAtmAppPvcVccServiceTypeB2A OBJECT-TYPE
                SYNTAX INTEGER  {
                                ubr(1),
                                vbr-express(2),
                                gfr2(3)
                                }
                MAX-ACCESS read-write
                STATUS current
                DESCRIPTION "Service type from side B to A"
                DEFVAL { ubr }
                ::= { ipAtmAppPvcVccEntry 7 }

ipAtmAppPvcVccPeakCellRateB2A OBJECT-TYPE
                SYNTAX Integer32
                MAX-ACCESS read-write
                STATUS current
                DESCRIPTION "peak rate - side B"
                DEFVAL { 1 }
                ::= { ipAtmAppPvcVccEntry 8 }

ipAtmAppPvcVccSusCellRateB2A OBJECT-TYPE
                SYNTAX Integer32
                MAX-ACCESS read-write
                STATUS current
                DESCRIPTION "sustained rate - side B"
                DEFVAL { 1 }
                ::= { ipAtmAppPvcVccEntry 9 }

ipAtmAppPvcVccMaxBurstSizeB2A OBJECT-TYPE
                SYNTAX Integer32
                MAX-ACCESS read-write
                STATUS current
                DESCRIPTION "maximum burst size - side B"
                DEFVAL { 1 }
                ::= { ipAtmAppPvcVccEntry 10 }

ipAtmAppPvcVccType OBJECT-TYPE
                SYNTAX INTEGER {
                                primary(0),
                                backup(1)
                               }
                MAX-ACCESS read-only
                STATUS current
                DESCRIPTION "Indicated in-band management atm 
                             connection type."
                DEFVAL { primary }
                ::= { ipAtmAppPvcVccEntry 11 }

ipAtmAppPvcVccRowStatus OBJECT-TYPE
                SYNTAX RowStatus
                MAX-ACCESS read-write
                STATUS current
                DESCRIPTION "row status"
                ::= { ipAtmAppPvcVccEntry 12 }

ipAtmAppPvcVccConnectionStatus OBJECT-TYPE
                SYNTAX INTEGER {
                                active(1),
                                inactive(2),
                                inactiveA2B-B2A(3),
                                inactiveA2B(4),
                                inactiveB2A(5)
                               }
                MAX-ACCESS read-only
                STATUS current
                DESCRIPTION "Indicates the current connections status.
                             Active:  All interfaces through which the 
                                      connection is going are in service.
                             Inactive:  One of the end interfaces of the 
                                        connection is not in service.

                             The rest of the states apply to connections going
                             through resource interfaces like DSP2 and FEC.  These
                             interfaces are dynamically allocated.

                             InactiveA2B-B2A:  Both the A2B and B2A resource
                                               interfaces are not in service.
                             InactiveA2B:  The A2B resource interface is not in 
                                           service.
                             InactiveB2A:  The B2A resource interface is not in 
                                           service.

                             If an end interface and the resource interfaces 
                             are out of service, the status will be inactive 
                             because the end interfaces take priority."
                DEFVAL { inactive }
                ::= { ipAtmAppPvcVccEntry 13 }


ipAtmAppPvcVccDualHomed OBJECT-TYPE
                SYNTAX INTEGER {
                                no(1),
                                yes(2)
                               }
                MAX-ACCESS read-only
                STATUS current
                DESCRIPTION "Does this PVC need a backup Dual homing PVC."
                DEFVAL { no }
                ::= { ipAtmAppPvcVccEntry 14 }


ipAtmAppPvcVccViB       OBJECT-TYPE
                SYNTAX INTEGER (0..1024)
                MAX-ACCESS read-write
                STATUS current
                DESCRIPTION "VI to associate the Egress part of the
                        A2B connection ."
                DEFVAL { 0 }
                ::= { ipAtmAppPvcVccEntry 15 }

ipAtmAppPvcVccCnfrmTypeB2A    OBJECT-TYPE
                SYNTAX INTEGER {
                                    best-effort(1),
                                one-bucket-notag-0plus1(2),
                                two-bucket-notag-0plus1-0plus1(3),
                                two-bucket-notag-0plus1-0(4),
                                two-bucket-tag-0plus1-0(5),
                                best-effort-tag(6)
                               }
                MAX-ACCESS read-write
                STATUS current
                DESCRIPTION "The following is the description of this field
                        This will be used in conjunction with the
                        service type field to get the correct
                        traffic behaviour. In the conformances the 
                        the 0 or 0plus1 refers to the clp bit in the
                        cells. If 0plus1 is the bucket reference then
                        the clp bit is ignored. If 0 is specified for 
                        the bucket then check only clp=0 cells.
                        1: Best Effort will try to send all cellsin a 
                        best effort way. This will follow the 
                        Aqueman Algorithm
                        2: one-bucket-notag-0plus1 will use 1 bucket
                        i.e is the PCR(0+1) bucket and drop all
                        cells in excess.
                        3: two-bucket-notag-0plus1-0plus1 uses 2 buckets.
                        The 2 buckets are pcr(0+1) and scr(0+1).
                        All cells conforming to both buckets will be
                        passed through. The rest will be dropped.
                        4: two-bucket-notag-0plus1-0 uses 2 buckets.
                        The 2 buckets are pcr(0+1) and scr(0) or 
                        pcr(0). Cells which conform to both buckets
                        are passed through. The rest are dropped.
                        5: two-bucket-tag-0plus1-0 uses 2 buckets.
                        The 2 buckets are pcr(0+1) and scr(0) or 
                        pcr(0). Cells which do not conform to the first
                        bucket are dropped. Cells which do not 
                        conform to the 2nd bucket are tagged.
                        6: best-effort-tag. Tag all cells and then
                        do a best effort.  "
                DEFVAL { best-effort }
                ::= { ipAtmAppPvcVccEntry 16 }



ipAtmAppPvcVccVUNIB       OBJECT-TYPE
                SYNTAX INTEGER (0..255)
                MAX-ACCESS read-write
                STATUS current
                DESCRIPTION "VUNI to associate the Egress part of the
                        A2B connection ."
                DEFVAL { 0 }
                ::= { ipAtmAppPvcVccEntry 17 }


ipAtmAppPvcVccMfsB2A OBJECT-TYPE
                SYNTAX INTEGER (1..65535)
                MAX-ACCESS read-write
                STATUS current
                DESCRIPTION "Maximum Frame Size for GFR traffic"
                DEFVAL { 1 }
                ::= { ipAtmAppPvcVccEntry 18 }

ipAtmAppPvcVccConnFailureCauseB    OBJECT-TYPE
                SYNTAX AtmConnFailureCause
                MAX-ACCESS read-only
                STATUS current
                DESCRIPTION "connection status reason code"
                ::= { ipAtmAppPvcVccEntry 19 }

ipAtmAppPvcVccTrafficShapingA2B     OBJECT-TYPE
                SYNTAX INTEGER {
                                disabled(1),
                                enabled(2)
                               }
                MAX-ACCESS read-write
                STATUS current
                DESCRIPTION "Traffic Shaping Support in the A2B direction."
                DEFVAL { disabled }
          ::= { ipAtmAppPvcVccEntry 20 }


ipAtmAppPvcVccOamStatus OBJECT-TYPE
                SYNTAX INTEGER {
                                unsupp(1),
                                end-Pt(2),
                                end-Seg-Pt(3)
                               }
                MAX-ACCESS read-write
                STATUS current
                DESCRIPTION "Indicates the OAM monitoring status.
                             The 3 possible states are:
                             Unsupp:  No monitoring enabled.
                             End-Pt:  A side is only an end point, therefore
                                it will respond to AIS/RDI.
                             End-Seg-Pt: Connection endPoint that is also
                             a segment endPoint."
                DEFVAL { unsupp }
                ::= { ipAtmAppPvcVccEntry 21 }

ipAtmAppSvcVccTable OBJECT-TYPE
                SYNTAX SEQUENCE OF IpAtmAppSvcVccEntry
                MAX-ACCESS not-accessible
                STATUS current
                DESCRIPTION "Table of SVC VCC connection entries"
                ::= { connectionConfig 5 }

ipAtmAppSvcVccEntry OBJECT-TYPE
                SYNTAX IpAtmAppSvcVccEntry
                MAX-ACCESS not-accessible
                STATUS current
                DESCRIPTION "Row definition of SVC VCC connection
                             attribution."
                INDEX { ipAtmAppSvcVccDestAddrA, ipAtmAppSvcVccSubnetMaskA,
                        ipAtmAppSvcVccIfB, ipAtmAppSvcVccVpiB, 
                        ipAtmAppSvcVccVciB }
                ::= { ipAtmAppSvcVccTable 1 }

IpAtmAppSvcVccEntry ::= SEQUENCE {
                ipAtmAppSvcVccDestAddrA          IpAddress,
                ipAtmAppSvcVccSubnetMaskA        IpAddress,
                ipAtmAppSvcVccIfB                Integer32,
                ipAtmAppSvcVccVpiB               INTEGER,
                ipAtmAppSvcVccVciB               INTEGER,
                ipAtmAppSvcVccServiceTypeA2B     INTEGER,
                ipAtmAppSvcVccServiceTypeB2A     INTEGER,
                ipAtmAppSvcVccPeakCellRateB2A    Integer32,
                ipAtmAppSvcVccSusCellRateB2A     Integer32,
                ipAtmAppSvcVccMaxBurstSizeB2A    Integer32,
                ipAtmAppSvcVccType               INTEGER,
                ipAtmAppSvcVccConnectionStatus   INTEGER,
                ipAtmAppSvcVccViB                INTEGER,
                ipAtmAppSvcVccCnfrmTypeB2A       INTEGER

                ,ipAtmAppSvcVccVUNIB             INTEGER

                ,ipAtmAppSvcVccTrafficShapingA2B INTEGER
                }

ipAtmAppSvcVccDestAddrA OBJECT-TYPE
                SYNTAX IpAddress
                MAX-ACCESS not-accessible
                STATUS current
                DESCRIPTION "Destination IP address,value is IP address."
                ::= { ipAtmAppSvcVccEntry 1 }

ipAtmAppSvcVccSubnetMaskA OBJECT-TYPE
                SYNTAX IpAddress
                MAX-ACCESS not-accessible
                STATUS current
                DESCRIPTION "The subnet mask of the destination IP address.
                             Value is an IP address."
                ::= { ipAtmAppSvcVccEntry 2 }

ipAtmAppSvcVccIfB OBJECT-TYPE
                SYNTAX Integer32
                MAX-ACCESS not-accessible
                STATUS current
                DESCRIPTION "interface index (slot/port/channel) SSPPCCC"
                ::= { ipAtmAppSvcVccEntry 3 }

ipAtmAppSvcVccVpiB OBJECT-TYPE
                SYNTAX INTEGER (0..4095)
                MAX-ACCESS not-accessible
                STATUS current
                DESCRIPTION "atm path identifier - side B"
                ::= { ipAtmAppSvcVccEntry 4 }

ipAtmAppSvcVccVciB OBJECT-TYPE
                SYNTAX INTEGER (0..65535)
                MAX-ACCESS not-accessible
                STATUS current
                DESCRIPTION "atm channel identifier - side B"
                ::= { ipAtmAppSvcVccEntry 5 }

ipAtmAppSvcVccServiceTypeA2B OBJECT-TYPE
                SYNTAX INTEGER  {
                                ubr(1),
                                vbr-express(2)
                                }
                MAX-ACCESS read-only
                STATUS current
                DESCRIPTION "Service type from side A to B."
                DEFVAL { ubr }
                ::= { ipAtmAppSvcVccEntry 6 }

ipAtmAppSvcVccServiceTypeB2A OBJECT-TYPE
                SYNTAX INTEGER  {
                                ubr(1),
                                vbr-express(2)
                                }
                MAX-ACCESS read-only
                STATUS current
                DESCRIPTION "Service type from side B to A."
                DEFVAL { ubr }
                ::= { ipAtmAppSvcVccEntry 7 }

ipAtmAppSvcVccPeakCellRateB2A OBJECT-TYPE
                SYNTAX Integer32
                MAX-ACCESS read-only
                STATUS current
                DESCRIPTION "peak rate - side B"
                DEFVAL { 1 }
                ::= { ipAtmAppSvcVccEntry 8 }

ipAtmAppSvcVccSusCellRateB2A OBJECT-TYPE
                SYNTAX Integer32
                MAX-ACCESS read-only
                STATUS current
                DESCRIPTION "sustained rate - side B"
                DEFVAL { 1 }
                ::= { ipAtmAppSvcVccEntry 9 }

ipAtmAppSvcVccMaxBurstSizeB2A OBJECT-TYPE
                SYNTAX Integer32
                MAX-ACCESS read-only
                STATUS current
                DESCRIPTION "maximum burst size - side B"
                DEFVAL { 1 }
                ::= { ipAtmAppSvcVccEntry 10 }

ipAtmAppSvcVccType OBJECT-TYPE
                SYNTAX INTEGER {
                                primary(0),
                                backup(1)
                               }
                MAX-ACCESS read-only
                STATUS current
                DESCRIPTION "Type of using SVC VCC connection."
                DEFVAL { primary }
                ::= { ipAtmAppSvcVccEntry 11 }

ipAtmAppSvcVccConnectionStatus OBJECT-TYPE
                SYNTAX INTEGER {
                                active(1),
                                inactive(2),
                                inactiveA2B-B2A(3),
                                inactiveA2B(4),
                                inactiveB2A(5)
                               }
                MAX-ACCESS read-only
                STATUS current
                DESCRIPTION "Indicates the current connections status.
                             Active:  All interfaces through which the 
                                      connection is going are in service.
                             Inactive:  One of the end interfaces of the 
                                        connection is not in service.

                             The rest of the states apply to connections going
                             through resource interfaces like DSP2 and FEC.  These
                             interfaces are dynamically allocated.

                             InactiveA2B-B2A:  Both the A2B and B2A resource
                                               interfaces are not in service.
                             InactiveA2B:  The A2B resource interface is not in 
                                           service.
                             InactiveB2A:  The B2A resource interface is not in 
                                           service.

                             If an end interface and the resource interfaces 
                             are out of service, the status will be inactive 
                             because the end interfaces take priority."
                DEFVAL { inactive }
                ::= { ipAtmAppSvcVccEntry 12 }

ipAtmAppSvcVccViB       OBJECT-TYPE
                SYNTAX INTEGER (0..1024)
                MAX-ACCESS read-write
                STATUS current 
                DESCRIPTION "VI to associate the Egress part of the
                        A2B connection ."
                DEFVAL { 0 }
                ::= { ipAtmAppSvcVccEntry 13 }

ipAtmAppSvcVccCnfrmTypeB2A    OBJECT-TYPE
                SYNTAX INTEGER {
                                    best-effort(1),
                                one-bucket-notag-0plus1(2),
                                two-bucket-notag-0plus1-0plus1(3),
                                two-bucket-notag-0plus1-0(4),
                                two-bucket-tag-0plus1-0(5),
                                best-effort-tag(6)
                               }
                MAX-ACCESS read-write
                STATUS current
                DESCRIPTION "The following is the description of this field
                        This will be used in conjunction with the
                        service type field to get the correct
                        traffic behaviour. In the conformances the 
                        the 0 or 0plus1 refers to the clp bit in the
                        cells. If 0plus1 is the bucket reference then
                        the clp bit is ignored. If 0 is specified for 
                        the bucket then check only clp=0 cells.
                        1: Best Effort will try to send all cellsin a 
                        best effort way. This will follow the 
                        Aqueman Algorithm
                        2: one-bucket-notag-0plus1 will use 1 bucket
                        i.e is the PCR(0+1) bucket and drop all
                        cells in excess.
                        3: two-bucket-notag-0plus1-0plus1 uses 2 buckets.
                        The 2 buckets are pcr(0+1) and scr(0+1).
                        All cells conforming to both buckets will be
                        passed through. The rest will be dropped.
                        4: two-bucket-notag-0plus1-0 uses 2 buckets.
                        The 2 buckets are pcr(0+1) and scr(0) or 
                        pcr(0). Cells which conform to both buckets
                        are passed through. The rest are dropped.
                        5: two-bucket-tag-0plus1-0 uses 2 buckets.
                        The 2 buckets are pcr(0+1) and scr(0) or 
                        pcr(0). Cells which do not conform to the first
                        bucket are dropped. Cells which do not 
                        conform to the 2nd bucket are tagged.
                        6: best-effort-tag. Tag all cells and then
                        do a best effort.  "
                DEFVAL { best-effort }
                ::= { ipAtmAppSvcVccEntry 14 }


ipAtmAppSvcVccVUNIB       OBJECT-TYPE
                SYNTAX INTEGER (0..255)
                MAX-ACCESS read-write
                STATUS current 
                DESCRIPTION "VUNI to associate the Egress part of the
                        A2B connection ."
                DEFVAL { 0 }
                ::= { ipAtmAppSvcVccEntry 15 }


ipAtmAppSvcVccTrafficShapingA2B     OBJECT-TYPE
                SYNTAX INTEGER {
                                disabled(1),
                                enabled(2)
                               }
                MAX-ACCESS read-write
                STATUS current
                DESCRIPTION "Traffic Shaping Support in the A2B direction."
                DEFVAL { disabled }
                ::= { ipAtmAppSvcVccEntry 16 }

cirEmAtmPvcVccTable OBJECT-TYPE
                SYNTAX SEQUENCE OF CirEmAtmPvcVccEntry
                MAX-ACCESS not-accessible
                STATUS current
                DESCRIPTION "Table of Circuit Emulation to ATM VCCs"
                ::= { connectionConfig 6 }

cirEmAtmPvcVccEntry OBJECT-TYPE
                SYNTAX CirEmAtmPvcVccEntry
                MAX-ACCESS not-accessible
                STATUS current
                DESCRIPTION "Row definition of circuit emulation to atm
                              connections."
                INDEX { cirEmAtmPvcVccIfA, cirEmAtmPvcVccIfB,
                        cirEmAtmPvcVccVpiB, cirEmAtmPvcVccVciB }
                ::= { cirEmAtmPvcVccTable 1 }

CirEmAtmPvcVccEntry ::= SEQUENCE {
                             cirEmAtmPvcVccIfA                   IntfIndex,
                             cirEmAtmPvcVccIfB                   IntfIndex,
                             cirEmAtmPvcVccVpiB                  INTEGER,
                             cirEmAtmPvcVccVciB                  INTEGER,
                             cirEmAtmPvcVccServiceType           INTEGER,
                             cirEmAtmPvcVccVoiceCompressionA2B   INTEGER,
                             cirEmAtmPvcVccSilenceDetectionA2B   INTEGER,
                             cirEmAtmPvcVccEchoCancellationA2B   INTEGER,
                             cirEmAtmPvcVccFlow                  INTEGER,
                             cirEmAtmPvcVccRowStatus             RowStatus,
                             cirEmAtmPvcVccCngToneDetectionA2B   INTEGER,
                             cirEmAtmPvcVccCodingTranslationA2B  INTEGER,
                             cirEmAtmPvcVccVoiceCompressionB2A   INTEGER,
                             cirEmAtmPvcVccSilenceDetectionB2A   INTEGER,
                             cirEmAtmPvcVccEchoCancellationB2A   INTEGER,
                             cirEmAtmPvcVccCngToneDetectionB2A   INTEGER,
                             cirEmAtmPvcVccCodingTranslationB2A  INTEGER,
                             cirEmAtmPvcVccSarTypeB              INTEGER,
                             cirEmAtmPvcVccConnectionStatus      INTEGER,

                             cirEmAtmPvcVccDualHomed             INTEGER,

                             cirEmAtmPvcVccOamStatus             INTEGER,
                             cirEmAtmPvcVccViB                   INTEGER,
                             cirEmAtmPvcVccCnfrmTypeB2A          INTEGER,


                             cirEmAtmPvcVccVUNIB                 INTEGER,

                             cirEmAtmPvcVccAal2Cid               INTEGER,
                             cirEmAtmPvcVccOAMConnEndPtStatus    INTEGER,
                             cirEmAtmPvcVccOAMConnSegEndPtStatus INTEGER, 
                             cirEmAtmPvcVccConnFailureCauseA     ConnFailureCause,
                             cirEmAtmPvcVccConnFailureCauseB     AtmConnFailureCause,
                             cirEmAtmPvcVccDigitCollectTypeA2B   INTEGER,
                             cirEmAtmPvcVccDigitCollectTypeB2A   INTEGER,
                             cirEmAtmPvcVccEncodingStdA2B        INTEGER,
                             cirEmAtmPvcVccEncodingStdB2A        INTEGER,
                             cirEmAtmPvcVccEncodingProfileIdA2B  INTEGER,
                             cirEmAtmPvcVccEncodingProfileIdB2A  INTEGER

                                         }

cirEmAtmPvcVccIfA        OBJECT-TYPE
                SYNTAX IntfIndex
                MAX-ACCESS not-accessible
                STATUS current
                DESCRIPTION "Interface index for side A, the circuit emulation
                             side, of a circuit emulation-atm PVC VCC 
                             connection.  Number value is interpreted as an 
                             interface of the form, SSPPCCC, where SS is the 
                             card slot, PP is the port number, and CCC is the 
                             channel number."
                ::= { cirEmAtmPvcVccEntry 1 }

cirEmAtmPvcVccIfB OBJECT-TYPE
                SYNTAX IntfIndex
                MAX-ACCESS not-accessible
                STATUS current
                DESCRIPTION "Interface index for side B, the atm side, of a 
                             circuit emulation-atm PVC VCC connection.  Number 
                             value is interpreted as an interface of the form, 
                             SSPPCCC, where SS is the card slot, PP is the port                              number, and CCC is the channel number."
                ::= { cirEmAtmPvcVccEntry 2 }

cirEmAtmPvcVccVpiB OBJECT-TYPE
                SYNTAX INTEGER (0..4095)
                MAX-ACCESS not-accessible
                STATUS current
                DESCRIPTION "VPI value for side B, the atm side,  of a
                             circuit emulation-atm PVC VCC connection.  Valid 
                             range is a number between 0 and 4095."
                ::= { cirEmAtmPvcVccEntry 3 }

cirEmAtmPvcVccVciB OBJECT-TYPE
                SYNTAX INTEGER (0..65535)
                MAX-ACCESS not-accessible
                STATUS current
                DESCRIPTION "VCI value for side B, the atm side,  of a
                             circuit emulation-atm PVC VCC connection.  Valid 
                             range is a number between 0 and 65535."
                ::= { cirEmAtmPvcVccEntry 4 }

cirEmAtmPvcVccServiceType OBJECT-TYPE
                SYNTAX INTEGER {
                                cbr-1(1),
                                cbr-2(2),
                                cbr-3(3),
                                cbr-4(4)
                               }
                MAX-ACCESS read-write
                STATUS current
                DESCRIPTION "service type"
                ::= { cirEmAtmPvcVccEntry 5 }

cirEmAtmPvcVccVoiceCompressionA2B OBJECT-TYPE
                SYNTAX INTEGER  {
                                none(1),
                                g726-16k(2),
                                g726-24k(3),
                                g726-32k(4),
                                g726-40k(5),
                                g729a-8k(6)
                                }
                MAX-ACCESS read-write
                STATUS current
                DESCRIPTION "Voice Compression Algorithm"
                DEFVAL { none }
                ::= { cirEmAtmPvcVccEntry 6 }

cirEmAtmPvcVccSilenceDetectionA2B OBJECT-TYPE
                SYNTAX INTEGER  {
                                 disabled(1),
                                 enabled(2)
                                }
                MAX-ACCESS read-write
                STATUS current
                DESCRIPTION "silence detection off/on"
                DEFVAL { disabled }
                ::= { cirEmAtmPvcVccEntry 7 }

cirEmAtmPvcVccEchoCancellationA2B OBJECT-TYPE
                SYNTAX INTEGER  {
                                 none(1),
                                 g165-nearEnd(2),
                                 g168(3)
                                }
                MAX-ACCESS read-write
                STATUS current
                DESCRIPTION "Echo Cancellation Algorithm"
                DEFVAL { none }
                ::= { cirEmAtmPvcVccEntry 8 }

cirEmAtmPvcVccFlow OBJECT-TYPE
                SYNTAX INTEGER  {
                                 duplex(1),
                                 simplexA2B(2),
                                 simplexB2A(3),
                                 pointToMultipointA2B(4),
                                 pointToMultipointB2A(5)
                                }
                MAX-ACCESS read-write
                STATUS current
                DESCRIPTION "Flow Type  "
                DEFVAL { duplex }
                ::= { cirEmAtmPvcVccEntry 9 }

cirEmAtmPvcVccRowStatus OBJECT-TYPE
                SYNTAX RowStatus
                MAX-ACCESS read-write
                STATUS current
                DESCRIPTION "row status"
                ::= { cirEmAtmPvcVccEntry 10 }

cirEmAtmPvcVccCngToneDetectionA2B OBJECT-TYPE
                SYNTAX INTEGER  {
                                 disabled(1),
                                 bypass(2),
                                 g726-32k(3),
                                 faxRelay(4),
                                 fxRlyMdmBypass(5)
                                }
                MAX-ACCESS read-write
                STATUS current
                DESCRIPTION "Calling Tone Detection Algorithm,
                             one of the enum value, g726-32k(3)
                             is obsoleted on 01Mar99 such that
                             user would not be able to configure
                             CE-ATM.Fax Relay is to allow detection
                             of fax Calling Tones. In faxRelay Mode
                             only Fax calling tone is detected . In
                             fxRlyMdmBypass faxRelay is detected
                             and Modem is done in bypass mode"
                DEFVAL { disabled }
                ::= { cirEmAtmPvcVccEntry 11 }

cirEmAtmPvcVccCodingTranslationA2B OBJECT-TYPE
                SYNTAX INTEGER  {
                                 none(1),
                                 muLaw2muLaw(2),
                                 aLaw2aLaw(3),
                                 muLaw2aLaw(4),
                                 aLaw2muLaw(5)
                                }
                MAX-ACCESS read-write
                STATUS current
                DESCRIPTION "Coding rule translation type."
                DEFVAL { none }
                ::= { cirEmAtmPvcVccEntry 12 }

cirEmAtmPvcVccVoiceCompressionB2A OBJECT-TYPE
                SYNTAX INTEGER  {
                                none(1),
                                g726-16k(2),
                                g726-24k(3),
                                g726-32k(4),
                                g726-40k(5),
                                g729a-8k(6)
                                }
                MAX-ACCESS read-write
                STATUS current
                DESCRIPTION "Voice Compression Algorithm"
                DEFVAL { none }
                ::= { cirEmAtmPvcVccEntry 13 }

cirEmAtmPvcVccSilenceDetectionB2A OBJECT-TYPE
                SYNTAX INTEGER  {
                                 disabled(1),
                                 enabled(2)
                                }
                MAX-ACCESS read-write
                STATUS current
                DESCRIPTION "silence detection off/on"
                DEFVAL { disabled }
                ::= { cirEmAtmPvcVccEntry 14 }

cirEmAtmPvcVccEchoCancellationB2A OBJECT-TYPE
                SYNTAX INTEGER  {
                                 none(1),
                                 g165-nearEnd(2),
                                 g168(3)
                                }
                MAX-ACCESS read-write
                STATUS current
                DESCRIPTION "Echo Cancellation Algorithm"
                DEFVAL { none }
                ::= { cirEmAtmPvcVccEntry 15 }

cirEmAtmPvcVccCngToneDetectionB2A OBJECT-TYPE
                SYNTAX INTEGER  {
                                 disabled(1),
                                 bypass(2),
                                 g726-32k(3),
                                 faxRelay(4),
                                 fxRlyMdmBypass(5) 
                                }
                MAX-ACCESS read-write
                STATUS current
                DESCRIPTION "Calling Tone Detection Algorithm,
                             one of the enum value, g726-32k(3)
                             is obsoleted on 01Mar99 such that
                             user would not be able to configure
                             CE-ATM.Fax Relay is to allow detection
                             of fax Calling Tones. In faxRelay Mode
                             only Fax calling tone is detected . In
                             fxRlyMdmBypass faxRelay is detected
                             and Modem is done in bypass mode"
                DEFVAL { disabled }
                ::= { cirEmAtmPvcVccEntry 16 }

cirEmAtmPvcVccCodingTranslationB2A OBJECT-TYPE
                SYNTAX INTEGER  {
                                 none(1),
                                 muLaw2muLaw(2),
                                 aLaw2aLaw(3),
                                 muLaw2aLaw(4),
                                 aLaw2muLaw(5)
                                }
                MAX-ACCESS read-write
                STATUS current
                DESCRIPTION "Coding rule translation type."
                DEFVAL { none }
                ::= { cirEmAtmPvcVccEntry 17 }

cirEmAtmPvcVccSarTypeB OBJECT-TYPE
                SYNTAX INTEGER  {
                                aal2(3),
                                aal1(4),
                                aal2Std(5)
                                }
                MAX-ACCESS read-write
                STATUS current
                DESCRIPTION "This field will only be used when selecting voice 
                             compression, in other cases it will be set to 
                             aal1."
                DEFVAL { aal1 }
                ::= { cirEmAtmPvcVccEntry 18 }

cirEmAtmPvcVccConnectionStatus OBJECT-TYPE
                SYNTAX INTEGER {
                                active(1),
                                inactive(2),
                                inactiveA2B-B2A(3),
                                inactiveA2B(4),
                                inactiveB2A(5)
                               }
                MAX-ACCESS read-only
                STATUS current
                DESCRIPTION "Indicates the current connections status.
                             Active:  All interfaces through which the 
                                      connection is going are in service.
                             Inactive:  One of the end interfaces of the 
                                        connection is not in service.

                             The rest of the states apply to connections going
                             through resource interfaces like DSP2 and FEC.  These
                             interfaces are dynamically allocated.

                             InactiveA2B-B2A:  Both the A2B and B2A resource
                                               interfaces are not in service.
                             InactiveA2B:  The A2B resource interface is not in 
                                           service.
                             InactiveB2A:  The B2A resource interface is not in 
                                           service.

                             If an end interface and the resource interfaces 
                             are out of service, the status will be inactive 
                             because the end interfaces take priority."
                DEFVAL { inactive }
                ::= { cirEmAtmPvcVccEntry 19 }


cirEmAtmPvcVccDualHomed OBJECT-TYPE
                SYNTAX INTEGER {
                                no(1),
                                yes(2)
                               }
                MAX-ACCESS read-only
                STATUS current
                DESCRIPTION "Does this PVC need a backup Dual homing PVC."
                DEFVAL { no }
                ::= { cirEmAtmPvcVccEntry 20 }


cirEmAtmPvcVccOamStatus OBJECT-TYPE
                SYNTAX INTEGER {
                                unsupp(1),
                                end-Pt(2),
                                end-Seg-Pt(3)
                               }
                MAX-ACCESS read-write
                STATUS current
                DESCRIPTION "Indicates the OAM monitoring status of side A.
                             The 2 possible states are:
                             Unsupp:  No monitoring enabled.
                             End-Pt:  A side is only an end point, therefore
                                it will respond to AIS/RDI."
                DEFVAL { unsupp }
                ::= { cirEmAtmPvcVccEntry 21 }

cirEmAtmPvcVccViB       OBJECT-TYPE
                SYNTAX INTEGER (0..1024)
                MAX-ACCESS read-write
                STATUS current
                DESCRIPTION "VI to associate the Egress part of the
                        A2B connection ." 
                DEFVAL { 0 }
                ::= { cirEmAtmPvcVccEntry 22 }


cirEmAtmPvcVccCnfrmTypeB2A    OBJECT-TYPE
                SYNTAX INTEGER {
                                    best-effort(1),
                                one-bucket-notag-0plus1(2),
                                two-bucket-notag-0plus1-0plus1(3),
                                two-bucket-notag-0plus1-0(4),
                                two-bucket-tag-0plus1-0(5),
                                best-effort-tag(6)
                               }
                MAX-ACCESS read-write
                STATUS current
                DESCRIPTION "The following is the description of this field
                        This will be used in conjunction with the
                        service type field to get the correct
                        traffic behaviour. In the conformances the 
                        the 0 or 0plus1 refers to the clp bit in the
                        cells. If 0plus1 is the bucket reference then
                        the clp bit is ignored. If 0 is specified for 
                        the bucket then check only clp=0 cells.
                        1: Best Effort will try to send all cellsin a 
                        best effort way. This will follow the 
                        Aqueman Algorithm
                        2: one-bucket-notag-0plus1 will use 1 bucket
                        i.e is the PCR(0+1) bucket and drop all
                        cells in excess.
                        3: two-bucket-notag-0plus1-0plus1 uses 2 buckets.
                        The 2 buckets are pcr(0+1) and scr(0+1).
                        All cells conforming to both buckets will be
                        passed through. The rest will be dropped.
                        4: two-bucket-notag-0plus1-0 uses 2 buckets.
                        The 2 buckets are pcr(0+1) and scr(0) or 
                        pcr(0). Cells which conform to both buckets
                        are passed through. The rest are dropped.
                        5: two-bucket-tag-0plus1-0 uses 2 buckets.
                        The 2 buckets are pcr(0+1) and scr(0) or 
                        pcr(0). Cells which do not conform to the first
                        bucket are dropped. Cells which do not 
                        conform to the 2nd bucket are tagged.
                        6: best-effort-tag. Tag all cells and then
                        do a best effort.  "
                DEFVAL { best-effort }
                ::= { cirEmAtmPvcVccEntry 23 }

cirEmAtmPvcVccVUNIB       OBJECT-TYPE
                SYNTAX INTEGER (0..255)
                MAX-ACCESS read-write
                STATUS current
                DESCRIPTION "VUNI to associate the Egress part of the
                        A2B connection ." 
                DEFVAL { 0 }
                ::= { cirEmAtmPvcVccEntry 24 }


cirEmAtmPvcVccAal2Cid OBJECT-TYPE
                SYNTAX INTEGER (0..255)
                MAX-ACCESS read-write
                STATUS current
                DESCRIPTION "Aal2 Cid Used to pack ce chan in an
                        Atm Trunk. This value will be unique
                        per Atm Trunk. This field will be applicable
                        when Aal type is chosen to be Standard Aal2."
                DEFVAL { 0 }
                ::= { cirEmAtmPvcVccEntry 25 }

cirEmAtmPvcVccOAMConnEndPtStatus    OBJECT-TYPE
                 SYNTAX INTEGER {
                                ete-active(1),
                                ete-ais-state(2),
                                ete-rdi-state(3),
                                ete-ais-rdi-state(4)
                                }
                MAX-ACCESS read-only
                STATUS current
                DESCRIPTION "Connection endpoint status. Valid only 
                        at connection endpoint."
                ::= { cirEmAtmPvcVccEntry 26 }

cirEmAtmPvcVccOAMConnSegEndPtStatus    OBJECT-TYPE
                SYNTAX INTEGER {
                                seg-active(1),
                                seg-ais-state(2),
                                seg-rdi-state(3),
                                seg-ais-rdi-state(4)
                                }
                MAX-ACCESS read-only
                STATUS current
                DESCRIPTION "Segment endpoint status. Valid only at
                        segment/connection endpoints."
                ::= { cirEmAtmPvcVccEntry 27 }

cirEmAtmPvcVccConnFailureCauseA    OBJECT-TYPE
                SYNTAX ConnFailureCause
                MAX-ACCESS read-only
                STATUS current
                DESCRIPTION " connestion status reason code"
                ::= { cirEmAtmPvcVccEntry 28 }

cirEmAtmPvcVccConnFailureCauseB    OBJECT-TYPE
                SYNTAX AtmConnFailureCause
                MAX-ACCESS read-only
                STATUS current
                DESCRIPTION "connection status reason code"
                ::= { cirEmAtmPvcVccEntry 29 }



cirEmAtmPvcVccDigitCollectTypeA2B    OBJECT-TYPE
                SYNTAX  INTEGER   {
                                none(1),
                                dtmf(2),
                                mf(3),
                                mf-r2-frwd(4),
                                mf-r2-bkwd(5)
                 }
                MAX-ACCESS read-write
                STATUS current
                DESCRIPTION " Identify the digital tone setting.
                          dtmf  -- dual tone multifrequency dialed digits,
                          mf -- multifrequency dialed digits,
                          mf-r2-frwd -- R2 multifrequency forward dialed digits.
                          mf-r2-bkwd-- R2 multifrequency backward dialed digits"
                DEFVAL { none }
                ::= { cirEmAtmPvcVccEntry 30 }

cirEmAtmPvcVccDigitCollectTypeB2A    OBJECT-TYPE
                SYNTAX  INTEGER   {
                                none(1),
                                dtmf(2),
                                mf(3),
                                mf-r2-frwd(4),
                                mf-r2-bkwd(5)
                 }
                MAX-ACCESS read-write
                STATUS current
                DESCRIPTION " Identify the digital tone setting.
                          dtmf  -- dual tone multifrequency dialed digits,
                          mf -- multifrequency dialed digits,
                          mf-r2-frwd -- R2 multifrequency forward dialed digits.
                          mf-r2-bkwd-- R2 multifrequency backward dialed digits"
                DEFVAL { none }
                ::= { cirEmAtmPvcVccEntry 31 }



cirEmAtmPvcVccEncodingStdA2B    OBJECT-TYPE
                SYNTAX  INTEGER   {
                                         user(1),
                                         atmForum(2),
                                         itu-t(3)
                           }
                MAX-ACCESS read-write
                STATUS current
                DESCRIPTION " These are profiles defined according to standards
                     User-Profile - No restrictions or checks, user
                              freedom to choose any combination
                              of Params.
                     Atm Forum - These are profies defined by AF in
                           document AF-VMOA-0145.000. In these
                           cases the Identifiers are used and
                           not the table numbers.
                     Itu-t - These profiles are used from the I-366-2.
                   "
                DEFVAL { user }
                ::= { cirEmAtmPvcVccEntry 32 }

cirEmAtmPvcVccEncodingStdB2A    OBJECT-TYPE
                SYNTAX  INTEGER   {
                                         user(1),
                                         atmForum(2),
                                         itu-t(3)
                           }
                MAX-ACCESS read-write
                STATUS current
                DESCRIPTION " These are profiles defined according to standards
                     User-Profile - No restrictions or checks, user
                              freedom to choose any combination
                              of Params.
                     Atm Forum - These are profies defined by AF in
                           document AF-VMOA-0145.000. In these
                           cases the Identifiers are used and
                           not the table numbers.
                     Itu-t - These profiles are used from the I-366-2.
                   "
                DEFVAL { user }
                ::= { cirEmAtmPvcVccEntry 33 }


cirEmAtmPvcVccEncodingProfileIdA2B    OBJECT-TYPE
                SYNTAX  INTEGER  (1..256)
                MAX-ACCESS read-write
                STATUS current
                DESCRIPTION " These are profiles defined according to standards
                     User-Profile - No restrictions or checks, user
                              freedom to choose any combination
                              of Params.
                     Atm Forum - These are profies defined by AF in
                           document AF-VMOA-0145.000. In these
                           cases the Identifiers are used and
                           not the table numbers.
                     Itu-t - These profiles are used from the I-366-2.
                   "

                DEFVAL { 1 }
                ::= { cirEmAtmPvcVccEntry 34 }

cirEmAtmPvcVccEncodingProfileIdB2A    OBJECT-TYPE
                SYNTAX  INTEGER (1..256)
                MAX-ACCESS read-write
                STATUS current
                DESCRIPTION " These are profiles defined according to standards
                     User-Profile - No restrictions or checks, user
                              freedom to choose any combination
                              of Params.
                     Atm Forum - These are profies defined by AF in
                           document AF-VMOA-0145.000. In these
                           cases the Identifiers are used and
                           not the table numbers.
                     Itu-t - These profiles are used from the I-366-2.
                   "
                DEFVAL { 1 }
                ::= { cirEmAtmPvcVccEntry 35 }


 --     In    ____________________________________ Out
 --    ______| SWITCH                            |__________
 --     Out  |                                   |  In
 --          |___________________________________|
 --  Frame Relay UNI A                           ATM UNI/NNI B
 --                                   

 -- The Frame Relay to ATM Inter-working PVC Table

frAtmPvcVccTable OBJECT-TYPE
                    SYNTAX SEQUENCE OF FrAtmPvcVccEntry
                    MAX-ACCESS not-accessible
                    STATUS current
                    DESCRIPTION "Table of frame relay to ATM IWF connections"
                    ::= { connectionConfig 7 }

frAtmPvcVccEntry OBJECT-TYPE
                SYNTAX FrAtmPvcVccEntry
                MAX-ACCESS not-accessible
                STATUS current
                DESCRIPTION "Row definition of frame relay to ATM IWF 
                              connections "
                INDEX { frAtmPvcVccIfA, frAtmPvcVccDlciA, frAtmPvcVccIfB,
                        frAtmPvcVccVpiB, frAtmPvcVccVciB }
                ::= { frAtmPvcVccTable 1 }

FrAtmPvcVccEntry ::= SEQUENCE
                             {
                              frAtmPvcVccIfA                    IntfIndex,
                              frAtmPvcVccDlciA                  Integer32,
                              frAtmPvcVccIfB                    IntfIndex,
                              frAtmPvcVccVpiB                   INTEGER,
                              frAtmPvcVccVciB                   INTEGER,
                              frAtmPvcVccMaxFrameSizeIn         Integer32,
                              frAtmPvcVccBcIn                   Integer32,
                              frAtmPvcVccBeIn                   Integer32,
                              frAtmPvcVccCirIn                  Integer32,
                              frAtmPvcVccMaxFrameSizeOut        Integer32,
                              frAtmPvcVccBcOut                  Integer32,
                              frAtmPvcVccBeOut                  Integer32,
                              frAtmPvcVccCirOut                 Integer32,
                              frAtmPvcVccServiceType            INTEGER,
                              frAtmPvcVccFlow                   INTEGER,
                              frAtmPvcVccRowStatus              RowStatus,
                              frAtmPvcVccTimeLenIn              INTEGER,
                              frAtmPvcVccInterWorkingFuncIn     INTEGER,
                              frAtmPvcVccTimeLenOut             INTEGER,
                              frAtmPvcVccInterWorkingFuncOut    INTEGER,
                              frAtmPvcVccPeakCellRateA2B        Integer32,
                              frAtmPvcVccSusCellRateA2B         Integer32,
                              frAtmPvcVccMaxBurstSizeA2B        Integer32,
                              frAtmPvcVccPeakCellRateB2A        Integer32,
                              frAtmPvcVccSusCellRateB2A         Integer32,
                              frAtmPvcVccMaxBurstSizeB2A        Integer32,
                              frAtmPvcVccConnectionStatus       INTEGER,

                              frAtmPvcVccDualHomed              INTEGER,

                              frAtmPvcVccOamStatus              INTEGER,
                              frAtmPvcVccViB                    INTEGER,
                              frAtmPvcVccCnfrmTypeB2A           INTEGER,

                              frAtmPvcVccVUNIB                  INTEGER,

                              frAtmPvcVccOAMConnEndPtStatus     INTEGER,
                              frAtmPvcVccOAMSegEndPtStatus      INTEGER,
                              frAtmPvcVccMfsB2A                 INTEGER,
                              frAtmPvcVccConnFailureCauseA      FrConnFailureCause,
                              frAtmPvcVccConnFailureCauseB      AtmConnFailureCause,
                              frAtmPvcVccTrafficShapingA2B      INTEGER
                             }

frAtmPvcVccIfA        OBJECT-TYPE
                SYNTAX IntfIndex
                MAX-ACCESS not-accessible
                STATUS current
                DESCRIPTION "Interface index for side A, the frame relay side, 
                             of a frame relay-atm PVC VCC connection.  Number 
                             value is interpreted as an interface of the form, 
                             SSPPCCC, where SS is the card slot, PP is the port 
                             number, and CCC is the channel number."
                ::= { frAtmPvcVccEntry 1 }

frAtmPvcVccDlciA OBJECT-TYPE
                SYNTAX Integer32
                MAX-ACCESS not-accessible
                STATUS current
                DESCRIPTION "DLCI value for side A, the frame relay side, 
                             of a frame relay-atm PVC VCC connection.  Valid
                             range is a number between 0 and 1023."
                ::= { frAtmPvcVccEntry 2 }

frAtmPvcVccIfB OBJECT-TYPE
                SYNTAX IntfIndex
                MAX-ACCESS not-accessible
                STATUS current
                DESCRIPTION "Interface index for side B, the atm side, of a 
                             frame relay-atm PVC VCC connection.  Number value 
                             is interpreted as an interface of the form, 
                             SSPPCCC, where SS is the card slot, PP is the port 
                             number, and CCC is the channel number."
                ::= { frAtmPvcVccEntry 3 }

frAtmPvcVccVpiB OBJECT-TYPE
                SYNTAX INTEGER (0..4095)
                MAX-ACCESS not-accessible
                STATUS current
                DESCRIPTION "VPI value for side B, the atm side, of a frame
                             relay-atm PVC VCC connection.  Valid range is a 
                             number between 0 and 4095."
                ::= { frAtmPvcVccEntry 4 }

frAtmPvcVccVciB OBJECT-TYPE
                SYNTAX INTEGER (0..65535)
                MAX-ACCESS not-accessible
                STATUS current
                DESCRIPTION "VCI value for side B, the atm side, of a frame
                             relay-atm PVC VCC connection.  Valid range is a 
                             number between 0 and 65535."
                ::= { frAtmPvcVccEntry 5 }

frAtmPvcVccMaxFrameSizeIn OBJECT-TYPE
                SYNTAX Integer32
                MAX-ACCESS read-write
                STATUS current
                DESCRIPTION "The value of this object is the size in octets of
                                  the largest frame relay information field for this
                                    PVC in the ingress direction (out of the frame 
                             relay UNI)."
                DEFVAL { 4096 }
                ::= { frAtmPvcVccEntry 6 }

frAtmPvcVccBcIn OBJECT-TYPE
                SYNTAX Integer32
                MAX-ACCESS read-write
                STATUS current
                DESCRIPTION "The value of this object is equal to the
                                  committed burst size (Bc) parameter (measured in
                                  bits) for this PVC in the ingress
                                  direction (into the frame relay UNI)."
                DEFVAL { 0 }
                ::= { frAtmPvcVccEntry 7 }

frAtmPvcVccBeIn OBJECT-TYPE
                SYNTAX Integer32
                MAX-ACCESS read-write
                STATUS current
                DESCRIPTION "The value of this object is equal to the excess
                                  burst size (Be) parameter (measured in bits) for
                             this PVC in the ingress direction (into
                                    the frame relay UNI)."
                DEFVAL { 45000000 }
                ::= { frAtmPvcVccEntry 8 }

frAtmPvcVccCirIn OBJECT-TYPE
                SYNTAX Integer32
                MAX-ACCESS read-write
                STATUS current
                DESCRIPTION "The value of this object is equal to the
                                  committed information rate (CIR) parameter
                                  (measured in bits per second) for this PVC
                             in the ingress direction (into the frame
                                  relay UNI)."
                DEFVAL { 0 }
                ::= { frAtmPvcVccEntry 9 }

frAtmPvcVccMaxFrameSizeOut OBJECT-TYPE
                SYNTAX Integer32
                MAX-ACCESS read-write
                STATUS current
                DESCRIPTION "The value of this object is the size in octets of
                                  the largest frame relay information field for this
                                    PVC in the egress direction (out of the frame 
                             relay UNI)."
                DEFVAL { 4096 }
                ::= { frAtmPvcVccEntry 10 }

frAtmPvcVccBcOut OBJECT-TYPE
                SYNTAX Integer32
                MAX-ACCESS read-write
                STATUS current
                DESCRIPTION "The value of this object is equal to the
                                  committed burst size (Bc) parameter (measured in
                                  bits) for this PVC in the egress
                                  direction (into the frame relay UNI)."
                DEFVAL { 0 }
                ::= { frAtmPvcVccEntry 11 }

frAtmPvcVccBeOut OBJECT-TYPE
                SYNTAX Integer32
                MAX-ACCESS read-write
                STATUS current
                DESCRIPTION "The value of this object is equal to the excess
                                  burst size (Be) parameter (measured in bits) for
                             this PVC in the egress direction (into
                                    the frame relay UNI)"
                DEFVAL { 45000000 }
                ::= { frAtmPvcVccEntry 12 }

frAtmPvcVccCirOut OBJECT-TYPE
                SYNTAX Integer32
                MAX-ACCESS read-write
                STATUS current
                DESCRIPTION "The value of this object is equal to the
                                  committed information rate (CIR) parameter
                                  (measured in bits per second) for this PVC
                             in the egress direction (into the frame
                                  relay UNI)."
                DEFVAL { 0 }
                ::= { frAtmPvcVccEntry 13 }

frAtmPvcVccServiceType OBJECT-TYPE
                SYNTAX INTEGER {
                                ubr(1),
                                vbr-nrt2(2),
                                vbr-nrt1(3),
                                vbr-rt2(4),
                                vbr-rt1(5),
                                vbr-express(6),
                                gfr2(7)
                               }
                MAX-ACCESS read-write
                STATUS current
                DESCRIPTION "service type, Frame relay traffic is carried
                             by VBR type of service only."
                DEFVAL { ubr }
                ::= { frAtmPvcVccEntry 14 }

frAtmPvcVccFlow OBJECT-TYPE
                SYNTAX INTEGER {
                                duplex(1),
                                simplexA2B(2),
                                simplexB2A(3)
                               }
                MAX-ACCESS read-write
                STATUS current
                DESCRIPTION "Flow Type"
                DEFVAL { duplex }
                ::= { frAtmPvcVccEntry 15 }

frAtmPvcVccRowStatus OBJECT-TYPE
                SYNTAX RowStatus
                MAX-ACCESS read-write
                STATUS current
                DESCRIPTION "row status"
                ::= { frAtmPvcVccEntry 16 }

frAtmPvcVccTimeLenIn OBJECT-TYPE
                SYNTAX INTEGER (64..4000)
                MAX-ACCESS read-only
                STATUS current
                DESCRIPTION "The time interval over which CIR and the burst
                             sizes (Bc and Be) are measured in the A2B 
                             direction.  The unit is milliseconds."
                DEFVAL { 1000 }
                ::= { frAtmPvcVccEntry 17 }

frAtmPvcVccInterWorkingFuncIn OBJECT-TYPE
                SYNTAX INTEGER {

                                frf8-Transl(1),
                                frf8-Pass(2),

                                frf5(3)
                               }
                MAX-ACCESS read-write
                STATUS current
                DESCRIPTION "InterWorking function."



                DEFVAL { frf8-Transl }

                ::= { frAtmPvcVccEntry 18 }

frAtmPvcVccTimeLenOut OBJECT-TYPE
                SYNTAX INTEGER (64..4000)
                MAX-ACCESS read-only
                STATUS current
                DESCRIPTION "The time interval over which CIR and the burst
                             sizes (Bc and Be) are measured in the A2B 
                             direction.  The unit is milliseconds."
                DEFVAL { 1000 }
                ::= { frAtmPvcVccEntry 19 }

frAtmPvcVccInterWorkingFuncOut OBJECT-TYPE
                SYNTAX INTEGER {

                                frf8-Transl(1),
                                frf8-Pass(2),

                                frf5(3)
                               }
                MAX-ACCESS read-write
                STATUS current
                DESCRIPTION "InterWorking function."



                DEFVAL { frf8-Transl }

                ::= { frAtmPvcVccEntry 20 }

frAtmPvcVccPeakCellRateA2B OBJECT-TYPE
                SYNTAX Integer32
                MAX-ACCESS read-only
                STATUS current
                DESCRIPTION "Peak cell rate - side A, in cells per second, 
                                  this will reflect the frame relay parameters in
                                    atm terms."
                DEFVAL { 1 }
                ::= { frAtmPvcVccEntry 21 }

frAtmPvcVccSusCellRateA2B OBJECT-TYPE
                SYNTAX Integer32
                MAX-ACCESS read-only
                STATUS current
                DESCRIPTION "Sustained cell rate - side A, in cells per second,
                                  this will reflect the frame relay parameters in
                                    atm terms."
                DEFVAL { 1 }
                ::= { frAtmPvcVccEntry 22 }

frAtmPvcVccMaxBurstSizeA2B OBJECT-TYPE
                SYNTAX Integer32
                MAX-ACCESS read-only
                STATUS current
                DESCRIPTION "Maximum burst size - side A, in cells, 
                                  this will reflect the frame relay parameters in
                                    atm terms."
                DEFVAL { 1 }
                ::= { frAtmPvcVccEntry 23 }

frAtmPvcVccPeakCellRateB2A OBJECT-TYPE
                SYNTAX Integer32
                MAX-ACCESS read-only
                STATUS current
                DESCRIPTION "Peak cell rate - side B, in cells per second, 
                                  this will reflect the frame relay parameters in
                                    atm terms."
                DEFVAL { 1 }
                ::= { frAtmPvcVccEntry 24 }

frAtmPvcVccSusCellRateB2A OBJECT-TYPE
                SYNTAX Integer32
                MAX-ACCESS read-only
                STATUS current
                DESCRIPTION "Sustained cell rate - side B, in cells per second,
                                  this will reflect the frame relay parameters in
                                    atm terms."
                DEFVAL { 1 }
                ::= { frAtmPvcVccEntry 25 }

frAtmPvcVccMaxBurstSizeB2A OBJECT-TYPE
                SYNTAX Integer32
                MAX-ACCESS read-only
                STATUS current
                DESCRIPTION "Maximum burst size - side B, in cells, 
                                  this will reflect the frame relay parameters in
                                    atm terms."
                DEFVAL { 1 }
                ::= { frAtmPvcVccEntry 26 }

frAtmPvcVccConnectionStatus OBJECT-TYPE
                SYNTAX INTEGER {
                                active(1),
                                inactive(2),
                                inactiveA2B-B2A(3),
                                inactiveA2B(4),
                                inactiveB2A(5)
                               }
                MAX-ACCESS read-only
                STATUS current
                DESCRIPTION "Indicates the current connections status.
                             Active:  All interfaces through which the 
                                      connection is going are in service.
                             Inactive:  One of the end interfaces of the 
                                        connection is not in service.

                             The rest of the states apply to connections going
                             through resource interfaces like DSP2 and FEC.  These
                             interfaces are dynamically allocated.

                             InactiveA2B-B2A:  Both the A2B and B2A resource
                                               interfaces are not in service.
                             InactiveA2B:  The A2B resource interface is not in 
                                           service.
                             InactiveB2A:  The B2A resource interface is not in 
                                           service.

                             If an end interface and the resource interfaces 
                             are out of service, the status will be inactive 
                             because the end interfaces take priority."
                DEFVAL { inactive }
                ::= { frAtmPvcVccEntry 27 }


frAtmPvcVccDualHomed OBJECT-TYPE
                SYNTAX INTEGER {
                                no(1),
                                yes(2)
                               }
                MAX-ACCESS read-only
                STATUS current
                DESCRIPTION "Does this PVC need a backup Dual homing PVC."
                DEFVAL { no }
                ::= { frAtmPvcVccEntry 28 }


frAtmPvcVccOamStatus OBJECT-TYPE
                SYNTAX INTEGER {
                                unsupp(1),
                                end-Pt(2),
                                end-Seg-Pt(3)
                               }
                MAX-ACCESS read-write
                STATUS current
                DESCRIPTION "Indicates the OAM monitoring status of side A.
                             The 2 possible states are:
                             Unsupp:  No monitoring enabled.
                             End-Pt:  A side is only an end point, therefore
                                it will respond to AIS/RDI."
                DEFVAL { unsupp }
                ::= { frAtmPvcVccEntry 29 }

frAtmPvcVccViB  OBJECT-TYPE
                SYNTAX INTEGER (0..1024)
                MAX-ACCESS read-write
                STATUS current
                DESCRIPTION "VI to associate the Egress part of the
                        A2B connection ."
                DEFVAL { 0 }
                ::= { frAtmPvcVccEntry 30 }

frAtmPvcVccCnfrmTypeB2A    OBJECT-TYPE
                SYNTAX INTEGER {
                                    best-effort(1),
                                one-bucket-notag-0plus1(2),
                                two-bucket-notag-0plus1-0plus1(3),
                                two-bucket-notag-0plus1-0(4),
                                two-bucket-tag-0plus1-0(5),
                                best-effort-tag(6)
                               }
                MAX-ACCESS read-write
                STATUS current
                DESCRIPTION "The following is the description of this field
                        This will be used in conjunction with the
                        service type field to get the correct
                        traffic behaviour. In the conformances the 
                        the 0 or 0plus1 refers to the clp bit in the
                        cells. If 0plus1 is the bucket reference then
                        the clp bit is ignored. If 0 is specified for 
                        the bucket then check only clp=0 cells.
                        1: Best Effort will try to send all cellsin a 
                        best effort way. This will follow the 
                        Aqueman Algorithm
                        2: one-bucket-notag-0plus1 will use 1 bucket
                        i.e is the PCR(0+1) bucket and drop all
                        cells in excess.
                        3: two-bucket-notag-0plus1-0plus1 uses 2 buckets.
                        The 2 buckets are pcr(0+1) and scr(0+1).
                        All cells conforming to both buckets will be
                        passed through. The rest will be dropped.
                        4: two-bucket-notag-0plus1-0 uses 2 buckets.
                        The 2 buckets are pcr(0+1) and scr(0) or 
                        pcr(0). Cells which conform to both buckets
                        are passed through. The rest are dropped.
                        5: two-bucket-tag-0plus1-0 uses 2 buckets.
                        The 2 buckets are pcr(0+1) and scr(0) or 
                        pcr(0). Cells which do not conform to the first
                        bucket are dropped. Cells which do not 
                        conform to the 2nd bucket are tagged.
                        6: best-effort-tag. Tag all cells and then
                        do a best effort.  "
                DEFVAL { best-effort }
                ::= { frAtmPvcVccEntry 31 }


frAtmPvcVccVUNIB  OBJECT-TYPE
                SYNTAX INTEGER (0..255)
                MAX-ACCESS read-write
                STATUS current
                DESCRIPTION "VUNI to associate the Egress part of the
                        A2B connection ."
                DEFVAL { 0 }
                ::= { frAtmPvcVccEntry 32 }


frAtmPvcVccOAMConnEndPtStatus    OBJECT-TYPE
                 SYNTAX INTEGER {
                                ete-active(1),
                                ete-ais-state(2),
                                ete-rdi-state(3),
                                ete-ais-rdi-state(4)
                                }
                MAX-ACCESS read-only
                STATUS current
                DESCRIPTION "Connection endpoint status. Valid only 
                        at connection endpoint."
                ::= { frAtmPvcVccEntry 33 }
                
frAtmPvcVccOAMSegEndPtStatus    OBJECT-TYPE
                SYNTAX INTEGER {
                                seg-active(1), 
                                seg-ais-state(2),
                                seg-rdi-state(3),
                                seg-ais-rdi-state(4)
                                }
                MAX-ACCESS read-only
                STATUS current
                DESCRIPTION "Segment endpoint status. Valid only at
                        segment/connection endpoint."
                 ::= { frAtmPvcVccEntry 34 }

frAtmPvcVccMfsB2A OBJECT-TYPE
                SYNTAX INTEGER (1..65535)
                MAX-ACCESS read-write 
                STATUS current
                DESCRIPTION "Maximum Frame Size for GFR traffic" 
                DEFVAL { 1 }
                ::= { frAtmPvcVccEntry 35 }

frAtmPvcVccConnFailureCauseA    OBJECT-TYPE
                SYNTAX FrConnFailureCause
                MAX-ACCESS read-only
                STATUS current
                DESCRIPTION " connestion status reason code"
                ::= { frAtmPvcVccEntry 36 }

frAtmPvcVccConnFailureCauseB    OBJECT-TYPE
                SYNTAX AtmConnFailureCause
                MAX-ACCESS read-only
                STATUS current
                DESCRIPTION "connection status reason code"
                ::= { frAtmPvcVccEntry 37 }

frAtmPvcVccTrafficShapingA2B     OBJECT-TYPE
                SYNTAX INTEGER {
                                disabled(1),
                                enabled(2)
                               }
                MAX-ACCESS read-write
                STATUS current
                DESCRIPTION "Traffic Shaping Support in the A2B direction."
                DEFVAL { disabled }
                ::= { frAtmPvcVccEntry 38 }



 --     In    ____________________________________ Out
 --    ______| SWITCH                            |__________
 --     Out  |                                   |  In
 --          |___________________________________|
 --  Frame Relay UNI A                           Frame Relay UNI B
 --                                   

 -- The Frame Relay PVC Table

frFrPvcTable         OBJECT-TYPE
                    SYNTAX SEQUENCE OF FrFrPvcEntry
                    MAX-ACCESS not-accessible
                    STATUS current
                    DESCRIPTION "Table of frame relay to frame relay connections"
                    ::= { connectionConfig 8 }

frFrPvcEntry         OBJECT-TYPE
                SYNTAX FrFrPvcEntry
                MAX-ACCESS not-accessible
                STATUS current
                DESCRIPTION "Row definition of frame relay to frame relay PVC
                             connections  "
                INDEX { frFrPvcIfA, frFrPvcDlciA,
                        frFrPvcIfB, frFrPvcDlciB }
                ::= { frFrPvcTable 1 }

FrFrPvcEntry ::= SEQUENCE {
                           frFrPvcIfA                        IntfIndex,
                           frFrPvcDlciA                  Integer32,
                           frFrPvcIfB                        IntfIndex,
                           frFrPvcDlciB                        Integer32,
                           frFrPvcMaxFrameSizeA2B         Integer32,
                           frFrPvcBcA2B                   Integer32,
                           frFrPvcBeA2B                        Integer32,
                           frFrPvcCirA2B                  Integer32,
                           frFrPvcMaxFrameSizeB2A         Integer32,
                           frFrPvcBcB2A                  Integer32,
                           frFrPvcBeB2A                  Integer32,
                           frFrPvcCirB2A                 Integer32,
                           frFrPvcServiceType                 INTEGER,
                           frFrPvcFlow                         INTEGER,
                           frFrPvcRowStatus                RowStatus,
                           frFrPvcTimeLenA2B                 INTEGER,
                           frFrPvcInterWorkingFuncA2B         INTEGER,
                           frFrPvcTimeLenB2A                 INTEGER,
                           frFrPvcInterWorkingFuncB2A         INTEGER,
                           frFrPvcPeakCellRateA2B        Integer32,
                           frFrPvcSusCellRateA2B        Integer32,
                           frFrPvcMaxBurstSizeA2B        Integer32,
                           frFrPvcPeakCellRateB2A        Integer32,
                           frFrPvcSusCellRateB2A        Integer32,
                           frFrPvcMaxBurstSizeB2A        Integer32,
                           frFrPvcConnectionStatus      INTEGER,
                           frFrPvcConnFailureCauseA     FrConnFailureCause,
                           frFrPvcConnFailureCauseB     FrConnFailureCause
                          }

frFrPvcIfA        OBJECT-TYPE
                SYNTAX IntfIndex
                MAX-ACCESS not-accessible
                STATUS current
                DESCRIPTION "Interface index for side A of a frame relay-frame
                             relay PVC connection.  Number value is interpreted 
                             as an interface of the form, SSPPCCC, where SS is 
                             the card slot, PP is the port number, and CCC is 
                             the channel number."
                ::= { frFrPvcEntry 1 }

frFrPvcDlciA OBJECT-TYPE
                SYNTAX Integer32
                MAX-ACCESS not-accessible
                STATUS current
                DESCRIPTION "DLCI value for side A of a frame relay-frame relay
                             PVC connection.  Valid range is a number between
                             0 and 1023."
                ::= { frFrPvcEntry 2 }

frFrPvcIfB OBJECT-TYPE
                SYNTAX IntfIndex
                MAX-ACCESS not-accessible
                STATUS current
                DESCRIPTION "Interface index for side B of a frame relay-frame
                             relay PVC connection.  Number value is interpreted 
                             as an interface of the form, SSPPCCC, where SS is 
                             the card slot, PP is the port number, and CCC is 
                             the channel number."
                ::= { frFrPvcEntry 3 }

frFrPvcDlciB OBJECT-TYPE
                SYNTAX Integer32
                MAX-ACCESS not-accessible
                STATUS current
                DESCRIPTION "DLCI value for side B of a frame relay-frame relay
                             PVC connection.  Valid range is a number between
                             0 and 1023."
                ::= { frFrPvcEntry 4 }

frFrPvcMaxFrameSizeA2B OBJECT-TYPE
                SYNTAX Integer32
                MAX-ACCESS read-write
                STATUS current
                DESCRIPTION "The value of this object is the size in octets of
                                  the largest frame relay information field for this
                                    PVC in the A to B direction."
                DEFVAL { 4096 }
                ::= { frFrPvcEntry 5 }

frFrPvcBcA2B OBJECT-TYPE
                SYNTAX Integer32
                MAX-ACCESS read-write
                STATUS current
                DESCRIPTION "The value of this object is equal to the
                                  committed burst size (Bc) parameter (measured in
                                  bits) for this PVC in the A to B direction."
                DEFVAL { 0 }
                ::= { frFrPvcEntry 6 }

frFrPvcBeA2B OBJECT-TYPE
                SYNTAX Integer32
                MAX-ACCESS read-write
                STATUS current
                DESCRIPTION "The value of this object is equal to the excess
                                  burst size (Be) parameter (measured in bits) for
                             this PVC in the A to B direction."
                DEFVAL { 45000000 }
                ::= { frFrPvcEntry 7 }

frFrPvcCirA2B OBJECT-TYPE
                SYNTAX Integer32
                MAX-ACCESS read-write
                STATUS current
                DESCRIPTION "The value of this object is equal to the
                                  committed information rate (CIR) parameter
                                  (measured in bits per second) for this PVC
                             in the A to B direction."
                DEFVAL { 0 }
                ::= { frFrPvcEntry 8 }

frFrPvcMaxFrameSizeB2A OBJECT-TYPE
                SYNTAX Integer32
                MAX-ACCESS read-write
                STATUS current
                DESCRIPTION "The value of this object is the size in octets of
                                  the largest frame relay information field for this
                                    PVC in the B to A direction."
                DEFVAL { 4096 }
                ::= { frFrPvcEntry 9 }

frFrPvcBcB2A OBJECT-TYPE
                SYNTAX Integer32
                MAX-ACCESS read-write
                STATUS current
                DESCRIPTION "The value of this object is equal to the
                                  committed burst size (Bc) parameter (measured in
                                  bits) for this PVC in the B to A direction."
                DEFVAL { 0 }
                ::= { frFrPvcEntry 10 }

frFrPvcBeB2A OBJECT-TYPE
                SYNTAX Integer32
                MAX-ACCESS read-write
                STATUS current
                DESCRIPTION "The value of this object is equal to the excess
                                  burst size (Be) parameter (measured in bits) for
                             this PVC in the B to A direction."
                DEFVAL { 45000000 }
                ::= { frFrPvcEntry 11 }

frFrPvcCirB2A OBJECT-TYPE
                SYNTAX Integer32
                MAX-ACCESS read-write
                STATUS current
                DESCRIPTION "The value of this object is equal to the
                                  committed information rate (CIR) parameter
                                  (measured in bits per second) for this PVC
                             in the B to A direction."
                DEFVAL { 0 }
                ::= { frFrPvcEntry 12 }

frFrPvcServiceType OBJECT-TYPE
                SYNTAX INTEGER {
                                ubr(1),
                                vbr-nrt2(2),
                                vbr-nrt1(3),
                                vbr-rt2(4),
                                vbr-rt1(5),
                                vbr-express(6)
                               }
                MAX-ACCESS read-write
                STATUS current
                DESCRIPTION "service type, Frame relay traffic is carried
                             by VBR type of service only."
                DEFVAL { ubr }
                ::= { frFrPvcEntry 13 }

frFrPvcFlow        OBJECT-TYPE
                SYNTAX INTEGER {
                                duplex(1),
                                simplexA2B(2)
                               }
                MAX-ACCESS read-write
                STATUS current
                DESCRIPTION " Flow Type"
                DEFVAL { duplex }
                ::= { frFrPvcEntry 14 }

frFrPvcRowStatus OBJECT-TYPE
                SYNTAX RowStatus
                MAX-ACCESS read-write
                STATUS current
                DESCRIPTION "row status"
                ::= { frFrPvcEntry 15 }

frFrPvcTimeLenA2B OBJECT-TYPE
                SYNTAX INTEGER (64..4000)
                MAX-ACCESS read-only
                STATUS current
                DESCRIPTION "The time interval over which CIR and the burst
                             sizes (Bc and Be) are measured in the A2B 
                             direction.  The unit is milliseconds."
                DEFVAL { 1000 }
                ::= { frFrPvcEntry 16 }

frFrPvcInterWorkingFuncA2B OBJECT-TYPE
                SYNTAX INTEGER {
                                frf8-Transl(1),
                                frf8-Pass(2),
                                frf5(3)
                               }
                MAX-ACCESS read-write
                STATUS current
                DESCRIPTION "InterWorking function."
                DEFVAL { frf8-Transl }
                ::= { frFrPvcEntry 17 }

frFrPvcTimeLenB2A OBJECT-TYPE
                SYNTAX INTEGER (64..4000)
                MAX-ACCESS read-only
                STATUS current
                DESCRIPTION "The time interval over which CIR and the burst
                             sizes (Bc and Be) are measured in the A2B 
                             direction.  The unit is milliseconds."
                DEFVAL { 1000 }
                ::= { frFrPvcEntry 18 }

frFrPvcInterWorkingFuncB2A OBJECT-TYPE
                SYNTAX INTEGER {
                                frf8-Transl(1),
                                frf8-Pass(2),
                                frf5(3)
                               }
                MAX-ACCESS read-write
                STATUS current
                DESCRIPTION "InterWorking function."
                DEFVAL { frf8-Transl }
                ::= { frFrPvcEntry 19 }

frFrPvcPeakCellRateA2B OBJECT-TYPE
                SYNTAX Integer32
                MAX-ACCESS read-only
                STATUS current
                DESCRIPTION "Peak cell rate - side A, in cells per second, 
                                  this will reflect the frame relay parameters in
                                    atm terms."
                DEFVAL { 1 }
                ::= { frFrPvcEntry 20 }

frFrPvcSusCellRateA2B OBJECT-TYPE
                SYNTAX Integer32
                MAX-ACCESS read-only
                STATUS current
                DESCRIPTION "Sustained cell rate - side A, in cells per second,
                                  this will reflect the frame relay parameters in
                                    atm terms."
                DEFVAL { 1 }
                ::= { frFrPvcEntry 21 }

frFrPvcMaxBurstSizeA2B OBJECT-TYPE
                SYNTAX Integer32
                MAX-ACCESS read-only
                STATUS current
                DESCRIPTION "Maximum burst size - side A, in cells, 
                                  this will reflect the frame relay parameters in
                                    atm terms."
                DEFVAL { 1 }
                ::= { frFrPvcEntry 22 }

frFrPvcPeakCellRateB2A OBJECT-TYPE
                SYNTAX Integer32
                MAX-ACCESS read-only
                STATUS current
                DESCRIPTION "Peak cell rate - side B, in cells per second, 
                                  this will reflect the frame relay parameters in
                                    atm terms."
                DEFVAL { 1 }
                ::= { frFrPvcEntry 23 }

frFrPvcSusCellRateB2A OBJECT-TYPE
                SYNTAX Integer32
                MAX-ACCESS read-only
                STATUS current
                DESCRIPTION "Sustained cell rate - side B, in cells per second,
                                  this will reflect the frame relay parameters in
                                    atm terms."
                DEFVAL { 1 }
                ::= { frFrPvcEntry 24 }

frFrPvcMaxBurstSizeB2A OBJECT-TYPE
                SYNTAX Integer32
                MAX-ACCESS read-only
                STATUS current
                DESCRIPTION "Maximum burst size - side B, in cells, 
                                  this will reflect the frame relay parameters in
                                    atm terms."
                DEFVAL { 1 }
                ::= { frFrPvcEntry 25 }

frFrPvcConnectionStatus OBJECT-TYPE
                SYNTAX INTEGER {
                                active(1),
                                inactive(2),
                                inactiveA2B-B2A(3),
                                inactiveA2B(4),
                                inactiveB2A(5)
                               }
                MAX-ACCESS read-only
                STATUS current
                DESCRIPTION "Indicates the current connections status.
                             Active:  All interfaces through which the 
                                      connection is going are in service.
                             Inactive:  One of the end interfaces of the 
                                        connection is not in service.

                             The rest of the states apply to connections going
                             through resource interfaces like DSP2 and FEC.  These
                             interfaces are dynamically allocated.

                             InactiveA2B-B2A:  Both the A2B and B2A resource
                                               interfaces are not in service.
                             InactiveA2B:  The A2B resource interface is not in 
                                           service.
                             InactiveB2A:  The B2A resource interface is not in 
                                           service.

                             If an end interface and the resource interfaces 
                             are out of service, the status will be inactive 
                             because the end interfaces take priority."
                DEFVAL { inactive }
                ::= { frFrPvcEntry 26 }

frFrPvcConnFailureCauseA    OBJECT-TYPE
                SYNTAX FrConnFailureCause
                MAX-ACCESS read-only
                STATUS current
                DESCRIPTION " connestion status reason code"
                ::= { frFrPvcEntry 27 }

frFrPvcConnFailureCauseB    OBJECT-TYPE
                SYNTAX FrConnFailureCause
                MAX-ACCESS read-only
                STATUS current
                DESCRIPTION "connection status reason code"
                ::= { frFrPvcEntry 28 }


vbrAtmPvcVccTable         OBJECT-TYPE
                    SYNTAX SEQUENCE OF VbrAtmPvcVccEntry
                    MAX-ACCESS not-accessible
                    STATUS current
                    DESCRIPTION "Table of terminal emulation to ATM network 
                             IWF connections "
                    ::= { connectionConfig 9 }

vbrAtmPvcVccEntry         OBJECT-TYPE
                SYNTAX VbrAtmPvcVccEntry
                MAX-ACCESS not-accessible
                STATUS current
                DESCRIPTION "Row definition of terminal emulation to ATM 
                             network IWF connections"
                INDEX { vbrAtmPvcVccIfA, vbrAtmPvcVccIfB,
                        vbrAtmPvcVccVpiB, vbrAtmPvcVccVciB }
                ::= { vbrAtmPvcVccTable 1 }

VbrAtmPvcVccEntry ::= SEQUENCE {
                           vbrAtmPvcVccIfA                IntfIndex,
                           vbrAtmPvcVccIfB                IntfIndex,
                           vbrAtmPvcVccVpiB               INTEGER,
                           vbrAtmPvcVccVciB               INTEGER,
                           vbrAtmPvcVccServiceType        INTEGER,
                           vbrAtmPvcVccPeakCellRateA2B    Integer32,
                           vbrAtmPvcVccSusCellRateA2B     Integer32,
                           vbrAtmPvcVccMaxBurstSizeA2B    Integer32,
                           vbrAtmPvcVccPeakCellRateB2A    Integer32,
                           vbrAtmPvcVccSusCellRateB2A     Integer32,
                           vbrAtmPvcVccMaxBurstSizeB2A    Integer32,
                           vbrAtmPvcVccFlow               INTEGER,
                           vbrAtmPvcVccRowStatus          RowStatus,
                           vbrAtmPvcVccConnectionStatus   INTEGER,

                           vbrAtmPvcVccDualHomed          INTEGER,

                           vbrAtmPvcVccOamStatus          INTEGER,
                           vbrAtmPvcVccViB                INTEGER,
                           vbrAtmPvcVccCnfrmTypeB2A       INTEGER,

                           vbrAtmPvcVccVUNIB              INTEGER,

                           vbrAtmPvcVccOAMConnEndPtStatus INTEGER,
                           vbrAtmPvcVccOAMSegEndPtStatus  INTEGER,
                           vbrAtmPvcVccMfsB2A             INTEGER,
                           vbrAtmPvcVccConnFailureCauseA  ConnFailureCause,
                           vbrAtmPvcVccConnFailureCauseB  AtmConnFailureCause,
                           vbrAtmPvcVccSarTypeB           INTEGER,
                           vbrAtmPvcVccAal2Cid            INTEGER,
                           vbrAtmPvcVccTrafficShapingA2B  INTEGER
                          }

vbrAtmPvcVccIfA        OBJECT-TYPE
                SYNTAX IntfIndex
                MAX-ACCESS not-accessible
                STATUS current
                DESCRIPTION "Interface index for side A, the variable bit rate
                             side, of a variable bit rate-atm PVC VCC 
                             connection.  Number value is interpreted as an 
                             interface of the form, SSPPCCC, where SS is the 
                             card slot, PP is the port number, and CCC is the 
                             channel number."
                ::= { vbrAtmPvcVccEntry 1 }

vbrAtmPvcVccIfB OBJECT-TYPE
                SYNTAX IntfIndex
                MAX-ACCESS not-accessible
                STATUS current
                DESCRIPTION "Interface index for side B, the atm side, of a 
                             variable bit rate-atm PVC VCC connection.  Number 
                             value is interpreted as an interface of the form, 
                             SSPPCCC, where SS is the card slot, PP is the port 
                             number, and CCC is the channel number."
                ::= { vbrAtmPvcVccEntry 2 }

vbrAtmPvcVccVpiB OBJECT-TYPE
               SYNTAX INTEGER (0..4095)
               MAX-ACCESS not-accessible
               STATUS current
               DESCRIPTION "VPI value for side B, the atm side, of a variable
                            bit rate-atm PVC VCC connection.  Valid range is a 
                            number between 0 and 4095."
               ::= { vbrAtmPvcVccEntry 3 }

vbrAtmPvcVccVciB OBJECT-TYPE
               SYNTAX INTEGER (0..65535)
               MAX-ACCESS not-accessible
               STATUS current
               DESCRIPTION "VCI value for side B, the atm side, of a variable
                            bit rate-atm PVC VCC connection.  Valid range is a 
                            number between 0 and 65535."
               ::= { vbrAtmPvcVccEntry 4 }

vbrAtmPvcVccServiceType OBJECT-TYPE
              SYNTAX INTEGER {
                              ubr(1),
                              vbr-nrt2(2),
                              vbr-nrt1(3),
                              vbr-rt2(4),
                              vbr-rt1(5),
                              vbr-express(6),
                              gfr2(7)
                              }
             MAX-ACCESS read-write
             STATUS current
             DESCRIPTION "service type"
             DEFVAL { ubr }
             ::= { vbrAtmPvcVccEntry 5 }

vbrAtmPvcVccPeakCellRateA2B        OBJECT-TYPE
                SYNTAX Integer32
                MAX-ACCESS read-write
                STATUS current
                DESCRIPTION "peak cell rate - side A, in cell per second"
                DEFVAL { 1 }
                ::= { vbrAtmPvcVccEntry 6 }
 
vbrAtmPvcVccSusCellRateA2B OBJECT-TYPE
                SYNTAX Integer32
                MAX-ACCESS read-write
                STATUS current
                DESCRIPTION "sustained rate - side A, in cell per second"
                DEFVAL { 1 }
                ::= { vbrAtmPvcVccEntry 7 }
 
vbrAtmPvcVccMaxBurstSizeA2B        OBJECT-TYPE
                SYNTAX Integer32
                MAX-ACCESS read-write
                STATUS current
                DESCRIPTION "maximum burst size - side A, in cells"
                DEFVAL { 1 }
                ::= { vbrAtmPvcVccEntry 8 }
 
vbrAtmPvcVccPeakCellRateB2A        OBJECT-TYPE
                SYNTAX Integer32
                MAX-ACCESS read-write
                STATUS current
                DESCRIPTION "peak rate - side B, in cell per second."
                DEFVAL { 1 }
                ::= { vbrAtmPvcVccEntry 9 }
 
vbrAtmPvcVccSusCellRateB2A OBJECT-TYPE
                SYNTAX Integer32
                MAX-ACCESS read-write
                STATUS current
                DESCRIPTION "sustained rate - side B, in cell per second."
                DEFVAL { 1 }
                ::= { vbrAtmPvcVccEntry 10 }
 
vbrAtmPvcVccMaxBurstSizeB2A        OBJECT-TYPE
                SYNTAX Integer32
                MAX-ACCESS read-write
                STATUS current
                DESCRIPTION "maximum burst size - side B, in cells."
                DEFVAL { 1 }
                ::= { vbrAtmPvcVccEntry 11 }

vbrAtmPvcVccFlow OBJECT-TYPE
                SYNTAX INTEGER {
                                duplex(1),
                                simplexA2B(2),
                                simplexB2A(3)
                               }
                MAX-ACCESS read-write
                STATUS current
                DESCRIPTION "Flow type"
                DEFVAL { duplex }
                ::= { vbrAtmPvcVccEntry 12 }

vbrAtmPvcVccRowStatus OBJECT-TYPE
                SYNTAX RowStatus
                MAX-ACCESS read-write
                STATUS current
                DESCRIPTION "row status"
                ::= { vbrAtmPvcVccEntry 13 }

vbrAtmPvcVccConnectionStatus OBJECT-TYPE
                SYNTAX INTEGER {
                                active(1),
                                inactive(2),
                                inactiveA2B-B2A(3),
                                inactiveA2B(4),
                                inactiveB2A(5)
                               }
                MAX-ACCESS read-only
                STATUS current
                DESCRIPTION "Indicates the current connections status.
                             Active:  All interfaces through which the 
                                      connection is going are in service.
                             Inactive:  One of the end interfaces of the 
                                        connection is not in service.

                             The rest of the states apply to connections going
                             through resource interfaces like DSP2 and FEC.  
                             These interfaces are dynamically allocated.

                             InactiveA2B-B2A:  Both the A2B and B2A resource
                                               interfaces are not in service.
                             InactiveA2B:  The A2B resource interface is not in 
                                           service.
                             InactiveB2A:  The B2A resource interface is not in 
                                           service.

                             If an end interface and the resource interfaces 
                             are out of service, the status will be inactive 
                             because the end interfaces take priority."
                DEFVAL { inactive }
                ::= { vbrAtmPvcVccEntry 14 }


vbrAtmPvcVccDualHomed OBJECT-TYPE
                SYNTAX INTEGER {
                                no(1),
                                yes(2)
                               }
                MAX-ACCESS read-only
                STATUS current
                DESCRIPTION "Does this PVC need a backup Dual homing PVC."
                DEFVAL { no }
                ::= { vbrAtmPvcVccEntry 15 }


vbrAtmPvcVccOamStatus OBJECT-TYPE
                SYNTAX INTEGER {
                                unsupp(1),
                                end-Pt(2),
                                end-Seg-Pt(3)
                               }
                MAX-ACCESS read-write
                STATUS current
                DESCRIPTION "Indicates the OAM monitoring status of side A.
                             The 2 possible states are:
                             Unsupp:  No monitoring enabled.
                             End-Pt:  A side is only an end point, therefore
                                it will respond to AIS/RDI.
                             End-Seg-Pt: Connection endPoint that is also 
                             a segment endPoint."
                DEFVAL { unsupp }
                ::= { vbrAtmPvcVccEntry 16 }

vbrAtmPvcVccViB OBJECT-TYPE
                SYNTAX INTEGER (0..1024)
                MAX-ACCESS read-write
                STATUS current
                DESCRIPTION "VI to associate the Egress part of the
                        A2B connection ." 
                DEFVAL { 0 }
                ::= { vbrAtmPvcVccEntry 17 }


vbrAtmPvcVccCnfrmTypeB2A    OBJECT-TYPE
                SYNTAX INTEGER {
                                    best-effort(1),
                                one-bucket-notag-0plus1(2),
                                two-bucket-notag-0plus1-0plus1(3),
                                two-bucket-notag-0plus1-0(4),
                                two-bucket-tag-0plus1-0(5),
                                best-effort-tag(6)
                               }
                MAX-ACCESS read-write
                STATUS current
                DESCRIPTION "The following is the description of this field
                        This will be used in conjunction with the
                        service type field to get the correct
                        traffic behaviour. In the conformances the 
                        the 0 or 0plus1 refers to the clp bit in the
                        cells. If 0plus1 is the bucket reference then
                        the clp bit is ignored. If 0 is specified for 
                        the bucket then check only clp=0 cells.
                        1: Best Effort will try to send all cellsin a 
                        best effort way. This will follow the 
                        Aqueman Algorithm
                        2: one-bucket-notag-0plus1 will use 1 bucket
                        i.e is the PCR(0+1) bucket and drop all
                        cells in excess.
                        3: two-bucket-notag-0plus1-0plus1 uses 2 buckets.
                        The 2 buckets are pcr(0+1) and scr(0+1).
                        All cells conforming to both buckets will be
                        passed through. The rest will be dropped.
                        4: two-bucket-notag-0plus1-0 uses 2 buckets.
                        The 2 buckets are pcr(0+1) and scr(0) or 
                        pcr(0). Cells which conform to both buckets
                        are passed through. The rest are dropped.
                        5: two-bucket-tag-0plus1-0 uses 2 buckets.
                        The 2 buckets are pcr(0+1) and scr(0) or 
                        pcr(0). Cells which do not conform to the first
                        bucket are dropped. Cells which do not 
                        conform to the 2nd bucket are tagged.
                        6: best-effort-tag. Tag all cells and then
                        do a best effort.  "
                DEFVAL { best-effort }
                ::= { vbrAtmPvcVccEntry 18 }


vbrAtmPvcVccVUNIB OBJECT-TYPE
                SYNTAX INTEGER (0..255)
                MAX-ACCESS read-write
                STATUS current
                DESCRIPTION "VUNI to associate the Egress part of the
                        A2B connection ." 
                DEFVAL { 0 }
                ::= { vbrAtmPvcVccEntry 19 }


vbrAtmPvcVccOAMConnEndPtStatus    OBJECT-TYPE
                 SYNTAX INTEGER {
                                ete-active(1),
                                ete-ais-state(2),
                                ete-rdi-state(3),
                                ete-ais-rdi-state(4)
                                }
                MAX-ACCESS read-only
                STATUS current
                DESCRIPTION "Connection endpoint status. Valid only 
                        at connection endpoint."
                ::= { vbrAtmPvcVccEntry 20 }

vbrAtmPvcVccOAMSegEndPtStatus    OBJECT-TYPE
                SYNTAX INTEGER {
                                seg-active(1),
                                seg-ais-state(2),
                                seg-rdi-state(3),
                                seg-ais-rdi-state(4)
                                }
                MAX-ACCESS read-only
                STATUS current
                DESCRIPTION "Segment endpoint status. Valid only at
                        segment/connection endpoint."
                ::= { vbrAtmPvcVccEntry 21 }

vbrAtmPvcVccMfsB2A OBJECT-TYPE
                SYNTAX INTEGER (1..65535)
                MAX-ACCESS read-write
                STATUS current
                DESCRIPTION "Maximum Frame Size for GFR traffic"
                DEFVAL { 1 }
                ::= { vbrAtmPvcVccEntry 22 }

vbrAtmPvcVccConnFailureCauseA    OBJECT-TYPE
                SYNTAX ConnFailureCause
                MAX-ACCESS read-only
                STATUS current
                DESCRIPTION " connestion status reason code"
                ::= { vbrAtmPvcVccEntry 23 }

vbrAtmPvcVccConnFailureCauseB    OBJECT-TYPE
                SYNTAX AtmConnFailureCause
                MAX-ACCESS read-only
                STATUS current
                DESCRIPTION "connection status reason code"
                ::= { vbrAtmPvcVccEntry 24 }


vbrAtmPvcVccSarTypeB OBJECT-TYPE
                SYNTAX INTEGER  { 
                                none(1),
                                aal5(2),                                        
                                aal2Std(3)
                                }
                MAX-ACCESS read-write
                STATUS current
                DESCRIPTION "This field will be used to connect hdlc
                             to atm directly when sar type is none or aal5 or
                             go through dsp2 first when sar type is aal2Std."
                DEFVAL { aal5 }
                ::= { vbrAtmPvcVccEntry 25 }

vbrAtmPvcVccAal2Cid OBJECT-TYPE
                SYNTAX INTEGER (0..255)
                MAX-ACCESS read-write
                STATUS current
                DESCRIPTION "Aal2 Cid Used to pack hdlc chan in an
                        Atm Trunk. This value will be unique
                        per Atm Trunk. This field will be applicable
                        when Aal type is chosen to be Standard Aal2."
                DEFVAL { 0 }
                ::= { vbrAtmPvcVccEntry 26  }

vbrAtmPvcVccTrafficShapingA2B     OBJECT-TYPE
                SYNTAX INTEGER {
                                disabled(1),
                                enabled(2)
                               }
                MAX-ACCESS read-write
                STATUS current
                DESCRIPTION "Traffic Shaping Support in the A2B direction."
                DEFVAL { disabled }
                ::= { vbrAtmPvcVccEntry 27 }


cirEmCirEmPvcTable OBJECT-TYPE
                SYNTAX SEQUENCE OF CirEmCirEmPvcEntry
                MAX-ACCESS not-accessible
                STATUS current
                DESCRIPTION "Table of Circuit Emulation to Circuit Emulation"
                ::= { connectionConfig 10 }
 
cirEmCirEmPvcEntry OBJECT-TYPE
                SYNTAX CirEmCirEmPvcEntry
                MAX-ACCESS not-accessible
                STATUS current
                DESCRIPTION "Row definition of circuit emulation to
                              circuit emulation connections."
                INDEX { cirEmCirEmPvcIfA, cirEmCirEmPvcIfB
                      }
                ::= { cirEmCirEmPvcTable 1 }
 
CirEmCirEmPvcEntry ::= SEQUENCE {
                              cirEmCirEmPvcIfA                  IntfIndex,
                              cirEmCirEmPvcIfB                  IntfIndex,
                              cirEmCirEmPvcEchoCancellationA2B        INTEGER,
                              cirEmCirEmPvcFlow                 INTEGER,
                              cirEmCirEmPvcRowStatus            RowStatus,
                              cirEmCirEmPvcCodingTranslationA2B        INTEGER,
                              cirEmCirEmPvcEchoCancellationB2A        INTEGER,
                              cirEmCirEmPvcCodingTranslationB2A        INTEGER,
                              cirEmCirEmPvcConnectionStatus     INTEGER,
                              cirEmCirEmPvcInterworking             INTEGER,
                              cirEmCirEmPvcServiceType          INTEGER,
                              cirEmCirEmPvcConnFailureCauseA   ConnFailureCause,
                              cirEmCirEmPvcConnFailureCauseB   ConnFailureCause
                              }
 
cirEmCirEmPvcIfA       OBJECT-TYPE
                SYNTAX IntfIndex
                MAX-ACCESS not-accessible
                STATUS current
                DESCRIPTION "Interface index for side A of a circuit 
                             emulation-circuit emulation PVC connection.  Number
                             value is interpreted as an interface of the form, 
                             SSPPCCC, where SS is the card slot, PP is the port 
                             number, and CCC is the channel number."
                ::= { cirEmCirEmPvcEntry 1 }
 
cirEmCirEmPvcIfB OBJECT-TYPE
                SYNTAX IntfIndex
                MAX-ACCESS not-accessible
                STATUS current
                DESCRIPTION "Interface index for side B of a circuit 
                             emulation-circuit emulation PVC connection.  Number
                             value is interpreted as an interface of the form, 
                             SSPPCCC, where SS is the card slot, PP is the port 
                             number, and CCC is the channel number."
                ::= { cirEmCirEmPvcEntry 2 }
 

 
cirEmCirEmPvcEchoCancellationA2B OBJECT-TYPE
                SYNTAX INTEGER  {
                                 none(1),
                                 g165-nearEnd(2),
                                 g168(3)
                                }
                MAX-ACCESS read-write
                STATUS current
                DESCRIPTION "Echo cancellation off/on"
                DEFVAL { none }
                ::= { cirEmCirEmPvcEntry 5 }
 
cirEmCirEmPvcFlow OBJECT-TYPE
                SYNTAX INTEGER  {
                                 duplex(1),
                                 simplexA2B(2)
                                }
                MAX-ACCESS read-write
                STATUS current
                DESCRIPTION "Flow Type    "
                DEFVAL { duplex }
                ::= { cirEmCirEmPvcEntry 6 }
 
cirEmCirEmPvcRowStatus OBJECT-TYPE
                SYNTAX RowStatus
                MAX-ACCESS read-write
                STATUS current
                DESCRIPTION "row status"
                ::= { cirEmCirEmPvcEntry 7 }

cirEmCirEmPvcCodingTranslationA2B OBJECT-TYPE
                SYNTAX INTEGER  {
                                 none(1),
                                 muLaw2muLaw(2),
                                 aLaw2aLaw(3),
                                 muLaw2aLaw(4),
                                 aLaw2muLaw(5)
                                }
                MAX-ACCESS read-write
                STATUS current
                DESCRIPTION "Coding rule translation type."
                DEFVAL { none }
                ::= { cirEmCirEmPvcEntry 8 }
 
cirEmCirEmPvcEchoCancellationB2A OBJECT-TYPE
                SYNTAX INTEGER  {
                                 none(1),
                                 g165-nearEnd(2),
                                 g168(3)
                                }
                MAX-ACCESS read-write
                STATUS current
                DESCRIPTION "Echo cancellation off/on"
                DEFVAL { none }
                ::= { cirEmCirEmPvcEntry 9 }
 
cirEmCirEmPvcCodingTranslationB2A OBJECT-TYPE
                SYNTAX INTEGER  {
                                 none(1),
                                 muLaw2muLaw(2),
                                 aLaw2aLaw(3),
                                 muLaw2aLaw(4),
                                 aLaw2muLaw(5)
                                }
                MAX-ACCESS read-write
                STATUS current
                DESCRIPTION "Coding rule translation type."
                DEFVAL { none }
                ::= { cirEmCirEmPvcEntry 10 }
 
cirEmCirEmPvcConnectionStatus OBJECT-TYPE
                SYNTAX INTEGER {
                                active(1),
                                inactive(2),
                                inactiveA2B-B2A(3),
                                inactiveA2B(4),
                                inactiveB2A(5)
                               }
                MAX-ACCESS read-only
                STATUS current
                DESCRIPTION "Indicates the current connections status.
                             Active:  All interfaces through which the 
                                      connection is going are in service.
                             Inactive:  One of the end interfaces of the 
                                        connection is not in service.

                             The rest of the states apply to connections going
                             through resource interfaces like DSP2 and FEC.  These
                             interfaces are dynamically allocated.

                             InactiveA2B-B2A:  Both the A2B and B2A resource
                                               interfaces are not in service.
                             InactiveA2B:  The A2B resource interface is not in 
                                           service.
                             InactiveB2A:  The B2A resource interface is not in 
                                           service.

                             If an end interface and the resource interfaces 
                             are out of service, the status will be inactive 
                             because the end interfaces take priority."
                DEFVAL { inactive }
                ::= { cirEmCirEmPvcEntry 11 }

cirEmCirEmPvcInterworking OBJECT-TYPE
                SYNTAX INTEGER  {
                                 disabled(1),
                                 enabled(2)
                                }
                MAX-ACCESS read-write
                STATUS current
                DESCRIPTION "CE - CE interworking enable/disabled "
                DEFVAL { enabled }
                ::= { cirEmCirEmPvcEntry 12 }

cirEmCirEmPvcServiceType OBJECT-TYPE
                  SYNTAX INTEGER {
                                      cbr-1(1),
                                cbr-2(2),
                                cbr-3(3),
                                cbr-4(4)
                                }
                MAX-ACCESS read-write
                STATUS current
                DESCRIPTION "service type"
                DEFVAL { cbr-1 }
                ::= { cirEmCirEmPvcEntry 13 }

cirEmCirEmPvcConnFailureCauseA    OBJECT-TYPE
                SYNTAX ConnFailureCause
                MAX-ACCESS read-only
                STATUS current
                DESCRIPTION " connestion status reason code"
                ::= { cirEmCirEmPvcEntry 14 }

cirEmCirEmPvcConnFailureCauseB    OBJECT-TYPE
                SYNTAX ConnFailureCause
                MAX-ACCESS read-only
                STATUS current
                DESCRIPTION "connection status reason code"
                ::= { cirEmCirEmPvcEntry 15 }

vbrVbrPvcTable  OBJECT-TYPE
                SYNTAX SEQUENCE OF VbrVbrPvcEntry
                MAX-ACCESS not-accessible
                STATUS current
                DESCRIPTION "Table of terminal emulation to ATM network
                             IWF connections "
                ::= { connectionConfig 11 }
 
vbrVbrPvcEntry  OBJECT-TYPE
                SYNTAX VbrVbrPvcEntry
                MAX-ACCESS not-accessible
                STATUS current
                DESCRIPTION "Row definition of terminal emulation to ATM
                             network IWF connections"
                INDEX { vbrVbrPvcIfA, vbrVbrPvcIfB
                      }
                ::= { vbrVbrPvcTable 1 }
 
VbrVbrPvcEntry ::= SEQUENCE {
                           vbrVbrPvcIfA                 IntfIndex,
                           vbrVbrPvcIfB                 IntfIndex,
                           vbrVbrPvcPeakCellRateA2B     Integer32,
                           vbrVbrPvcSusCellRateA2B      Integer32,
                           vbrVbrPvcMaxBurstSizeA2B     Integer32,
                           vbrVbrPvcPeakCellRateB2A     Integer32,
                           vbrVbrPvcSusCellRateB2A      Integer32,
                           vbrVbrPvcMaxBurstSizeB2A     Integer32,
                           vbrVbrPvcFlow                INTEGER,
                           vbrVbrPvcRowStatus           RowStatus,
                           vbrVbrPvcConnectionStatus        INTEGER,
                           vbrVbrPvcServiceType         INTEGER,
                           vbrVbrPvcConnFailureCauseA        ConnFailureCause,
                           vbrVbrPvcConnFailureCauseB        ConnFailureCause
                          }
 
vbrVbrPvcIfA    OBJECT-TYPE
                SYNTAX IntfIndex
                MAX-ACCESS not-accessible
                STATUS current
                DESCRIPTION "Interface index for side A of a variable bit 
                             rate-variable bit rate PVC connection.  Number
                             value is interpreted as an interface of the form, 
                             SSPPCCC, where SS is the card slot, PP is the port 
                             number, and CCC is the channel number."
                ::= { vbrVbrPvcEntry 1 }
 
vbrVbrPvcIfB OBJECT-TYPE
                SYNTAX IntfIndex
                MAX-ACCESS not-accessible
                STATUS current
                DESCRIPTION "Interface index for side B of a variable bit 
                             rate-variable bit rate PVC connection.  Number
                             value is interpreted as an interface of the form, 
                             SSPPCCC, where SS is the card slot, PP is the port 
                             number, and CCC is the channel number."
                ::= { vbrVbrPvcEntry 2 }
 
vbrVbrPvcPeakCellRateA2B        OBJECT-TYPE
                SYNTAX Integer32
                MAX-ACCESS read-write
                STATUS current
                DESCRIPTION "peak cell rate - side A, in cell per second"
                DEFVAL { 1 }
                ::= { vbrVbrPvcEntry 3 }
 
vbrVbrPvcSusCellRateA2B OBJECT-TYPE
                SYNTAX Integer32
                MAX-ACCESS read-write
                STATUS current
                DESCRIPTION "sustained rate - side A, in cell per second"
                DEFVAL { 1 }
                ::= { vbrVbrPvcEntry 4 }

vbrVbrPvcMaxBurstSizeA2B        OBJECT-TYPE
                SYNTAX Integer32
                MAX-ACCESS read-write
                STATUS current
                DESCRIPTION "maximum burst size - side A, in cells"
                DEFVAL { 1 }
                ::= { vbrVbrPvcEntry 5 }
 
vbrVbrPvcPeakCellRateB2A        OBJECT-TYPE
                SYNTAX Integer32
                MAX-ACCESS read-write
                STATUS current
                DESCRIPTION "peak rate - side B, in cell per second."
                DEFVAL { 1 }
                ::= { vbrVbrPvcEntry 6 }
 
vbrVbrPvcSusCellRateB2A OBJECT-TYPE
                SYNTAX Integer32
                MAX-ACCESS read-write
                STATUS current
                DESCRIPTION "sustained rate - side B, in cell per second."
                DEFVAL { 1 }
                ::= { vbrVbrPvcEntry 7 }
 
vbrVbrPvcMaxBurstSizeB2A        OBJECT-TYPE
                SYNTAX Integer32
                MAX-ACCESS read-write
                STATUS current
                DESCRIPTION "maximum burst size - side B, in cells."
                DEFVAL { 1 }
                ::= { vbrVbrPvcEntry 8 }
 
vbrVbrPvcFlow   OBJECT-TYPE
                SYNTAX INTEGER        {
                                duplex(1),
                                simplexA2B(2)
                                } 
                MAX-ACCESS read-write
                STATUS current
                DESCRIPTION "Flow Type"
                DEFVAL { duplex }
                ::= { vbrVbrPvcEntry 9 }
 
vbrVbrPvcRowStatus OBJECT-TYPE
                SYNTAX RowStatus
                MAX-ACCESS read-write
                STATUS current
                DESCRIPTION "row status"
                ::= { vbrVbrPvcEntry 10 }

vbrVbrPvcConnectionStatus OBJECT-TYPE
                SYNTAX INTEGER {
                                active(1),
                                inactive(2),
                                inactiveA2B-B2A(3),
                                inactiveA2B(4),
                                inactiveB2A(5)
                               }
                MAX-ACCESS read-only
                STATUS current
                DESCRIPTION "Indicates the current connections status.
                             Active:  All interfaces through which the 
                                      connection is going are in service.
                             Inactive:  One of the end interfaces of the 
                                        connection is not in service.

                             The rest of the states apply to connections going
                             through resource interfaces like DSP2 and FEC.  These
                             interfaces are dynamically allocated.

                             InactiveA2B-B2A:  Both the A2B and B2A resource
                                               interfaces are not in service.
                             InactiveA2B:  The A2B resource interface is not in 
                                           service.
                             InactiveB2A:  The B2A resource interface is not in 
                                           service.

                             If an end interface and the resource interfaces 
                             are out of service, the status will be inactive 
                             because the end interfaces take priority."
                DEFVAL { inactive }
                ::= { vbrVbrPvcEntry 11 }

vbrVbrPvcServiceType OBJECT-TYPE
                        SYNTAX INTEGER {
                                              ubr(1),
                                        vbr-nrt2(2),
                                        vbr-nrt1(3),
                                        vbr-rt2(4),
                                        vbr-rt1(5),
                                        vbr-express(6)
                                       }
                            MAX-ACCESS read-write
                        STATUS current
                        DESCRIPTION "service type"
                        DEFVAL { ubr }
                        ::= { vbrVbrPvcEntry 12 }

vbrVbrPvcConnFailureCauseA    OBJECT-TYPE
                SYNTAX ConnFailureCause
                MAX-ACCESS read-only
                STATUS current
                DESCRIPTION " connestion status reason code"
                ::= { vbrVbrPvcEntry 13 }

vbrVbrPvcConnFailureCauseB    OBJECT-TYPE
                SYNTAX ConnFailureCause
                MAX-ACCESS read-only
                STATUS current
                DESCRIPTION "connection status reason code"
                ::= { vbrVbrPvcEntry 14 }

bridgeBridgePvcTable OBJECT-TYPE
                SYNTAX SEQUENCE OF BridgeBridgePvcEntry
                MAX-ACCESS not-accessible
                STATUS current
                DESCRIPTION " A table of bridge-bridge PVC connection"
                ::= { connectionConfig 12 }
 
bridgeBridgePvcEntry OBJECT-TYPE
                SYNTAX BridgeBridgePvcEntry 
                MAX-ACCESS not-accessible
                STATUS current
                DESCRIPTION "Row definitions of bridge-bridge PVC
                             connection attributes"
                INDEX { bridgeBridgePvcIfA,
                        bridgeBridgePvcIfB}
                ::= { bridgeBridgePvcTable 1 }
 
BridgeBridgePvcEntry ::= SEQUENCE {
                        bridgeBridgePvcIfA                Integer32,
                        bridgeBridgePvcIfB                Integer32,
                        bridgeBridgePvcRowStatus        RowStatus,
                        bridgeBridgePvcConnectionStatus INTEGER,
                        bridgeBridgePvcConnFailureCauseA  ConnFailureCause,
                        bridgeBridgePvcConnFailureCauseB  ConnFailureCause
                        }
 
bridgeBridgePvcIfA OBJECT-TYPE
                SYNTAX Integer32
                MAX-ACCESS not-accessible
                STATUS current
                DESCRIPTION "Interface index for side A of a bridge-bridge
                             PVC connection.  Number value is interpreted as an 
                             interface of the form, SSPPCCC, where SS is the 
                             card slot, PP is the port number, and CCC is the 
                             channel number."
                ::= { bridgeBridgePvcEntry 1 }
 
bridgeBridgePvcIfB OBJECT-TYPE
                SYNTAX Integer32
                MAX-ACCESS not-accessible
                STATUS current
                DESCRIPTION "Interface index for side B of a bridge-bridge
                             PVC connection.  Number value is interpreted as an 
                             interface of the form, SSPPCCC, where SS is the 
                             card slot, PP is the port number, and CCC is the 
                             channel number."
                ::= { bridgeBridgePvcEntry 2 }
 
bridgeBridgePvcRowStatus OBJECT-TYPE
                SYNTAX RowStatus
                MAX-ACCESS read-write
                STATUS current
                DESCRIPTION "row status"
                ::= { bridgeBridgePvcEntry 3 }

bridgeBridgePvcConnectionStatus OBJECT-TYPE
                SYNTAX INTEGER {
                                active(1),
                                inactive(2),
                                inactiveA2B-B2A(3),
                                inactiveA2B(4),
                                inactiveB2A(5)
                               }
                MAX-ACCESS read-only
                STATUS current
                DESCRIPTION "Indicates the current connections status.
                             Active:  All interfaces through which the 
                                      connection is going are in service.
                             Inactive:  One of the end interfaces of the 
                                        connection is not in service.

                             The rest of the states apply to connections going
                             through resource interfaces like DSP2 and FEC.  These
                             interfaces are dynamically allocated.

                             InactiveA2B-B2A:  Both the A2B and B2A resource
                                               interfaces are not in service.
                             InactiveA2B:  The A2B resource interface is not in 
                                           service.
                             InactiveB2A:  The B2A resource interface is not in 
                                           service.

                             If an end interface and the resource interfaces 
                             are out of service, the status will be inactive 
                             because the end interfaces take priority."
                DEFVAL { inactive }
                ::= { bridgeBridgePvcEntry 4 }

bridgeBridgePvcConnFailureCauseA    OBJECT-TYPE
                SYNTAX ConnFailureCause
                MAX-ACCESS read-only
                STATUS current
                DESCRIPTION " connestion status reason code"
                ::= { bridgeBridgePvcEntry 5 }

bridgeBridgePvcConnFailureCauseB    OBJECT-TYPE
                SYNTAX ConnFailureCause
                MAX-ACCESS read-only
                STATUS current
                DESCRIPTION "connection status reason code"
                ::= { bridgeBridgePvcEntry 6 }


bridgeAtmPvcVccTable OBJECT-TYPE
                    SYNTAX SEQUENCE OF BridgeAtmPvcVccEntry
                    MAX-ACCESS not-accessible
                    STATUS current
                    DESCRIPTION "Table of bridge Atm PVC VCC connection entries"
                    ::= { connectionConfig 13 }

bridgeAtmPvcVccEntry OBJECT-TYPE
                SYNTAX BridgeAtmPvcVccEntry
                MAX-ACCESS not-accessible
                STATUS current
                DESCRIPTION "Row definition of bridge atm PVC VCC connection
                             attribution."
                INDEX { bridgeAtmPvcVccIfA, bridgeAtmPvcVccIfB,
                        bridgeAtmPvcVccVpiB, bridgeAtmPvcVccVciB }
                ::= { bridgeAtmPvcVccTable 1 }

BridgeAtmPvcVccEntry ::= SEQUENCE {
                        bridgeAtmPvcVccIfA                Integer32,
                        bridgeAtmPvcVccIfB                Integer32,
                        bridgeAtmPvcVccVpiB               INTEGER,
                        bridgeAtmPvcVccVciB               INTEGER,
                        bridgeAtmPvcVccServiceType        INTEGER,
                        bridgeAtmPvcVccPeakCellRateB2A    Integer32,
                        bridgeAtmPvcVccSusCellRateB2A     Integer32,
                        bridgeAtmPvcVccMaxBurstSizeB2A    Integer32,
                        bridgeAtmPvcVccRowStatus          RowStatus,
                        bridgeAtmPvcVccConnectionStatus   INTEGER,

                        bridgeAtmPvcVccDualHomed          INTEGER,

                        bridgeAtmPvcVccViB                INTEGER,
                        bridgeAtmPvcVccCnfrmTypeB2A       INTEGER,

                        bridgeAtmPvcVccVUNIB              INTEGER,

                        bridgeAtmPvcVccMfsB2A             INTEGER,
                        bridgeAtmPvcVccConnFailureCauseA  ConnFailureCause,
                        bridgeAtmPvcVccConnFailureCauseB  AtmConnFailureCause,
                        bridgeAtmPvcVccOamStatus          INTEGER,
                        bridgeAtmPvcVccTrafficShapingA2B  INTEGER
                        }

bridgeAtmPvcVccIfA OBJECT-TYPE
                SYNTAX Integer32
                MAX-ACCESS not-accessible
                STATUS current
                DESCRIPTION "Interface index for side A, the bridge side, of a 
                             bridge-atm PVC VCC connection.  Number value is 
                             interpreted as an interface of the form, SSPPCCC, 
                             where SS is the card slot, PP is the port number, 
                             and CCC is the channel number."
                ::= { bridgeAtmPvcVccEntry 1 }

bridgeAtmPvcVccIfB OBJECT-TYPE
                SYNTAX Integer32
                MAX-ACCESS not-accessible
                STATUS current
                DESCRIPTION "Interface index for side B, the atm side, of a 
                             bridge-atm PVC VCC connection.  Number value is 
                             interpreted as an interface of the form, SSPPCCC, 
                             where SS is the card slot, PP is the port number, 
                             and CCC is the channel number."
                ::= { bridgeAtmPvcVccEntry 2 }

bridgeAtmPvcVccVpiB OBJECT-TYPE
                SYNTAX INTEGER (0..4095)
                MAX-ACCESS not-accessible
                STATUS current
                DESCRIPTION "VPI value for side B, the atm side, of a 
                             bridge-atm PVC VCC connection.  Valid range is a 
                             number between 0 and 4095."
                ::= { bridgeAtmPvcVccEntry 3 }

bridgeAtmPvcVccVciB OBJECT-TYPE
                SYNTAX INTEGER (0..65535)
                MAX-ACCESS not-accessible
                STATUS current
                DESCRIPTION "VCI value for side B, the atm side, of a 
                             bridge-atm PVC VCC connection.  Valid range is a 
                             number between 0 and 65535."
                ::= { bridgeAtmPvcVccEntry 4 }

bridgeAtmPvcVccServiceType OBJECT-TYPE
                SYNTAX INTEGER {
                                ubr(1),
                                vbr-nrt2(2),
                                vbr-nrt1(3),
                                vbr-rt2(4),
                                vbr-rt1(5),
                                vbr-express(6),
                                gfr2(7)
                               }
                MAX-ACCESS read-write
                STATUS current
                DESCRIPTION "service type"
                DEFVAL { ubr }
                ::= { bridgeAtmPvcVccEntry 5 }

bridgeAtmPvcVccPeakCellRateB2A OBJECT-TYPE
                SYNTAX Integer32
                MAX-ACCESS read-write
                STATUS current
                DESCRIPTION "peak rate - side B, in cell per second."
                DEFVAL { 1 }
                ::= { bridgeAtmPvcVccEntry 6 }
 
bridgeAtmPvcVccSusCellRateB2A OBJECT-TYPE
                SYNTAX Integer32
                MAX-ACCESS read-write
                STATUS current
                DESCRIPTION "sustained rate - side B, in cell per second."
                DEFVAL { 1 }
                ::= { bridgeAtmPvcVccEntry 7 }
 
bridgeAtmPvcVccMaxBurstSizeB2A OBJECT-TYPE
                SYNTAX Integer32
                MAX-ACCESS read-write
                STATUS current
                DESCRIPTION "maximum burst size - side B, in cells."
                DEFVAL { 1 }
                ::= { bridgeAtmPvcVccEntry 8 }

bridgeAtmPvcVccRowStatus OBJECT-TYPE
                SYNTAX RowStatus
                MAX-ACCESS read-write
                STATUS current
                DESCRIPTION "row status"
                ::= { bridgeAtmPvcVccEntry 9 }

bridgeAtmPvcVccConnectionStatus OBJECT-TYPE
                SYNTAX INTEGER {
                                active(1),
                                inactive(2),
                                inactiveA2B-B2A(3),
                                inactiveA2B(4),
                                inactiveB2A(5)
                               }
                MAX-ACCESS read-only
                STATUS current
                DESCRIPTION "Indicates the current connections status.
                             Active:  All interfaces through which the 
                                      connection is going are in service.
                             Inactive:  One of the end interfaces of the 
                                        connection is not in service.

                             The rest of the states apply to connections going
                             through resource interfaces like DSP2 and FEC.  These
                             interfaces are dynamically allocated.

                             InactiveA2B-B2A:  Both the A2B and B2A resource
                                               interfaces are not in service.
                             InactiveA2B:  The A2B resource interface is not in 
                                           service.
                             InactiveB2A:  The B2A resource interface is not in 
                                           service.

                             If an end interface and the resource interfaces 
                             are out of service, the status will be inactive 
                             because the end interfaces take priority."
                DEFVAL { inactive }
                ::= { bridgeAtmPvcVccEntry 10 }


bridgeAtmPvcVccDualHomed OBJECT-TYPE
                SYNTAX INTEGER {
                                no(1),
                                yes(2)
                               }
                MAX-ACCESS read-only
                STATUS current
                DESCRIPTION "Does this PVC need a backup Dual homing PVC."
                DEFVAL { no }
                ::= { bridgeAtmPvcVccEntry 11 }


bridgeAtmPvcVccViB      OBJECT-TYPE
                SYNTAX INTEGER (0..1024)
                MAX-ACCESS read-write 
                STATUS current 
                DESCRIPTION "VI to associate the Egress part of the
                        A2B connection ."
                DEFVAL { 0 }
                ::= { bridgeAtmPvcVccEntry 12 }

bridgeAtmPvcVccCnfrmTypeB2A    OBJECT-TYPE
                SYNTAX INTEGER {
                                    best-effort(1),
                                one-bucket-notag-0plus1(2),
                                two-bucket-notag-0plus1-0plus1(3),
                                two-bucket-notag-0plus1-0(4),
                                two-bucket-tag-0plus1-0(5),
                                best-effort-tag(6)
                               }
                MAX-ACCESS read-write
                STATUS current
                DESCRIPTION "The following is the description of this field
                        This will be used in conjunction with the
                        service type field to get the correct
                        traffic behaviour. In the conformances the 
                        the 0 or 0plus1 refers to the clp bit in the
                        cells. If 0plus1 is the bucket reference then
                        the clp bit is ignored. If 0 is specified for 
                        the bucket then check only clp=0 cells.
                        1: Best Effort will try to send all cellsin a 
                        best effort way. This will follow the 
                        Aqueman Algorithm
                        2: one-bucket-notag-0plus1 will use 1 bucket
                        i.e is the PCR(0+1) bucket and drop all
                        cells in excess.
                        3: two-bucket-notag-0plus1-0plus1 uses 2 buckets.
                        The 2 buckets are pcr(0+1) and scr(0+1).
                        All cells conforming to both buckets will be
                        passed through. The rest will be dropped.
                        4: two-bucket-notag-0plus1-0 uses 2 buckets.
                        The 2 buckets are pcr(0+1) and scr(0) or 
                        pcr(0). Cells which conform to both buckets
                        are passed through. The rest are dropped.
                        5: two-bucket-tag-0plus1-0 uses 2 buckets.
                        The 2 buckets are pcr(0+1) and scr(0) or 
                        pcr(0). Cells which do not conform to the first
                        bucket are dropped. Cells which do not 
                        conform to the 2nd bucket are tagged.
                        6: best-effort-tag. Tag all cells and then
                        do a best effort.  "
                DEFVAL { best-effort }
                ::= { bridgeAtmPvcVccEntry 14 }


bridgeAtmPvcVccVUNIB      OBJECT-TYPE
                SYNTAX INTEGER (0..255)
                MAX-ACCESS read-write 
                STATUS current 
                DESCRIPTION "VUNI to associate the Egress part of the
                        A2B connection ."
                DEFVAL { 0 }
                ::= { bridgeAtmPvcVccEntry 15 }


bridgeAtmPvcVccMfsB2A OBJECT-TYPE
                SYNTAX INTEGER (1..65535)
                MAX-ACCESS read-write
                STATUS current
                DESCRIPTION "Maximum Frame Size for GFR traffic"
                DEFVAL { 1 }
                ::= { bridgeAtmPvcVccEntry 16 }

bridgeAtmPvcVccConnFailureCauseA    OBJECT-TYPE
                SYNTAX ConnFailureCause
                MAX-ACCESS read-only
                STATUS current
                DESCRIPTION " connestion status reason code"
                ::= { bridgeAtmPvcVccEntry 17 }

bridgeAtmPvcVccConnFailureCauseB    OBJECT-TYPE
                SYNTAX AtmConnFailureCause
                MAX-ACCESS read-only
                STATUS current
                DESCRIPTION "connection status reason code"
                ::= { bridgeAtmPvcVccEntry 18 }

bridgeAtmPvcVccOamStatus OBJECT-TYPE
                SYNTAX INTEGER {
                                unsupp(1),
                                end-Pt(2),                              
                                end-Seg-Pt(3)                         
                               }
                MAX-ACCESS read-write
                STATUS current
                DESCRIPTION "Indicates the OAM monitoring status of side A.
                             The 3 possible states are:
                             Unsupp:  No monitoring enabled.
                             End-Pt:  A side is only an end point, therefore
                             End-Seg-Pt:  A side is both an end point and a
                                segment point."                    
                DEFVAL { unsupp }
                ::= { bridgeAtmPvcVccEntry 19 }

bridgeAtmPvcVccTrafficShapingA2B     OBJECT-TYPE
                SYNTAX INTEGER {
                                disabled(1),
                                enabled(2)
                               }
                MAX-ACCESS read-write
                STATUS current
                DESCRIPTION "Traffic Shaping Support in the A2B direction."
                DEFVAL { disabled }
                ::= { bridgeAtmPvcVccEntry 20 }


cirEmAtmBkPvcVccTable OBJECT-TYPE
                SYNTAX SEQUENCE OF CirEmAtmBkPvcVccEntry
                MAX-ACCESS not-accessible
                STATUS current
                DESCRIPTION "This table is used to manage CES DHPVC backup pvc."
                ::= { connectionConfig 14 }

cirEmAtmBkPvcVccEntry OBJECT-TYPE
                SYNTAX CirEmAtmBkPvcVccEntry
                MAX-ACCESS not-accessible
                STATUS current
                DESCRIPTION "An entry in the CES DHPVC table.  There is one 
                             entry in the table corresponding to each active
                             row in the cirEmAtmPvcVccTable for which the
                             cirEmAtmPvcVccDualHomed object takes the value
                             'yes.'"
                INDEX { cirEmAtmPvcVccIfA, cirEmAtmPvcVccIfB,
                        cirEmAtmPvcVccVpiB, cirEmAtmPvcVccVciB }
                ::= { cirEmAtmBkPvcVccTable 1 }

CirEmAtmBkPvcVccEntry ::= SEQUENCE {
                             cirEmAtmBkPvcVccIfB                IntfIndex,
                             cirEmAtmBkPvcVccVpiB                  INTEGER,
                             cirEmAtmBkPvcVccVciB                  INTEGER,
                             cirEmAtmBkPvcVccActivePvc                INTEGER,
                             cirEmAtmBkPvcVccAutoSwitch                INTEGER,
                             cirEmAtmBkPvcVccRowStatus                RowStatus,
                             cirEmAtmBkPvcVccViB                INTEGER,

                             cirEmAtmBkPvcVccVUNIB              INTEGER,

                             cirEmAtmBkPvcVccConnFailureCauseB   AtmConnFailureCause
                             }

cirEmAtmBkPvcVccIfB OBJECT-TYPE
                SYNTAX IntfIndex
                MAX-ACCESS read-write
                STATUS current
                DESCRIPTION "Interface index for side B, the atm side, of a 
                             backup circuit emulation-atm DHPVC VCC connection.
                             Number value is interpreted as an interface of the
                             form, SSPPCCC, where SS is the card slot, PP is 
                             the port number, and CCC is the channel number."
                ::= { cirEmAtmBkPvcVccEntry 1 }

cirEmAtmBkPvcVccVpiB OBJECT-TYPE
                SYNTAX INTEGER (0..4095)
                MAX-ACCESS read-write
                STATUS current
                DESCRIPTION "VPI value for side B, the atm side, of a backup
                             circuit emulation-atm DHPVC VCC connection.  Valid 
                             range is a number between 0 and 4095."
                ::= { cirEmAtmBkPvcVccEntry 2 }

cirEmAtmBkPvcVccVciB OBJECT-TYPE
                SYNTAX INTEGER (0..65535)
                MAX-ACCESS read-write
                STATUS current
                DESCRIPTION "VCI value for side B, the atm side, of a backup
                             circuit emulation-atm DHPVC VCC connection.  Valid 
                             range is a number between 0 and 65535."
                ::= { cirEmAtmBkPvcVccEntry 3 }

cirEmAtmBkPvcVccActivePvc OBJECT-TYPE
                SYNTAX INTEGER {
                                primary(1),
                                backup(2),
                                none(3)
                               }
                MAX-ACCESS read-only
                STATUS current
                DESCRIPTION "Current active PVC."
                DEFVAL { none }
                ::= { cirEmAtmBkPvcVccEntry 4 }

cirEmAtmBkPvcVccAutoSwitch OBJECT-TYPE
                SYNTAX INTEGER  {
                                yes(1),
                                no(2)
                                }
                MAX-ACCESS read-write
                STATUS current
                DESCRIPTION "Auto switch back to primary link when primary link
                             is recovered."
                DEFVAL { yes }
                ::= { cirEmAtmBkPvcVccEntry 5 }

cirEmAtmBkPvcVccRowStatus OBJECT-TYPE
                SYNTAX RowStatus
                MAX-ACCESS read-write
                STATUS current
                DESCRIPTION "row status"
                ::= { cirEmAtmBkPvcVccEntry 6 }

cirEmAtmBkPvcVccViB OBJECT-TYPE
                SYNTAX INTEGER (0..1024)
                MAX-ACCESS read-write
                STATUS current
                DESCRIPTION "VI to associate the Egress part of the
                        A2B connection ."
                DEFVAL { 0 }
                ::= { cirEmAtmBkPvcVccEntry 7 }


cirEmAtmBkPvcVccVUNIB OBJECT-TYPE
                SYNTAX INTEGER (0..255)
                MAX-ACCESS read-write
                STATUS current
                DESCRIPTION "VUNI to associate the Egress part of the
                        A2B connection ."
                DEFVAL { 0 }
                ::= { cirEmAtmBkPvcVccEntry 8 }


cirEmAtmBkPvcVccConnFailureCauseB    OBJECT-TYPE
                SYNTAX AtmConnFailureCause
                MAX-ACCESS read-only
                STATUS current
                DESCRIPTION "connection status reason code"
                ::= { cirEmAtmBkPvcVccEntry 9 }

vbrAtmBkPvcVccTable OBJECT-TYPE
                    SYNTAX SEQUENCE OF VbrAtmBkPvcVccEntry
                    MAX-ACCESS not-accessible
                    STATUS current
                    DESCRIPTION "This table is used to manage terminal emulation 
                             DHPVC backup pvc."
                    ::= { connectionConfig 15 }

vbrAtmBkPvcVccEntry OBJECT-TYPE
                SYNTAX VbrAtmBkPvcVccEntry
                MAX-ACCESS not-accessible
                STATUS current
                DESCRIPTION "An entry in the terminal emulation DHPVC table.
                             There is one entry in the table corresponding to
                             each active row in the vbrAtmPvcVccTable for which
                             the vbrAtmPvcVccDualHomed object takes the value
                             'yes'."
                INDEX { vbrAtmPvcVccIfA, vbrAtmPvcVccIfB,
                        vbrAtmPvcVccVpiB, vbrAtmPvcVccVciB }
                ::= { vbrAtmBkPvcVccTable 1 }

VbrAtmBkPvcVccEntry ::= SEQUENCE {
                           vbrAtmBkPvcVccIfB                IntfIndex,
                           vbrAtmBkPvcVccVpiB                INTEGER,
                           vbrAtmBkPvcVccVciB                INTEGER,
                           vbrAtmBkPvcVccActivePvc        INTEGER,
                           vbrAtmBkPvcVccAutoSwitch        INTEGER,
                           vbrAtmBkPvcVccRowStatus        RowStatus,
                           vbrAtmBkPvcVccViB            INTEGER,

                           vbrAtmBkPvcVccVUNIB          INTEGER,

                           vbrAtmBkPvcVccConnFailureCauseB  AtmConnFailureCause
                          }

vbrAtmBkPvcVccIfB OBJECT-TYPE
                SYNTAX IntfIndex
                MAX-ACCESS read-write
                STATUS current
                DESCRIPTION "Interface index for side B, the atm side, of a 
                             backup terminal emulation-atm DHPVC VCC connection.
                             Number value is interpreted as an interface of the
                             form, SSPPCCC, where SS is the card slot, PP is 
                             the port number, and CCC is the channel number."
                ::= { vbrAtmBkPvcVccEntry 1 }

vbrAtmBkPvcVccVpiB OBJECT-TYPE
                SYNTAX INTEGER (0..4095)
                MAX-ACCESS read-write
                STATUS current
                DESCRIPTION "VPI value for side B, the atm side, of a backup
                             terminal emulation-atm DHPVC VCC connection.  
                             Valid range is a number between 0 and 4095."
                ::= { vbrAtmBkPvcVccEntry 2 }

vbrAtmBkPvcVccVciB OBJECT-TYPE
                SYNTAX INTEGER (0..65535)
                MAX-ACCESS read-write
                STATUS current
                DESCRIPTION "VCI value for side B, the atm side, of a backup
                             terminal emulation-atm DHPVC VCC connection.  
                             Valid range is a number between 0 and 65535."
                ::= { vbrAtmBkPvcVccEntry 3 }

vbrAtmBkPvcVccActivePvc OBJECT-TYPE
                SYNTAX INTEGER {
                                primary(1),
                                backup(2),
                                none(3)
                               }
                MAX-ACCESS read-only
                STATUS current
                DESCRIPTION "Current active PVC."
                DEFVAL { none }
                ::= { vbrAtmBkPvcVccEntry 4 }

vbrAtmBkPvcVccAutoSwitch OBJECT-TYPE
                SYNTAX INTEGER  {
                                yes(1),
                                no(2)
                                }
                MAX-ACCESS read-write
                STATUS current
                DESCRIPTION "Auto switch back to primary link when primary link
                             is recovered."
                DEFVAL { yes }
                ::= { vbrAtmBkPvcVccEntry 5 }

vbrAtmBkPvcVccRowStatus OBJECT-TYPE
                SYNTAX RowStatus
                MAX-ACCESS read-write
                STATUS current
                DESCRIPTION "row status"
                ::= { vbrAtmBkPvcVccEntry 6 }


vbrAtmBkPvcVccViB OBJECT-TYPE
                SYNTAX INTEGER (0..1024)
                MAX-ACCESS read-write
                STATUS current
                DESCRIPTION "VI to associate the Egress part of the
                        A2B connection ."
                DEFVAL { 0 }
                ::= { vbrAtmBkPvcVccEntry 7 }


vbrAtmBkPvcVccVUNIB OBJECT-TYPE
                SYNTAX INTEGER (0..255)
                MAX-ACCESS read-write
                STATUS current
                DESCRIPTION "VUNI to associate the Egress part of the
                        A2B connection ."
                DEFVAL { 0 }
                ::= { vbrAtmBkPvcVccEntry 8 }


vbrAtmBkPvcVccConnFailureCauseB    OBJECT-TYPE
                SYNTAX AtmConnFailureCause
                MAX-ACCESS read-only
                STATUS current
                DESCRIPTION "connection status reason code"
                ::= { vbrAtmBkPvcVccEntry 9 }



atmSpvcVccAddrTable OBJECT-TYPE
                SYNTAX SEQUENCE OF AtmSpvcVccAddrEntry
                MAX-ACCESS not-accessible
                STATUS current
                DESCRIPTION "Table of SPVC ATM network interface addresses."
                ::= { connectionConfig 16 }

atmSpvcVccAddrEntry OBJECT-TYPE
                SYNTAX AtmSpvcVccAddrEntry
                MAX-ACCESS  not-accessible
                STATUS current
                DESCRIPTION "Row definition of ATM SPVC address table."
                INDEX { atmSpvcVccIfA }
                ::= { atmSpvcVccAddrTable 1 }

AtmSpvcVccAddrEntry ::= SEQUENCE {
                        atmSpvcVccIfA                        IntfIndex,
                        atmSpvcVccAtmPortAddr                OCTET STRING,
                        atmSpvcVccAddrRowStatus                RowStatus
                }

atmSpvcVccIfA        OBJECT-TYPE
                SYNTAX IntfIndex
                MAX-ACCESS not-accessible
                STATUS current
                DESCRIPTION "Interface index for side A of an ATM SPVC VCC 
                             connection.  Number value is interpreted as an 
                             interface of the form, SSPPCCC, where SS is the 
                             card slot, PP is the port number, and CCC is the 
                             channel number."
                ::= { atmSpvcVccAddrEntry 1 }

atmSpvcVccAtmPortAddr OBJECT-TYPE
                SYNTAX OCTET STRING (SIZE(1..20))
                MAX-ACCESS read-write
                STATUS current
                DESCRIPTION "Local ATM port NSAP address."
                ::= { atmSpvcVccAddrEntry 2 }

atmSpvcVccAddrRowStatus OBJECT-TYPE
                SYNTAX RowStatus
                MAX-ACCESS read-write
                STATUS current
                DESCRIPTION "This is used to configure a NSAP address on the
                             local port.  Only when the address is configured
                             can SPVC connections be established."
                ::= { atmSpvcVccAddrEntry 3 }


atmSpvcVccTable        OBJECT-TYPE
                SYNTAX SEQUENCE OF AtmSpvcVccEntry
                MAX-ACCESS not-accessible
                STATUS current
                DESCRIPTION "Table of SPVC ATM virtual channel connections."
                ::= { connectionConfig 17 }

atmSpvcVccEntry        OBJECT-TYPE
                SYNTAX AtmSpvcVccEntry
                MAX-ACCESS not-accessible
                STATUS current
                DESCRIPTION "Row definition of ATM SPVC VCC connections."
                INDEX { atmSpvcVccIfA, atmSpvcVccVpiA, atmSpvcVccVciA }
                ::= { atmSpvcVccTable 1 }

AtmSpvcVccEntry        ::= SEQUENCE {
                atmSpvcVccVpiA                  INTEGER,
                atmSpvcVccVciA                  INTEGER,
                atmSpvcVccIfB                   IntfIndex,
                atmSpvcVccVpiB                  INTEGER,
                atmSpvcVccVciB                  INTEGER,
                atmSpvcVccServiceTypeA2B        INTEGER,
                atmSpvcVccSarTypeA2B            INTEGER,
                atmSpvcVccPeakCellRateA2B       Integer32,
                atmSpvcVccSusCellRateA2B        Integer32,
                atmSpvcVccMaxBurstSizeA2B       Integer32,
                atmSpvcVccFrwdErrCorrectionA2B  INTEGER,
                atmSpvcVccServiceTypeB2A        INTEGER,
                atmSpvcVccSarTypeB2A            INTEGER,
                atmSpvcVccPeakCellRateB2A       Integer32,
                atmSpvcVccSusCellRateB2A        Integer32,
                atmSpvcVccMaxBurstSizeB2A       Integer32,
                atmSpvcVccFrwdErrCorrectionB2A  INTEGER,
                atmSpvcVccFlow                  INTEGER,
                atmSpvcVccType                  INTEGER,
                atmSpvcVccConnType              INTEGER,
                atmSpvcVccLeafReference         INTEGER,
                atmSpvcVccOperStatus            INTEGER,
                atmSpvcVccRowStatus             RowStatus,
                atmSpvcVccViA                   INTEGER,
                atmSpvcVccViB                   INTEGER,
                atmSpvcVccTrafficShapingA2B     INTEGER,
                atmSpvcVccTrafficShapingB2A     INTEGER
                }

atmSpvcVccVpiA        OBJECT-TYPE
                SYNTAX INTEGER (0..4095)
                MAX-ACCESS not-accessible
                STATUS current
                DESCRIPTION "VPI value for side A of an ATM SPVC VCC connection.
                             Valid range is a number between 0 and 4095."
                ::= { atmSpvcVccEntry 1 }

atmSpvcVccVciA        OBJECT-TYPE
                SYNTAX INTEGER (0..65535)
                MAX-ACCESS not-accessible
                STATUS current
                DESCRIPTION "VCI value for side A of an ATM SPVC VCC connection.
                             Valid range is a number between 0 and 65535."
                ::= { atmSpvcVccEntry 2 }

atmSpvcVccIfB        OBJECT-TYPE
                SYNTAX IntfIndex
                MAX-ACCESS read-only
                STATUS current
                DESCRIPTION "Interface index for side B of an ATM SPVC VCC 
                             connection.  Number value is interpreted as an 
                             interface of the form, SSPPCCC, where SS is the 
                             card slot, PP is the port number, and CCC is the 
                             channel number."
                ::= { atmSpvcVccEntry 3 }

atmSpvcVccVpiB        OBJECT-TYPE
                SYNTAX INTEGER (0..4095)
                MAX-ACCESS read-only
                STATUS current
                DESCRIPTION "VPI value for side B of an ATM SPVC VCC connection.
                             Valid range is a number between 0 and 4095."
                ::= { atmSpvcVccEntry 4 }

atmSpvcVccVciB        OBJECT-TYPE
                SYNTAX INTEGER (0..65535)
                MAX-ACCESS read-only
                STATUS current
                DESCRIPTION "VCI value for side B of an ATM SPVC VCC connection.
                             Valid range is a number between 0 and 65535."
                ::= { atmSpvcVccEntry 5 }

atmSpvcVccServiceTypeA2B OBJECT-TYPE
                SYNTAX INTEGER  {
                                ubr(1),
                                vbr-nrt2(2),
                                vbr-nrt1(3),
                                vbr-rt2(4),
                                vbr-rt1(5),
                                vbr-express(6),
                                cbr4(7),
                                cbr3(8),
                                cbr2(9),
                cbr1(10)
                                }
                MAX-ACCESS read-write
                STATUS current
                DESCRIPTION "Service type, ATM port."
                DEFVAL { ubr }
                ::= { atmSpvcVccEntry 6 }

atmSpvcVccSarTypeA2B OBJECT-TYPE
                SYNTAX INTEGER  {
                                aal5(1),
                                aal3-4(2),
                                aal2(3),
                                aal1(4),
                                null(5)
                                }
                MAX-ACCESS read-write
                STATUS current
                DESCRIPTION "SAR type used in ATM adaption, ATM port."
                DEFVAL { null }
                ::= { atmSpvcVccEntry 7 }

atmSpvcVccPeakCellRateA2B OBJECT-TYPE
                SYNTAX Integer32
                MAX-ACCESS read-write
                STATUS current
                DESCRIPTION "Peak cell rate - side A, ATM port, in cells per
                             second."
                DEFVAL { 1 }
                ::= { atmSpvcVccEntry 8 }

atmSpvcVccSusCellRateA2B OBJECT-TYPE
                SYNTAX Integer32
                MAX-ACCESS read-write
                STATUS current
                DESCRIPTION "Sustained cell rate - side A, ATM port, in cells
                             per second."
                DEFVAL { 1 }
                ::= { atmSpvcVccEntry 9 }

atmSpvcVccMaxBurstSizeA2B OBJECT-TYPE
                SYNTAX Integer32
                MAX-ACCESS read-write
                STATUS current
                DESCRIPTION "Maximum burst size - side A, ATM port, in cells
                             per second."
                DEFVAL { 1 }
                ::= { atmSpvcVccEntry 10 }

atmSpvcVccFrwdErrCorrectionA2B OBJECT-TYPE
                SYNTAX INTEGER {
                                none(1),
                                eighthRate(2),
                                quarterRate(3),
                                halfRate(4),
                                autoHiQ(5),
                                auto(6),
                                autoLoQ(7)
                               }
                MAX-ACCESS read-write
                STATUS current
                DESCRIPTION "Forward error correction scheme, ATM port side."
                DEFVAL { none }
                ::= { atmSpvcVccEntry 11 }

atmSpvcVccServiceTypeB2A OBJECT-TYPE
                SYNTAX INTEGER  {
                                ubr(1),
                                vbr-nrt2(2),
                                vbr-nrt1(3),
                                vbr-rt2(4),
                                vbr-rt1(5),
                                vbr-express(6),
                                cbr4(7),
                                cbr3(8),
                                cbr2(9),
                cbr1(10)
                                }
                MAX-ACCESS read-write
                STATUS current
                DESCRIPTION "Service type, ATM trunk side."
                DEFVAL { ubr }
                ::= { atmSpvcVccEntry 12 }

atmSpvcVccSarTypeB2A OBJECT-TYPE
                SYNTAX INTEGER  {
                                aal5(1),
                                aal3-4(2),
                                aal2(3),
                                aal1(4),
                                null(5)
                                }
                MAX-ACCESS read-write
                STATUS current
                DESCRIPTION "SAR type used in ATM adaption, ATM trunk side."
                DEFVAL { null }
                ::= { atmSpvcVccEntry 13 }

atmSpvcVccPeakCellRateB2A OBJECT-TYPE
                SYNTAX Integer32
                MAX-ACCESS read-write
                STATUS current
                DESCRIPTION "Peak cell rate - side B, ATM trunk, in cells per
                             second."
                DEFVAL { 1 }
                ::= { atmSpvcVccEntry 14 }

atmSpvcVccSusCellRateB2A        OBJECT-TYPE
                SYNTAX Integer32
                MAX-ACCESS read-write
                STATUS current
                DESCRIPTION "Sustained cell rate - side B, ATM trunk, in cells
                             per second."
                DEFVAL { 1 }
                ::= { atmSpvcVccEntry 15 }

atmSpvcVccMaxBurstSizeB2A OBJECT-TYPE
                SYNTAX Integer32
                MAX-ACCESS read-write
                STATUS current
                DESCRIPTION "Maximum burst size - side A, ATM trunk, in cells
                             per second."
                DEFVAL { 1 }
                ::= { atmSpvcVccEntry 16 }

atmSpvcVccFrwdErrCorrectionB2A OBJECT-TYPE
                SYNTAX INTEGER {
                                none(1),
                                eighthRate(2),
                                quarterRate(3),
                                halfRate(4),
                                autoHiQ(5),
                                auto(6),
                                autoLoQ(7)
                               }
                MAX-ACCESS read-write
                STATUS current
                DESCRIPTION "Forward error correction scheme, ATM trunk side."
                DEFVAL { none }
                ::= { atmSpvcVccEntry 17 }

atmSpvcVccFlow        OBJECT-TYPE
                SYNTAX INTEGER        {
                                duplex(1),
                                simplexA2B(2),
                                pointToMultipointA2B(3),
                                simplexB2A(4)
                                }
                MAX-ACCESS read-write
                STATUS current
                DESCRIPTION "Type of flow, pointToMultipointA2B is for future
                             support."
                DEFVAL { duplex }
                ::= { atmSpvcVccEntry 18 }

atmSpvcVccType        OBJECT-TYPE
                SYNTAX INTEGER  {
                                nonsecured(1),
                                secured(2)
                                }
                MAX-ACCESS read-write
                STATUS current
                DESCRIPTION "Type of connection."
                DEFVAL { nonsecured }
                ::= { atmSpvcVccEntry 19 }

atmSpvcVccConnType OBJECT-TYPE
                SYNTAX INTEGER  {
                                activeSvc(1),
                                passiveSvc(2)
                                }
                MAX-ACCESS read-write
                STATUS current
                DESCRIPTION "The type of connection:
                             activeSvc - attempt calls, whenever not 
                               established.
                             passiveSvc - accept calls."
                ::= { atmSpvcVccEntry 20 }

atmSpvcVccLeafReference OBJECT-TYPE
                SYNTAX INTEGER (1..65535)
                MAX-ACCESS read-only
                STATUS current
                DESCRIPTION "An arbitrary integer which serves to distinguish
                             the mulitple leaves attached to a root of a 
                             point-to-multipoint SPVC.  If point-to-point SPVC, 
                             the value should be 1."
                ::= { atmSpvcVccEntry 21 }

atmSpvcVccOperStatus OBJECT-TYPE
                SYNTAX INTEGER  {
                                other(1),
                                establishmentInProgress(2),
                                connected(3),
                                retriesExhausted(4),
                                noAddressSupplied(5),
                                lowerLayerDown(6)
                                }
                MAX-ACCESS read-only
                STATUS current
                DESCRIPTION "The operation status of the connection:
                             other - none of the types specified below.
                             establishmentInProgress - connection is not 
                                operational, but call attempts are ongoing.
                             connected - connection is currently operational.
                             retriesExhausted - retry limit has been reached 
                                and call attempts have ceased.
                             noAddressSupplied - no remote address has been 
                                configured, so no call attempts are initiated.
                             lowerLayerDown - SPVC handler is not operational."
                ::= { atmSpvcVccEntry 22 }

atmSpvcVccRowStatus OBJECT-TYPE
                SYNTAX RowStatus
                MAX-ACCESS read-write
                STATUS current
                DESCRIPTION "Used to create and delete a soft PVC.  When this
                             object is set to 'active', an attempt is made to 
                             set up the soft PVC.  When this object has the 
                             value 'active' and is set to another value, any 
                             setup or connection in-progress is released."
                ::= { atmSpvcVccEntry 23 }

atmSpvcVccViA   OBJECT-TYPE
                SYNTAX INTEGER (0..1024)
                MAX-ACCESS read-write
                STATUS current
                DESCRIPTION "VI to associate the Egress part of the
                        B2A connection ."
                DEFVAL { 0 }
                ::= { atmSpvcVccEntry 24 }

atmSpvcVccViB   OBJECT-TYPE
                SYNTAX INTEGER (0..1024)
                MAX-ACCESS read-write
                STATUS current
                DESCRIPTION "VI to associate the Egress part of the
                        A2B connection ."
                DEFVAL { 0 }
                ::= { atmSpvcVccEntry 25 }

atmSpvcVccTrafficShapingA2B     OBJECT-TYPE
                SYNTAX INTEGER {
                                disabled(1),
                                enabled(2)
                               }
                MAX-ACCESS read-write
                STATUS current
                DESCRIPTION "Traffic Shaping Support in the A2B direction."
                DEFVAL { disabled }
                ::= { atmSpvcVccEntry 26 }

atmSpvcVccTrafficShapingB2A     OBJECT-TYPE
                SYNTAX INTEGER {
                                disabled(1),
                                enabled(2)
                               }
                MAX-ACCESS read-write
                STATUS current
                DESCRIPTION "Traffic Shaping Support in the B2A direction."
                DEFVAL { disabled }
                ::= { atmSpvcVccEntry 27 }

atmSpvcVccActiveSvcTable OBJECT-TYPE
                SYNTAX SEQUENCE OF AtmSpvcVccActiveSvcEntry
                MAX-ACCESS not-accessible
                STATUS current
                DESCRIPTION "The table used to manage active SVCs established 
                             across ATM networks between ATM entities."
                ::= { connectionConfig 18 }

atmSpvcVccActiveSvcEntry OBJECT-TYPE
                SYNTAX AtmSpvcVccActiveSvcEntry
                MAX-ACCESS not-accessible
                STATUS current
                DESCRIPTION "An entry in the ATM active SVC table.  There is one
                             entry in the table corresponding to each active row
                             in the atm SPVC VCC Table for which the 
                             atmSpvcVccConnType takes the value 'activeSvc'."
                INDEX { atmSpvcVccIfA, atmSpvcVccVpiA, atmSpvcVccVciA }
                ::= { atmSpvcVccActiveSvcTable 1 }

AtmSpvcVccActiveSvcEntry ::= SEQUENCE {
                atmSpvcVccRemoteAtmPortAddr        OCTET STRING,
                atmSpvcVccRemoteSelectType        INTEGER,
                atmSpvcVccRemoteVpi                INTEGER,
                atmSpvcVccRemoteVci                INTEGER,
                atmSpvcVccRetryInterval                INTEGER,
                atmSpvcVccRetryLimit                INTEGER,
                atmSpvcVccRestart                INTEGER,
                atmSpvcVccRetryFailure                Integer32,
                atmSpvcVccReleaseCause                INTEGER,
                atmSpvcVccReleaseDiag                OCTET STRING
                }

atmSpvcVccRemoteAtmPortAddr OBJECT-TYPE
                SYNTAX OCTET STRING (SIZE(1..20))
                MAX-ACCESS read-write
                STATUS current
                DESCRIPTION "Remote ATM port NSAP address, not meaningful if 
                             passive type of connection."
                ::= { atmSpvcVccActiveSvcEntry 1 }

atmSpvcVccRemoteSelectType OBJECT-TYPE
                SYNTAX INTEGER  {
                                required(1),
                                any(2)
                                }
                MAX-ACCESS read-write
                STATUS current
                DESCRIPTION "Indicates whether the remote VPI/VCI values are to 
                             be used at the destination.  If 'any' is used, the 
                             destination switch will choose the VPI/VCI values. 
                             In such a case, once the SPVC is connected, the 
                             value of this object will change to 'required', 
                             such that the same VPI/VCI values will continue to 
                             be used even if the connection is torn down and 
                             re-established.  If the value 'required' is
                             specified, the values:  atmSpvcVccRemoteVpi and 
                             atmSpvcVccRemoteVci, must be supplied and are used
                             at the destination."
                ::= { atmSpvcVccActiveSvcEntry 2 }

atmSpvcVccRemoteVpi OBJECT-TYPE
                SYNTAX INTEGER (0..4095)
                MAX-ACCESS read-write
                STATUS current
                DESCRIPTION "VPI value to be used at the destination of an 
                             ATM SPVC VCC connection.  Valid range is a number 
                             between 0 and 4095.  If atmSpvcVccRemoteSelectType 
                             is configured as 'any', then this value is not 
                             relevant."
                ::= { atmSpvcVccActiveSvcEntry 3 }

atmSpvcVccRemoteVci OBJECT-TYPE
                SYNTAX INTEGER (0..65535)
                MAX-ACCESS read-write
                STATUS current
                DESCRIPTION "VCI value to be used at the destination of an ATM 
                             SPVC VCC connection.  Valid range is a number 
                             between 0 and 65535.  If atmSpvcVccRemoteSelectType
                             is configured as 'any', then this value is not 
                             relevant."
                ::= { atmSpvcVccActiveSvcEntry 4 }

atmSpvcVccRetryInterval OBJECT-TYPE
                SYNTAX INTEGER (0..3600)
                MAX-ACCESS read-write
                STATUS current
                DESCRIPTION "The time to wait before attempting to establish 
                             the SVC after a previous failed call attempt.  A 
                             value of 0 indicates retry will be attempted immediately."
                ::= { atmSpvcVccActiveSvcEntry 5 }

atmSpvcVccRetryLimit OBJECT-TYPE
                SYNTAX INTEGER (0..65535)
                MAX-ACCESS read-write
                STATUS current
                DESCRIPTION "A maximum limit on how many retries should be 
                             attempted.  A value of 0 indicates no limit."
                ::= { atmSpvcVccActiveSvcEntry 6 }

atmSpvcVccRestart OBJECT-TYPE
                SYNTAX INTEGER  {
                                restart(1),
                                noop(2)
                                }
                MAX-ACCESS read-write
                STATUS current
                DESCRIPTION "The active SVC is released, if necessary, and a 
                             new setup procedure is begun if 'restart', 
                             otherwise, noop."
                ::= { atmSpvcVccActiveSvcEntry 7 }

atmSpvcVccRetryFailure OBJECT-TYPE
                SYNTAX Integer32
                MAX-ACCESS read-only
                STATUS current
                DESCRIPTION "Indicates how many attempts to establish the 
                             connection have failed.  It it reset whenever a 
                             connection is successfully established or the SVC 
                             is restarted."
                ::= { atmSpvcVccActiveSvcEntry 8 }

atmSpvcVccReleaseCause OBJECT-TYPE
                SYNTAX INTEGER (1..127)
                MAX-ACCESS read-only
                STATUS current
                DESCRIPTION "CAUSE field value of the last RELEASE message 
                             received for this SVC."
                ::= { atmSpvcVccActiveSvcEntry 9 }

atmSpvcVccReleaseDiag OBJECT-TYPE
                SYNTAX OCTET STRING (SIZE(0..8))
                MAX-ACCESS read-only
                STATUS current
                DESCRIPTION "DIAGNOSTICS field value of the last RELEASE 
                             message received for this SVC."
                ::= { atmSpvcVccActiveSvcEntry 10 }


cirEmAtmSpvcVccTable OBJECT-TYPE
                SYNTAX SEQUENCE OF CirEmAtmSpvcVccEntry
                MAX-ACCESS not-accessible
                STATUS current
                DESCRIPTION "Table of Circuit Emulation to ATM Soft PVCs."
                ::= { connectionConfig 19 }

cirEmAtmSpvcVccEntry OBJECT-TYPE
                SYNTAX CirEmAtmSpvcVccEntry
                MAX-ACCESS not-accessible
                STATUS current
                DESCRIPTION "Row definition of circuit emulation to ATM SPVC
                              connections."
                INDEX { cirEmAtmSpvcVccIfA }
                ::= { cirEmAtmSpvcVccTable 1 }

CirEmAtmSpvcVccEntry ::= SEQUENCE {
                        cirEmAtmSpvcVccIfA                         IntfIndex,
                        cirEmAtmSpvcVccIfB                        IntfIndex,
                        cirEmAtmSpvcVccVpiB                          INTEGER,
                        cirEmAtmSpvcVccVciB                          INTEGER,
                        cirEmAtmSpvcVccVoiceCompressionA2B        INTEGER,
                        cirEmAtmSpvcVccSilenceDetectionA2B        INTEGER,
                        cirEmAtmSpvcVccEchoCancellationA2B        INTEGER,
                        cirEmAtmSpvcVccCngToneDetectionA2B        INTEGER,
                        cirEmAtmSpvcVccCodingTranslationA2B        INTEGER,
                        cirEmAtmSpvcVccVoiceCompressionB2A        INTEGER,
                        cirEmAtmSpvcVccSilenceDetectionB2A        INTEGER,
                        cirEmAtmSpvcVccEchoCancellationB2A        INTEGER,
                        cirEmAtmSpvcVccCngToneDetectionB2A        INTEGER,
                        cirEmAtmSpvcVccCodingTranslationB2A        INTEGER,
                        cirEmAtmSpvcVccFlow                        INTEGER,
                        cirEmAtmSpvcVccServiceType                INTEGER,
                        cirEmAtmSpvcVccConnType                        INTEGER,
                        cirEmAtmSpvcVccCePortAddr                OCTET STRING,
                        cirEmAtmSpvcVccOperStatus                INTEGER,
                        cirEmAtmSpvcVccRowStatus                RowStatus,
                        cirEmAtmSpvcVccViB                        INTEGER
                        }

cirEmAtmSpvcVccIfA OBJECT-TYPE
                SYNTAX IntfIndex
                MAX-ACCESS not-accessible
                STATUS current
                DESCRIPTION "Interface index for side A, the circuit emulation
                             side, of a circuit emulation-atm SPVC VCC 
                             connection.  Number value is interpreted as an 
                             interface of the form, SSPPCCC, where SS is the 
                             card slot, PP is the port number, and CCC is the 
                             channel number."
                ::= { cirEmAtmSpvcVccEntry 1 }

cirEmAtmSpvcVccIfB OBJECT-TYPE
                SYNTAX IntfIndex
                MAX-ACCESS read-only
                STATUS current
                DESCRIPTION "Interface index for side B, the atm side, of a 
                             circuit emulation-atm SPVC VCC connection.  Number 
                             value is interpreted as an interface of the form, 
                             SSPPCCC, where SS is the card slot, PP is the port                              number, and CCC is the channel number."
                ::= { cirEmAtmSpvcVccEntry 2 }

cirEmAtmSpvcVccVpiB OBJECT-TYPE
                SYNTAX INTEGER (0..4095)
                MAX-ACCESS read-only
                STATUS current
                DESCRIPTION "VPI value for side B, the atm side,  of a
                             circuit emulation-atm SPVC VCC connection.  Valid 
                             range is a number between 0 and 4095."
                ::= { cirEmAtmSpvcVccEntry 3 }

cirEmAtmSpvcVccVciB OBJECT-TYPE
                SYNTAX INTEGER (0..65535)
                MAX-ACCESS read-only
                STATUS current
                DESCRIPTION "VCI value for side B, the atm side,  of a
                             circuit emulation-atm SPVC VCC connection.  Valid 
                             range is a number between 0 and 65535."
                ::= { cirEmAtmSpvcVccEntry 4 }

cirEmAtmSpvcVccVoiceCompressionA2B OBJECT-TYPE
                SYNTAX INTEGER  {
                                none(1),
                                g726-16k(2),
                                g726-24k(3),
                                g726-32k(4),
                                g726-40k(5)
                                }
                MAX-ACCESS read-write
                STATUS current
                DESCRIPTION "Voice Compression Algorithm"
                DEFVAL { none }
                ::= { cirEmAtmSpvcVccEntry 5 }

cirEmAtmSpvcVccSilenceDetectionA2B OBJECT-TYPE
                SYNTAX INTEGER  {
                                 disabled(1),
                                 enabled(2)
                                }
                MAX-ACCESS read-write
                STATUS current
                DESCRIPTION "silence detection off/on"
                DEFVAL { disabled }
                ::= { cirEmAtmSpvcVccEntry 6 }

cirEmAtmSpvcVccEchoCancellationA2B OBJECT-TYPE
                SYNTAX INTEGER  {
                                 none(1),
                                 g165-nearEnd(2),
                                 g168(3)
                                }
                MAX-ACCESS read-write
                STATUS current
                DESCRIPTION "Echo Cancellation Algorithm"
                DEFVAL { none }
                ::= { cirEmAtmSpvcVccEntry 7 }

cirEmAtmSpvcVccCngToneDetectionA2B OBJECT-TYPE
                SYNTAX INTEGER  {
                                 disabled(1),
                                 bypass(2),
                                 g726-32k(3)
                                }
                MAX-ACCESS read-write
                STATUS current
                DESCRIPTION "Calling Tone Detection Algorithm,
                             one of the enum value, g726-32k(3)
                             is obsoleted on 01Mar99 such that
                             user would not be able to configure
                             CE-ATM"
                DEFVAL { disabled }
                ::= { cirEmAtmSpvcVccEntry 8 }

cirEmAtmSpvcVccCodingTranslationA2B OBJECT-TYPE
                SYNTAX INTEGER  {
                                 none(1),
                                 muLaw2muLaw(2),
                                 aLaw2aLaw(3),
                                 muLaw2aLaw(4),
                                 aLaw2muLaw(5)
                                }
                MAX-ACCESS read-write
                STATUS current
                DESCRIPTION "Coding rule translation type."
                DEFVAL { none }
                ::= { cirEmAtmSpvcVccEntry 9 }

cirEmAtmSpvcVccVoiceCompressionB2A OBJECT-TYPE
                SYNTAX INTEGER  {
                                none(1),
                                g726-16k(2),
                                g726-24k(3),
                                g726-32k(4),
                                g726-40k(5)
                                }
                MAX-ACCESS read-write
                STATUS current
                DESCRIPTION "Voice Compression Algorithm"
                DEFVAL { none }
                ::= { cirEmAtmSpvcVccEntry 10 }

cirEmAtmSpvcVccSilenceDetectionB2A OBJECT-TYPE
                SYNTAX INTEGER  {
                                 disabled(1),
                                 enabled(2)
                                }
                MAX-ACCESS read-write
                STATUS current
                DESCRIPTION "silence detection off/on"
                DEFVAL { disabled }
                ::= { cirEmAtmSpvcVccEntry 11 }

cirEmAtmSpvcVccEchoCancellationB2A OBJECT-TYPE
                SYNTAX INTEGER  {
                                 none(1),
                                 g165-nearEnd(2),
                                 g168(3)
                                }
                MAX-ACCESS read-write
                STATUS current
                DESCRIPTION "Echo Cancellation Algorithm"
                DEFVAL { none }
                ::= { cirEmAtmSpvcVccEntry 12 }

cirEmAtmSpvcVccCngToneDetectionB2A OBJECT-TYPE
                SYNTAX INTEGER  {
                                 disabled(1),
                                 bypass(2),
                                 g726-32k(3)
                                }
                MAX-ACCESS read-write
                STATUS current
                DESCRIPTION "Calling Tone Detection Algorithm,
                             one of the enum value, g726-32k(3)
                             is obsoleted on 01Mar99 such that
                             user would not be able to configure
                             CE-ATM"
                DEFVAL { disabled }
                ::= { cirEmAtmSpvcVccEntry 13 }

cirEmAtmSpvcVccCodingTranslationB2A OBJECT-TYPE
                SYNTAX INTEGER  {
                                 none(1),
                                 muLaw2muLaw(2),
                                 aLaw2aLaw(3),
                                 muLaw2aLaw(4),
                                 aLaw2muLaw(5)
                                }
                MAX-ACCESS read-write
                STATUS current
                DESCRIPTION "Coding rule translation type."
                DEFVAL { none }
                ::= { cirEmAtmSpvcVccEntry 14 }

cirEmAtmSpvcVccFlow OBJECT-TYPE
                SYNTAX INTEGER  {
                                 duplex(1),
                                 simplexA2B(2),
                                 simplexB2A(3),
                                 pointToMultipointA2B(4),
                                 pointToMultipointB2A(5)
                                }
                MAX-ACCESS read-write
                STATUS current
                DESCRIPTION "Flow Type, pointToMultipointA2B and 
                             pointToMultipointB2A are for future support."
                DEFVAL { duplex }
                ::= { cirEmAtmSpvcVccEntry 15 }

cirEmAtmSpvcVccServiceType OBJECT-TYPE
                SYNTAX INTEGER {
                                cbr-1(1),
                                cbr-2(2),
                                cbr-3(3),
                                cbr-4(4)
                               }
                MAX-ACCESS read-write
                STATUS current
                DESCRIPTION "service type"
                ::= { cirEmAtmSpvcVccEntry 16 }

cirEmAtmSpvcVccConnType    OBJECT-TYPE
                SYNTAX INTEGER{
                                activeSvc(1),
                                passiveSvc(2)
                                }
                MAX-ACCESS read-write
                STATUS current
                DESCRIPTION "The type of connection: activeSvc - attempt calls,
                                whenever not established;
                             passiveSvc - accepts calls"
                ::= { cirEmAtmSpvcVccEntry 17 }

cirEmAtmSpvcVccCePortAddr OBJECT-TYPE
                SYNTAX OCTET STRING (SIZE(1..20))
                MAX-ACCESS read-write
                STATUS current
                DESCRIPTION "local CES port nsap address"
                ::= { cirEmAtmSpvcVccEntry 18 }

cirEmAtmSpvcVccOperStatus OBJECT-TYPE
                SYNTAX INTEGER {
                                other(1),
                                establishmentInProgress(2),
                                connected(3),
                                retriesExhausted(4),
                                noAddressSupplied(5),
                                lowerLayerDown(6)
                                }
                MAX-ACCESS read-only
                STATUS current
                DESCRIPTION "other - none of the types specified below;
                             establishmentInProgress - connection is not 
                                operational, but call attempts are ongoing;
                             connected - connection is currently operational;
                             retriesExhausted - retry limit has been reached 
                                and call attempts have ceased;
                             noAddressSupplied - no remote address has been 
                                configured, so no call attempts are initiated;
                             lowerLayerDown - SPVC handler is not operational."
                ::= { cirEmAtmSpvcVccEntry 19 }

cirEmAtmSpvcVccRowStatus  OBJECT-TYPE
                SYNTAX     RowStatus
                MAX-ACCESS read-write
                STATUS     current
                DESCRIPTION "Used to create and delete a soft PVCC.  When this 
                             object is set to 'active' an attempt is made to 
                             set up the soft PVCC.  When this object has the 
                             value 'active' and is set to another value, any 
                             set-up or connection in-progess is released."
                ::= { cirEmAtmSpvcVccEntry 20 }

cirEmAtmSpvcVccViB      OBJECT-TYPE
                SYNTAX INTEGER (0..1024)
                MAX-ACCESS read-write
                STATUS current
                DESCRIPTION "VI to associate the Egress part of 
                                the B2A connection ."
                DEFVAL { 0 } 
                ::= { cirEmAtmSpvcVccEntry 21 }

cirEmAtmSpvcVccActiveSvcTable OBJECT-TYPE
                SYNTAX SEQUENCE OF CirEmAtmSpvcVccActiveSvcEntry
                MAX-ACCESS  not-accessible
                STATUS current
                DESCRIPTION "The table used to manage active SVCs established 
                             across ATM networks between CES entities."
                ::= { connectionConfig 20 }

cirEmAtmSpvcVccActiveSvcEntry OBJECT-TYPE
                SYNTAX CirEmAtmSpvcVccActiveSvcEntry
                MAX-ACCESS  not-accessible
                STATUS current
                DESCRIPTION "An entry in the CES active SVC table. There is 
                             one entry in the table corresponding to each 
                              active row in the cirEmAtmSpvcVccRowStatus for 
                             which the cirEmAtmSpvcVccConnType takes the value
                             'activeSvc'."
                INDEX { cirEmAtmSpvcVccIfA }
                ::= { cirEmAtmSpvcVccActiveSvcTable 1 }

CirEmAtmSpvcVccActiveSvcEntry ::= SEQUENCE {
                              cirEmAtmSpvcVccRemoteCePortAddr    OCTET STRING,
                              cirEmAtmSpvcVccRetryInterval       INTEGER,
                              cirEmAtmSpvcVccRetryLimit          INTEGER,
                              cirEmAtmSpvcVccRestart             INTEGER,
                              cirEmAtmSpvcVccRetryFailure        Integer32,
                              cirEmAtmSpvcVccReleaseCause        INTEGER,
                              cirEmAtmSpvcVccReleaseDiag         OCTET STRING
                              }

cirEmAtmSpvcVccRemoteCePortAddr        OBJECT-TYPE
                SYNTAX OCTET STRING (SIZE(1..20))
                MAX-ACCESS read-write
                STATUS current
                DESCRIPTION "The ATM address supporting the corresponding far 
                             end CES IWF process.  If no address is supplied, 
                             no attempts to establish the active SVC are 
                             initiated."
                ::= { cirEmAtmSpvcVccActiveSvcEntry 1 }

cirEmAtmSpvcVccRetryInterval OBJECT-TYPE
                SYNTAX INTEGER (0..3600)
                UNITS      "seconds"
                MAX-ACCESS read-write
                STATUS current
                DESCRIPTION "The time to wait before attempting to establish 
                             the SVC after previous failed call attempt. 
                             0 indicates retry will be attempted immediately."
                DEFVAL { 10 }
                ::= { cirEmAtmSpvcVccActiveSvcEntry 2 }

cirEmAtmSpvcVccRetryLimit OBJECT-TYPE
                SYNTAX INTEGER (0..65535)
                MAX-ACCESS read-write
                STATUS current
                DESCRIPTION "A maximum limit on how many retries. 
                             0 indicates no limit."
                DEFVAL { 0 }
                ::= { cirEmAtmSpvcVccActiveSvcEntry 3 }

cirEmAtmSpvcVccRestart OBJECT-TYPE
                SYNTAX INTEGER {
                                restart(1),
                                noop(2)
                                }
                MAX-ACCESS read-write
                STATUS current
                DESCRIPTION "restart, the active SVC is released if necessary 
                             and a new setup procedure is begun; or noop"
                ::= { cirEmAtmSpvcVccActiveSvcEntry 4 }

cirEmAtmSpvcVccRetryFailure OBJECT-TYPE
                SYNTAX Integer32 
                MAX-ACCESS read-only
                STATUS current
                DESCRIPTION "Indicates how many attempts to establish the 
                             connection have failed.  It is reset whenever a 
                             connection is successfully established or the SVC 
                             is restarted."
                ::= { cirEmAtmSpvcVccActiveSvcEntry 5 }

cirEmAtmSpvcVccReleaseCause OBJECT-TYPE
                SYNTAX INTEGER(1..127) 
                MAX-ACCESS read-only
                STATUS current
                DESCRIPTION "CAUSE field value of the last RELEASE message 
                             received for this SVC."
                ::= { cirEmAtmSpvcVccActiveSvcEntry 6 }

cirEmAtmSpvcVccReleaseDiag OBJECT-TYPE
                SYNTAX OCTET STRING (SIZE(0..8)) 
                MAX-ACCESS read-only
                STATUS current
                DESCRIPTION "DIAGNOSTICS field value of the last RELEASE 
                             message received for this SVC."
                ::= { cirEmAtmSpvcVccActiveSvcEntry 7 }


vbrAtmSpvcVccTable OBJECT-TYPE
                SYNTAX SEQUENCE OF VbrAtmSpvcVccEntry
                MAX-ACCESS not-accessible
                STATUS current
                DESCRIPTION "Table of SPVC atm virtual channel connections"
                ::= { connectionConfig 21 }

vbrAtmSpvcVccEntry OBJECT-TYPE
                SYNTAX VbrAtmSpvcVccEntry
                MAX-ACCESS not-accessible
                STATUS current
                DESCRIPTION "Row definition of atm SPVC VCC connections"
                INDEX { vbrAtmSpvcVccIfA }
                ::= { vbrAtmSpvcVccTable 1 }

VbrAtmSpvcVccEntry ::= SEQUENCE {
                        vbrAtmSpvcVccIfA                IntfIndex,
                        vbrAtmSpvcVccIfB                IntfIndex,
                        vbrAtmSpvcVccVpiB               INTEGER,
                        vbrAtmSpvcVccVciB               INTEGER,
                        vbrAtmSpvcVccServiceType        INTEGER,
                        vbrAtmSpvcVccPeakCellRateA2B    Integer32,
                        vbrAtmSpvcVccSusCellRateA2B     Integer32,
                        vbrAtmSpvcVccMaxBurstSizeA2B    Integer32,
                        vbrAtmSpvcVccPeakCellRateB2A    Integer32,
                        vbrAtmSpvcVccSusCellRateB2A     Integer32,
                        vbrAtmSpvcVccMaxBurstSizeB2A    Integer32,
                        vbrAtmSpvcVccFlow               INTEGER,
                        vbrAtmSpvcVccConnType           INTEGER,
                        vbrAtmSpvcVccVbrPortAddr        OCTET STRING,
                        vbrAtmSpvcVccOperStatus         INTEGER,
                        vbrAtmSpvcVccRowStatus          RowStatus,
                        vbrAtmSpvcVccViB                INTEGER,
                        vbrAtmSpvcVccTrafficShapingA2B  INTEGER
                                }

vbrAtmSpvcVccIfA OBJECT-TYPE
                SYNTAX IntfIndex
                MAX-ACCESS not-accessible
                STATUS current
                DESCRIPTION "Interface index for side A, the variable bit rate
                             side, of a variable bit rate-atm SPVC VCC 
                             connection.  Number value is interpreted as an 
                             interface of the form, SSPPCCC, where SS is the 
                             card slot, PP is the port number, and CCC is the 
                             channel number."
                ::= { vbrAtmSpvcVccEntry 1 }

vbrAtmSpvcVccIfB OBJECT-TYPE
                SYNTAX IntfIndex
                MAX-ACCESS read-only
                STATUS current
                DESCRIPTION "Interface index for side B, the atm side, of a 
                             variable bit rate-atm SPVC VCC connection.  Number 
                             value is interpreted as an interface of the form, 
                             SSPPCCC, where SS is the card slot, PP is the port 
                             number, and CCC is the channel number."
                ::= { vbrAtmSpvcVccEntry 2 }

vbrAtmSpvcVccVpiB OBJECT-TYPE
                SYNTAX INTEGER (0..4095)
                MAX-ACCESS read-only
                STATUS current
                DESCRIPTION "VPI value for side B, the atm side,  of a
                             variable bit rate-atm SPVC VCC connection.  Valid 
                             range is a number between 0 and 4095."
                ::= { vbrAtmSpvcVccEntry 3 }

vbrAtmSpvcVccVciB OBJECT-TYPE
                SYNTAX INTEGER (0..65535)
                MAX-ACCESS read-only
                STATUS current
                DESCRIPTION "VCI value for side B, the atm side,  of a
                             variable bit rate-atm SPVC VCC connection.  Valid 
                             range is a number between 0 and 65535."
                ::= { vbrAtmSpvcVccEntry 4 }

vbrAtmSpvcVccServiceType OBJECT-TYPE
                SYNTAX INTEGER  {
                                ubr(1),
                                vbr-nrt1(2),
                                vbr-nrt2(3),
                                vbr-rt1(4),
                                vbr-rt2(5),
                                vbr-express(6)
                                }
                MAX-ACCESS read-write
                STATUS current
                DESCRIPTION "service type"
                DEFVAL { ubr }
                ::= { vbrAtmSpvcVccEntry 5 }

vbrAtmSpvcVccPeakCellRateA2B OBJECT-TYPE
                SYNTAX Integer32
                MAX-ACCESS read-write
                STATUS current
                DESCRIPTION "peak cell rate - side A, in cell per second"
                DEFVAL { 1 }
                ::= { vbrAtmSpvcVccEntry 6 }

vbrAtmSpvcVccSusCellRateA2B OBJECT-TYPE
                SYNTAX Integer32
                MAX-ACCESS read-write
                STATUS current
                DESCRIPTION "sustained rate - side A, in cell per second"
                DEFVAL { 1 }
                ::= { vbrAtmSpvcVccEntry 7 }

vbrAtmSpvcVccMaxBurstSizeA2B OBJECT-TYPE
                SYNTAX Integer32
                MAX-ACCESS read-write
                STATUS current
                DESCRIPTION "maximum burst size - side A,  in cells"
                DEFVAL { 1 }
                ::= { vbrAtmSpvcVccEntry 8 }

vbrAtmSpvcVccPeakCellRateB2A OBJECT-TYPE
                SYNTAX Integer32
                MAX-ACCESS read-write
                STATUS current
                DESCRIPTION "peak rate - side B, ATM trunk, in cell per second."
                DEFVAL { 1 }
                ::= { vbrAtmSpvcVccEntry 9 }

vbrAtmSpvcVccSusCellRateB2A OBJECT-TYPE
                SYNTAX Integer32
                MAX-ACCESS read-write
                STATUS current
                DESCRIPTION "sustained rate - side B, ATM trunk, in cell per 
                             second."
                DEFVAL { 1 }
                ::= { vbrAtmSpvcVccEntry 10 }

vbrAtmSpvcVccMaxBurstSizeB2A OBJECT-TYPE
                SYNTAX Integer32
                MAX-ACCESS read-write
                STATUS current
                DESCRIPTION "maximum burst size - side B, ATM trunk, in cells."
                DEFVAL { 1 }
                ::= { vbrAtmSpvcVccEntry 11 }

vbrAtmSpvcVccFlow OBJECT-TYPE
                SYNTAX INTEGER  {
                                duplex(1),
                                simplexA2B(2),
                                simplexB2A(3) 
                                }
                MAX-ACCESS read-write
                STATUS current
                DESCRIPTION "type of flow"
                DEFVAL { duplex }
                ::= { vbrAtmSpvcVccEntry 12 }

vbrAtmSpvcVccConnType OBJECT-TYPE
                SYNTAX INTEGER{
                                activeSvc(1),
                                passiveSvc(2)
                                } 
                MAX-ACCESS read-write
                STATUS current
                DESCRIPTION "The type of connection: activeSvc - attempt calls,
                                whenever not established;
                             passiveSvc - accepts calls"
                ::= { vbrAtmSpvcVccEntry 13 }

vbrAtmSpvcVccVbrPortAddr OBJECT-TYPE
                SYNTAX OCTET STRING (SIZE(1..20))
                MAX-ACCESS read-write
                STATUS current
                DESCRIPTION "local Vbr port nsap address"
                ::= { vbrAtmSpvcVccEntry 14 }

vbrAtmSpvcVccOperStatus OBJECT-TYPE
                SYNTAX INTEGER {
                                other(1),
                                establishmentInProgress(2),
                                connected(3),
                                retriesExhausted(4),
                                noAddressSupplied(5),
                                lowerLayerDown(6)
                                } 
                MAX-ACCESS read-only
                STATUS current
                DESCRIPTION "other - none of the types specified below;
                             establishmentInProgress - connection is not 
                                operational, but call attempts are ongoing;
                             connected - connection is currently operational;
                             retriesExhausted - retry limit has been reached 
                                and call attempts have ceased;
                             noAddressSupplied - no remote address has been 
                                configured, so no call attempts are initiated;
                             lowerLayerDown - SPVC handler is not operational."
                ::= { vbrAtmSpvcVccEntry 15 }

vbrAtmSpvcVccRowStatus OBJECT-TYPE
                SYNTAX RowStatus
                MAX-ACCESS read-write
                STATUS current
                DESCRIPTION "Used to create and delete a soft PVCC.  When this 
                             object is set to 'active' an attempt is made to 
                             set up the soft PVCC.  When this object has the 
                             value 'active' and is set to another value, any 
                             set-up or connection in-progess is released."
                ::= { vbrAtmSpvcVccEntry 16 }

vbrAtmSpvcVccViB OBJECT-TYPE
                SYNTAX INTEGER (0..1024)
                MAX-ACCESS read-write
                STATUS current
                DESCRIPTION "VI to associate the Egress part of the
                        B2A connection ."
                DEFVAL { 0 }
                ::= { vbrAtmSpvcVccEntry 17 }

vbrAtmSpvcVccTrafficShapingA2B     OBJECT-TYPE
                SYNTAX INTEGER {
                                disabled(1),
                                enabled(2)
                               }
                MAX-ACCESS read-write
                STATUS current
                DESCRIPTION "Traffic Shaping Support in the A2B direction."
                DEFVAL { disabled }
                ::= { vbrAtmSpvcVccEntry 18 }


vbrAtmSpvcVccActiveSvcTable OBJECT-TYPE
                SYNTAX SEQUENCE OF VbrAtmSpvcVccActiveSvcEntry
                MAX-ACCESS not-accessible
                STATUS current
                DESCRIPTION "The table used to manage active SVCs established 
                             across ATM networks between ATM entities."
                ::= { connectionConfig 22 }

vbrAtmSpvcVccActiveSvcEntry OBJECT-TYPE
                SYNTAX VbrAtmSpvcVccActiveSvcEntry
                MAX-ACCESS  not-accessible
                STATUS current
                DESCRIPTION "An entry in the Terminal Emulation ATM active SVC
                             table. There is one entry in the table 
                             corresponding to each active row in the 
                             vbrAtmSpvcVccTable for which the 
                             vbrAtmSpvcVccConnType
                             takes the value 'activeSvc'."
                INDEX { vbrAtmSpvcVccIfA }
                ::= { vbrAtmSpvcVccActiveSvcTable 1 }

VbrAtmSpvcVccActiveSvcEntry ::= SEQUENCE {
                        vbrAtmSpvcVccRemoteVbrPortAddr        OCTET STRING,
                        vbrAtmSpvcVccRetryInterval        INTEGER,
                        vbrAtmSpvcVccRetryLimit                INTEGER,
                        vbrAtmSpvcVccRestart                INTEGER,
                        vbrAtmSpvcVccRetryFailure        Integer32,
                        vbrAtmSpvcVccReleaseCause        INTEGER,
                        vbrAtmSpvcVccReleaseDiag        OCTET STRING
                }

vbrAtmSpvcVccRemoteVbrPortAddr OBJECT-TYPE
                SYNTAX OCTET STRING (SIZE(1..20))
                MAX-ACCESS read-write
                STATUS current
                DESCRIPTION "remote VBR port nsap address implemening IWF, not 
                             meaningful if passive type of connection"
                ::= { vbrAtmSpvcVccActiveSvcEntry 1 }

vbrAtmSpvcVccRetryInterval OBJECT-TYPE
                SYNTAX INTEGER (0..3600)
                UNITS "seconds"
                MAX-ACCESS read-write
                STATUS current
                DESCRIPTION "the time to wait before attempting to establish 
                             the SVC after previous failed call attempt. 
                             0 indicates retry will be attempted immediately."
                DEFVAL { 10 }
                ::= { vbrAtmSpvcVccActiveSvcEntry 2 }

vbrAtmSpvcVccRetryLimit        OBJECT-TYPE
                SYNTAX INTEGER (0..65535)
                MAX-ACCESS read-write
                STATUS current
                DESCRIPTION "a maximum limit on how many retries. 
                             0 indicates no limit."
                DEFVAL { 0 }
                ::= { vbrAtmSpvcVccActiveSvcEntry 3 }

vbrAtmSpvcVccRestart OBJECT-TYPE
                SYNTAX INTEGER {
                                restart(1),
                                noop(2)
                                }
                MAX-ACCESS read-write
                STATUS current
                DESCRIPTION "restart, the active SVC is released if necessary 
                             and a new setup procedure is begun; or noop"
                ::= { vbrAtmSpvcVccActiveSvcEntry 4 }

vbrAtmSpvcVccRetryFailure OBJECT-TYPE
                SYNTAX Integer32 
                MAX-ACCESS read-only
                STATUS current
                DESCRIPTION "indicates how many attempts to establish the 
                             connection have failed.  It is reset whenever a 
                             connection is successfully established or the SVC 
                             is restarted."
                ::= { vbrAtmSpvcVccActiveSvcEntry 5 }

vbrAtmSpvcVccReleaseCause OBJECT-TYPE
                SYNTAX INTEGER(1..127) 
                MAX-ACCESS read-only
                STATUS current
                DESCRIPTION "CAUSE field value of the last RELEASE message 
                             received for this SVC"
                ::= { vbrAtmSpvcVccActiveSvcEntry 6 }

vbrAtmSpvcVccReleaseDiag OBJECT-TYPE
                SYNTAX OCTET STRING (SIZE(0..8)) 
                MAX-ACCESS read-only
                STATUS current
                DESCRIPTION "DIAGNOSTICS field value of the last RELEASE 
                             message received for this SVC"
                ::= { vbrAtmSpvcVccActiveSvcEntry 7 }


atmSpvcVccRlsTable OBJECT-TYPE
                SYNTAX SEQUENCE OF AtmSpvcVccRlsEntry
                MAX-ACCESS not-accessible
                STATUS current
                DESCRIPTION "This table is an extension of atmSpvcVccTable
                             and is used to release a ATM-ATM SPVC connection
                             without deleting the configured data."
                ::= { connectionConfig 23 }

atmSpvcVccRlsEntry OBJECT-TYPE
                SYNTAX AtmSpvcVccRlsEntry
                MAX-ACCESS  not-accessible
                STATUS current
                DESCRIPTION "Row definition of CES SPVC release table.  This 
                             entry is created whenever an entry is created in
                             atmSpvcVccTable."
                INDEX { atmSpvcVccIfA, atmSpvcVccVpiA, atmSpvcVccVciA }
                ::= { atmSpvcVccRlsTable 1 }

AtmSpvcVccRlsEntry ::= SEQUENCE {
                        atmSpvcVccRelease        INTEGER
                }

atmSpvcVccRelease OBJECT-TYPE
                SYNTAX INTEGER {
                                release(1),
                                noop(2)
                                }
                MAX-ACCESS read-write
                STATUS current
                DESCRIPTION "Release the connnection established on the endpoint
                             and if the endpoint is Active, do not retry."
                ::= { atmSpvcVccRlsEntry 1 }


cirEmAtmSpvcVccRlsTable OBJECT-TYPE
                SYNTAX SEQUENCE OF CirEmAtmSpvcVccRlsEntry
                MAX-ACCESS not-accessible
                STATUS current
                DESCRIPTION "This table is an extension of cirEmAtmSpvcVccTable
                             and is used to release a TE-ATM SPVC connection
                             without deleting the configured data."
                ::= { connectionConfig 24 }

cirEmAtmSpvcVccRlsEntry OBJECT-TYPE
                SYNTAX CirEmAtmSpvcVccRlsEntry
                MAX-ACCESS  not-accessible
                STATUS current
                DESCRIPTION "Row definition of CES SPVC release table.  This 
                             entry is created whenever an entry is created in
                             cirEmAtmSpvcVccTable."
                INDEX { cirEmAtmSpvcVccIfA }
                ::= { cirEmAtmSpvcVccRlsTable 1 }

CirEmAtmSpvcVccRlsEntry ::= SEQUENCE {
                        cirEmAtmSpvcVccRelease        INTEGER
                }

cirEmAtmSpvcVccRelease OBJECT-TYPE
                SYNTAX INTEGER {
                                release(1),
                                noop(2)
                                }
                MAX-ACCESS read-write
                STATUS current
                DESCRIPTION "Release the connnection established on the endpoint
                             and if the endpoint is Active, do not retry."
                ::= { cirEmAtmSpvcVccRlsEntry 1 }


vbrAtmSpvcVccRlsTable OBJECT-TYPE
                SYNTAX SEQUENCE OF VbrAtmSpvcVccRlsEntry
                MAX-ACCESS not-accessible
                STATUS current
                DESCRIPTION "This table is an extension of vbrAtmSpvcVccTable
                             and is used to release a TE-ATM SPVC connection
                             without deleting the configured data."
                ::= { connectionConfig 25 }

vbrAtmSpvcVccRlsEntry OBJECT-TYPE
                SYNTAX VbrAtmSpvcVccRlsEntry
                MAX-ACCESS  not-accessible
                STATUS current
                DESCRIPTION "Row definition of TE SPVC release table.  This 
                             entry is created whenever an entry is created in
                             vbrAtmSpvcVccTable."
                INDEX { vbrAtmSpvcVccIfA }
                ::= { vbrAtmSpvcVccRlsTable 1 }

VbrAtmSpvcVccRlsEntry ::= SEQUENCE {
                        vbrAtmSpvcVccRelease        INTEGER
                }

vbrAtmSpvcVccRelease OBJECT-TYPE
                SYNTAX INTEGER {
                                release(1),
                                noop(2)
                                }
                MAX-ACCESS read-write
                STATUS current
                DESCRIPTION "Release the connnection established on the endpoint
                             and if the endpoint is Active, do not retry."
                ::= { vbrAtmSpvcVccRlsEntry 1 }




frAtmBkPvcVccTable OBJECT-TYPE
                SYNTAX SEQUENCE OF FrAtmBkPvcVccEntry
                MAX-ACCESS not-accessible
                STATUS current
                DESCRIPTION "This table is used to manage frame relay DHPVC 
                             backup pvc."
                ::= { connectionConfig 26 }

frAtmBkPvcVccEntry OBJECT-TYPE
                SYNTAX FrAtmBkPvcVccEntry
                MAX-ACCESS not-accessible
                STATUS current
                DESCRIPTION "An entry in the frame relay DHPVC table.  There is 
                             one entry in the table corresponding to each active
                             row in the frAtmPvcVccTable for which the
                             frAtmPvcVccDualHomed object takes the value
                             'yes.'"
                INDEX { frAtmPvcVccIfA, frAtmPvcVccDlciA, frAtmPvcVccIfB,
                        frAtmPvcVccVpiB, frAtmPvcVccVciB }
                ::= { frAtmBkPvcVccTable 1 }

FrAtmBkPvcVccEntry ::= SEQUENCE {
                             frAtmBkPvcVccIfB                IntfIndex,
                             frAtmBkPvcVccVpiB          INTEGER,
                             frAtmBkPvcVccVciB          INTEGER,
                             frAtmBkPvcVccActivePvc        INTEGER,
                             frAtmBkPvcVccAutoSwitch        INTEGER,
                             frAtmBkPvcVccRowStatus        RowStatus,
                             frAtmBkPvcVccViB           INTEGER,

                             frAtmBkPvcVccVUNIB         INTEGER,

                             frAtmBkPvcVccConnFailureCauseB  AtmConnFailureCause
                             }

frAtmBkPvcVccIfB OBJECT-TYPE
                SYNTAX IntfIndex
                MAX-ACCESS read-write
                STATUS current
                DESCRIPTION "Interface index for side B, the atm side, of a 
                             backup frame relay-atm DHPVC VCC connection.
                             Number value is interpreted as an interface of the
                             form, SSPPCCC, where SS is the card slot, PP is 
                             the port number, and CCC is the channel number."
                ::= { frAtmBkPvcVccEntry 1 }

frAtmBkPvcVccVpiB OBJECT-TYPE
                SYNTAX INTEGER (0..4095)
                MAX-ACCESS read-write
                STATUS current
                DESCRIPTION "VPI value for side B, the atm side, of a backup
                             frame relay-atm DHPVC VCC connection.  Valid 
                             range is a number between 0 and 4095."
                ::= { frAtmBkPvcVccEntry 2 }

frAtmBkPvcVccVciB OBJECT-TYPE
                SYNTAX INTEGER (0..65535)
                MAX-ACCESS read-write
                STATUS current
                DESCRIPTION "VCI value for side B, the atm side, of a backup
                             frame relay-atm DHPVC VCC connection.  Valid 
                             range is a number between 0 and 65535."
                ::= { frAtmBkPvcVccEntry 3 }

frAtmBkPvcVccActivePvc OBJECT-TYPE
                SYNTAX INTEGER {
                                primary(1),
                                backup(2),
                                none(3)
                               }
                MAX-ACCESS read-only
                STATUS current
                DESCRIPTION "Current active PVC."
                DEFVAL { none }
                ::= { frAtmBkPvcVccEntry 4 }

frAtmBkPvcVccAutoSwitch OBJECT-TYPE
                SYNTAX INTEGER  {
                                yes(1),
                                no(2)
                                }
                MAX-ACCESS read-write
                STATUS current
                DESCRIPTION "Auto switch back to primary link when primary link
                             is recovered."
                DEFVAL { yes }
                ::= { frAtmBkPvcVccEntry 5 }

frAtmBkPvcVccRowStatus OBJECT-TYPE
                SYNTAX RowStatus
                MAX-ACCESS read-write
                STATUS current
                DESCRIPTION "row status"
                ::= { frAtmBkPvcVccEntry 6 }

frAtmBkPvcVccViB OBJECT-TYPE
                SYNTAX INTEGER (0..1024)
                MAX-ACCESS read-write 
                STATUS current
                DESCRIPTION "VI to associate the Egress part of the
                        A2B connection ."
                DEFVAL { 0 } 
                ::= { frAtmBkPvcVccEntry 7 }


frAtmBkPvcVccVUNIB OBJECT-TYPE
                SYNTAX INTEGER (0..255)
                MAX-ACCESS read-write 
                STATUS current
                DESCRIPTION "VUNI to associate the Egress part of the
                        A2B connection ."
                DEFVAL { 0 } 
                ::= { frAtmBkPvcVccEntry 8 }


frAtmBkPvcVccConnFailureCauseB    OBJECT-TYPE
                SYNTAX AtmConnFailureCause
                MAX-ACCESS read-only
                STATUS current
                DESCRIPTION "connection status reason code"
                ::= { frAtmBkPvcVccEntry 9 }

atmBkPvcVccTable OBJECT-TYPE
                    SYNTAX SEQUENCE OF AtmBkPvcVccEntry
                    MAX-ACCESS not-accessible
                    STATUS current
                    DESCRIPTION "This table is used to manage ATM to ATM
                             DHPVC backup pvc."
                    ::= { connectionConfig 27 }

atmBkPvcVccEntry OBJECT-TYPE
                SYNTAX AtmBkPvcVccEntry
                MAX-ACCESS not-accessible
                STATUS current
                DESCRIPTION "An entry in the ATM to ATM DHPVC table.
                             There is one entry in the table corresponding to
                             each active row in the atmPvcVccTable for which
                             the atmPvcVccDualHomed object takes the value
                             'yes'."
                INDEX { atmPvcVccIfA, atmPvcVccVpiA, atmPvcVccVciA,
                        atmPvcVccIfB, atmPvcVccVpiB, atmPvcVccVciB }
                ::= { atmBkPvcVccTable 1 }

AtmBkPvcVccEntry ::= SEQUENCE {
                           atmBkPvcVccIfB                IntfIndex,
                           atmBkPvcVccVpiB                INTEGER,
                           atmBkPvcVccVciB                INTEGER,
                           atmBkPvcVccActivePvc                INTEGER,
                           atmBkPvcVccAutoSwitch        INTEGER,
                           atmBkPvcVccRowStatus                RowStatus,
                           atmBkPvcVccViB               INTEGER,

                           atmBkPvcVccVUNIB             INTEGER,

                           atmBkPvcVccConnFailureCauseB    AtmConnFailureCause
                          }

atmBkPvcVccIfB OBJECT-TYPE
                SYNTAX IntfIndex
                MAX-ACCESS read-write
                STATUS current
                DESCRIPTION "Interface index for side B, the atm side, of a 
                             backup ATM-to-ATM DHPVC VCC connection.
                             Number value is interpreted as an interface of the
                             form, SSPPCCC, where SS is the card slot, PP is 
                             the port number, and CCC is the channel number."
                ::= { atmBkPvcVccEntry 1 }

atmBkPvcVccVpiB OBJECT-TYPE
                SYNTAX INTEGER (0..4095)
                MAX-ACCESS read-write
                STATUS current
                DESCRIPTION "VPI value for side B, the atm side, of a backup
                             ATM-to-ATM DHPVC VCC connection.  
                             Valid range is a number between 0 and 4095."
                ::= { atmBkPvcVccEntry 2 }

atmBkPvcVccVciB OBJECT-TYPE
                SYNTAX INTEGER (0..65535)
                MAX-ACCESS read-write
                STATUS current
                DESCRIPTION "VCI value for side B, the atm side, of a backup
                             ATM-to-ATM DHPVC VCC connection.  
                             Valid range is a number between 0 and 65535."
                ::= { atmBkPvcVccEntry 3 }

atmBkPvcVccActivePvc OBJECT-TYPE
                SYNTAX INTEGER {
                                primary(1),
                                backup(2),
                                none(3)
                               }
                MAX-ACCESS read-only
                STATUS current
                DESCRIPTION "Current active PVC."
                DEFVAL { none }
                ::= { atmBkPvcVccEntry 4 }

atmBkPvcVccAutoSwitch OBJECT-TYPE
                SYNTAX INTEGER  {
                                yes(1),
                                no(2)
                                }
                MAX-ACCESS read-write
                STATUS current
                DESCRIPTION "Auto switch back to primary link when primary link
                             is recovered."
                DEFVAL { yes }
                ::= { atmBkPvcVccEntry 5 }

atmBkPvcVccRowStatus OBJECT-TYPE
                SYNTAX RowStatus
                MAX-ACCESS read-write
                STATUS current
                DESCRIPTION "row status"
                ::= { atmBkPvcVccEntry 6 }

atmBkPvcVccViB OBJECT-TYPE
                SYNTAX INTEGER (0..1024)
                MAX-ACCESS read-write
                STATUS current
                DESCRIPTION "VI to associate the Egress part of the
                        A2B connection ."
                DEFVAL { 0 }
                ::= { atmBkPvcVccEntry 7 }


atmBkPvcVccVUNIB OBJECT-TYPE
                SYNTAX INTEGER (0..255)
                MAX-ACCESS read-write
                STATUS current
                DESCRIPTION "VUNI to associate the Egress part of the
                        A2B connection ."
                DEFVAL { 0 }
                ::= { atmBkPvcVccEntry 8 }


atmBkPvcVccConnFailureCauseB    OBJECT-TYPE
                SYNTAX AtmConnFailureCause
                MAX-ACCESS read-only
                STATUS current
                DESCRIPTION "connection status reason code"
                ::= { atmBkPvcVccEntry 9 }

atmBkPvcVpcTable OBJECT-TYPE
                SYNTAX SEQUENCE OF AtmBkPvcVpcEntry
                MAX-ACCESS not-accessible
                STATUS current
                DESCRIPTION "This table is used to manage ATM to ATM DHPVC 
                             backup pvc."
                ::= { connectionConfig 28 }

atmBkPvcVpcEntry OBJECT-TYPE
                SYNTAX AtmBkPvcVpcEntry
                MAX-ACCESS not-accessible
                STATUS current
                DESCRIPTION "An entry in the ATM to ATM DHPVC table.  There is 
                             one entry in the table corresponding to each 
                             active row in the atmPvcVpcTable for which the 
                             atmPvcVpcDualHomed object takes the value 'yes'."
                INDEX { atmPvcVpcIfA, atmPvcVpcVpiA, 
                        atmPvcVpcIfB, atmPvcVpcVpiB }
                ::= { atmBkPvcVpcTable 1 }

AtmBkPvcVpcEntry ::= SEQUENCE {
                atmBkPvcVpcIfB                        IntfIndex,
                atmBkPvcVpcVpiB                        INTEGER,
                atmBkPvcVpcActivePvc                INTEGER,
                atmBkPvcVpcAutoSwitch                INTEGER,
                atmBkPvcVpcRowStatus                RowStatus,
                atmBkPvcVpcViB                  INTEGER,

                atmBkPvcVpcVUNIB                INTEGER,

                atmBkPvcVpcConnFailureCauseB    AtmConnFailureCause
                }

atmBkPvcVpcIfB        OBJECT-TYPE
                SYNTAX IntfIndex
                MAX-ACCESS read-write
                STATUS current
                DESCRIPTION "Interface index for side B of an ATM-to-ATM PVC VPC
                             backup DHPVC connection.  Number value is 
                             interpreted as an interface of the form, SSPPCCC, 
                             where SS is the card slot, PP is the port number, 
                             and CCC is the channel number."
                ::= { atmBkPvcVpcEntry 1 }

atmBkPvcVpcVpiB        OBJECT-TYPE
                SYNTAX INTEGER (0..4095)
                MAX-ACCESS read-write
                STATUS current
                DESCRIPTION "VPI value for side B of an ATM-to-ATM PVC VPC backup
                             DHPVC connection.  Valid range is a number between
                             0 and 4095."
                ::= { atmBkPvcVpcEntry 2 }

atmBkPvcVpcActivePvc OBJECT-TYPE
                SYNTAX INTEGER {
                                primary(1),
                                backup(2),
                                none(3)
                               }
                MAX-ACCESS read-only
                STATUS current
                DESCRIPTION "Current active PVC."
                DEFVAL { none }
                ::= { atmBkPvcVpcEntry 3 }

atmBkPvcVpcAutoSwitch OBJECT-TYPE
                SYNTAX INTEGER  {
                                yes(1),
                                no(2)
                                }
                MAX-ACCESS read-write
                STATUS current
                DESCRIPTION "Auto switch back to primary link when primary link
                             is recovered."
                DEFVAL { yes }
                ::= { atmBkPvcVpcEntry 4 }

atmBkPvcVpcRowStatus OBJECT-TYPE
                SYNTAX RowStatus
                MAX-ACCESS read-write
                STATUS current
                DESCRIPTION "row status"
                ::= { atmBkPvcVpcEntry 5 }

atmBkPvcVpcViB OBJECT-TYPE
                SYNTAX INTEGER (0..1024)
                MAX-ACCESS read-write
                STATUS current
                DESCRIPTION "VI to associate the Egress part of the
                        A2B connection ."
                DEFVAL { 0 } 
                ::= { atmBkPvcVpcEntry 6 }


atmBkPvcVpcVUNIB OBJECT-TYPE
                SYNTAX INTEGER (0..255)
                MAX-ACCESS read-write
                STATUS current
                DESCRIPTION "VUNI to associate the Egress part of the
                        A2B connection ."
                DEFVAL { 0 } 
                ::= { atmBkPvcVpcEntry 7 }


atmBkPvcVpcConnFailureCauseB    OBJECT-TYPE
                SYNTAX AtmConnFailureCause
                MAX-ACCESS read-only
                STATUS current
                DESCRIPTION "connection status reason code"
                ::= { atmBkPvcVpcEntry 8 }

bridgeAtmBkPvcVccTable OBJECT-TYPE
                    SYNTAX SEQUENCE OF BridgeAtmBkPvcVccEntry
                    MAX-ACCESS not-accessible
                    STATUS current
                    DESCRIPTION "This table is used to manage bridge to atm DHPVC
                             backup pvc."
                    ::= { connectionConfig 29 }

bridgeAtmBkPvcVccEntry OBJECT-TYPE
                SYNTAX BridgeAtmBkPvcVccEntry
                MAX-ACCESS not-accessible
                STATUS current
                DESCRIPTION "An entry in the bridge to atm DHPVC table.  There
                             is one entry in the table corresponding to each
                             active row in the bridgeAtmPvcVccTable for which
                             the bridgeAtmPvcVccDualHomed object takes the
                             value 'yes'."
                INDEX { bridgeAtmPvcVccIfA, bridgeAtmPvcVccIfB,
                        bridgeAtmPvcVccVpiB, bridgeAtmPvcVccVciB }
                ::= { bridgeAtmBkPvcVccTable 1 }

BridgeAtmBkPvcVccEntry ::= SEQUENCE {
                        bridgeAtmBkPvcVccIfB                IntfIndex,
                        bridgeAtmBkPvcVccVpiB                INTEGER,
                        bridgeAtmBkPvcVccVciB                INTEGER,
                        bridgeAtmBkPvcVccActivePvc        INTEGER,
                        bridgeAtmBkPvcVccAutoSwitch        INTEGER,
                        bridgeAtmBkPvcVccRowStatus        RowStatus,
                        bridgeAtmBkPvcVccViB            INTEGER,

                        bridgeAtmBkPvcVccVUNIB          INTEGER,

                        bridgeAtmBkPvcVccConnFailureCauseB  AtmConnFailureCause
                        }

bridgeAtmBkPvcVccIfB OBJECT-TYPE
                SYNTAX IntfIndex
                MAX-ACCESS read-write
                STATUS current
                DESCRIPTION "Interface index for side B, the atm side, of a 
                             backup bridge-atm DHPVC VCC connection.  Number 
                             value is interpreted as an interface of the form, 
                             SSPPCCC, where SS is the card slot, PP is the port
                             number, and CCC is the channel number."
                ::= { bridgeAtmBkPvcVccEntry 1 }

bridgeAtmBkPvcVccVpiB OBJECT-TYPE
                SYNTAX INTEGER (0..4095)
                MAX-ACCESS read-write
                STATUS current
                DESCRIPTION "VPI value for side B, the atm side, of a backup
                             bridge-atm DHPVC VCC connection.  Valid range is a 
                             number between 0 and 4095."
                ::= { bridgeAtmBkPvcVccEntry 2 }

bridgeAtmBkPvcVccVciB OBJECT-TYPE
                SYNTAX INTEGER (0..65535)
                MAX-ACCESS read-write
                STATUS current
                DESCRIPTION "VCI value for side B, the atm side, of a backup
                             bridge-atm DHPVC VCC connection.  Valid range is a 
                             number between 0 and 65535."
                ::= { bridgeAtmBkPvcVccEntry 3 }

bridgeAtmBkPvcVccActivePvc OBJECT-TYPE
                SYNTAX INTEGER {
                                primary(1),
                                backup(2),
                                none(3)
                               }
                MAX-ACCESS read-only
                STATUS current
                DESCRIPTION "Current active PVC."
                DEFVAL { none }
                ::= { bridgeAtmBkPvcVccEntry 4 }

bridgeAtmBkPvcVccAutoSwitch OBJECT-TYPE
                SYNTAX INTEGER  {
                                yes(1),
                                no(2)
                                }
                MAX-ACCESS read-write
                STATUS current
                DESCRIPTION "Auto switch back to primary link when primary link
                             is recovered."
                DEFVAL { yes }
                ::= { bridgeAtmBkPvcVccEntry 5 }

bridgeAtmBkPvcVccRowStatus OBJECT-TYPE
                SYNTAX RowStatus
                MAX-ACCESS read-write
                STATUS current
                DESCRIPTION "row status"
                ::= { bridgeAtmBkPvcVccEntry 6 }

bridgeAtmBkPvcVccViB OBJECT-TYPE
                SYNTAX INTEGER (0..1024)
                MAX-ACCESS read-write
                STATUS current
                DESCRIPTION "VI to associate the Egress part of the
                                A2B connection ."
                DEFVAL { 0 }
                ::= { bridgeAtmBkPvcVccEntry 7 }


bridgeAtmBkPvcVccVUNIB OBJECT-TYPE
                SYNTAX INTEGER (0..255)
                MAX-ACCESS read-write
                STATUS current
                DESCRIPTION "VUNI to associate the Egress part of the
                                A2B connection ."
                DEFVAL { 0 }
                ::= { bridgeAtmBkPvcVccEntry 8 }


bridgeAtmBkPvcVccConnFailureCauseB    OBJECT-TYPE
                SYNTAX AtmConnFailureCause
                MAX-ACCESS read-only
                STATUS current
                DESCRIPTION "connection status reason code"
                ::= { bridgeAtmBkPvcVccEntry 9 }

ipAtmBkAppPvcVccTable OBJECT-TYPE
                SYNTAX SEQUENCE OF IpAtmBkAppPvcVccEntry
                MAX-ACCESS not-accessible
                STATUS current
                DESCRIPTION "This table is used to manage in-band management to
                             atm DHPVC backup pvc."
                ::= { connectionConfig 30 }

ipAtmBkAppPvcVccEntry OBJECT-TYPE
                SYNTAX IpAtmBkAppPvcVccEntry
                MAX-ACCESS not-accessible
                STATUS current
                DESCRIPTION "An entry in the in-band management to atm DHPVC 
                             table.  There is one entry in the table 
                             corresponding to each active row in the 
                             ipAtmAppPvcVccTable for which the 
                             ipAtmAppPvcVccDualHomed object takes the value 
                             'yes'."
                INDEX { ipAtmAppPvcVccDestAddrA, ipAtmAppPvcVccSubnetMaskA,
                        ipAtmAppPvcVccIfB, ipAtmAppPvcVccVpiB, 
                        ipAtmAppPvcVccVciB }
                ::= { ipAtmBkAppPvcVccTable 1 }

IpAtmBkAppPvcVccEntry ::= SEQUENCE {
                ipAtmBkAppPvcVccIfB                IntfIndex,
                ipAtmBkAppPvcVccVpiB                INTEGER,
                ipAtmBkAppPvcVccVciB                INTEGER,
                ipAtmBkAppPvcVccActivePvc        INTEGER,
                ipAtmBkAppPvcVccAutoSwitch        INTEGER,
                ipAtmBkAppPvcVccRowStatus        RowStatus,
                ipAtmBkAppPvcVccViB             INTEGER,

                ipAtmBkAppPvcVccVUNIB           INTEGER,

                ipAtmBkAppPvcVccConnFailureCauseB  AtmConnFailureCause
                }

ipAtmBkAppPvcVccIfB OBJECT-TYPE
                SYNTAX IntfIndex
                MAX-ACCESS read-write
                STATUS current
                DESCRIPTION "Interface index for side B, the atm side, of a 
                             backup in-band management-atm DHPVC VCC connection.
                             Number value is interpreted as an interface of the
                             form, SSPPCCC, where SS is the card slot, PP is 
                             the port number, and CCC is the channel number."
                ::= { ipAtmBkAppPvcVccEntry 1 }

ipAtmBkAppPvcVccVpiB OBJECT-TYPE
                SYNTAX INTEGER (0..4095)
                MAX-ACCESS read-write
                STATUS current
                DESCRIPTION "VPI value for side B, the atm side, of a backup 
                             in-band management-atm DHPVC VCC connection.  Valid
                             range is a number between 0 and 4095."
                ::= { ipAtmBkAppPvcVccEntry 2 }

ipAtmBkAppPvcVccVciB OBJECT-TYPE
                SYNTAX INTEGER (0..65535)
                MAX-ACCESS read-write
                STATUS current
                DESCRIPTION "VCI value for side B, the atm side, of a backup
                             in-band management-atm DHPVC VCC connection.  Valid
                             range is a number between 0 and 65535."
                ::= { ipAtmBkAppPvcVccEntry 3 }

ipAtmBkAppPvcVccActivePvc OBJECT-TYPE
                SYNTAX INTEGER {
                                primary(1),
                                backup(2),
                                none(3)
                               }
                MAX-ACCESS read-only
                STATUS current
                DESCRIPTION "Current active PVC."
                DEFVAL { none }
                ::= { ipAtmBkAppPvcVccEntry 4 }

ipAtmBkAppPvcVccAutoSwitch OBJECT-TYPE
                SYNTAX INTEGER  {
                                yes(1),
                                no(2)
                                }
                MAX-ACCESS read-write
                STATUS current
                DESCRIPTION "Auto switch back to primary link when primary link
                             is recovered."
                DEFVAL { yes }
                ::= { ipAtmBkAppPvcVccEntry 5 }

ipAtmBkAppPvcVccRowStatus OBJECT-TYPE
                SYNTAX RowStatus
                MAX-ACCESS read-write
                STATUS current
                DESCRIPTION "row status"
                ::= { ipAtmBkAppPvcVccEntry 6 }


ipAtmBkAppPvcVccViB OBJECT-TYPE
                SYNTAX INTEGER (0..1024)
                MAX-ACCESS read-write
                STATUS current
                DESCRIPTION "VI to associate the Egress part of the
                                A2B connection ."
                DEFVAL { 0 }
                ::= { ipAtmBkAppPvcVccEntry 7 }


ipAtmBkAppPvcVccVUNIB OBJECT-TYPE
                SYNTAX INTEGER (0..255)
                MAX-ACCESS read-write
                STATUS current
                DESCRIPTION "VUNI to associate the Egress part of the
                                A2B connection ."
                DEFVAL { 0 }
                ::= { ipAtmBkAppPvcVccEntry 8 }


ipAtmBkAppPvcVccConnFailureCauseB    OBJECT-TYPE
                SYNTAX AtmConnFailureCause
                MAX-ACCESS read-only
                STATUS current
                DESCRIPTION "connection status reason code"
                 ::= { ipAtmBkAppPvcVccEntry 9 }



 

spvcAddrTable OBJECT-TYPE
                SYNTAX SEQUENCE OF SpvcAddrEntry
                MAX-ACCESS not-accessible
                STATUS current
                DESCRIPTION "Table of SPVC network interface addresses."
                ::= { connectionConfig 31 }

spvcAddrEntry OBJECT-TYPE
                SYNTAX SpvcAddrEntry
                MAX-ACCESS  not-accessible
                STATUS current
                DESCRIPTION "Row definition of SPVC address table."
                INDEX { spvcAddrIfA }
                ::= { spvcAddrTable 1 }

SpvcAddrEntry ::= SEQUENCE {
                        spvcAddrIfA                            IntfIndex,
                        spvcAddrLocalPortAddr   OCTET STRING,
                        spvcAddrRowStatus                RowStatus
                }

spvcAddrIfA        OBJECT-TYPE
                SYNTAX IntfIndex
                MAX-ACCESS not-accessible
                STATUS current
                DESCRIPTION "Interface index for side A of an SPVC 
                             connection.  Number value is interpreted as an 
                             interface of the form, SSPPCCC, where SS is the 
                             card slot, PP is the port number, and CCC is the 
                             channel number."
                ::= { spvcAddrEntry 1 }

spvcAddrLocalPortAddr OBJECT-TYPE
                SYNTAX OCTET STRING (SIZE(1..20))
                MAX-ACCESS read-write
                STATUS current
                DESCRIPTION "Local port NSAP address."
                ::= { spvcAddrEntry 2 }

spvcAddrRowStatus OBJECT-TYPE
                SYNTAX RowStatus
                MAX-ACCESS read-write
                STATUS current
                DESCRIPTION "This is used to configure a NSAP address on the
                             local port.  Only when the address is configured
                             can SPVC connections be established."
                ::= { spvcAddrEntry 3 }





 


frAtmSpvcVccTable OBJECT-TYPE
        SYNTAX SEQUENCE OF FrAtmSpvcVccEntry
        MAX-ACCESS not-accessible
        STATUS current
        DESCRIPTION "Table of frame relay to ATM IWF connections"
        ::= { connectionConfig 32 }

frAtmSpvcVccEntry OBJECT-TYPE
        SYNTAX FrAtmSpvcVccEntry
        MAX-ACCESS not-accessible
        STATUS current
        DESCRIPTION "Row definition of frame relay to ATM IWF 
              connections "
        INDEX { spvcAddrIfA, frAtmSpvcVccDlciA}
        ::= { frAtmSpvcVccTable 1 }

FrAtmSpvcVccEntry ::= SEQUENCE 
        {
        frAtmSpvcVccDlciA                           Integer32,
        frAtmSpvcVccIfB                             IntfIndex,
        frAtmSpvcVccVpiB                            INTEGER,
        frAtmSpvcVccVciB                            INTEGER,
        frAtmSpvcVccMaxFrameSizeIn                  Integer32,
        frAtmSpvcVccBcIn                            Integer32,
        frAtmSpvcVccBeIn                            Integer32,
        frAtmSpvcVccCirIn                           Integer32,
        frAtmSpvcVccMaxFrameSizeOut                 Integer32,
        frAtmSpvcVccBcOut                           Integer32,
        frAtmSpvcVccBeOut                           Integer32,
        frAtmSpvcVccCirOut                          Integer32,
        frAtmSpvcVccServiceType                     INTEGER,
        frAtmSpvcVccFlow                            INTEGER,
        frAtmSpvcVccTimeLenIn                       INTEGER,
        frAtmSpvcVccTimeLenOut                      INTEGER,
        frAtmSpvcVccPeakCellRateA2B                 Integer32,
        frAtmSpvcVccSusCellRateA2B                  Integer32,
        frAtmSpvcVccMaxBurstSizeA2B                 Integer32,
        frAtmSpvcVccPeakCellRateB2A                 Integer32,
        frAtmSpvcVccSusCellRateB2A                  Integer32,
        frAtmSpvcVccMaxBurstSizeB2A                 Integer32,
        frAtmSpvcVccInterWorkingFunc                INTEGER,
        frAtmSpvcVccConnType                        INTEGER,
        frAtmSpvcVccOperStatus                      INTEGER,
        frAtmSpvcVccRowStatus                       RowStatus,
        frAtmSpvcVccRemoteFrPortAddr                OCTET STRING,
        frAtmSpvcVccRemoteSelectType                INTEGER,
        frAtmSpvcVccRemoteDlci                      INTEGER,
        frAtmSpvcVccRemoteVpi                       INTEGER,
        frAtmSpvcVccRemoteVci                       INTEGER,
        frAtmSpvcVccRetryInterval                   INTEGER,
        frAtmSpvcVccRetryLimit                      INTEGER,
        frAtmSpvcVccRestart                         INTEGER,
        frAtmSpvcVccRetryFailure                    Integer32,
        frAtmSpvcVccReleaseCause                    INTEGER,    
        frAtmSpvcVccReleaseDiag                     OCTET STRING,
        frAtmSpvcVccRelease                         INTEGER,
        frAtmSpvcVccStatsCellsEncodedHiA            Integer32,
        frAtmSpvcVccStatsCellsEncodedLoA            Integer32,
        frAtmSpvcVccStatsCellsDecodedHiA            Integer32,
        frAtmSpvcVccStatsCellsDecodedLoA            Integer32,
        frAtmSpvcVccStatsInCellCountHiB             Integer32,
        frAtmSpvcVccStatsInCellCountLoB             Integer32,
        frAtmSpvcVccStatsOutCellCountHiB            Integer32,
        frAtmSpvcVccStatsOutCellCountLoB            Integer32,
        frAtmSpvcVccStatsTimer                      Integer32,
        frAtmSpvcVccStatsFramesDroppedA             Integer32,
        frAtmSpvcVccStatsOdometerCellsEncodedHiA    Integer32,
        frAtmSpvcVccStatsOdometerCellsEncodedLoA    Integer32,
        frAtmSpvcVccStatsOdometerCellsDecodedHiA    Integer32,
        frAtmSpvcVccStatsOdometerCellsDecodedLoA    Integer32,
        frAtmSpvcVccStatsInOdometerCellCountHiB     Integer32,
        frAtmSpvcVccStatsInOdometerCellCountLoB     Integer32,
        frAtmSpvcVccStatsOutOdometerCellCountHiB    Integer32,
        frAtmSpvcVccStatsOutOdometerCellCountLoB    Integer32,
        frAtmSpvcVccStatsOdometerTimer              Integer32,
        frAtmSpvcVccStatsOdometerReset              INTEGER,
        frAtmSpvcVccStatsAal5ErrFramesA             Integer32,
        frAtmSpvcVccStatsFramesTaggedA              Integer32,
        frAtmSpvcVccStatsCellsDroppedB              Integer32,
        frAtmSpvcVccStatsCellsTaggedB               Integer32

        ,frAtmSpvcVccVUNIB                          INTEGER


        ,frAtmSpvcVccTrafficShapingA2B              INTEGER
        ,frAtmSpvcVccPriority                       INTEGER
        }

frAtmSpvcVccDlciA OBJECT-TYPE
        SYNTAX INTEGER (0..1023)
        MAX-ACCESS not-accessible
        STATUS current
        DESCRIPTION "DLCI value for side A, the frame relay side, 
                 of a frame relay-atm SPVC VCC connection.  Valid
                 range is a number between 0 and 1023."
        ::= { frAtmSpvcVccEntry 1 }

frAtmSpvcVccIfB OBJECT-TYPE
        SYNTAX IntfIndex
        MAX-ACCESS read-only
        STATUS current
        DESCRIPTION "Interface index for side B, the atm side, of a 
                 frame relay-atm SPVC VCC connection.  Number value 
                 is interpreted as an interface of the form, 
                 SSPPCCC, where SS is the card slot, PP is the port 
                 number, and CCC is the channel number."
        ::= { frAtmSpvcVccEntry 2 }

frAtmSpvcVccVpiB OBJECT-TYPE
        SYNTAX INTEGER (0..4095)
        MAX-ACCESS read-only
        STATUS current
        DESCRIPTION "VPI value for side B, the atm side, of a frame
                 relay-atm SPVC VCC connection.  Valid range is a 
                 number between 0 and 4095."
        ::= { frAtmSpvcVccEntry 3 }

frAtmSpvcVccVciB OBJECT-TYPE
        SYNTAX INTEGER (0..65535)
        MAX-ACCESS read-only
        STATUS current
        DESCRIPTION "VCI value for side B, the atm side, of a frame
                 relay-atm SPVC VCC connection.  Valid range is a 
                 number between 0 and 65535."
        ::= { frAtmSpvcVccEntry 4 }

frAtmSpvcVccMaxFrameSizeIn OBJECT-TYPE
        SYNTAX Integer32
        MAX-ACCESS read-write
        STATUS current
        DESCRIPTION "The value of this object is the size in octets of
                 the largest frame relay information field for this
                 SPVC in the ingress direction (out of the frame 
                 relay UNI)."
        DEFVAL { 4096 }
        ::= { frAtmSpvcVccEntry 5 }

frAtmSpvcVccBcIn OBJECT-TYPE
        SYNTAX Integer32
        MAX-ACCESS read-write
        STATUS current
        DESCRIPTION "The value of this object is equal to the
                 committed burst size (Bc) parameter (measured in
                 bits) for this SPVC in the ingress
                 direction (into the frame relay UNI)."
        DEFVAL { 0 }
        ::= { frAtmSpvcVccEntry 6 }

frAtmSpvcVccBeIn OBJECT-TYPE
        SYNTAX Integer32
        MAX-ACCESS read-write
        STATUS current
        DESCRIPTION "The value of this object is equal to the excess
                 burst size (Be) parameter (measured in bits) for
                 this SPVC in the ingress direction (into
                 the frame relay UNI)."
        DEFVAL { 45000000 }
        ::= { frAtmSpvcVccEntry 7 }

frAtmSpvcVccCirIn OBJECT-TYPE
        SYNTAX Integer32
        MAX-ACCESS read-write
        STATUS current
        DESCRIPTION "The value of this object is equal to the
                 committed information rate (CIR) parameter
                 (measured in bits per second) for this SPVC
                 in the ingress direction (into the frame
                 relay UNI)."
        DEFVAL { 0 }
        ::= { frAtmSpvcVccEntry 8 }

frAtmSpvcVccMaxFrameSizeOut OBJECT-TYPE
        SYNTAX Integer32
        MAX-ACCESS read-write
        STATUS current
        DESCRIPTION "The value of this object is the size in octets of
                 the largest frame relay information field for this
                 SPVC in the egress direction (out of the frame 
                 relay UNI)."
        DEFVAL { 4096 }
        ::= { frAtmSpvcVccEntry 9 }

frAtmSpvcVccBcOut OBJECT-TYPE
        SYNTAX Integer32
        MAX-ACCESS read-write
        STATUS current
        DESCRIPTION "The value of this object is equal to the
                 committed burst size (Bc) parameter (measured in
                 bits) for this SPVC in the egress
                 direction (into the frame relay UNI)."
        DEFVAL { 0 }
        ::= { frAtmSpvcVccEntry 10 }

frAtmSpvcVccBeOut OBJECT-TYPE
        SYNTAX Integer32
        MAX-ACCESS read-write
        STATUS current
        DESCRIPTION "The value of this object is equal to the excess
                 burst size (Be) parameter (measured in bits) for
                 this SPVC in the egress direction (into
                 the frame relay UNI)"
        DEFVAL { 45000000 }
        ::= { frAtmSpvcVccEntry 11 }

frAtmSpvcVccCirOut OBJECT-TYPE
        SYNTAX Integer32
        MAX-ACCESS read-write
        STATUS current
        DESCRIPTION "The value of this object is equal to the
                 committed information rate (CIR) parameter
                 (measured in bits per second) for this SPVC
                 in the egress direction (into the frame
                 relay UNI)."
        DEFVAL { 0 }
        ::= { frAtmSpvcVccEntry 12 }

frAtmSpvcVccServiceType OBJECT-TYPE
        SYNTAX INTEGER {
                ubr(1),
                vbr-nrt2(2),
                vbr-nrt1(3),
                vbr-rt2(4),
                vbr-rt1(5),
                vbr-express(6)
                   }
        MAX-ACCESS read-write
        STATUS current
        DESCRIPTION "service type, Frame relay traffic is carried
                 by VBR type of service only."
        DEFVAL { ubr }
        ::= { frAtmSpvcVccEntry 13 }

frAtmSpvcVccFlow OBJECT-TYPE
        SYNTAX INTEGER {
                duplex(1),
                simplexA2B(2),
                simplexB2A(3)
                   }
        MAX-ACCESS read-write
        STATUS current
        DESCRIPTION "Flow Type"
        DEFVAL { duplex }
        ::= { frAtmSpvcVccEntry 14 }

frAtmSpvcVccTimeLenIn OBJECT-TYPE
        SYNTAX INTEGER (64..4000)
        MAX-ACCESS read-only
        STATUS current
        DESCRIPTION "The time interval over which CIR and the burst
                 sizes (Bc and Be) are measured in the A2B 
                 direction.  The unit is milliseconds."
        DEFVAL { 1000 }
        ::= { frAtmSpvcVccEntry 15 }

frAtmSpvcVccTimeLenOut OBJECT-TYPE
        SYNTAX INTEGER (64..4000)
        MAX-ACCESS read-only
        STATUS current
        DESCRIPTION "The time interval over which CIR and the burst
                 sizes (Bc and Be) are measured in the A2B 
                 direction.  The unit is milliseconds."
        DEFVAL { 1000 }
        ::= { frAtmSpvcVccEntry 16 }

frAtmSpvcVccPeakCellRateA2B OBJECT-TYPE
        SYNTAX Integer32
        MAX-ACCESS read-only
        STATUS current
        DESCRIPTION "Peak cell rate - side A, in cells per second, 
                 this will reflect the frame relay parameters in
                 atm terms."
        DEFVAL { 1 }
        ::= { frAtmSpvcVccEntry 17 }

frAtmSpvcVccSusCellRateA2B OBJECT-TYPE
        SYNTAX Integer32
        MAX-ACCESS read-only
        STATUS current
        DESCRIPTION "Sustained cell rate - side A, in cells per second,
                 this will reflect the frame relay parameters in
                 atm terms."
        DEFVAL { 1 }
        ::= { frAtmSpvcVccEntry 18 }

frAtmSpvcVccMaxBurstSizeA2B OBJECT-TYPE
        SYNTAX Integer32
        MAX-ACCESS read-only
        STATUS current
        DESCRIPTION "Maximum burst size - side A, in cells, 
                 this will reflect the frame relay parameters in
                 atm terms."
        DEFVAL { 1 }
        ::= { frAtmSpvcVccEntry 19 }

frAtmSpvcVccPeakCellRateB2A OBJECT-TYPE
        SYNTAX Integer32
        MAX-ACCESS read-only
        STATUS current
        DESCRIPTION "Peak cell rate - side B, in cells per second, 
                 this will reflect the frame relay parameters in
                 atm terms."
        DEFVAL { 1 }
        ::= { frAtmSpvcVccEntry 20 }

frAtmSpvcVccSusCellRateB2A OBJECT-TYPE
        SYNTAX Integer32
        MAX-ACCESS read-only
        STATUS current
        DESCRIPTION "Sustained cell rate - side B, in cells per second,
                 this will reflect the frame relay parameters in
                 atm terms."
        DEFVAL { 1 }
        ::= { frAtmSpvcVccEntry 21 }

frAtmSpvcVccMaxBurstSizeB2A OBJECT-TYPE
        SYNTAX Integer32
        MAX-ACCESS read-only
        STATUS current
        DESCRIPTION "Maximum burst size - side B, in cells, 
                 this will reflect the frame relay parameters in
                 atm terms."
        DEFVAL { 1 }
        ::= { frAtmSpvcVccEntry 22 }

frAtmSpvcVccInterWorkingFunc OBJECT-TYPE
        SYNTAX INTEGER {

                frf8-Transl(1),
                frf8-Pass(2),
                frf5(3)
                   }
        MAX-ACCESS read-write
        STATUS current
        DESCRIPTION "InterWorking function."
        DEFVAL { frf8-Transl }
        ::= { frAtmSpvcVccEntry 23 }

frAtmSpvcVccConnType    OBJECT-TYPE
        SYNTAX INTEGER{
                activeSvc(1),
                passiveSvc(2)
                }
        MAX-ACCESS read-write
        STATUS current
        DESCRIPTION "The type of connection: activeSvc - attempt calls,
                 whenever not established; passiveSvc - accepts calls"
        ::= { frAtmSpvcVccEntry 24 }

frAtmSpvcVccOperStatus OBJECT-TYPE
        SYNTAX INTEGER {
                other(1),
                establishmentInProgress(2),
                connected(3),
                retriesExhausted(4),
                noAddressSupplied(5),
                lowerLayerDown(6),
                waitingForCall(7),
                waitingForRetryTimer(8)
                }
        MAX-ACCESS read-only
        STATUS current
        DESCRIPTION "other - none of the types specified below;
                 establishmentInProgress - connection is not
                        operational, but call attempts are ongoing;
                 connected - connection is currently operational;
                 retriesExhausted - retry limit has been reached
                        and call attempts have ceased;
                 noAddressSupplied - no remote address has been
                        configured, so no call attempts are initiated;
                 lowerLayerDown - SPVC handler is not operational."
        ::= { frAtmSpvcVccEntry 25 }

frAtmSpvcVccRowStatus OBJECT-TYPE
        SYNTAX RowStatus
        MAX-ACCESS read-write
        STATUS current
        DESCRIPTION "row status"
        ::= { frAtmSpvcVccEntry 26 }

frAtmSpvcVccRemoteFrPortAddr OBJECT-TYPE
        SYNTAX OCTET STRING (SIZE(1..20))
        MAX-ACCESS read-write
        STATUS current
        DESCRIPTION "The ATM address supporting the corresponding far
                 end FR IWF process.  If no address is supplied, 
                 no attempts to establish the active SVC are 
                 initiated."
        ::= { frAtmSpvcVccEntry 27 }
 
frAtmSpvcVccRemoteSelectType OBJECT-TYPE
        SYNTAX INTEGER  {
                required(1),
                any(2)
                }
        MAX-ACCESS read-write
        STATUS current
        DESCRIPTION "Indicates whether the remote DLCI/VPI/VCI values are to
                 be used at the destination.  If 'any' is used, the
                 destination switch will choose the DLCI/VPI/VCI values.
                 In such a case, once the SPVC is connected, the
                 value of this object will change to 'required',
                 such that the same DLCI/VPI/VCI values will continue to
                 be used even if the connection is torn down and
                 re-established.  If the value 'required' is
                 specified, the values:  frAtmSpvcVccRemoteDlci or
                 frAtmSpvcVccRemoteVpi and frAtmSpvcVccRemoteVci, must 
                 be supplied and are used at the destination."
        ::= { frAtmSpvcVccEntry 28 }
 
frAtmSpvcVccRemoteDlci OBJECT-TYPE
        SYNTAX INTEGER (0..4095)
        MAX-ACCESS read-write
        STATUS current
        DESCRIPTION "DLCI value to be used at the destination of an
                 ATM SPVC VCC connection.  Valid range is a number
                 between 0 and 4095.  If frAtmSpvcVccRemoteSelectType
                 is configured as 'any', then this value is not
                 relevant."
        ::= { frAtmSpvcVccEntry 29 }
 
frAtmSpvcVccRemoteVpi OBJECT-TYPE
        SYNTAX INTEGER (0..4095)
        MAX-ACCESS read-write
        STATUS current
        DESCRIPTION "VPI value to be used at the destination of an
                 ATM SPVC VCC connection.  Valid range is a number
                 between 0 and 4095.  If frAtmSpvcVccRemoteSelectType
                 is configured as 'any', then this value is not
                 relevant."
        ::= { frAtmSpvcVccEntry 30 }
 
frAtmSpvcVccRemoteVci OBJECT-TYPE
        SYNTAX INTEGER (0..65535)
        MAX-ACCESS read-write
        STATUS current
        DESCRIPTION "VCI value to be used at the destination of an ATM
                 SPVC VCC connection.  Valid range is a number
                 between 0 and 65535.  If frAtmSpvcVccRemoteSelectType
                 is configured as 'any', then this value is not
                 relevant."
        ::= { frAtmSpvcVccEntry 31 }
 

frAtmSpvcVccRetryInterval OBJECT-TYPE
        SYNTAX INTEGER (0..3600)
        UNITS      "seconds"
        MAX-ACCESS read-write
        STATUS current
        DESCRIPTION "The time to wait before attempting to establish
                 the SVC after previous failed call attempt. 
                 0 indicates retry will be attempted immediately."
        DEFVAL { 10 }    
        ::= { frAtmSpvcVccEntry 32 }
     
frAtmSpvcVccRetryLimit OBJECT-TYPE
        SYNTAX INTEGER (0..65535) 
        MAX-ACCESS read-write
        STATUS current
        DESCRIPTION "A maximum limit on how many retries.     
                 0 indicates no limit."
        DEFVAL { 0 }  
        ::= { frAtmSpvcVccEntry 33 }

frAtmSpvcVccRestart OBJECT-TYPE
        SYNTAX INTEGER {
                restart(1),
                noop(2)
                }
        MAX-ACCESS read-write
        STATUS current
        DESCRIPTION "restart, the active SVC is released if necessary
                 and a new setup procedure is begun; or noop"
        ::= { frAtmSpvcVccEntry 34 }

frAtmSpvcVccRetryFailure OBJECT-TYPE
        SYNTAX Integer32
        MAX-ACCESS read-only
        STATUS current
        DESCRIPTION "Indicates how many attempts to establish the
                 connection have failed.  It is reset whenever a
                 connection is successfully established or the SVC
                 is restarted."
        ::= { frAtmSpvcVccEntry 35 }

frAtmSpvcVccReleaseCause OBJECT-TYPE
        SYNTAX INTEGER(1..127)
        MAX-ACCESS read-only
        STATUS current
        DESCRIPTION "CAUSE field value of the last RELEASE message
                 received for this SVC."
        ::= { frAtmSpvcVccEntry 36 }

frAtmSpvcVccReleaseDiag OBJECT-TYPE
        SYNTAX OCTET STRING (SIZE(0..8))
        MAX-ACCESS read-only
        STATUS current
        DESCRIPTION "DIAGNOSTICS field value of the last RELEASE
                 message received for this SVC."
        ::= { frAtmSpvcVccEntry 37 }

frAtmSpvcVccRelease OBJECT-TYPE
        SYNTAX INTEGER {
                release(1),
                noop(2)
                }
        MAX-ACCESS read-write
        STATUS current
        DESCRIPTION "Release the connnection established on the endpoint
                 and if the endpoint is Active, do not retry."
        ::= { frAtmSpvcVccEntry 38 }

frAtmSpvcVccStatsCellsEncodedHiA OBJECT-TYPE
        SYNTAX Integer32
        MAX-ACCESS read-only
        STATUS current
        DESCRIPTION "Cells encoded on side A- (High order portion) "
        ::= { frAtmSpvcVccEntry 39 }

frAtmSpvcVccStatsCellsEncodedLoA OBJECT-TYPE
        SYNTAX Integer32
        MAX-ACCESS read-only
        STATUS current
        DESCRIPTION "Cells encoded on side A- (Low order portion)"
        ::= { frAtmSpvcVccEntry 40 }

frAtmSpvcVccStatsCellsDecodedHiA OBJECT-TYPE
        SYNTAX Integer32
        MAX-ACCESS read-only
        STATUS current
        DESCRIPTION "Cells decoded on side A- (High order portion)"
        ::= { frAtmSpvcVccEntry 41 }

frAtmSpvcVccStatsCellsDecodedLoA OBJECT-TYPE
        SYNTAX Integer32
        MAX-ACCESS read-only
        STATUS current
        DESCRIPTION "Cells decoded on side A- (Low order portion)"
        ::= { frAtmSpvcVccEntry 42 }

frAtmSpvcVccStatsInCellCountHiB OBJECT-TYPE
        SYNTAX Integer32
        MAX-ACCESS read-only
        STATUS current
        DESCRIPTION "Valid cells received (Input Billing Count)"
        ::= { frAtmSpvcVccEntry 43 }

frAtmSpvcVccStatsInCellCountLoB OBJECT-TYPE
        SYNTAX Integer32
        MAX-ACCESS read-only
        STATUS current
        DESCRIPTION "Valid cells received (Input Billing Count)"
        ::= { frAtmSpvcVccEntry 44 }

frAtmSpvcVccStatsOutCellCountHiB OBJECT-TYPE
        SYNTAX Integer32
        MAX-ACCESS read-only
        STATUS current
        DESCRIPTION "Valid cells transmitted (Output Billing Count)"
        ::= { frAtmSpvcVccEntry 45 }

frAtmSpvcVccStatsOutCellCountLoB OBJECT-TYPE
        SYNTAX Integer32
        MAX-ACCESS read-only
        STATUS current
        DESCRIPTION "Valid cells transmitted (Output Billing Count)"
        ::= { frAtmSpvcVccEntry 46 }

frAtmSpvcVccStatsTimer OBJECT-TYPE
        SYNTAX Integer32
        MAX-ACCESS read-only
        STATUS current
        DESCRIPTION "Number of seconds stats have been collecting"
        ::= { frAtmSpvcVccEntry 47 }

frAtmSpvcVccStatsFramesDroppedA OBJECT-TYPE
        SYNTAX Integer32
        MAX-ACCESS read-only
        STATUS current
        DESCRIPTION "Number of frames dropped for a given DLCI for A2B
                 direction, only applicable to the input side."
        ::= { frAtmSpvcVccEntry 48 }

frAtmSpvcVccStatsOdometerCellsEncodedHiA OBJECT-TYPE
        SYNTAX Integer32
        MAX-ACCESS read-only
        STATUS current
        DESCRIPTION "Cells encoded on side A- (High order portion) "
        ::= { frAtmSpvcVccEntry 49 }

frAtmSpvcVccStatsOdometerCellsEncodedLoA OBJECT-TYPE
        SYNTAX Integer32
        MAX-ACCESS read-only
        STATUS current
        DESCRIPTION "Cells encoded on side A- (Low order portion)"
        ::= { frAtmSpvcVccEntry 50 }

frAtmSpvcVccStatsOdometerCellsDecodedHiA OBJECT-TYPE
        SYNTAX Integer32
        MAX-ACCESS read-only
        STATUS current
        DESCRIPTION "Cells decoded on side A- (High order portion) "
        ::= { frAtmSpvcVccEntry 51 }

frAtmSpvcVccStatsOdometerCellsDecodedLoA OBJECT-TYPE
        SYNTAX Integer32
        MAX-ACCESS read-only
        STATUS current
        DESCRIPTION "Cells decoded on side A- (Low order portion) "
        ::= { frAtmSpvcVccEntry 52 }

frAtmSpvcVccStatsInOdometerCellCountHiB OBJECT-TYPE
        SYNTAX Integer32
        MAX-ACCESS read-only
        STATUS current
        DESCRIPTION "Valid cells received (Input Billing Count)"
        ::= { frAtmSpvcVccEntry 53 }

frAtmSpvcVccStatsInOdometerCellCountLoB OBJECT-TYPE
        SYNTAX Integer32
        MAX-ACCESS read-only
        STATUS current
        DESCRIPTION "Valid cells received (Input Billing Count)"
        ::= { frAtmSpvcVccEntry 54 }

frAtmSpvcVccStatsOutOdometerCellCountHiB OBJECT-TYPE
        SYNTAX Integer32
        MAX-ACCESS read-only
        STATUS current
        DESCRIPTION "Valid cells transmitted (Output Billing Count)"
        ::= { frAtmSpvcVccEntry 55 }

frAtmSpvcVccStatsOutOdometerCellCountLoB OBJECT-TYPE
        SYNTAX Integer32
        MAX-ACCESS read-only
        STATUS current
        DESCRIPTION "Valid cells transmitted (Output Billing Count)"
        ::= { frAtmSpvcVccEntry 56 }

frAtmSpvcVccStatsOdometerTimer OBJECT-TYPE
        SYNTAX Integer32
        MAX-ACCESS read-only
        STATUS current
        DESCRIPTION "Number of seconds since odometer was reset."
        ::= { frAtmSpvcVccEntry 57 }

frAtmSpvcVccStatsOdometerReset OBJECT-TYPE
        SYNTAX INTEGER {
                reset(1)
                   }
        MAX-ACCESS read-write
        STATUS current
        DESCRIPTION "Odometer reset button."
        ::= { frAtmSpvcVccEntry 58 }

frAtmSpvcVccStatsAal5ErrFramesA OBJECT-TYPE 
                SYNTAX Integer32
                MAX-ACCESS read-only
                STATUS current
                DESCRIPTION "Number of Aal5 Errored Frames, which are not
                                dropped due to UPC in A2B dir, 
                                only applicable to Input Side"
                ::= { frAtmSpvcVccEntry 59 }

frAtmSpvcVccStatsFramesTaggedA OBJECT-TYPE
                SYNTAX Integer32
                MAX-ACCESS read-only
                STATUS current
                DESCRIPTION "Number of  Frames tagged due to UPC in A2B
                                dir, only applicable to Input Side"
                ::= { frAtmSpvcVccEntry 60 }

frAtmSpvcVccStatsCellsDroppedB OBJECT-TYPE
                SYNTAX Integer32
                MAX-ACCESS read-only
                STATUS current
                DESCRIPTION "Cells Dropped on the Incoming side of B"
                ::= { frAtmSpvcVccEntry 61 }

frAtmSpvcVccStatsCellsTaggedB OBJECT-TYPE
                SYNTAX Integer32
                MAX-ACCESS read-only
                STATUS current
                DESCRIPTION "Cells Tagged on the Incoming side of B"
                ::= { frAtmSpvcVccEntry 62 }


frAtmSpvcVccVUNIB  OBJECT-TYPE
                SYNTAX INTEGER (0..255)
                MAX-ACCESS read-write
                STATUS current
                DESCRIPTION "VUNI to associate the Egress part of the
                        B2A connection ."
                DEFVAL { 0 }
                ::= { frAtmSpvcVccEntry 63 }


frAtmSpvcVccTrafficShapingA2B     OBJECT-TYPE
                SYNTAX INTEGER {
                                disabled(1),
                                enabled(2)
                               }
                MAX-ACCESS read-write
                STATUS current
                DESCRIPTION "Traffic Shaping Support in the A2B direction."
                DEFVAL { disabled }
                ::= { frAtmSpvcVccEntry 64 }

frAtmSpvcVccPriority OBJECT-TYPE
        SYNTAX INTEGER  {
                priority-1(1),
                priority-2(2),
                priority-3(3),
                priority-4(4)
                }
        MAX-ACCESS read-write
        STATUS current
        DESCRIPTION "Priority of SPVC - priority-1 being highest priority ."
        DEFVAL { priority-1 }
        ::= { frAtmSpvcVccEntry 65 }

 


atmAtmSpvcVccTable OBJECT-TYPE
        SYNTAX SEQUENCE OF AtmAtmSpvcVccEntry
        MAX-ACCESS not-accessible
        STATUS current
        DESCRIPTION "Table of SPVC ATM virtual channel connections."
        ::= { connectionConfig 33 }

atmAtmSpvcVccEntry OBJECT-TYPE
        SYNTAX AtmAtmSpvcVccEntry
        MAX-ACCESS not-accessible
        STATUS current
        DESCRIPTION "Row definition of ATM SPVC VCC connections."
        INDEX { spvcAddrIfA, atmAtmSpvcVccVpiA, atmAtmSpvcVccVciA, atmAtmSpvcVccRemoteAtmPortAddr }
        ::= { atmAtmSpvcVccTable 1 }

AtmAtmSpvcVccEntry ::= SEQUENCE {
        atmAtmSpvcVccVpiA                          INTEGER,
        atmAtmSpvcVccVciA                          INTEGER,
        atmAtmSpvcVccRemoteAtmPortAddr             OCTET STRING,
        atmAtmSpvcVccIfB                           IntfIndex,
        atmAtmSpvcVccVpiB                          INTEGER,
        atmAtmSpvcVccVciB                          INTEGER,
        atmAtmSpvcVccServiceTypeA2B                INTEGER,
        atmAtmSpvcVccSarTypeA2B                    INTEGER,
        atmAtmSpvcVccPeakCellRateA2B               Integer32,
        atmAtmSpvcVccSusCellRateA2B                Integer32,
        atmAtmSpvcVccMaxBurstSizeA2B               Integer32,
        atmAtmSpvcVccFrwdErrCorrectionA2B          INTEGER,
        atmAtmSpvcVccServiceTypeB2A                INTEGER,
        atmAtmSpvcVccSarTypeB2A                    INTEGER,
        atmAtmSpvcVccPeakCellRateB2A               Integer32,
        atmAtmSpvcVccSusCellRateB2A                Integer32,
        atmAtmSpvcVccMaxBurstSizeB2A               Integer32,
        atmAtmSpvcVccFrwdErrCorrectionB2A          INTEGER,
        atmAtmSpvcVccFlow                          INTEGER,
        atmAtmSpvcVccType                          INTEGER,
        atmAtmSpvcVccConnType                      INTEGER,
        atmAtmSpvcVccLeafReference                 INTEGER,
        atmAtmSpvcVccOperStatus                    INTEGER,
        atmAtmSpvcVccRowStatus                     RowStatus,
        atmAtmSpvcVccRemoteSelectType              INTEGER,
        atmAtmSpvcVccRemoteVpi                     INTEGER,
        atmAtmSpvcVccRemoteVci                     INTEGER,
        atmAtmSpvcVccRetryInterval                 INTEGER,
        atmAtmSpvcVccRetryLimit                    INTEGER,
        atmAtmSpvcVccRestart                       INTEGER,
        atmAtmSpvcVccRetryFailure                  Integer32,
        atmAtmSpvcVccReleaseCause                  INTEGER,
        atmAtmSpvcVccReleaseDiag                   OCTET STRING,
        atmAtmSpvcVccRelease                       INTEGER,
        atmAtmSpvcVccStatsInCellCountHiA           Integer32,
        atmAtmSpvcVccStatsInCellCountLoA           Integer32,
        atmAtmSpvcVccStatsOutCellCountHiA          Integer32,
        atmAtmSpvcVccStatsOutCellCountLoA          Integer32,
        atmAtmSpvcVccStatsInCellCountHiB           Integer32,
        atmAtmSpvcVccStatsInCellCountLoB           Integer32,
        atmAtmSpvcVccStatsOutCellCountHiB          Integer32,
        atmAtmSpvcVccStatsOutCellCountLoB          Integer32,
        atmAtmSpvcVccStatsTimer                    Integer32,
        atmAtmSpvcVccStatsFrwdErrCrrctnRateA2B     INTEGER,
        atmAtmSpvcVccStatsFrwdErrCrrctnRateB2A     INTEGER,
        atmAtmSpvcVccStatsInOdometerCellCountHiA   Integer32,
        atmAtmSpvcVccStatsInOdometerCellCountLoA   Integer32,
        atmAtmSpvcVccStatsOutOdometerCellCountHiA  Integer32,
        atmAtmSpvcVccStatsOutOdometerCellCountLoA  Integer32,
        atmAtmSpvcVccStatsInOdometerCellCountHiB   Integer32,
        atmAtmSpvcVccStatsInOdometerCellCountLoB   Integer32,
        atmAtmSpvcVccStatsOutOdometerCellCountHiB  Integer32,
        atmAtmSpvcVccStatsOutOdometerCellCountLoB  Integer32,
        atmAtmSpvcVccStatsOdometerTimer            Integer32,
        atmAtmSpvcVccStatsOdometerReset            INTEGER,
        atmAtmSpvcVccViA                           INTEGER,
        atmAtmSpvcVccViB                           INTEGER,
        atmAtmSpvcVccStatsCellsDroppedA            Integer32,
        atmAtmSpvcVccStatsCellsTaggedA             Integer32,
        atmAtmSpvcVccStatsCellsDroppedB            Integer32,
        atmAtmSpvcVccStatsCellsTaggedB             Integer32

        ,atmAtmSpvcVccVUNIA                        INTEGER,
        atmAtmSpvcVccVUNIB                         INTEGER,

        atmAtmSpvcVccTrafficShapingA2B             INTEGER,
        atmAtmSpvcVccTrafficShapingB2A             INTEGER,
        atmAtmSpvcVccPriority                      INTEGER
        }

atmAtmSpvcVccVpiA    OBJECT-TYPE
        SYNTAX INTEGER (0..4095)
        MAX-ACCESS not-accessible
        STATUS current
        DESCRIPTION "VPI value for side A of an ATM SPVC VCC connection.
                 Valid range is a number between 0 and 4095."
        ::= { atmAtmSpvcVccEntry 1 }

atmAtmSpvcVccVciA    OBJECT-TYPE
        SYNTAX INTEGER (0..65535)
        MAX-ACCESS not-accessible
        STATUS current
        DESCRIPTION "VCI value for side A of an ATM SPVC VCC connection.
                 Valid range is a number between 0 and 65535."
        ::= { atmAtmSpvcVccEntry 2 }

atmAtmSpvcVccRemoteAtmPortAddr OBJECT-TYPE
        SYNTAX OCTET STRING (SIZE(1..20))
        MAX-ACCESS not-accessible
        STATUS current
        DESCRIPTION "Remote ATM port NSAP address, not meaningful if 
                 passive type of connection."
        ::= { atmAtmSpvcVccEntry 3 }

atmAtmSpvcVccIfB    OBJECT-TYPE
        SYNTAX IntfIndex
        MAX-ACCESS read-only
        STATUS current
        DESCRIPTION "Interface index for side B of an ATM SPVC VCC 
                 connection.  Number value is interpreted as an 
                 interface of the form, SSPPCCC, where SS is the 
                 card slot, PP is the port number, and CCC is the 
                 channel number."
        ::= { atmAtmSpvcVccEntry 4 }

atmAtmSpvcVccVpiB    OBJECT-TYPE
        SYNTAX INTEGER (0..4095)
        MAX-ACCESS read-only
        STATUS current
        DESCRIPTION "VPI value for side B of an ATM SPVC VCC connection.
                 Valid range is a number between 0 and 4095."
        ::= { atmAtmSpvcVccEntry 5 }

atmAtmSpvcVccVciB    OBJECT-TYPE
        SYNTAX INTEGER (0..65535)
        MAX-ACCESS read-only
        STATUS current
        DESCRIPTION "VCI value for side B of an ATM SPVC VCC connection.
                 Valid range is a number between 0 and 65535."
        ::= { atmAtmSpvcVccEntry 6 }

atmAtmSpvcVccServiceTypeA2B OBJECT-TYPE
        SYNTAX INTEGER  {
                ubr(1),
                vbr-nrt2(2),
                vbr-nrt1(3),
                vbr-rt2(4),
                vbr-rt1(5),
                vbr-express(6),
                cbr4(7),
                cbr3(8),
                cbr2(9)
                }
        MAX-ACCESS read-write
        STATUS current
        DESCRIPTION "Service type, ATM port."
        DEFVAL { ubr }
        ::= { atmAtmSpvcVccEntry 7 }

atmAtmSpvcVccSarTypeA2B OBJECT-TYPE
        SYNTAX INTEGER  {
                aal5(1),
                aal3-4(2),
                aal2(3),
                aal1(4),
                null(5)
                }
        MAX-ACCESS read-write
        STATUS current
        DESCRIPTION "SAR type used in ATM adaption, ATM port."
        DEFVAL { null }
        ::= { atmAtmSpvcVccEntry 8 }

atmAtmSpvcVccPeakCellRateA2B OBJECT-TYPE
        SYNTAX Integer32
        MAX-ACCESS read-write
        STATUS current
        DESCRIPTION "Peak cell rate - side A, ATM port, in cells per
                 second."
        DEFVAL { 1 }
        ::= { atmAtmSpvcVccEntry 9 }

atmAtmSpvcVccSusCellRateA2B OBJECT-TYPE
        SYNTAX Integer32
        MAX-ACCESS read-write
        STATUS current
        DESCRIPTION "Sustained cell rate - side A, ATM port, in cells
                 per second."
        DEFVAL { 1 }
        ::= { atmAtmSpvcVccEntry 10 }

atmAtmSpvcVccMaxBurstSizeA2B OBJECT-TYPE
        SYNTAX Integer32
        MAX-ACCESS read-write
        STATUS current
        DESCRIPTION "Maximum burst size - side A, ATM port, in cells
                 per second."
        DEFVAL { 1 }
        ::= { atmAtmSpvcVccEntry 11 }

atmAtmSpvcVccFrwdErrCorrectionA2B OBJECT-TYPE
        SYNTAX INTEGER {
                none(1),
                eighthRate(2),
                quarterRate(3),
                halfRate(4),
                autoHiQ(5),
                auto(6),
                autoLoQ(7)
                   }
        MAX-ACCESS read-write
        STATUS current
        DESCRIPTION "Forward error correction scheme, ATM port side."
        DEFVAL { none }
        ::= { atmAtmSpvcVccEntry 12 }

atmAtmSpvcVccServiceTypeB2A OBJECT-TYPE
        SYNTAX INTEGER  {
                ubr(1),
                vbr-nrt2(2),
                vbr-nrt1(3),
                vbr-rt2(4),
                vbr-rt1(5),
                vbr-express(6),
                cbr4(7),
                cbr3(8),
                cbr2(9)
                }
        MAX-ACCESS read-write
        STATUS current
        DESCRIPTION "Service type, ATM trunk side."
        DEFVAL { ubr }
        ::= { atmAtmSpvcVccEntry 13 }

atmAtmSpvcVccSarTypeB2A OBJECT-TYPE
        SYNTAX INTEGER  {
                aal5(1),
                aal3-4(2),
                aal2(3),
                aal1(4),
                null(5)
                }
        MAX-ACCESS read-write
        STATUS current
        DESCRIPTION "SAR type used in ATM adaption, ATM trunk side."
        DEFVAL { null }
        ::= { atmAtmSpvcVccEntry 14 }

atmAtmSpvcVccPeakCellRateB2A OBJECT-TYPE
        SYNTAX Integer32
        MAX-ACCESS read-write
        STATUS current
        DESCRIPTION "Peak cell rate - side B, ATM trunk, in cells per
                 second."
        DEFVAL { 1 }
        ::= { atmAtmSpvcVccEntry 15 }

atmAtmSpvcVccSusCellRateB2A    OBJECT-TYPE
        SYNTAX Integer32
        MAX-ACCESS read-write
        STATUS current
        DESCRIPTION "Sustained cell rate - side B, ATM trunk, in cells
                 per second."
        DEFVAL { 1 }
        ::= { atmAtmSpvcVccEntry 16 }

atmAtmSpvcVccMaxBurstSizeB2A OBJECT-TYPE
        SYNTAX Integer32
        MAX-ACCESS read-write
        STATUS current
        DESCRIPTION "Maximum burst size - side A, ATM trunk, in cells
                 per second."
        DEFVAL { 1 }
        ::= { atmAtmSpvcVccEntry 17 }

atmAtmSpvcVccFrwdErrCorrectionB2A OBJECT-TYPE
        SYNTAX INTEGER {
                none(1),
                eighthRate(2),
                quarterRate(3),
                halfRate(4),
                autoHiQ(5),
                auto(6),
                autoLoQ(7)
                   }
        MAX-ACCESS read-write
        STATUS current
        DESCRIPTION "Forward error correction scheme, ATM trunk side."
        DEFVAL { none }
        ::= { atmAtmSpvcVccEntry 18 }

atmAtmSpvcVccFlow    OBJECT-TYPE
        SYNTAX INTEGER    {
                duplex(1),
                simplexA2B(2),
                pointToMultipointA2B(3),
                simplexB2A(4),
                pointToMultipointB2A(5)
                }
        MAX-ACCESS read-write
        STATUS current
        DESCRIPTION "Type of flow, pointToMultipointA2B is for future
                 support."
        DEFVAL { duplex }
        ::= { atmAtmSpvcVccEntry 19 }

atmAtmSpvcVccType    OBJECT-TYPE
        SYNTAX INTEGER  {
                nonsecured(1),
                secured(2)
                }
        MAX-ACCESS read-write
        STATUS current
        DESCRIPTION "Type of connection."
        DEFVAL { nonsecured }
        ::= { atmAtmSpvcVccEntry 20 }

atmAtmSpvcVccConnType OBJECT-TYPE
        SYNTAX INTEGER  {
                activeSvc(1),
                passiveSvc(2)
                }
        MAX-ACCESS read-write
        STATUS current
        DESCRIPTION "The type of connection:
                 activeSvc - attempt calls, whenever not 
                   established.
                 passiveSvc - accept calls."
        ::= { atmAtmSpvcVccEntry 21 }

atmAtmSpvcVccLeafReference OBJECT-TYPE
        SYNTAX INTEGER (1..65535)
        MAX-ACCESS read-only
        STATUS current
        DESCRIPTION "An arbitrary integer which serves to distinguish
                 the mulitple leaves attached to a root of a 
                 point-to-multipoint SPVC.  If point-to-point SPVC, 
                 the value should be 1."
        ::= { atmAtmSpvcVccEntry 22 }

atmAtmSpvcVccOperStatus OBJECT-TYPE
        SYNTAX INTEGER  {
                other(1),
                establishmentInProgress(2),
                connected(3),
                retriesExhausted(4),
                noAddressSupplied(5),
                lowerLayerDown(6),
                waitingForCall(7),
                waitingForRetryTimer(8)
                }
        MAX-ACCESS read-only
        STATUS current
        DESCRIPTION "The operation status of the connection:
                 other - none of the types specified below.
                 establishmentInProgress - connection is not 
                operational, but call attempts are ongoing.
                 connected - connection is currently operational.
                 retriesExhausted - retry limit has been reached 
                and call attempts have ceased.
                 noAddressSupplied - no remote address has been 
                configured, so no call attempts are initiated.
                 lowerLayerDown - SPVC handler is not operational."
        ::= { atmAtmSpvcVccEntry 23 }

atmAtmSpvcVccRowStatus OBJECT-TYPE
        SYNTAX RowStatus
        MAX-ACCESS read-write
        STATUS current
        DESCRIPTION "Used to create and delete a soft PVC.  When this
                 object is set to 'active', an attempt is made to 
                 set up the soft PVC.  When this object has the 
                 value 'active' and is set to another value, any 
                 setup or connection in-progress is released."
        ::= { atmAtmSpvcVccEntry 24 }


atmAtmSpvcVccRemoteSelectType OBJECT-TYPE
        SYNTAX INTEGER  {
                required(1),
                any(2)
                }
        MAX-ACCESS read-write
        STATUS current
        DESCRIPTION "Indicates whether the remote VPI/VCI values are to 
                 be used at the destination.  If 'any' is used, the 
                 destination switch will choose the VPI/VCI values. 
                 In such a case, once the SPVC is connected, the 
                 value of this object will change to 'required', 
                 such that the same VPI/VCI values will continue to 
                 be used even if the connection is torn down and 
                 re-established.  If the value 'required' is
                 specified, the values:  atmAtmSpvcVccRemoteVpi and 
                 atmAtmSpvcVccRemoteVci, must be supplied and are used
                 at the destination."
        ::= { atmAtmSpvcVccEntry 25 }

atmAtmSpvcVccRemoteVpi OBJECT-TYPE
        SYNTAX INTEGER (0..4095)
        MAX-ACCESS read-write
        STATUS current
        DESCRIPTION "VPI value to be used at the destination of an 
                 ATM SPVC VCC connection.  Valid range is a number 
                 between 0 and 4095.  If atmAtmSpvcVccRemoteSelectType 
                 is configured as 'any', then this value is not 
                 relevant."
        ::= { atmAtmSpvcVccEntry 26 }

atmAtmSpvcVccRemoteVci OBJECT-TYPE
        SYNTAX INTEGER (0..65535)
        MAX-ACCESS read-write
        STATUS current
        DESCRIPTION "VCI value to be used at the destination of an ATM 
                 SPVC VCC connection.  Valid range is a number 
                 between 0 and 65535.  If atmAtmSpvcVccRemoteSelectType
                 is configured as 'any', then this value is not 
                 relevant."
        ::= { atmAtmSpvcVccEntry 27 }

atmAtmSpvcVccRetryInterval OBJECT-TYPE
        SYNTAX INTEGER (0..3600)
        MAX-ACCESS read-write
        STATUS current
        DESCRIPTION "The time to wait before attempting to establish 
                 the SVC after a previous failed call attempt.  A 
                 value of 0 indicates retries will be attempted immediately."
        ::= { atmAtmSpvcVccEntry 28 }

atmAtmSpvcVccRetryLimit OBJECT-TYPE
        SYNTAX INTEGER (0..65535)
        MAX-ACCESS read-write
        STATUS current
        DESCRIPTION "A maximum limit on how many retries should be 
                 attempted.  A value of 0 indicates no limit."
        ::= { atmAtmSpvcVccEntry 29 }

atmAtmSpvcVccRestart OBJECT-TYPE
        SYNTAX INTEGER  {
                restart(1),
                noop(2)
                }
        MAX-ACCESS read-write
        STATUS current
        DESCRIPTION "The active SVC is released, if necessary, and a 
                 new setup procedure is begun if 'restart', 
                 otherwise, noop."
        ::= { atmAtmSpvcVccEntry 30 }

atmAtmSpvcVccRetryFailure OBJECT-TYPE
        SYNTAX Integer32
        MAX-ACCESS read-only
        STATUS current
        DESCRIPTION "Indicates how many attempts to establish the 
                 connection have failed.  It it reset whenever a 
                 connection is successfully established or the SVC 
                 is restarted."
        ::= { atmAtmSpvcVccEntry 31 }

atmAtmSpvcVccReleaseCause OBJECT-TYPE
        SYNTAX INTEGER (1..127)
        MAX-ACCESS read-only
        STATUS current
        DESCRIPTION "CAUSE field value of the last RELEASE message 
                 received for this SVC."
        ::= { atmAtmSpvcVccEntry 32 }

atmAtmSpvcVccReleaseDiag OBJECT-TYPE
        SYNTAX OCTET STRING (SIZE(0..8))
        MAX-ACCESS read-only
        STATUS current
        DESCRIPTION "DIAGNOSTICS field value of the last RELEASE 
                 message received for this SVC."
        ::= { atmAtmSpvcVccEntry 33 }


atmAtmSpvcVccRelease OBJECT-TYPE
        SYNTAX INTEGER {
                release(1),
                noop(2)
                }
        MAX-ACCESS read-only
        STATUS current
        DESCRIPTION "Release the connnection established on the endpoint
                 and if the endpoint is Active, do not retry."
        ::= { atmAtmSpvcVccEntry 34 }


atmAtmSpvcVccStatsInCellCountHiA OBJECT-TYPE
        SYNTAX Integer32
        MAX-ACCESS read-only
        STATUS current
        DESCRIPTION "Valid Cells received on A - (High order portion)"
        ::= { atmAtmSpvcVccEntry 35 }

atmAtmSpvcVccStatsInCellCountLoA OBJECT-TYPE
        SYNTAX Integer32
        MAX-ACCESS read-only
        STATUS current
        DESCRIPTION "Valid Cells received on A - (Low order portion) "
        ::= { atmAtmSpvcVccEntry 36 }

atmAtmSpvcVccStatsOutCellCountHiA OBJECT-TYPE
        SYNTAX Integer32
        MAX-ACCESS read-only
        STATUS current
        DESCRIPTION "Valid cells transmitted on A -(High order portion)"
        ::= { atmAtmSpvcVccEntry 37 }

atmAtmSpvcVccStatsOutCellCountLoA OBJECT-TYPE
        SYNTAX Integer32
        MAX-ACCESS read-only
        STATUS current
        DESCRIPTION "Valid cells transmitted on A -(Low order portion)"
        ::= { atmAtmSpvcVccEntry 38 }

atmAtmSpvcVccStatsInCellCountHiB OBJECT-TYPE
        SYNTAX Integer32
        MAX-ACCESS read-only
        STATUS current
        DESCRIPTION "Valid Cells received on B - (High order portion)"
        ::= { atmAtmSpvcVccEntry 39 }

atmAtmSpvcVccStatsInCellCountLoB OBJECT-TYPE
        SYNTAX Integer32
        MAX-ACCESS read-only
        STATUS current
        DESCRIPTION "Valid Cells received on B - (Low order portion) "
        ::= { atmAtmSpvcVccEntry 40 }

atmAtmSpvcVccStatsOutCellCountHiB OBJECT-TYPE
        SYNTAX Integer32
        MAX-ACCESS read-only
        STATUS current
        DESCRIPTION "Valid cells transmitted on B -(High order portion)"
        ::= { atmAtmSpvcVccEntry 41 }

atmAtmSpvcVccStatsOutCellCountLoB OBJECT-TYPE
        SYNTAX Integer32
        MAX-ACCESS read-only
        STATUS current
        DESCRIPTION "Valid cells transmitted on B -(Low order portion)"
        ::= { atmAtmSpvcVccEntry 42 }

atmAtmSpvcVccStatsTimer OBJECT-TYPE
        SYNTAX Integer32
        MAX-ACCESS read-only
        STATUS current
        DESCRIPTION "Number of seconds stats have been collecting"
        ::= { atmAtmSpvcVccEntry 43 }

atmAtmSpvcVccStatsFrwdErrCrrctnRateA2B OBJECT-TYPE
        SYNTAX INTEGER {
                none(1),
                eighthRate(2),
                quarterRate(3),
                halfRate(4)
                   }
        MAX-ACCESS read-only
        STATUS current
        DESCRIPTION "Displays the Forward error correction rate being 
                 used by the FEC module in the A2B direction.  This
                 field is dynamic when Auto rates are selected.  In
                 other cases, it will display the rate set by the 
                 user."
        DEFVAL { none }
        ::= { atmAtmSpvcVccEntry 44 }

atmAtmSpvcVccStatsFrwdErrCrrctnRateB2A OBJECT-TYPE
        SYNTAX INTEGER {
                none(1),
                eighthRate(2),
                quarterRate(3),
                halfRate(4)
                   }
        MAX-ACCESS read-only
        STATUS current
        DESCRIPTION "Displays the Forward error correction rate being 
                 used by the FEC module in the B2A direction.  This
                 field is dynamic when Auto rates are selected.  In
                 other cases, it will display the rate set by the 
                 user."
        DEFVAL { none }
        ::= { atmAtmSpvcVccEntry 45 }

atmAtmSpvcVccStatsInOdometerCellCountHiA OBJECT-TYPE
        SYNTAX Integer32
        MAX-ACCESS read-only
        STATUS current
        DESCRIPTION "Valid cells received (Input Billing Count)"
        ::= { atmAtmSpvcVccEntry 46 }

atmAtmSpvcVccStatsInOdometerCellCountLoA OBJECT-TYPE
        SYNTAX Integer32
        MAX-ACCESS read-only
        STATUS current
        DESCRIPTION "Valid cells transmitted (Output Billing Count)"
        ::= { atmAtmSpvcVccEntry 47 }

atmAtmSpvcVccStatsOutOdometerCellCountHiA OBJECT-TYPE
        SYNTAX Integer32
        MAX-ACCESS read-only
        STATUS current
        DESCRIPTION "Valid cells transmitted (Output Billing Count)"
        ::= { atmAtmSpvcVccEntry 48 }

atmAtmSpvcVccStatsOutOdometerCellCountLoA OBJECT-TYPE
        SYNTAX Integer32
        MAX-ACCESS read-only
        STATUS current
        DESCRIPTION "Valid cells transmitted (Output Billing Count)"
        ::= { atmAtmSpvcVccEntry 49 }

atmAtmSpvcVccStatsInOdometerCellCountHiB OBJECT-TYPE
        SYNTAX Integer32
        MAX-ACCESS read-only
        STATUS current
        DESCRIPTION "Valid cells received (Input Billing Count)"
        ::= { atmAtmSpvcVccEntry 50 }

atmAtmSpvcVccStatsInOdometerCellCountLoB OBJECT-TYPE
        SYNTAX Integer32
        MAX-ACCESS read-only
        STATUS current
        DESCRIPTION "Valid cells transmitted (Output Billing Count)"
        ::= { atmAtmSpvcVccEntry 51 }

atmAtmSpvcVccStatsOutOdometerCellCountHiB OBJECT-TYPE
        SYNTAX Integer32
        MAX-ACCESS read-only
        STATUS current
        DESCRIPTION "Valid cells transmitted (Output Billing Count)"
        ::= { atmAtmSpvcVccEntry 52 }

atmAtmSpvcVccStatsOutOdometerCellCountLoB OBJECT-TYPE
        SYNTAX Integer32
        MAX-ACCESS read-only
        STATUS current
        DESCRIPTION "Valid cells transmitted (Output Billing Count)"
        ::= { atmAtmSpvcVccEntry 53 }

atmAtmSpvcVccStatsOdometerTimer OBJECT-TYPE
        SYNTAX Integer32
        MAX-ACCESS read-only
        STATUS current
        DESCRIPTION "Number of seconds since odometer was reset."
        ::= { atmAtmSpvcVccEntry 54 }

atmAtmSpvcVccStatsOdometerReset OBJECT-TYPE
        SYNTAX INTEGER {
                reset(1)
                   }
        MAX-ACCESS read-write
        STATUS current
        DESCRIPTION "Odometer reset button."
        ::= { atmAtmSpvcVccEntry 55 }


atmAtmSpvcVccViA   OBJECT-TYPE
        SYNTAX INTEGER (0..1024)
        MAX-ACCESS read-write
        STATUS current
        DESCRIPTION "VI to associate the Egress part of the B2A connection ."
            DEFVAL { 0 }
        ::= { atmAtmSpvcVccEntry 56 }


atmAtmSpvcVccViB   OBJECT-TYPE
        SYNTAX INTEGER (0..1024)
        MAX-ACCESS read-write
        STATUS current
        DESCRIPTION "VI to associate the Egress part of the A2B connection ."
        DEFVAL { 0 }
        ::= { atmAtmSpvcVccEntry 57 }

atmAtmSpvcVccStatsCellsDroppedA OBJECT-TYPE
                SYNTAX Integer32
                MAX-ACCESS read-only
                STATUS current
                DESCRIPTION "Cells Dropped on the Incoming side of A"
                ::= { atmAtmSpvcVccEntry 58 }

atmAtmSpvcVccStatsCellsTaggedA OBJECT-TYPE
                SYNTAX Integer32
                MAX-ACCESS read-only
                STATUS current
                DESCRIPTION "Cells Tagged on the Incoming side of A"
                ::= { atmAtmSpvcVccEntry 59 }

atmAtmSpvcVccStatsCellsDroppedB OBJECT-TYPE
                SYNTAX Integer32
                MAX-ACCESS read-only
                STATUS current
                DESCRIPTION "Cells Dropped on the Incoming side of B"
                ::= { atmAtmSpvcVccEntry 60 }

atmAtmSpvcVccStatsCellsTaggedB OBJECT-TYPE
                SYNTAX Integer32
                MAX-ACCESS read-only
                STATUS current
                DESCRIPTION "Cells Tagged on the Incoming side of B"
                ::= { atmAtmSpvcVccEntry 61 }


atmAtmSpvcVccVUNIA   OBJECT-TYPE
        SYNTAX INTEGER (0..255)
        MAX-ACCESS read-write
        STATUS current
        DESCRIPTION "VUNI to associate the Egress part of the B2A connection ."
            DEFVAL { 0 }
        ::= { atmAtmSpvcVccEntry 62 }


atmAtmSpvcVccVUNIB   OBJECT-TYPE
        SYNTAX INTEGER (0..255)
        MAX-ACCESS read-write
        STATUS current
        DESCRIPTION "VUNI to associate the Egress part of the A2B connection ."
        DEFVAL { 0 }
        ::= { atmAtmSpvcVccEntry 63 }


atmAtmSpvcVccTrafficShapingA2B     OBJECT-TYPE
        SYNTAX INTEGER {
                         disabled(1),
                         enabled(2)
                          }
        MAX-ACCESS read-write
        STATUS current
        DESCRIPTION "Traffic Shaping Support in the A2B direction."
        DEFVAL { disabled }
        ::= { atmAtmSpvcVccEntry 64 }

atmAtmSpvcVccTrafficShapingB2A     OBJECT-TYPE
        SYNTAX INTEGER {
                         disabled(1),
                         enabled(2)
                          }
        MAX-ACCESS read-write
        STATUS current
        DESCRIPTION "Traffic Shaping Support in the B2A direction."
        DEFVAL { disabled }
        ::= { atmAtmSpvcVccEntry 65 }

atmAtmSpvcVccPriority OBJECT-TYPE
        SYNTAX INTEGER  {
                priority-1(1),
                priority-2(2),
                priority-3(3),
                priority-4(4)
                }
        MAX-ACCESS read-write
        STATUS current
        DESCRIPTION "Priority of SPVC - priority-1 being highest priority ."
        DEFVAL { priority-1 }
        ::= { atmAtmSpvcVccEntry 66 }


 


cirAtmSpvcVccTable OBJECT-TYPE
        SYNTAX SEQUENCE OF CirAtmSpvcVccEntry
        MAX-ACCESS not-accessible
        STATUS current
        DESCRIPTION "Table of Circuit Emulation to ATM Soft PVCs."
        ::= { connectionConfig 34 }

cirAtmSpvcVccEntry OBJECT-TYPE
        SYNTAX CirAtmSpvcVccEntry
        MAX-ACCESS not-accessible
        STATUS current
        DESCRIPTION "Row definition of circuit emulation to ATM SPVC
          connections."
        INDEX { spvcAddrIfA, cirAtmSpvcVccRemoteCePortAddr }
        ::= { cirAtmSpvcVccTable 1 }

CirAtmSpvcVccEntry ::= SEQUENCE {
        cirAtmSpvcVccRemoteCePortAddr                 OCTET STRING,
        cirAtmSpvcVccIfB                              IntfIndex,
        cirAtmSpvcVccVpiB                             INTEGER,
        cirAtmSpvcVccVciB                             INTEGER,
        cirAtmSpvcVccVoiceCompressionA2B              INTEGER,
        cirAtmSpvcVccSilenceDetectionA2B              INTEGER,
        cirAtmSpvcVccEchoCancellationA2B              INTEGER,
        cirAtmSpvcVccCngToneDetectionA2B              INTEGER,
        cirAtmSpvcVccCodingTranslationA2B             INTEGER,
        cirAtmSpvcVccVoiceCompressionB2A              INTEGER,
        cirAtmSpvcVccSilenceDetectionB2A              INTEGER,
        cirAtmSpvcVccEchoCancellationB2A              INTEGER,
        cirAtmSpvcVccCngToneDetectionB2A              INTEGER,
        cirAtmSpvcVccCodingTranslationB2A             INTEGER,
        cirAtmSpvcVccFlow                             INTEGER,
        cirAtmSpvcVccServiceType                      INTEGER,
        cirAtmSpvcVccConnType                         INTEGER,
        cirAtmSpvcVccOperStatus                       INTEGER,
        cirAtmSpvcVccRowStatus                        RowStatus,
        cirAtmSpvcVccViB                              INTEGER,
        cirAtmSpvcVccRetryInterval                    INTEGER,
        cirAtmSpvcVccRetryLimit                       INTEGER,
        cirAtmSpvcVccRestart                          INTEGER,
        cirAtmSpvcVccRetryFailure                     Integer32,
        cirAtmSpvcVccReleaseCause                     INTEGER,
        cirAtmSpvcVccReleaseDiag                      OCTET STRING,
        cirAtmSpvcVccRelease                          INTEGER,
        cirAtmSpvcVccStatsCellsEncodedHiA             Integer32,
        cirAtmSpvcVccStatsCellsEncodedLoA             Integer32,
        cirAtmSpvcVccStatsCellsDecodedHiA             Integer32,
        cirAtmSpvcVccStatsCellsDecodedLoA             Integer32,
        cirAtmSpvcVccStatsInCellCountHiB              Integer32,
        cirAtmSpvcVccStatsInCellCountLoB              Integer32,
        cirAtmSpvcVccStatsOutCellCountHiB             Integer32,
        cirAtmSpvcVccStatsOutCellCountLoB             Integer32,
        cirAtmSpvcVccStatsTimer                       Integer32,
        cirAtmSpvcVccStatsOdometerCellsEncodedHiA     Integer32,
        cirAtmSpvcVccStatsOdometerCellsEncodedLoA     Integer32,
        cirAtmSpvcVccStatsOdometerCellsDecodedHiA     Integer32,
        cirAtmSpvcVccStatsOdometerCellsDecodedLoA     Integer32,
        cirAtmSpvcVccStatsInOdometerCellCountHiB      Integer32,
        cirAtmSpvcVccStatsInOdometerCellCountLoB      Integer32,
        cirAtmSpvcVccStatsOutOdometerCellCountHiB     Integer32,
        cirAtmSpvcVccStatsOutOdometerCellCountLoB     Integer32,
        cirAtmSpvcVccStatsOdometerTimer               Integer32,
        cirAtmSpvcVccStatsOdometerReset               INTEGER,
        cirAtmSpvcVccStatsCellsDroppedB               Integer32,
        cirAtmSpvcVccStatsCellsTaggedB                Integer32,

        cirAtmSpvcVccVUNIB                              INTEGER,

        cirAtmSpvcVccSarTypeB                        Integer32,
        cirAtmSpvcVccPriority                        INTEGER
        }

cirAtmSpvcVccRemoteCePortAddr    OBJECT-TYPE
        SYNTAX OCTET STRING (SIZE(1..20))
        MAX-ACCESS not-accessible
        STATUS current
        DESCRIPTION "The ATM address supporting the corresponding far 
         end CES IWF process.  If no address is supplied, 
         no attempts to establish the active SVC are 
         initiated."
        ::= { cirAtmSpvcVccEntry 1 }

cirAtmSpvcVccIfB OBJECT-TYPE
        SYNTAX IntfIndex
        MAX-ACCESS read-only
        STATUS current
        DESCRIPTION "Interface index for side B, the atm side, of a 
         circuit emulation-atm SPVC VCC connection.  Number 
         value is interpreted as an interface of the form, 
         SSPPCCC, where SS is the card slot, PP is the port                  number, and CCC is the channel number."
        ::= { cirAtmSpvcVccEntry 2 }

cirAtmSpvcVccVpiB OBJECT-TYPE
        SYNTAX INTEGER (0..4095)
        MAX-ACCESS read-only
        STATUS current
        DESCRIPTION "VPI value for side B, the atm side,  of a
         circuit emulation-atm SPVC VCC connection.  Valid 
         range is a number between 0 and 4095."
        ::= { cirAtmSpvcVccEntry 3 }

cirAtmSpvcVccVciB OBJECT-TYPE
        SYNTAX INTEGER (0..65535)
        MAX-ACCESS read-only
        STATUS current
        DESCRIPTION "VCI value for side B, the atm side,  of a
         circuit emulation-atm SPVC VCC connection.  Valid 
         range is a number between 0 and 65535."
        ::= { cirAtmSpvcVccEntry 4 }

cirAtmSpvcVccVoiceCompressionA2B OBJECT-TYPE
        SYNTAX INTEGER  {
                none(1),
                g726-16k(2),
                g726-24k(3),
                g726-32k(4),
                g726-40k(5),
                                g729a-8k(6)
                }
        MAX-ACCESS read-write
        STATUS current
        DESCRIPTION "Voice Compression Algorithm"
        DEFVAL { none }
        ::= { cirAtmSpvcVccEntry 5 }

cirAtmSpvcVccSilenceDetectionA2B OBJECT-TYPE
        SYNTAX INTEGER  {
                 disabled(1),
                 enabled(2)
                }
        MAX-ACCESS read-write
        STATUS current
        DESCRIPTION "silence detection off/on"
        DEFVAL { disabled }
        ::= { cirAtmSpvcVccEntry 6 }

cirAtmSpvcVccEchoCancellationA2B OBJECT-TYPE
        SYNTAX INTEGER  {
                 none(1),
                 g165-nearEnd(2),
                 g168(3)
                }
        MAX-ACCESS read-write
        STATUS current
        DESCRIPTION "Echo Cancellation Algorithm"
        DEFVAL { none }
        ::= { cirAtmSpvcVccEntry 7 }

cirAtmSpvcVccCngToneDetectionA2B OBJECT-TYPE
        SYNTAX INTEGER  {
                 disabled(1),
                 bypass(2),
                 g726-32k(3)
                }
        MAX-ACCESS read-write
        STATUS current
        DESCRIPTION "Calling Tone Detection Algorithm,
         one of the enum value, g726-32k(3)
         is obsoleted on 01Mar99 such that
         user would not be able to configure
         CE-ATM"
        DEFVAL { disabled }
        ::= { cirAtmSpvcVccEntry 8 }

cirAtmSpvcVccCodingTranslationA2B OBJECT-TYPE
        SYNTAX INTEGER  {
                                 none(1),
                                 muLaw2muLaw(2),
                                 aLaw2aLaw(3),
                                 muLaw2aLaw(4),
                                 aLaw2muLaw(5)
                }
        MAX-ACCESS read-write
        STATUS current
        DESCRIPTION "Coding rule translation type."
        DEFVAL { none }
        ::= { cirAtmSpvcVccEntry 9 }

cirAtmSpvcVccVoiceCompressionB2A OBJECT-TYPE
        SYNTAX INTEGER  {
                none(1),
                g726-16k(2),
                g726-24k(3),
                g726-32k(4),
                g726-40k(5),
                                g729a-8k(6)
                }
        MAX-ACCESS read-write
        STATUS current
        DESCRIPTION "Voice Compression Algorithm"
        DEFVAL { none }
        ::= { cirAtmSpvcVccEntry 10 }

cirAtmSpvcVccSilenceDetectionB2A OBJECT-TYPE
        SYNTAX INTEGER  {
                 disabled(1),
                 enabled(2)
                }
        MAX-ACCESS read-write
        STATUS current
        DESCRIPTION "silence detection off/on"
        DEFVAL { disabled }
        ::= { cirAtmSpvcVccEntry 11 }

cirAtmSpvcVccEchoCancellationB2A OBJECT-TYPE
        SYNTAX INTEGER  {
                 none(1),
                 g165-nearEnd(2),
                 g168(3)
                }
        MAX-ACCESS read-write
        STATUS current
        DESCRIPTION "Echo Cancellation Algorithm"
        DEFVAL { none }
        ::= { cirAtmSpvcVccEntry 12 }

cirAtmSpvcVccCngToneDetectionB2A OBJECT-TYPE
        SYNTAX INTEGER  {
                 disabled(1),
                 bypass(2),
                 g726-32k(3)
                }
        MAX-ACCESS read-write
        STATUS current
        DESCRIPTION "Calling Tone Detection Algorithm,
         one of the enum value, g726-32k(3)
         is obsoleted on 01Mar99 such that
         user would not be able to configure
         CE-ATM"
        DEFVAL { disabled }
        ::= { cirAtmSpvcVccEntry 13 }

cirAtmSpvcVccCodingTranslationB2A OBJECT-TYPE
        SYNTAX INTEGER  {
                                 none(1),
                                 muLaw2muLaw(2),
                                 aLaw2aLaw(3),
                                 muLaw2aLaw(4),
                                 aLaw2muLaw(5)
                }
        MAX-ACCESS read-write
        STATUS current
        DESCRIPTION "Coding rule translation type."
        DEFVAL { none }
        ::= { cirAtmSpvcVccEntry 14 }

cirAtmSpvcVccFlow OBJECT-TYPE
        SYNTAX INTEGER  {
                 duplex(1),
                 simplexA2B(2),
                 simplexB2A(3),
                 pointToMultipointA2B(4),
                 pointToMultipointB2A(5)
                }
        MAX-ACCESS read-write
        STATUS current
        DESCRIPTION "Flow Type, pointToMultipointA2B and 
         pointToMultipointB2A are for future support."
        DEFVAL { duplex }
        ::= { cirAtmSpvcVccEntry 15 }

cirAtmSpvcVccServiceType OBJECT-TYPE
        SYNTAX INTEGER {
                cbr-2(2),
                cbr-3(3),
                cbr-4(4)
           }
        MAX-ACCESS read-write
        STATUS current
        DESCRIPTION "service type"
        ::= { cirAtmSpvcVccEntry 16 }

cirAtmSpvcVccConnType    OBJECT-TYPE
                SYNTAX INTEGER{
                                activeSvc(1),
                                passiveSvc(2)
                                }
                MAX-ACCESS read-write
                STATUS current
                DESCRIPTION "The type of connection: activeSvc - attempt calls,
                whenever not established;
                             passiveSvc - accepts calls"
                ::= { cirAtmSpvcVccEntry 17 }

cirAtmSpvcVccOperStatus OBJECT-TYPE
                SYNTAX INTEGER {
                                other(1),
                                establishmentInProgress(2),
                                connected(3),
                                retriesExhausted(4),
                                noAddressSupplied(5),
                                lowerLayerDown(6),
                                waitingForCall(7),
                                waitingForRetryTimer(8)
                                }
                MAX-ACCESS read-only
                STATUS current
                DESCRIPTION "other - none of the types specified below;
                             establishmentInProgress - connection is not 
                operational, but call attempts are ongoing;
                             connected - connection is currently operational;
                             retriesExhausted - retry limit has been reached 
                and call attempts have ceased;
                             noAddressSupplied - no remote address has been 
                configured, so no call attempts are initiated;
                             lowerLayerDown - SPVC handler is not operational."
                ::= { cirAtmSpvcVccEntry 18 }

cirAtmSpvcVccRowStatus  OBJECT-TYPE
                SYNTAX     RowStatus
                MAX-ACCESS read-write
                STATUS     current
                DESCRIPTION "Used to create and delete a soft PVCC.  When this 
         object is set to 'active' an attempt is made to 
         set up the soft PVCC.  When this object has the 
         value 'active' and is set to another value, any 
         set-up or connection in-progess is released."
                ::= { cirAtmSpvcVccEntry 19 }

cirAtmSpvcVccViB      OBJECT-TYPE
        SYNTAX INTEGER (0..1024)
        MAX-ACCESS read-write
        STATUS current
        DESCRIPTION "VI to associate the Egress part of 
                the B2A connection ."
        DEFVAL { 0 } 
        ::= { cirAtmSpvcVccEntry 20 }


cirAtmSpvcVccRetryInterval OBJECT-TYPE
        SYNTAX INTEGER (0..3600)
        UNITS      "seconds"
        MAX-ACCESS read-write
        STATUS current
        DESCRIPTION "The time to wait before attempting to establish 
         the SVC after previous failed call attempt. 
         0 indicates  retries will be attempted immediately."
        DEFVAL { 10 }
        ::= { cirAtmSpvcVccEntry 21 }

cirAtmSpvcVccRetryLimit OBJECT-TYPE
        SYNTAX INTEGER (0..65535)
        MAX-ACCESS read-write
        STATUS current
        DESCRIPTION "A maximum limit on how many retries. 
         0 indicates no limit."
        DEFVAL { 0 }
        ::= { cirAtmSpvcVccEntry 22 }

cirAtmSpvcVccRestart OBJECT-TYPE
        SYNTAX INTEGER {
                restart(1),
                noop(2)
                }
        MAX-ACCESS read-write
        STATUS current
        DESCRIPTION "restart, the active SVC is released if necessary 
         and a new setup procedure is begun; or noop"
        ::= { cirAtmSpvcVccEntry 23 }

cirAtmSpvcVccRetryFailure OBJECT-TYPE
        SYNTAX Integer32 
        MAX-ACCESS read-only
        STATUS current
        DESCRIPTION "Indicates how many attempts to establish the 
         connection have failed.  It is reset whenever a 
         connection is successfully established or the SVC 
         is restarted."
        ::= { cirAtmSpvcVccEntry 24 }

cirAtmSpvcVccReleaseCause OBJECT-TYPE
        SYNTAX INTEGER(1..127) 
        MAX-ACCESS read-only
        STATUS current
        DESCRIPTION "CAUSE field value of the last RELEASE message 
         received for this SVC."
        ::= { cirAtmSpvcVccEntry 25 }

cirAtmSpvcVccReleaseDiag OBJECT-TYPE
        SYNTAX OCTET STRING (SIZE(0..8)) 
        MAX-ACCESS read-only
        STATUS current
        DESCRIPTION "DIAGNOSTICS field value of the last RELEASE 
         message received for this SVC."
        ::= { cirAtmSpvcVccEntry 26 }


cirAtmSpvcVccRelease OBJECT-TYPE
        SYNTAX INTEGER {
                release(1),
                noop(2)
                }
        MAX-ACCESS read-only
        STATUS current
        DESCRIPTION "Release the connnection established on the endpoint
         and if the endpoint is Active, do not retry."
        ::= { cirAtmSpvcVccEntry 27 }


cirAtmSpvcVccStatsCellsEncodedHiA OBJECT-TYPE
        SYNTAX Integer32
        MAX-ACCESS read-only
        STATUS current
        DESCRIPTION "Cells encoded on side A- (High order portion )"
        ::= { cirAtmSpvcVccEntry 28 }

cirAtmSpvcVccStatsCellsEncodedLoA OBJECT-TYPE
        SYNTAX Integer32
        MAX-ACCESS read-only
        STATUS current
        DESCRIPTION "Cells encoded on side A - ( Low order portion) "
        ::= { cirAtmSpvcVccEntry 29 }

cirAtmSpvcVccStatsCellsDecodedHiA OBJECT-TYPE
        SYNTAX Integer32
        MAX-ACCESS read-only
        STATUS current
        DESCRIPTION "Cells decoded on side A - ( High order portion) "
        ::= { cirAtmSpvcVccEntry 30 }

cirAtmSpvcVccStatsCellsDecodedLoA OBJECT-TYPE
        SYNTAX Integer32
        MAX-ACCESS read-only
        STATUS current
        DESCRIPTION "Cells decoded on side A - (Low order portion) "
        ::= { cirAtmSpvcVccEntry 31 }

cirAtmSpvcVccStatsInCellCountHiB OBJECT-TYPE
        SYNTAX Integer32
        MAX-ACCESS read-only
        STATUS current
        DESCRIPTION "Valid Cells received on B - (High order portion)"
        ::= { cirAtmSpvcVccEntry 32 }

cirAtmSpvcVccStatsInCellCountLoB OBJECT-TYPE
        SYNTAX Integer32
        MAX-ACCESS read-only
        STATUS current
        DESCRIPTION "Valid Cells received on B - (Low order portion) "
        ::= { cirAtmSpvcVccEntry 33 }

cirAtmSpvcVccStatsOutCellCountHiB OBJECT-TYPE
        SYNTAX Integer32
        MAX-ACCESS read-only
        STATUS current
        DESCRIPTION "Valid cells transmitted on B- (High order portion)"
        ::= { cirAtmSpvcVccEntry 34 }

cirAtmSpvcVccStatsOutCellCountLoB OBJECT-TYPE
        SYNTAX Integer32
        MAX-ACCESS read-only
        STATUS current
        DESCRIPTION "Valid cells transmitted on B -(Low order portion)"
        ::= { cirAtmSpvcVccEntry 35 }

cirAtmSpvcVccStatsTimer OBJECT-TYPE
        SYNTAX Integer32
        MAX-ACCESS read-only
        STATUS current
        DESCRIPTION "Number of seconds since stats have been collecting"
        ::= { cirAtmSpvcVccEntry 36 }

cirAtmSpvcVccStatsOdometerCellsEncodedHiA OBJECT-TYPE
        SYNTAX Integer32
        MAX-ACCESS read-only
        STATUS current
        DESCRIPTION "Cells encoded on side A- (High order portion) "
        ::= { cirAtmSpvcVccEntry 37 }

cirAtmSpvcVccStatsOdometerCellsEncodedLoA OBJECT-TYPE
        SYNTAX Integer32
        MAX-ACCESS read-only
        STATUS current
        DESCRIPTION "Cells encoded on side A- (Low order portion) "
        ::= { cirAtmSpvcVccEntry 38 }

cirAtmSpvcVccStatsOdometerCellsDecodedHiA OBJECT-TYPE
        SYNTAX Integer32
        MAX-ACCESS read-only
        STATUS current
        DESCRIPTION "Cells decoded on side A- (High order portion) "
        ::= { cirAtmSpvcVccEntry 39 }

cirAtmSpvcVccStatsOdometerCellsDecodedLoA OBJECT-TYPE
        SYNTAX Integer32
        MAX-ACCESS read-only
        STATUS current
        DESCRIPTION "Cells decoded on side A- (Low order portion) "
        ::= { cirAtmSpvcVccEntry 40 }

cirAtmSpvcVccStatsInOdometerCellCountHiB OBJECT-TYPE
        SYNTAX Integer32
        MAX-ACCESS read-only
        STATUS current
        DESCRIPTION "Valid cells received (Input Billing Count)"
        ::= { cirAtmSpvcVccEntry 41 }

cirAtmSpvcVccStatsInOdometerCellCountLoB OBJECT-TYPE
        SYNTAX Integer32
        MAX-ACCESS read-only
        STATUS current
        DESCRIPTION "Valid cells received (Input Billing Count)"
        ::= { cirAtmSpvcVccEntry 42 }

cirAtmSpvcVccStatsOutOdometerCellCountHiB OBJECT-TYPE
        SYNTAX Integer32
        MAX-ACCESS read-only
        STATUS current
        DESCRIPTION "Valid cells transmitted (Output Billing Count)"
        ::= { cirAtmSpvcVccEntry 43 }

cirAtmSpvcVccStatsOutOdometerCellCountLoB OBJECT-TYPE
        SYNTAX Integer32
        MAX-ACCESS read-only
        STATUS current
        DESCRIPTION "Valid cells transmitted (Output Billing Count)"
        ::= { cirAtmSpvcVccEntry 44 }

cirAtmSpvcVccStatsOdometerTimer OBJECT-TYPE
        SYNTAX Integer32
        MAX-ACCESS read-only
        STATUS current
        DESCRIPTION "Number of seconds since odometer was reset."
        ::= { cirAtmSpvcVccEntry 45 }

cirAtmSpvcVccStatsOdometerReset OBJECT-TYPE
        SYNTAX INTEGER {
                reset(1)
           }
        MAX-ACCESS read-write
        STATUS current
        DESCRIPTION "Odometer reset button."
        ::= { cirAtmSpvcVccEntry 46 }

cirAtmSpvcVccStatsCellsDroppedB OBJECT-TYPE
                SYNTAX Integer32
                MAX-ACCESS read-only
                STATUS current
                DESCRIPTION "Cells Dropped on the Incoming side of B"
                ::= { cirAtmSpvcVccEntry 47 }

cirAtmSpvcVccStatsCellsTaggedB OBJECT-TYPE
                SYNTAX Integer32
                MAX-ACCESS read-only
                STATUS current
                DESCRIPTION "Cells Tagged on the Incoming side of B"
                ::= { cirAtmSpvcVccEntry 48 }


cirAtmSpvcVccVUNIB      OBJECT-TYPE
        SYNTAX INTEGER (0..255)
        MAX-ACCESS read-write
        STATUS current
        DESCRIPTION "VUNI to associate the Egress part of 
                the B2A connection ."
        DEFVAL { 0 } 
        ::= { cirAtmSpvcVccEntry 49 }


cirAtmSpvcVccSarTypeB OBJECT-TYPE
        SYNTAX INTEGER  {
                aal1(1),
                aal2(2)
                }
        MAX-ACCESS read-write
        STATUS current
        DESCRIPTION "This field will only be used when selecting voice
                 compression, in other cases it will be set to
                 aal1."
        DEFVAL { aal1 }
        ::= { cirAtmSpvcVccEntry 50 }

cirAtmSpvcVccPriority OBJECT-TYPE
        SYNTAX INTEGER  {
                priority-1(1),
                priority-2(2),
                priority-3(3),
                priority-4(4)
                }
        MAX-ACCESS read-write
        STATUS current
        DESCRIPTION "Priority of SPVC - priority-1 being highest priority ."
        DEFVAL { priority-1 }
        ::= { cirAtmSpvcVccEntry 51 }


 


vbrAtmSpvcTable OBJECT-TYPE
        SYNTAX SEQUENCE OF VbrAtmSpvcEntry
        MAX-ACCESS not-accessible
        STATUS current
        DESCRIPTION "Table of SPVC atm virtual channel connections"
        ::= { connectionConfig 35 }

vbrAtmSpvcEntry OBJECT-TYPE
        SYNTAX VbrAtmSpvcEntry
        MAX-ACCESS not-accessible
        STATUS current
        DESCRIPTION "Row definition of atm SPVC VCC connections"
        INDEX { spvcAddrIfA, vbrAtmSpvcRemoteVbrPortAddr }
        ::= { vbrAtmSpvcTable 1 }

VbrAtmSpvcEntry ::= SEQUENCE {
        vbrAtmSpvcRemoteVbrPortAddr              OCTET STRING,
        vbrAtmSpvcIfB                            IntfIndex,
        vbrAtmSpvcVpiB                           INTEGER,
        vbrAtmSpvcVciB                           INTEGER,
        vbrAtmSpvcServiceType                    INTEGER,
        vbrAtmSpvcPeakCellRateA2B                Integer32,
        vbrAtmSpvcSusCellRateA2B                 Integer32,
        vbrAtmSpvcMaxBurstSizeA2B                Integer32,
        vbrAtmSpvcPeakCellRateB2A                Integer32,
        vbrAtmSpvcSusCellRateB2A                 Integer32,
        vbrAtmSpvcMaxBurstSizeB2A                Integer32,
        vbrAtmSpvcFlow                           INTEGER,
        vbrAtmSpvcConnType                       INTEGER,
        vbrAtmSpvcOperStatus                     INTEGER,
        vbrAtmSpvcRowStatus                      RowStatus,
        vbrAtmSpvcViB                            INTEGER,
        vbrAtmSpvcRetryInterval                  INTEGER,
        vbrAtmSpvcRetryLimit                     INTEGER,
        vbrAtmSpvcRestart                        INTEGER,
        vbrAtmSpvcRetryFailure                   Integer32,
        vbrAtmSpvcReleaseCause                   INTEGER,
        vbrAtmSpvcReleaseDiag                    OCTET STRING,
        vbrAtmSpvcRelease                        INTEGER,
        vbrAtmSpvcStatsCellsEncodedHiA           Integer32,
        vbrAtmSpvcStatsCellsEncodedLoA           Integer32,
        vbrAtmSpvcStatsCellsDecodedHiA           Integer32,
        vbrAtmSpvcStatsCellsDecodedLoA           Integer32,
        vbrAtmSpvcStatsInCellCountHiB            Integer32,
        vbrAtmSpvcStatsInCellCountLoB            Integer32,
        vbrAtmSpvcStatsOutCellCountHiB           Integer32,
        vbrAtmSpvcStatsOutCellCountLoB           Integer32,
        vbrAtmSpvcStatsTimer                     Integer32,
        vbrAtmSpvcStatsOdometerCellsEncodedHiA   Integer32,
        vbrAtmSpvcStatsOdometerCellsEncodedLoA   Integer32,
        vbrAtmSpvcStatsOdometerCellsDecodedHiA   Integer32,
        vbrAtmSpvcStatsOdometerCellsDecodedLoA   Integer32,
        vbrAtmSpvcStatsInOdometerCellCountHiB    Integer32,
        vbrAtmSpvcStatsInOdometerCellCountLoB    Integer32,
        vbrAtmSpvcStatsOutOdometerCellCountHiB   Integer32,
        vbrAtmSpvcStatsOutOdometerCellCountLoB   Integer32,
        vbrAtmSpvcStatsOdometerTimer             Integer32,
        vbrAtmSpvcStatsOdometerReset             INTEGER,
        vbrAtmSpvcStatsCellsDroppedB             Integer32,
        vbrAtmSpvcStatsCellsTaggedB              Integer32

        ,vbrAtmSpvcVUNIB                         INTEGER,

        vbrAtmSpvcTrafficShapingA2B              INTEGER,
        vbrAtmSpvcPriority                    INTEGER
        }

vbrAtmSpvcRemoteVbrPortAddr OBJECT-TYPE
        SYNTAX OCTET STRING (SIZE(1..20))
        MAX-ACCESS not-accessible
        STATUS current
        DESCRIPTION "remote VBR port nsap address implemening IWF, not 
                             meaningful if passive type of connection"
        ::= { vbrAtmSpvcEntry 1 }

vbrAtmSpvcIfB OBJECT-TYPE
        SYNTAX IntfIndex
        MAX-ACCESS read-only
        STATUS current
        DESCRIPTION "Interface index for side B, the atm side, of a 
         variable bit rate-atm SPVC VCC connection.  Number 
         value is interpreted as an interface of the form, 
         SSPPCCC, where SS is the card slot, PP is the port 
         number, and CCC is the channel number."
        ::= { vbrAtmSpvcEntry 2 }

vbrAtmSpvcVpiB OBJECT-TYPE
        SYNTAX INTEGER (0..4095)
        MAX-ACCESS read-only
        STATUS current
        DESCRIPTION "VPI value for side B, the atm side,  of a
         variable bit rate-atm SPVC VCC connection.  Valid 
         range is a number between 0 and 4095."
        ::= { vbrAtmSpvcEntry 3 }

vbrAtmSpvcVciB OBJECT-TYPE
        SYNTAX INTEGER (0..65535)
        MAX-ACCESS read-only
        STATUS current
        DESCRIPTION "VCI value for side B, the atm side,  of a
         variable bit rate-atm SPVC VCC connection.  Valid 
         range is a number between 0 and 65535."
        ::= { vbrAtmSpvcEntry 4 }

vbrAtmSpvcServiceType OBJECT-TYPE
        SYNTAX INTEGER  {
                ubr(1),
                vbr-nrt1(2),
                vbr-nrt2(3),
                vbr-rt1(4),
                vbr-rt2(5),
                vbr-express(6)
                }
        MAX-ACCESS read-write
        STATUS current
        DESCRIPTION "service type"
        DEFVAL { ubr }
        ::= { vbrAtmSpvcEntry 5 }

vbrAtmSpvcPeakCellRateA2B OBJECT-TYPE
        SYNTAX Integer32
        MAX-ACCESS read-write
        STATUS current
        DESCRIPTION "peak cell rate - side A, in cell per second"
        DEFVAL { 1 }
        ::= { vbrAtmSpvcEntry 6 }

vbrAtmSpvcSusCellRateA2B OBJECT-TYPE
        SYNTAX Integer32
        MAX-ACCESS read-write
        STATUS current
        DESCRIPTION "sustained rate - side A, in cell per second"
        DEFVAL { 1 }
        ::= { vbrAtmSpvcEntry 7 }

vbrAtmSpvcMaxBurstSizeA2B OBJECT-TYPE
        SYNTAX Integer32
        MAX-ACCESS read-write
        STATUS current
        DESCRIPTION "maximum burst size - side A,  in cells"
        DEFVAL { 1 }
        ::= { vbrAtmSpvcEntry 8 }

vbrAtmSpvcPeakCellRateB2A OBJECT-TYPE
        SYNTAX Integer32
        MAX-ACCESS read-write
        STATUS current
        DESCRIPTION "peak rate - side B, ATM trunk, in cell per second."
        DEFVAL { 1 }
        ::= { vbrAtmSpvcEntry 9 }

vbrAtmSpvcSusCellRateB2A OBJECT-TYPE
        SYNTAX Integer32
        MAX-ACCESS read-write
        STATUS current
        DESCRIPTION "sustained rate - side B, ATM trunk, in cell per 
         second."
        DEFVAL { 1 }
        ::= { vbrAtmSpvcEntry 10 }

vbrAtmSpvcMaxBurstSizeB2A OBJECT-TYPE
        SYNTAX Integer32
        MAX-ACCESS read-write
        STATUS current
        DESCRIPTION "maximum burst size - side B, ATM trunk, in cells."
        DEFVAL { 1 }
        ::= { vbrAtmSpvcEntry 11 }

vbrAtmSpvcFlow OBJECT-TYPE
        SYNTAX INTEGER  {
                duplex(1),
                simplexA2B(2),
                simplexB2A(3) 
                }
        MAX-ACCESS read-write
        STATUS current
        DESCRIPTION "type of flow"
        DEFVAL { duplex }
        ::= { vbrAtmSpvcEntry 12 }

vbrAtmSpvcConnType OBJECT-TYPE
        SYNTAX INTEGER{
                activeSvc(1),
                passiveSvc(2)
                } 
        MAX-ACCESS read-write
        STATUS current
                DESCRIPTION "The type of connection: activeSvc - attempt calls,
                whenever not established;
                             passiveSvc - accepts calls"
        ::= { vbrAtmSpvcEntry 13 }

vbrAtmSpvcOperStatus OBJECT-TYPE
        SYNTAX INTEGER {
                other(1),
                establishmentInProgress(2),
                connected(3),
                retriesExhausted(4),
                noAddressSupplied(5),
                lowerLayerDown(6),
                waitingForCall(7),
                waitingForRetryTimer(8)
                } 
        MAX-ACCESS read-only
        STATUS current
                DESCRIPTION "other - none of the types specified below;
                             establishmentInProgress - connection is not 
                operational, but call attempts are ongoing;
                             connected - connection is currently operational;
                             retriesExhausted - retry limit has been reached 
                and call attempts have ceased;
                             noAddressSupplied - no remote address has been 
                configured, so no call attempts are initiated;
                             lowerLayerDown - SPVC handler is not operational."
        ::= { vbrAtmSpvcEntry 14 }

vbrAtmSpvcRowStatus OBJECT-TYPE
        SYNTAX RowStatus
        MAX-ACCESS read-write
        STATUS current
                DESCRIPTION "Used to create and delete a soft PVCC.  When this 
         object is set to 'active' an attempt is made to 
         set up the soft PVCC.  When this object has the 
         value 'active' and is set to another value, any 
         set-up or connection in-progess is released."
        ::= { vbrAtmSpvcEntry 15 }

vbrAtmSpvcViB OBJECT-TYPE
        SYNTAX INTEGER (0..1024)
        MAX-ACCESS read-write
        STATUS current
        DESCRIPTION "VI to associate the Egress part of the
            B2A connection ."
        DEFVAL { 0 }
        ::= { vbrAtmSpvcEntry 16 }

vbrAtmSpvcRetryInterval OBJECT-TYPE
        SYNTAX INTEGER (0..3600)
        UNITS "seconds"
        MAX-ACCESS read-write
        STATUS current
        DESCRIPTION "the time to wait before attempting to establish 
         the SVC after previous failed call attempt. 
         0 indicates retries will be attempted immediately."
        DEFVAL { 10 }
        ::= { vbrAtmSpvcEntry 17 }

vbrAtmSpvcRetryLimit    OBJECT-TYPE
        SYNTAX INTEGER (0..65535)
        MAX-ACCESS read-write
        STATUS current
        DESCRIPTION "a maximum limit on how many retries. 
         0 indicates no limit."
        DEFVAL { 0 }
        ::= { vbrAtmSpvcEntry 18 }

vbrAtmSpvcRestart OBJECT-TYPE
        SYNTAX INTEGER {
                restart(1),
                noop(2)
                }
        MAX-ACCESS read-write
        STATUS current
        DESCRIPTION "restart, the active SVC is released if necessary 
         and a new setup procedure is begun; or noop"
        ::= { vbrAtmSpvcEntry 19 }

vbrAtmSpvcRetryFailure OBJECT-TYPE
        SYNTAX Integer32 
        MAX-ACCESS read-only
        STATUS current
        DESCRIPTION "indicates how many attempts to establish the 
         connection have failed.  It is reset whenever a 
         connection is successfully established or the SVC 
         is restarted."
        ::= { vbrAtmSpvcEntry 20 }

vbrAtmSpvcReleaseCause OBJECT-TYPE
        SYNTAX INTEGER(1..127) 
        MAX-ACCESS read-only
        STATUS current
        DESCRIPTION "CAUSE field value of the last RELEASE message 
         received for this SVC"
        ::= { vbrAtmSpvcEntry 21 }

vbrAtmSpvcReleaseDiag OBJECT-TYPE
        SYNTAX OCTET STRING (SIZE(0..8)) 
        MAX-ACCESS read-only
        STATUS current
        DESCRIPTION "DIAGNOSTICS field value of the last RELEASE 
         message received for this SVC"
        ::= { vbrAtmSpvcEntry 22 }

vbrAtmSpvcRelease OBJECT-TYPE
        SYNTAX INTEGER {
                release(1),
                noop(2)
                }
        MAX-ACCESS read-only
        STATUS current
        DESCRIPTION "Release the connnection established on the endpoint
         and if the endpoint is Active, do not retry."
        ::= { vbrAtmSpvcEntry 23 }

vbrAtmSpvcStatsCellsEncodedHiA OBJECT-TYPE
        SYNTAX Integer32
        MAX-ACCESS read-only
        STATUS current
        DESCRIPTION "Cells encoded on side A- (High order portion)"
        ::= { vbrAtmSpvcEntry 24 }

vbrAtmSpvcStatsCellsEncodedLoA OBJECT-TYPE
        SYNTAX Integer32
        MAX-ACCESS read-only
        STATUS current
        DESCRIPTION "ells encoded on side A - (Low order portion)"
        ::= { vbrAtmSpvcEntry 25 }

vbrAtmSpvcStatsCellsDecodedHiA OBJECT-TYPE
        SYNTAX Integer32
        MAX-ACCESS read-only
        STATUS current
        DESCRIPTION "Cells decoded on side A - (High order portion)"
        ::= { vbrAtmSpvcEntry 26 }

vbrAtmSpvcStatsCellsDecodedLoA OBJECT-TYPE
        SYNTAX Integer32
        MAX-ACCESS read-only
        STATUS current
        DESCRIPTION "Cells decoded on side A - (Low order portion)"
        ::= { vbrAtmSpvcEntry 27 }

vbrAtmSpvcStatsInCellCountHiB OBJECT-TYPE
        SYNTAX Integer32
        MAX-ACCESS read-only
        STATUS current
        DESCRIPTION "Valid Cells received on  B - (High order portion)"
        ::= { vbrAtmSpvcEntry 28}

vbrAtmSpvcStatsInCellCountLoB OBJECT-TYPE
        SYNTAX Integer32
        MAX-ACCESS read-only
        STATUS current
        DESCRIPTION "Valid Cells received on B - (Low order portion)"
        ::= { vbrAtmSpvcEntry 29 }

vbrAtmSpvcStatsOutCellCountHiB OBJECT-TYPE
        SYNTAX Integer32
        MAX-ACCESS read-only
        STATUS current
        DESCRIPTION "Valid cells transmitted on B -(High order portion)"
        ::= { vbrAtmSpvcEntry 30 }

vbrAtmSpvcStatsOutCellCountLoB OBJECT-TYPE
        SYNTAX Integer32
        MAX-ACCESS read-only
        STATUS current
        DESCRIPTION "Valid cells transmitted on B - (Low order portion)"
        ::= { vbrAtmSpvcEntry 31 }

vbrAtmSpvcStatsTimer OBJECT-TYPE
        SYNTAX Integer32
        MAX-ACCESS read-only
        STATUS current
        DESCRIPTION "Number of seconds stats have been collecting"
        ::= { vbrAtmSpvcEntry 32 }

vbrAtmSpvcStatsOdometerCellsEncodedHiA OBJECT-TYPE
        SYNTAX Integer32
        MAX-ACCESS read-only
        STATUS current
        DESCRIPTION "Cells encoded on side A- (High order portion)"
        ::= { vbrAtmSpvcEntry 33 }

vbrAtmSpvcStatsOdometerCellsEncodedLoA OBJECT-TYPE
        SYNTAX Integer32
        MAX-ACCESS read-only
        STATUS current
        DESCRIPTION "Cells encoded on side A- (Low order portion)"
        ::= { vbrAtmSpvcEntry 34 }

vbrAtmSpvcStatsOdometerCellsDecodedHiA OBJECT-TYPE
        SYNTAX Integer32
        MAX-ACCESS read-only
        STATUS current
        DESCRIPTION "Cells decoded on side A- (High order portion)"
        ::= { vbrAtmSpvcEntry 35 }

vbrAtmSpvcStatsOdometerCellsDecodedLoA OBJECT-TYPE
        SYNTAX Integer32
        MAX-ACCESS read-only
        STATUS current
        DESCRIPTION "Cells decoded on side A- (Low order portion)"
        ::= { vbrAtmSpvcEntry 36 }

vbrAtmSpvcStatsInOdometerCellCountHiB OBJECT-TYPE
        SYNTAX Integer32
        MAX-ACCESS read-only
        STATUS current
        DESCRIPTION "Valid Cells received on  B - (High order portion)"
        ::= { vbrAtmSpvcEntry 37 }

vbrAtmSpvcStatsInOdometerCellCountLoB OBJECT-TYPE
        SYNTAX Integer32
        MAX-ACCESS read-only
        STATUS current
        DESCRIPTION "Valid Cells received on  B - (Low order portion)"
        ::= { vbrAtmSpvcEntry 38 }

vbrAtmSpvcStatsOutOdometerCellCountHiB OBJECT-TYPE
        SYNTAX Integer32
        MAX-ACCESS read-only
        STATUS current
        DESCRIPTION "Valid Cells transmitted on B -(High order portion)"
        ::= { vbrAtmSpvcEntry 39 }

vbrAtmSpvcStatsOutOdometerCellCountLoB OBJECT-TYPE
        SYNTAX Integer32
        MAX-ACCESS read-only
        STATUS current
        DESCRIPTION "Valid Cells transmitted on B -(Low order portion)"
        ::= { vbrAtmSpvcEntry 40 }

vbrAtmSpvcStatsOdometerTimer OBJECT-TYPE
        SYNTAX Integer32
        MAX-ACCESS read-only
        STATUS current
        DESCRIPTION "Number of seconds since odometer was reset."
        ::= { vbrAtmSpvcEntry 41 }

vbrAtmSpvcStatsOdometerReset OBJECT-TYPE
        SYNTAX INTEGER {
                reset(1)
           }
        MAX-ACCESS read-write
        STATUS current
        DESCRIPTION "Odometer reset button."
        ::= { vbrAtmSpvcEntry 42 }

vbrAtmSpvcStatsCellsDroppedB OBJECT-TYPE
                SYNTAX Integer32
                MAX-ACCESS read-only
                STATUS current
                DESCRIPTION "Cells Dropped on the Incoming side of B"
                ::= { vbrAtmSpvcEntry 43 }

vbrAtmSpvcStatsCellsTaggedB OBJECT-TYPE
                SYNTAX Integer32
                MAX-ACCESS read-only
                STATUS current
                DESCRIPTION "Cells Tagged on the Incoming side of B"
                ::= { vbrAtmSpvcEntry 44 }


vbrAtmSpvcVUNIB OBJECT-TYPE
        SYNTAX INTEGER (0..255)
        MAX-ACCESS read-write
        STATUS current
        DESCRIPTION "VUNI to associate the Egress part of the
            B2A connection ."
        DEFVAL { 0 }
        ::= { vbrAtmSpvcEntry 45 }


vbrAtmSpvcTrafficShapingA2B   OBJECT-TYPE
        SYNTAX INTEGER {
                        disabled(1),
                        enabled(2)
                          }
        MAX-ACCESS read-write
        STATUS current
        DESCRIPTION "Traffic Shaping Support in the A2B direction."
        DEFVAL { disabled }
        ::= { vbrAtmSpvcEntry 46 }

vbrAtmSpvcPriority OBJECT-TYPE
        SYNTAX INTEGER  {
                priority-1(1),
                priority-2(2),
                priority-3(3),
                priority-4(4)
                }
        MAX-ACCESS read-write
        STATUS current
        DESCRIPTION "Priority of SPVC - priority-1 being highest priority ."
        DEFVAL { priority-1 }
        ::= { vbrAtmSpvcEntry 47 }




aal2TrunkConfigTable  OBJECT-TYPE
                SYNTAX SEQUENCE OF Aal2TrunkConfigEntry
                MAX-ACCESS not-accessible
                STATUS current
                DESCRIPTION "Table of terminal emulation to ATM network 
                        IWF connections "
                ::= { connectionConfig 36 }



aal2TrunkConfigEntry  OBJECT-TYPE
                SYNTAX Aal2TrunkConfigEntry
                MAX-ACCESS not-accessible
                STATUS current
                DESCRIPTION "Row definition of terminal emulation to ATM 
                network IWF connections"
                INDEX {  aal2TrunkConfigIf,
                        aal2TrunkConfigVpi, aal2TrunkConfigVci }
                ::= { aal2TrunkConfigTable 1 }

Aal2TrunkConfigEntry ::= SEQUENCE {
                aal2TrunkConfigIf                IntfIndex,
                aal2TrunkConfigVpi               INTEGER,
                aal2TrunkConfigVci               INTEGER,
                aal2TrunkConfigServiceType       INTEGER,
                aal2TrunkConfigPeakCellRateIgr   Integer32,
                aal2TrunkConfigSusCellRateIgr    Integer32,
                aal2TrunkConfigMaxBurstSizeIgr   Integer32,
                aal2TrunkConfigPeakCellRateEgr   Integer32,
                aal2TrunkConfigSusCellRateEgr    Integer32,
                aal2TrunkConfigMaxBurstSizeEgr   Integer32,
                aal2TrunkConfigFlow              INTEGER,
                aal2TrunkConfigRowStatus         RowStatus,
                aal2TrunkConfigConnectionStatus  INTEGER,
                aal2TrunkConfigViB               INTEGER,
                aal2TrunkConfigCnfrmTypeB2A      INTEGER,

                aal2TrunkConfigVUNIB             INTEGER,

                aal2TrunkAvailBwIgr              INTEGER,
                aal2TrunkAvailBwEgr              INTEGER,
                aal2TrunkGR303                   INTEGER,
                aal2TrunkConfigOamStatus         INTEGER,
                aal2TrunkConnFailureCauseB       AtmConnFailureCause,
                aal2TrunkCuTimer                 INTEGER
                }

aal2TrunkConfigIf OBJECT-TYPE
                SYNTAX IntfIndex
                MAX-ACCESS not-accessible
                STATUS current
                DESCRIPTION "Interface Id of the Atm Side of the Aal2 Trunk."
                ::= { aal2TrunkConfigEntry 1 }

aal2TrunkConfigVpi OBJECT-TYPE
                SYNTAX INTEGER (0..4095)
                MAX-ACCESS not-accessible
                STATUS current
                DESCRIPTION "VPI value for Atm side , the atm side, 
                        of a atm trunk connection.  
                        Valid range is a number between 0 and 4095."
                ::= { aal2TrunkConfigEntry 2 }

aal2TrunkConfigVci OBJECT-TYPE
                SYNTAX INTEGER (0..65535)
                MAX-ACCESS not-accessible
                STATUS current
                DESCRIPTION "VCI value for the atm side, of a variable
                        bit rate-atm PVC VCC connection.  
                        Valid range is a number between 0 and 65535."
                ::= { aal2TrunkConfigEntry 3 }

aal2TrunkConfigServiceType OBJECT-TYPE
                SYNTAX INTEGER {
                                cbr-1(1),
                                cbr-2(2),
                                cbr-3(3),
                                cbr-4(4),
                                ubr(5),
                                vbr-nrt2(6),
                                vbr-nrt1(7),
                                vbr-rt2(8),
                                vbr-rt1(9),
                                vbr-express(10)
                                }
                MAX-ACCESS read-write
                STATUS current
                DESCRIPTION "Service/Queue types supported for Aal2 Trunk 
                             connections.When using Vbr/Ubr type service
                             type oversubscription will have to be taken into 
                             account for which nature of traffic going over the
                             Trunk should be known before hand "
                DEFVAL { cbr-1 }
                ::= { aal2TrunkConfigEntry 4 }

aal2TrunkConfigPeakCellRateIgr        OBJECT-TYPE
                SYNTAX Integer32
                MAX-ACCESS read-write
                STATUS current
                DESCRIPTION "peak cell rate - atm side inp, in cell per 
                        second"
                DEFVAL { 1 }
                ::= { aal2TrunkConfigEntry 5 }
 
aal2TrunkConfigSusCellRateIgr OBJECT-TYPE
                SYNTAX Integer32
                MAX-ACCESS read-write
                STATUS current
                DESCRIPTION "sustained rate - atm side inp, in cell per 
                        second"
                DEFVAL { 1 }
                ::= { aal2TrunkConfigEntry 6 }
 
aal2TrunkConfigMaxBurstSizeIgr        OBJECT-TYPE
                SYNTAX Integer32
                MAX-ACCESS read-write
                STATUS current
                DESCRIPTION "maximum burst size - atm side inp, in cells"
                DEFVAL { 1 }
                ::= { aal2TrunkConfigEntry 7 }
 
aal2TrunkConfigPeakCellRateEgr        OBJECT-TYPE
                SYNTAX Integer32
                MAX-ACCESS read-write
                STATUS current
                DESCRIPTION "peak rate - atm side output, in cell per second."
                DEFVAL { 1 }
                ::= { aal2TrunkConfigEntry 8 }
 
aal2TrunkConfigSusCellRateEgr OBJECT-TYPE
                SYNTAX Integer32
                MAX-ACCESS read-write
                STATUS current
                DESCRIPTION "sustained rate - atm side output,in cell per second."
                DEFVAL { 1 }
                ::= { aal2TrunkConfigEntry 9 }
 
aal2TrunkConfigMaxBurstSizeEgr        OBJECT-TYPE
                SYNTAX Integer32
                MAX-ACCESS read-write
                STATUS current
                DESCRIPTION "maximum burst size - atm side output, in cells."
                DEFVAL { 1 }
                ::= { aal2TrunkConfigEntry 10 }

aal2TrunkConfigFlow OBJECT-TYPE 
                SYNTAX INTEGER {
                                duplex(1)
                                }
                MAX-ACCESS read-write
                STATUS current
                DESCRIPTION "Flow type"
                DEFVAL { duplex }
                  ::= { aal2TrunkConfigEntry 11 }

aal2TrunkConfigRowStatus OBJECT-TYPE
                SYNTAX RowStatus
                MAX-ACCESS read-write
                STATUS current
                DESCRIPTION "row status"
                ::= { aal2TrunkConfigEntry 12 }

aal2TrunkConfigConnectionStatus OBJECT-TYPE
                SYNTAX INTEGER {
                                active(1),
                                inactive(2),
                                inactiveA2B-B2A(3),
                                inactiveA2B(4),
                                inactiveB2A(5)
                                }
                MAX-ACCESS read-only
                STATUS current
                DESCRIPTION "Indicates the current connections status.
                        Active:  All interfaces through which the 
                        connection is going are in service.
                        Inactive:  One of the end interfaces of the 
                        connection is not in service.
                        The rest of the states apply to connections going
                        through resource interfaces like DSP2 and FEC.  These
                        interfaces are dynamically allocated .  
                        InactiveA2B-B2A:  Both the A2B and B2A resource
                        interfaces are not in service.
                        InactiveA2B:  The A2B resource interface is not in 
                        service.
                        InactiveB2A:  The B2A resource interface is not in 
                        service.
                        If an end interface and the resource interfaces 
                        are out of service, the status will be inactive 
                        because the end interfaces take priority."
                DEFVAL { inactive }
                ::= { aal2TrunkConfigEntry 13 }

aal2TrunkConfigViB OBJECT-TYPE
                SYNTAX INTEGER (0..1024)
                MAX-ACCESS read-write
                STATUS current
                DESCRIPTION "VI to associate the Egress part of the
                        A2B connection ." 
                DEFVAL { 0 }
                ::= { aal2TrunkConfigEntry 14 }


aal2TrunkConfigCnfrmTypeB2A    OBJECT-TYPE
                SYNTAX INTEGER { 
                                best-effort(1),
                                one-bucket-notag-0plus1(2),
                                two-bucket-notag-0plus1-0plus1(3),
                                two-bucket-notag-0plus1-0(4),
                                two-bucket-tag-0plus1-0(5),
                                best-effort-tag(6)
                               }
                MAX-ACCESS read-write
                STATUS current
                DESCRIPTION "The following is the description of this field
                        This will be used in conjunction with the
                        service type field to get the correct
                        traffic behaviour. In the conformances the the 0 or 
                        0plus1 refers to the clp bit in the cells. 
                        If 0plus1 is the bucket reference then
                        the clp bit is ignored. If 0 is specified for 
                        the bucket then check only clp=0 cells.
                        1: Best Effort will try to send all cellsin a 
                        best effort way. This will follow the 
                        Aqueman Algorithm
                        2: one-bucket-notag-0plus1 will use 1 bucket
                        i.e is the PCR(0+1) bucket and drop all
                        cells in excess.
                        3: two-bucket-notag-0plus1-0plus1 uses 2 buckets.
                        The 2 buckets are pcr(0+1) and scr(0+1).
                        All cells conforming to both buckets will be
                        passed through. The rest will be dropped.
                        4: two-bucket-notag-0plus1-0 uses 2 buckets.
                        The 2 buckets are pcr(0+1) and scr(0) or 
                        pcr(0). Cells which conform to both buckets
                        are passed through. The rest are dropped.
                        5: two-bucket-tag-0plus1-0 uses 2 buckets.
                        The 2 buckets are pcr(0+1) and scr(0) or 
                        pcr(0). Cells which do not conform to the first
                        bucket are dropped. Cells which do not 
                        conform to the 2nd bucket are tagged.
                        6: best-effort-tag. Tag all cells and then
                        do a best effort.  "
                DEFVAL { best-effort }
                ::= { aal2TrunkConfigEntry 15 }


aal2TrunkConfigVUNIB OBJECT-TYPE
                  SYNTAX INTEGER (0..255)
                MAX-ACCESS read-write
                STATUS current
                DESCRIPTION "VUNI to associate the Egress part of the A2B connection ." 
                  DEFVAL { 0 }
                  ::= { aal2TrunkConfigEntry 16 }


aal2TrunkAvailBwIgr  OBJECT-TYPE
                SYNTAX Integer32
                MAX-ACCESS read-only
                STATUS current
                DESCRIPTION "The Avail Bandwidth for that interface in cells per sec."
                    DEFVAL { 0 }
                ::= { aal2TrunkConfigEntry 17 }

aal2TrunkAvailBwEgr  OBJECT-TYPE
                SYNTAX Integer32
                MAX-ACCESS read-only
                STATUS current
                    DESCRIPTION "The Avail Bandwidth for that interface in
                        cells per sec."
                DEFVAL { 0 }
                  ::= { aal2TrunkConfigEntry 18 }

aal2TrunkGR303 OBJECT-TYPE
                SYNTAX INTEGER  {
                                disabled(1),
                                enabled(2)
                                } 
                MAX-ACCESS read-write
                STATUS current
                DESCRIPTION "This flag is used to check if a GR303 Feature
                        is enabled for the trunk."
                DEFVAL { disabled }
                ::= { aal2TrunkConfigEntry 19 }
                
aal2TrunkConfigOamStatus OBJECT-TYPE
                SYNTAX INTEGER {
                                unsupp(1),
                                end-Pt(2),
                                end-Seg-Pt(3) 
                               }
                MAX-ACCESS read-write
                STATUS current  
                DESCRIPTION "Indicates the OAM monitoring status of side A.
                             The 2 possible states are:
                             Unsupp:  No monitoring enabled.
                             End-Pt:  Atm side is only an end point, therefore
                                it will respond to AIS/RDI.
                             End-Seg-Pt:  A side is both an end point and a
                                segment point. "
                DEFVAL { unsupp }
                ::= { aal2TrunkConfigEntry 20 } 

aal2TrunkConnFailureCauseB    OBJECT-TYPE
                SYNTAX AtmConnFailureCause
                MAX-ACCESS read-only
                STATUS current
                DESCRIPTION "connection status reason code"
                ::= { aal2TrunkConfigEntry 21 }

aal2TrunkCuTimer  OBJECT-TYPE
                SYNTAX INTEGER (0..8)
                MAX-ACCESS read-write
                STATUS current
                DESCRIPTION "CuTimer represents 'combined use timer', 
                             is set to zero such that every ATM cell
                             transmitted contains one, and only one, 
                             AAL2 packet, and the first octet of the AAL2
                             packet header follows immediately after 
                             the Start Field in the ATM cell payload. If the
                             AAL2 packet payload is less than 44 octets, 
                             the remainder of the ATM cell payload
                             following the end of the AAL2 packet shall be 
                             filled with zeros as padding.
                             Each  increment of CuTimer means 5ms more to wait.
                             And cuTimer default value 4 means to wait 20ms
                             before the ATM cell is sent out."
                 DEFVAL { 4 }
                 ::= { aal2TrunkConfigEntry 22 }

--
-- gr303Aal2PvcVccTable
--
gr303Aal2PvcVccTable OBJECT-TYPE
                SYNTAX SEQUENCE OF Gr303Aal2PvcVccEntry
                MAX-ACCESS not-accessible
                STATUS current
                DESCRIPTION "Table of Gr303 to AAL2 Cid monitor VCCs"

                ::= { connectionConfig 37 }

gr303Aal2PvcVccEntry OBJECT-TYPE
                SYNTAX Gr303Aal2PvcVccEntry
                MAX-ACCESS not-accessible
                STATUS current
                DESCRIPTION "Row definition of circuit emulation to atm
                              connections."
                INDEX { gr303Aal2PvcVccGr303IgId,  gr303Aal2PvcVccGr303CallRef,
                gr303Aal2PvcVccIfB, gr303Aal2PvcVccVpiB, 
                gr303Aal2PvcVccVciB, gr303Aal2PvcVccAal2Cid}
                ::= { gr303Aal2PvcVccTable 1 }

Gr303Aal2PvcVccEntry ::= SEQUENCE {
                             gr303Aal2PvcVccGr303IgId                 INTEGER,
                             gr303Aal2PvcVccGr303CallRef        INTEGER,
                             gr303Aal2PvcVccIfB                        IntfIndex,
                             gr303Aal2PvcVccVpiB                  INTEGER,
                             gr303Aal2PvcVccVciB                  INTEGER,
                             gr303Aal2PvcVccAal2Cid                INTEGER,
                             gr303Aal2PvcVccRowStatus                RowStatus,
                 gr303Aal2PvcVccVoiceEncodingProfile INTEGER,
                 gr303Aal2PvcVccVoiceCompression INTEGER,
                 gr303Aal2PvcVccSilenceDetection INTEGER,
                 gr303Aal2PvcVccEchoCancellation INTEGER,
                 gr303Aal2PvcVccCngToneDetection INTEGER,
                 gr303Aal2PvcVccCodingTranslation INTEGER,
                             gr303Aal2PvcVccConnectionStatus        INTEGER,
                 gr303Aal2PvcVccAltLineType         INTEGER
                             }

gr303Aal2PvcVccGr303IgId OBJECT-TYPE
                SYNTAX INTEGER (0..84)
                MAX-ACCESS not-accessible
                STATUS current
                DESCRIPTION "GR303 interface group id on the GR303 side of the
        connection"
                ::= { gr303Aal2PvcVccEntry 1 }

gr303Aal2PvcVccGr303CallRef OBJECT-TYPE
                SYNTAX INTEGER (1..2048)
                MAX-ACCESS not-accessible
                STATUS current
                DESCRIPTION "The call reference value to be used in the signaling
                     packets on the GR303 interface for the connection on 
                     the AAL2CID corresponding to this connection"
                ::= { gr303Aal2PvcVccEntry 2 }

gr303Aal2PvcVccIfB OBJECT-TYPE
                SYNTAX IntfIndex
                MAX-ACCESS not-accessible
                STATUS current
                DESCRIPTION "Interface index for side B, the atm side, of a 
                             circuit emulation-atm PVC VCC connection.  Number 
                             value is interpreted as an interface of the form, 
                             SSPPCCC, where SS is the card slot, PP is the port
                 number, and CCC is the channel number."
                ::= { gr303Aal2PvcVccEntry 3 }

gr303Aal2PvcVccVpiB OBJECT-TYPE
                SYNTAX INTEGER (0..4095)
                MAX-ACCESS not-accessible
                STATUS current
                DESCRIPTION "VPI value for side B, the atm side,  of a
                             circuit emulation-atm PVC VCC connection.  Valid 
                             range is a number between 0 and 4095."
                ::= { gr303Aal2PvcVccEntry 4 }

gr303Aal2PvcVccVciB OBJECT-TYPE
                SYNTAX INTEGER (0..65535)
                MAX-ACCESS not-accessible
                STATUS current
                DESCRIPTION "VCI value for side B, the atm side,  of a
                             circuit emulation-atm PVC VCC connection.  Valid 
                             range is a number between 0 and 65535."
                ::= { gr303Aal2PvcVccEntry 5 }

gr303Aal2PvcVccAal2Cid OBJECT-TYPE
                SYNTAX INTEGER (0..255)
                MAX-ACCESS not-accessible
                STATUS current
                DESCRIPTION "Aal2 Cid Used to pack ce chan in an
                        Atm Trunk. This value will be unique
                        per Atm Trunk. This field will be applicable
                        when Aal type is chosen to be Standard Aal2."
                DEFVAL { 0 }
                ::= { gr303Aal2PvcVccEntry 6 }

gr303Aal2PvcVccRowStatus OBJECT-TYPE
                SYNTAX RowStatus
                MAX-ACCESS read-write
                STATUS current
                DESCRIPTION "row status"
                ::= { gr303Aal2PvcVccEntry 7 }

gr303Aal2PvcVccVoiceEncodingProfile OBJECT-TYPE
                SYNTAX INTEGER  {
                                itut-profile-1(1),
                                itut-profile-3(3),
                                af-profile-6(6),
                                itut-profile-7(7),
                                af-profile-7(8),
                                af-profile-8(9),
                                af-profile-9(10),
                                af-profile-10(11),
                                af-profile-12(12),
                                custom(256),
                                default (257)
                                }
                MAX-ACCESS read-write
                STATUS current
                DESCRIPTION "Profile for use by voice/voiceband data.
                     Profile-3 and Profile-7 are ITU-T predefined profiles
                     which specify the voice compression and silence removal
                     algorithms. If custom profile is chosen all DSP specific 
                     parameters have to be specified by the user. If default
                     profile is chosen all parameters on the  AAL2
                     trunk, containing this CID, will be used." 
                DEFVAL { itut-profile-1 }
                ::= { gr303Aal2PvcVccEntry 8 }

gr303Aal2PvcVccVoiceCompression OBJECT-TYPE
                SYNTAX INTEGER  {
                                none(1),
                                g726-16k(2),
                                g726-24k(3),
                                g726-32k(4),
                                g726-40k(5),
                                g729a-8k(6)
                                }
                MAX-ACCESS read-write
                STATUS current
                DESCRIPTION "Voice Compression Algorithm"
                DEFVAL { none }
                ::= { gr303Aal2PvcVccEntry 9 }

gr303Aal2PvcVccSilenceDetection OBJECT-TYPE
                SYNTAX INTEGER  {
                                 disabled(1),
                                 enabled(2)
                                }
                MAX-ACCESS read-write
                STATUS current
                DESCRIPTION "silence detection off/on"
                DEFVAL { disabled }
                ::= { gr303Aal2PvcVccEntry 10 }

gr303Aal2PvcVccEchoCancellation OBJECT-TYPE
                SYNTAX INTEGER  {
                                 none(1),
                                 g165-nearEnd(2),
                                 g168(3)
                                }
                MAX-ACCESS read-write
                STATUS current
                DESCRIPTION "Echo Cancellation Algorithm"
                DEFVAL { none }
                ::= { gr303Aal2PvcVccEntry 11 }


gr303Aal2PvcVccCngToneDetection OBJECT-TYPE
                SYNTAX INTEGER  {
                                 disabled(1),
                                 bypass(2)
                                }
                MAX-ACCESS read-write
                STATUS current
                DESCRIPTION "Calling Tone Detection Algorithm"
                DEFVAL { disabled }
                ::= { gr303Aal2PvcVccEntry 12 }

gr303Aal2PvcVccCodingTranslation OBJECT-TYPE
                SYNTAX INTEGER  {
                                 none(1),
                                 muLaw2muLaw(2),
                                 aLaw2aLaw(3),
                                 muLaw2aLaw(4),
                                 aLaw2muLaw(5)
                                }
                MAX-ACCESS read-write
                STATUS current
                DESCRIPTION "Coding rule translation type."
                DEFVAL { none }
                ::= { gr303Aal2PvcVccEntry 13 }


gr303Aal2PvcVccConnectionStatus OBJECT-TYPE
                SYNTAX INTEGER {
                                active(1),
                                inactive(2)
                               }
                MAX-ACCESS read-only
                STATUS current
                DESCRIPTION "Indicates the current connections status.
                             Active:  All interfaces through which the 
                                      connection is going are in service.
                             Inactive:  One of the end interfaces of the 
                                        connection is not in service.

                             The rest of the states apply to connections going
                             through resource interfaces like DSP2 and FEC.  These
                             interfaces are dynamically allocated.

                             If an end interface and the resource interfaces 
                             are out of service, the status will be inactive 
                             because the end interfaces take priority."
                DEFVAL { inactive }
                ::= { gr303Aal2PvcVccEntry 14 }

gr303Aal2PvcVccAltLineType OBJECT-TYPE
                SYNTAX INTEGER {
                                alt-LoopReverseBattery(1),
                alt-groundStart(9),
                                alt-loopStart (13),
                                alt-winkStart (29)
                               }
                MAX-ACCESS read-write
                STATUS current
                DESCRIPTION "Analog Line Termination Line Type on the subscriber side. 
        The ABCD bit codes for diffterent signal types depend on 
        the analog line type. The analog type can be overwritten by an EOC 
        message from the IDT"
                DEFVAL { alt-loopStart }
                ::= { gr303Aal2PvcVccEntry 15 }


--
-- atmAtmSpvcVpcTable - for SPVP support
--
atmAtmSpvcVpcTable OBJECT-TYPE
        SYNTAX SEQUENCE OF AtmAtmSpvcVpcEntry
        MAX-ACCESS not-accessible
        STATUS current
        DESCRIPTION "Table of SPVC ATM virtual path connections."
        ::= { connectionConfig 38 }

atmAtmSpvcVpcEntry OBJECT-TYPE
        SYNTAX AtmAtmSpvcVpcEntry
        MAX-ACCESS not-accessible
        STATUS current
        DESCRIPTION "Row definition of ATM SPVC VPC connections."
        INDEX { spvcAddrIfA, atmAtmSpvcVpcVpiA, atmAtmSpvcVpcRemoteAtmPortAddr }
        ::= { atmAtmSpvcVpcTable 1 }

AtmAtmSpvcVpcEntry ::= SEQUENCE {
        atmAtmSpvcVpcVpiA                          INTEGER,
        atmAtmSpvcVpcRemoteAtmPortAddr             OCTET STRING,
        atmAtmSpvcVpcIfB                           IntfIndex,
        atmAtmSpvcVpcVpiB                          INTEGER,
        atmAtmSpvcVpcServiceTypeA2B                INTEGER,
        atmAtmSpvcVpcSarTypeA2B                    INTEGER,
        atmAtmSpvcVpcPeakCellRateA2B               Integer32,
        atmAtmSpvcVpcSusCellRateA2B                Integer32,
        atmAtmSpvcVpcMaxBurstSizeA2B               Integer32,
        atmAtmSpvcVpcFrwdErrCorrectionA2B          INTEGER,
        atmAtmSpvcVpcServiceTypeB2A                INTEGER,
        atmAtmSpvcVpcSarTypeB2A                    INTEGER,
        atmAtmSpvcVpcPeakCellRateB2A               Integer32,
        atmAtmSpvcVpcSusCellRateB2A                Integer32,
        atmAtmSpvcVpcMaxBurstSizeB2A               Integer32,
        atmAtmSpvcVpcFrwdErrCorrectionB2A          INTEGER,
        atmAtmSpvcVpcFlow                          INTEGER,
        atmAtmSpvcVpcType                          INTEGER,
        atmAtmSpvcVpcConnType                      INTEGER,
        atmAtmSpvcVpcLeafReference                 INTEGER,
        atmAtmSpvcVpcOperStatus                    INTEGER,
        atmAtmSpvcVpcRowStatus                     RowStatus,
        atmAtmSpvcVpcRemoteSelectType              INTEGER,
        atmAtmSpvcVpcRemoteVpi                     INTEGER,
        atmAtmSpvcVpcRetryInterval                 INTEGER,
        atmAtmSpvcVpcRetryLimit                    INTEGER,
        atmAtmSpvcVpcRestart                       INTEGER,
        atmAtmSpvcVpcRetryFailure                  Integer32,
        atmAtmSpvcVpcReleaseCause                  INTEGER,
        atmAtmSpvcVpcReleaseDiag                   OCTET STRING,
        atmAtmSpvcVpcRelease                       INTEGER,
        atmAtmSpvcVpcStatsInCellCountHiA           Integer32,
        atmAtmSpvcVpcStatsInCellCountLoA           Integer32,
        atmAtmSpvcVpcStatsOutCellCountHiA          Integer32,
        atmAtmSpvcVpcStatsOutCellCountLoA          Integer32,
        atmAtmSpvcVpcStatsInCellCountHiB           Integer32,
        atmAtmSpvcVpcStatsInCellCountLoB           Integer32,
        atmAtmSpvcVpcStatsOutCellCountHiB          Integer32,
        atmAtmSpvcVpcStatsOutCellCountLoB          Integer32,
        atmAtmSpvcVpcStatsTimer                    Integer32,
        atmAtmSpvcVpcStatsFrwdErrCrrctnRateA2B     INTEGER,
        atmAtmSpvcVpcStatsFrwdErrCrrctnRateB2A     INTEGER,
        atmAtmSpvcVpcStatsInOdometerCellCountHiA   Integer32,
        atmAtmSpvcVpcStatsInOdometerCellCountLoA   Integer32,
        atmAtmSpvcVpcStatsOutOdometerCellCountHiA  Integer32,
        atmAtmSpvcVpcStatsOutOdometerCellCountLoA  Integer32,
        atmAtmSpvcVpcStatsInOdometerCellCountHiB   Integer32,
        atmAtmSpvcVpcStatsInOdometerCellCountLoB   Integer32,
        atmAtmSpvcVpcStatsOutOdometerCellCountHiB  Integer32,
        atmAtmSpvcVpcStatsOutOdometerCellCountLoB  Integer32,
        atmAtmSpvcVpcStatsOdometerTimer            Integer32,
        atmAtmSpvcVpcStatsOdometerReset            INTEGER,
        atmAtmSpvcVpcViA                           INTEGER,
        atmAtmSpvcVpcViB                           INTEGER,
        atmAtmSpvcVpcStatsCellsDroppedA            Integer32,
        atmAtmSpvcVpcStatsCellsTaggedA             Integer32,
        atmAtmSpvcVpcStatsCellsDroppedB            Integer32,
        atmAtmSpvcVpcStatsCellsTaggedB             Integer32

        ,atmAtmSpvcVpcVUNIA                        INTEGER,
        atmAtmSpvcVpcVUNIB                         INTEGER,

        atmAtmSpvcVpcTrafficShapingA2B             INTEGER,
        atmAtmSpvcVpcTrafficShapingB2A             INTEGER,
        atmAtmSpvcVpcPriority                    INTEGER
        }

atmAtmSpvcVpcVpiA    OBJECT-TYPE
        SYNTAX INTEGER (0..4095)
        MAX-ACCESS not-accessible
        STATUS current
        DESCRIPTION "VPI value for side A of an ATM SPVC VPC connection.
                 Valid range is a number between 0 and 4095."
        ::= { atmAtmSpvcVpcEntry 1 }

atmAtmSpvcVpcRemoteAtmPortAddr OBJECT-TYPE
        SYNTAX OCTET STRING (SIZE(1..20))
        MAX-ACCESS not-accessible
        STATUS current
        DESCRIPTION "Remote ATM port NSAP address, not meaningful if 
                 passive type of connection."
        ::= { atmAtmSpvcVpcEntry 2 }

atmAtmSpvcVpcIfB    OBJECT-TYPE
        SYNTAX IntfIndex
        MAX-ACCESS read-only
        STATUS current
        DESCRIPTION "Interface index for side B of an ATM SPVC VPC 
                 connection.  Number value is interpreted as an 
                 interface of the form, SSPPCCC, where SS is the 
                 card slot, PP is the port number, and CCC is the 
                 path number."
        ::= { atmAtmSpvcVpcEntry 3 }

atmAtmSpvcVpcVpiB    OBJECT-TYPE
        SYNTAX INTEGER (0..4095)
        MAX-ACCESS read-only
        STATUS current
        DESCRIPTION "VPI value for side B of an ATM SPVC VPC connection.
                 Valid range is a number between 0 and 4095."
        ::= { atmAtmSpvcVpcEntry 4 }

atmAtmSpvcVpcServiceTypeA2B OBJECT-TYPE
        SYNTAX INTEGER  {
                ubr(1),
                vbr-nrt2(2),
                vbr-nrt1(3),
                vbr-rt2(4),
                vbr-rt1(5),
                vbr-express(6),
                cbr4(7),
                cbr3(8),
                cbr2(9)
                }
        MAX-ACCESS read-write
        STATUS current
        DESCRIPTION "Service type, ATM port."
        DEFVAL { ubr }
        ::= { atmAtmSpvcVpcEntry 5 }

atmAtmSpvcVpcSarTypeA2B OBJECT-TYPE
        SYNTAX INTEGER  {
                aal5(1),
                aal3-4(2),
                aal2(3),
                aal1(4),
                null(5)
                }
        MAX-ACCESS read-write
        STATUS current
        DESCRIPTION "SAR type used in ATM adaption, ATM port."
        DEFVAL { null }
        ::= { atmAtmSpvcVpcEntry 6 }

atmAtmSpvcVpcPeakCellRateA2B OBJECT-TYPE
        SYNTAX Integer32
        MAX-ACCESS read-write
        STATUS current
        DESCRIPTION "Peak cell rate - side A, ATM port, in cells per
                 second."
        DEFVAL { 1 }
        ::= { atmAtmSpvcVpcEntry 7 }

atmAtmSpvcVpcSusCellRateA2B OBJECT-TYPE
        SYNTAX Integer32
        MAX-ACCESS read-write
        STATUS current
        DESCRIPTION "Sustained cell rate - side A, ATM port, in cells
                 per second."
        DEFVAL { 1 }
        ::= { atmAtmSpvcVpcEntry 8 }

atmAtmSpvcVpcMaxBurstSizeA2B OBJECT-TYPE
        SYNTAX Integer32
        MAX-ACCESS read-write
        STATUS current
        DESCRIPTION "Maximum burst size - side A, ATM port, in cells
                 per second."
        DEFVAL { 1 }
        ::= { atmAtmSpvcVpcEntry 9 }

atmAtmSpvcVpcFrwdErrCorrectionA2B OBJECT-TYPE
        SYNTAX INTEGER {
                none(1),
                eighthRate(2),
                quarterRate(3),
                halfRate(4),
                autoHiQ(5),
                auto(6),
                autoLoQ(7)
                   }
        MAX-ACCESS read-write
        STATUS current
        DESCRIPTION "Forward error correction scheme, ATM port side."
        DEFVAL { none }
        ::= { atmAtmSpvcVpcEntry 10 }

atmAtmSpvcVpcServiceTypeB2A OBJECT-TYPE
        SYNTAX INTEGER  {
                ubr(1),
                vbr-nrt2(2),
                vbr-nrt1(3),
                vbr-rt2(4),
                vbr-rt1(5),
                vbr-express(6),
                cbr4(7),
                cbr3(8),
                cbr2(9)
                }
        MAX-ACCESS read-write
        STATUS current
        DESCRIPTION "Service type, ATM trunk side."
        DEFVAL { ubr }
        ::= { atmAtmSpvcVpcEntry 11 }

atmAtmSpvcVpcSarTypeB2A OBJECT-TYPE
        SYNTAX INTEGER  {
                aal5(1),
                aal3-4(2),
                aal2(3),
                aal1(4),
                null(5)
                }
        MAX-ACCESS read-write
        STATUS current
        DESCRIPTION "SAR type used in ATM adaption, ATM trunk side."
        DEFVAL { null }
        ::= { atmAtmSpvcVpcEntry 12 }

atmAtmSpvcVpcPeakCellRateB2A OBJECT-TYPE
        SYNTAX Integer32
        MAX-ACCESS read-write
        STATUS current
        DESCRIPTION "Peak cell rate - side B, ATM trunk, in cells per
                 second."
        DEFVAL { 1 }
        ::= { atmAtmSpvcVpcEntry 13 }

atmAtmSpvcVpcSusCellRateB2A    OBJECT-TYPE
        SYNTAX Integer32
        MAX-ACCESS read-write
        STATUS current
        DESCRIPTION "Sustained cell rate - side B, ATM trunk, in cells
                 per second."
        DEFVAL { 1 }
        ::= { atmAtmSpvcVpcEntry 14 }

atmAtmSpvcVpcMaxBurstSizeB2A OBJECT-TYPE
        SYNTAX Integer32
        MAX-ACCESS read-write
        STATUS current
        DESCRIPTION "Maximum burst size - side A, ATM trunk, in cells
                 per second."
        DEFVAL { 1 }
        ::= { atmAtmSpvcVpcEntry 15 }

atmAtmSpvcVpcFrwdErrCorrectionB2A OBJECT-TYPE
        SYNTAX INTEGER {
                none(1),
                eighthRate(2),
                quarterRate(3),
                halfRate(4),
                autoHiQ(5),
                auto(6),
                autoLoQ(7)
                   }
        MAX-ACCESS read-write
        STATUS current
        DESCRIPTION "Forward error correction scheme, ATM trunk side."
        DEFVAL { none }
        ::= { atmAtmSpvcVpcEntry 16 }

atmAtmSpvcVpcFlow    OBJECT-TYPE
        SYNTAX INTEGER    {
                duplex(1),
                simplexA2B(2),
                pointToMultipointA2B(3),
                simplexB2A(4),
                pointToMultipointB2A(5)
                }
        MAX-ACCESS read-write
        STATUS current
        DESCRIPTION "Type of flow, pointToMultipointA2B is for future
                 support."
        DEFVAL { duplex }
        ::= { atmAtmSpvcVpcEntry 17 }

atmAtmSpvcVpcType    OBJECT-TYPE
        SYNTAX INTEGER  {
                nonsecured(1),
                secured(2)
                }
        MAX-ACCESS read-write
        STATUS current
        DESCRIPTION "Type of connection."
        DEFVAL { nonsecured }
        ::= { atmAtmSpvcVpcEntry 18 }

atmAtmSpvcVpcConnType OBJECT-TYPE
        SYNTAX INTEGER  {
                activeSvc(1),
                passiveSvc(2)
                }
        MAX-ACCESS read-write
        STATUS current
        DESCRIPTION "The type of connection:
                 activeSvc - attempt calls, whenever not 
                   established.
                 passiveSvc - accept calls."
        ::= { atmAtmSpvcVpcEntry 19 }

atmAtmSpvcVpcLeafReference OBJECT-TYPE
        SYNTAX INTEGER (1..65535)
        MAX-ACCESS read-only
        STATUS current
        DESCRIPTION "An arbitrary integer which serves to distinguish
                 the mulitple leaves attached to a root of a 
                 point-to-multipoint SPVC.  If point-to-point SPVC, 
                 the value should be 1."
        ::= { atmAtmSpvcVpcEntry 20 }

atmAtmSpvcVpcOperStatus OBJECT-TYPE
        SYNTAX INTEGER  {
                other(1),
                establishmentInProgress(2),
                connected(3),
                retriesExhausted(4),
                noAddressSupplied(5),
                lowerLayerDown(6),
                waitingForCall(7),
                waitingForRetryTimer(8)
                }
        MAX-ACCESS read-only
        STATUS current
        DESCRIPTION "The operation status of the connection:
                 other - none of the types specified below.
                 establishmentInProgress - connection is not 
                operational, but call attempts are ongoing.
                 connected - connection is currently operational.
                 retriesExhausted - retry limit has been reached 
                and call attempts have ceased.
                 noAddressSupplied - no remote address has been 
                configured, so no call attempts are initiated.
                 lowerLayerDown - SPVC handler is not operational."
        ::= { atmAtmSpvcVpcEntry 21 }

atmAtmSpvcVpcRowStatus OBJECT-TYPE
        SYNTAX RowStatus
        MAX-ACCESS read-write
        STATUS current
        DESCRIPTION "Used to create and delete a soft PVC.  When this
                 object is set to 'active', an attempt is made to 
                 set up the soft PVC.  When this object has the 
                 value 'active' and is set to another value, any 
                 setup or connection in-progress is released."
        ::= { atmAtmSpvcVpcEntry 22 }


atmAtmSpvcVpcRemoteSelectType OBJECT-TYPE
        SYNTAX INTEGER  {
                required(1),
                any(2)
                }
        MAX-ACCESS read-write
        STATUS current
        DESCRIPTION "Indicates whether the remote VPI values are to 
                 be used at the destination.  If 'any' is used, the 
                 destination switch will choose the VPI values. 
                 In such a case, once the SPVC is connected, the 
                 value of this object will change to 'required', 
                 such that the same VPI values will continue to 
                 be used even if the connection is torn down and 
                 re-established.  If the value 'required' is
                 specified, the values:  atmAtmSpvcVpcRemoteVpi and 
                 must be supplied and are used
                 at the destination."
        ::= { atmAtmSpvcVpcEntry 23 }

atmAtmSpvcVpcRemoteVpi OBJECT-TYPE
        SYNTAX INTEGER (0..4095)
        MAX-ACCESS read-write
        STATUS current
        DESCRIPTION "VPI value to be used at the destination of an 
                 ATM SPVC VPC connection.  Valid range is a number 
                 between 0 and 4095.  If atmAtmSpvcVpcRemoteSelectType 
                 is configured as 'any', then this value is not 
                 relevant."
        ::= { atmAtmSpvcVpcEntry 24 }

atmAtmSpvcVpcRetryInterval OBJECT-TYPE
        SYNTAX INTEGER (0..3600)
        MAX-ACCESS read-write
        STATUS current
        DESCRIPTION "The time to wait before attempting to establish 
                 the SVC after a previous failed call attempt.  A 
                 value of 0 indicates retries will be attempted immediately."
        ::= { atmAtmSpvcVpcEntry 25 }

atmAtmSpvcVpcRetryLimit OBJECT-TYPE
        SYNTAX INTEGER (0..65535)
        MAX-ACCESS read-write
        STATUS current
        DESCRIPTION "A maximum limit on how many retries should be 
                 attempted.  A value of 0 indicates no limit."
        ::= { atmAtmSpvcVpcEntry 26 }

atmAtmSpvcVpcRestart OBJECT-TYPE
        SYNTAX INTEGER  {
                restart(1),
                noop(2)
                }
        MAX-ACCESS read-write
        STATUS current
        DESCRIPTION "The active SVC is released, if necessary, and a 
                 new setup procedure is begun if 'restart', 
                 otherwise, noop."
        ::= { atmAtmSpvcVpcEntry 27 }

atmAtmSpvcVpcRetryFailure OBJECT-TYPE
        SYNTAX Integer32
        MAX-ACCESS read-only
        STATUS current
        DESCRIPTION "Indicates how many attempts to establish the 
                 connection have failed.  It it reset whenever a 
                 connection is successfully established or the SVC 
                 is restarted."
        ::= { atmAtmSpvcVpcEntry 28 }

atmAtmSpvcVpcReleaseCause OBJECT-TYPE
        SYNTAX INTEGER (1..127)
        MAX-ACCESS read-only
        STATUS current
        DESCRIPTION "CAUSE field value of the last RELEASE message 
                 received for this SVC."
        ::= { atmAtmSpvcVpcEntry 29 }

atmAtmSpvcVpcReleaseDiag OBJECT-TYPE
        SYNTAX OCTET STRING (SIZE(0..8))
        MAX-ACCESS read-only
        STATUS current
        DESCRIPTION "DIAGNOSTICS field value of the last RELEASE 
                 message received for this SVC."
        ::= { atmAtmSpvcVpcEntry 30 }


atmAtmSpvcVpcRelease OBJECT-TYPE
        SYNTAX INTEGER {
                release(1),
                noop(2)
                }
        MAX-ACCESS read-only
        STATUS current
        DESCRIPTION "Release the connnection established on the endpoint
                 and if the endpoint is Active, do not retry."
        ::= { atmAtmSpvcVpcEntry 31 }


atmAtmSpvcVpcStatsInCellCountHiA OBJECT-TYPE
        SYNTAX Integer32
        MAX-ACCESS read-only
        STATUS current
        DESCRIPTION "Valid Cells received on A - (High order portion)"
        ::= { atmAtmSpvcVpcEntry 32 }

atmAtmSpvcVpcStatsInCellCountLoA OBJECT-TYPE
        SYNTAX Integer32
        MAX-ACCESS read-only
        STATUS current
        DESCRIPTION "Valid Cells received on A - (Low order portion) "
        ::= { atmAtmSpvcVpcEntry 33 }

atmAtmSpvcVpcStatsOutCellCountHiA OBJECT-TYPE
        SYNTAX Integer32
        MAX-ACCESS read-only
        STATUS current
        DESCRIPTION "Valid cells transmitted on A -(High order portion)"
        ::= { atmAtmSpvcVpcEntry 34 }

atmAtmSpvcVpcStatsOutCellCountLoA OBJECT-TYPE
        SYNTAX Integer32
        MAX-ACCESS read-only
        STATUS current
        DESCRIPTION "Valid cells transmitted on A -(Low order portion)"
        ::= { atmAtmSpvcVpcEntry 35 }

atmAtmSpvcVpcStatsInCellCountHiB OBJECT-TYPE
        SYNTAX Integer32
        MAX-ACCESS read-only
        STATUS current
        DESCRIPTION "Valid Cells received on B - (High order portion)"
        ::= { atmAtmSpvcVpcEntry 36 }

atmAtmSpvcVpcStatsInCellCountLoB OBJECT-TYPE
        SYNTAX Integer32
        MAX-ACCESS read-only
        STATUS current
        DESCRIPTION "Valid Cells received on B - (Low order portion) "
        ::= { atmAtmSpvcVpcEntry 37 }

atmAtmSpvcVpcStatsOutCellCountHiB OBJECT-TYPE
        SYNTAX Integer32
        MAX-ACCESS read-only
        STATUS current
        DESCRIPTION "Valid cells transmitted on B -(High order portion)"
        ::= { atmAtmSpvcVpcEntry 38 }

atmAtmSpvcVpcStatsOutCellCountLoB OBJECT-TYPE
        SYNTAX Integer32
        MAX-ACCESS read-only
        STATUS current
        DESCRIPTION "Valid cells transmitted on B -(Low order portion)"
        ::= { atmAtmSpvcVpcEntry 39 }

atmAtmSpvcVpcStatsTimer OBJECT-TYPE
        SYNTAX Integer32
        MAX-ACCESS read-only
        STATUS current
        DESCRIPTION "Number of seconds stats have been collecting"
        ::= { atmAtmSpvcVpcEntry 40 }

atmAtmSpvcVpcStatsFrwdErrCrrctnRateA2B OBJECT-TYPE
        SYNTAX INTEGER {
                none(1),
                eighthRate(2),
                quarterRate(3),
                halfRate(4)
                   }
        MAX-ACCESS read-only
        STATUS current
        DESCRIPTION "Displays the Forward error correction rate being 
                 used by the FEC module in the A2B direction.  This
                 field is dynamic when Auto rates are selected.  In
                 other cases, it will display the rate set by the 
                 user."
        DEFVAL { none }
        ::= { atmAtmSpvcVpcEntry 41 }

atmAtmSpvcVpcStatsFrwdErrCrrctnRateB2A OBJECT-TYPE
        SYNTAX INTEGER {
                none(1),
                eighthRate(2),
                quarterRate(3),
                halfRate(4)
                   }
        MAX-ACCESS read-only
        STATUS current
        DESCRIPTION "Displays the Forward error correction rate being 
                 used by the FEC module in the B2A direction.  This
                 field is dynamic when Auto rates are selected.  In
                 other cases, it will display the rate set by the 
                 user."
        DEFVAL { none }
        ::= { atmAtmSpvcVpcEntry 42 }

atmAtmSpvcVpcStatsInOdometerCellCountHiA OBJECT-TYPE
        SYNTAX Integer32
        MAX-ACCESS read-only
        STATUS current
        DESCRIPTION "Valid cells received (Input Billing Count)"
        ::= { atmAtmSpvcVpcEntry 43 }

atmAtmSpvcVpcStatsInOdometerCellCountLoA OBJECT-TYPE
        SYNTAX Integer32
        MAX-ACCESS read-only
        STATUS current
        DESCRIPTION "Valid cells transmitted (Output Billing Count)"
        ::= { atmAtmSpvcVpcEntry 44 }

atmAtmSpvcVpcStatsOutOdometerCellCountHiA OBJECT-TYPE
        SYNTAX Integer32
        MAX-ACCESS read-only
        STATUS current
        DESCRIPTION "Valid cells transmitted (Output Billing Count)"
        ::= { atmAtmSpvcVpcEntry 45 }

atmAtmSpvcVpcStatsOutOdometerCellCountLoA OBJECT-TYPE
        SYNTAX Integer32
        MAX-ACCESS read-only
        STATUS current
        DESCRIPTION "Valid cells transmitted (Output Billing Count)"
        ::= { atmAtmSpvcVpcEntry 46 }

atmAtmSpvcVpcStatsInOdometerCellCountHiB OBJECT-TYPE
        SYNTAX Integer32
        MAX-ACCESS read-only
        STATUS current
        DESCRIPTION "Valid cells received (Input Billing Count)"
        ::= { atmAtmSpvcVpcEntry 47 }

atmAtmSpvcVpcStatsInOdometerCellCountLoB OBJECT-TYPE
        SYNTAX Integer32
        MAX-ACCESS read-only
        STATUS current
        DESCRIPTION "Valid cells transmitted (Output Billing Count)"
        ::= { atmAtmSpvcVpcEntry 48 }

atmAtmSpvcVpcStatsOutOdometerCellCountHiB OBJECT-TYPE
        SYNTAX Integer32
        MAX-ACCESS read-only
        STATUS current
        DESCRIPTION "Valid cells transmitted (Output Billing Count)"
        ::= { atmAtmSpvcVpcEntry 49 }

atmAtmSpvcVpcStatsOutOdometerCellCountLoB OBJECT-TYPE
        SYNTAX Integer32
        MAX-ACCESS read-only
        STATUS current
        DESCRIPTION "Valid cells transmitted (Output Billing Count)"
        ::= { atmAtmSpvcVpcEntry 50 }

atmAtmSpvcVpcStatsOdometerTimer OBJECT-TYPE
        SYNTAX Integer32
        MAX-ACCESS read-only
        STATUS current
        DESCRIPTION "Number of seconds since odometer was reset."
        ::= { atmAtmSpvcVpcEntry 51 }

atmAtmSpvcVpcStatsOdometerReset OBJECT-TYPE
        SYNTAX INTEGER {
                reset(1)
                   }
        MAX-ACCESS read-write
        STATUS current
        DESCRIPTION "Odometer reset button."
        ::= { atmAtmSpvcVpcEntry 52 }


atmAtmSpvcVpcViA   OBJECT-TYPE
        SYNTAX INTEGER (0..1024)
        MAX-ACCESS read-write
        STATUS current
        DESCRIPTION "VI to associate the Egress part of the B2A connection ."
            DEFVAL { 0 }
        ::= { atmAtmSpvcVpcEntry 53 }


atmAtmSpvcVpcViB   OBJECT-TYPE
        SYNTAX INTEGER (0..1024)
        MAX-ACCESS read-write
        STATUS current
        DESCRIPTION "VI to associate the Egress part of the A2B connection ."
        DEFVAL { 0 }
        ::= { atmAtmSpvcVpcEntry 54 }

atmAtmSpvcVpcStatsCellsDroppedA OBJECT-TYPE
                SYNTAX Integer32
                MAX-ACCESS read-only
                STATUS current
                DESCRIPTION "Cells Dropped on the Incoming side of A"
                ::= { atmAtmSpvcVpcEntry 55 }

atmAtmSpvcVpcStatsCellsTaggedA OBJECT-TYPE
                SYNTAX Integer32
                MAX-ACCESS read-only
                STATUS current
                DESCRIPTION "Cells Tagged on the Incoming side of A"
                ::= { atmAtmSpvcVpcEntry 56 }

atmAtmSpvcVpcStatsCellsDroppedB OBJECT-TYPE
                SYNTAX Integer32
                MAX-ACCESS read-only
                STATUS current
                DESCRIPTION "Cells Dropped on the Incoming side of B"
                ::= { atmAtmSpvcVpcEntry 57 }

atmAtmSpvcVpcStatsCellsTaggedB OBJECT-TYPE
                SYNTAX Integer32
                MAX-ACCESS read-only
                STATUS current
                DESCRIPTION "Cells Tagged on the Incoming side of B"
                ::= { atmAtmSpvcVpcEntry 58 }


atmAtmSpvcVpcVUNIA   OBJECT-TYPE
        SYNTAX INTEGER (0..255)
        MAX-ACCESS read-write
        STATUS current
        DESCRIPTION "VUNI to associate the Egress part of the B2A connection ."
            DEFVAL { 0 }
        ::= { atmAtmSpvcVpcEntry 59 }


atmAtmSpvcVpcVUNIB   OBJECT-TYPE
        SYNTAX INTEGER (0..255)
        MAX-ACCESS read-write
        STATUS current
        DESCRIPTION "VUNI to associate the Egress part of the A2B connection ."
        DEFVAL { 0 }
        ::= { atmAtmSpvcVpcEntry 60 }


atmAtmSpvcVpcTrafficShapingA2B     OBJECT-TYPE
        SYNTAX INTEGER {
                         disabled(1),
                         enabled(2)
                          }
        MAX-ACCESS read-write
        STATUS current
        DESCRIPTION "Traffic Shaping Support in the A2B direction."
        DEFVAL { disabled }
        ::= { atmAtmSpvcVpcEntry 61 }

atmAtmSpvcVpcTrafficShapingB2A     OBJECT-TYPE
        SYNTAX INTEGER {
                         disabled(1),
                         enabled(2)
                          }
        MAX-ACCESS read-write
        STATUS current
        DESCRIPTION "Traffic Shaping Support in the B2A direction."
        DEFVAL { disabled }
        ::= { atmAtmSpvcVpcEntry 62 }

atmAtmSpvcVpcPriority OBJECT-TYPE
        SYNTAX INTEGER  {
                priority-1(1),
                priority-2(2),
                priority-3(3),
                priority-4(4)
                }
        MAX-ACCESS read-write
        STATUS current
        DESCRIPTION "Priority of SPVC - priority-1 being highest priority ."
        DEFVAL { priority-1 }
        ::= { atmAtmSpvcVpcEntry 63 }

-- intfAtmPvcConnDisplayTable

intfAtmPvcConnDisplayTable         OBJECT-TYPE
                    SYNTAX SEQUENCE OF IntfAtmConnDisplayEntry
                    MAX-ACCESS not-accessible
                    STATUS current
                    DESCRIPTION "List of Pvc Connections on an Interface."
                    ::= { connectionConfig 39 }

intfAtmPvcConnDisplayEntry         OBJECT-TYPE
                SYNTAX IntfAtmConnDisplayEntry
                MAX-ACCESS not-accessible
                STATUS current
                DESCRIPTION "Gives list of pvc going towards the backplane
                             on a particluar interface"
                             
                INDEX { intfAtmPvcConnDisplaySlot,intfAtmPvcConnDisplayPort,
                        intfAtmPvcConnDisplayChannel,intfAtmPvcConnDisplayVpi,
                        intfAtmPvcConnDisplayVci}
                ::= { intfAtmPvcConnDisplayTable 1 }

IntfAtmConnDisplayEntry ::= SEQUENCE {
                             intfAtmPvcConnDisplaySlot                Integer32,
                             intfAtmPvcConnDisplayPort                Integer32,
                             intfAtmPvcConnDisplayChannel                Integer32,
                           intfAtmPvcConnDisplayVpi                INTEGER,
                           intfAtmPvcConnDisplayVci                INTEGER,
                           intfAtmPvcConnDisplayFlowType         INTEGER
                          }

intfAtmPvcConnDisplaySlot        OBJECT-TYPE
                SYNTAX Integer32
                MAX-ACCESS not-accessible
                STATUS current
                DESCRIPTION "Slot of the particular interface"
                ::= { intfAtmPvcConnDisplayEntry 1 }

intfAtmPvcConnDisplayPort        OBJECT-TYPE
                SYNTAX Integer32
                MAX-ACCESS not-accessible
                STATUS current
                DESCRIPTION "Port of the particular interface"
                ::= { intfAtmPvcConnDisplayEntry 2 }

intfAtmPvcConnDisplayChannel        OBJECT-TYPE
                SYNTAX Integer32
                MAX-ACCESS not-accessible
                STATUS current
                DESCRIPTION "Channel of the particular interface"
                ::= { intfAtmPvcConnDisplayEntry 3 }

intfAtmPvcConnDisplayVpi OBJECT-TYPE
                SYNTAX INTEGER (0..4095)
                MAX-ACCESS not-accessible
                STATUS current
                DESCRIPTION "VPI value for connection on Intf
                             Valid range is a number between 0 and 4095."
                ::= { intfAtmPvcConnDisplayEntry 4 }

intfAtmPvcConnDisplayVci OBJECT-TYPE
                SYNTAX INTEGER (0..65535)
                MAX-ACCESS not-accessible
                STATUS current
                DESCRIPTION "VCI value for connection on Intf 
                             Valid range is a number between 0 and 65535."
                ::= { intfAtmPvcConnDisplayEntry 5 }

intfAtmPvcConnDisplayFlowType OBJECT-TYPE
                SYNTAX INTEGER {
                                cnctnValid(1),
                                cnctnNull(2),
                                cnctnPtmpValid(3),
                                cnctnPtmpNull(4)
                               }
                MAX-ACCESS read-only
                STATUS current
                DESCRIPTION "Flow type:Indicates Flow Towards the Back Plane
                             cnctnValid: Traffic flow towards BP is enabled.
                             cnctnNull: Traffic flow towards BP is disabled.
                             cnctnPtmpValid: Traffic flow towards BP is enabled
                                             and it is point to multipoint
                                             connection.
                             cnctnPtmpNull: Traffic flow towards BP is disabled
                                             and it is point to multipoint
                                             connection."
                ::= { intfAtmPvcConnDisplayEntry 6}

-- User Service Profile Group userServiceConfig 

-- System Statistics Group sysStatistics 

-- Equipment Statistics Group equipStatistics

ds3PortStatsTable OBJECT-TYPE
                SYNTAX SEQUENCE OF Ds3PortStatsEntry
                MAX-ACCESS not-accessible
                STATUS current
                DESCRIPTION "Table of statisics for a DS3 port"
                ::= { equipStatistics 1 }

ds3PortStatsEntry OBJECT-TYPE
                SYNTAX Ds3PortStatsEntry
                MAX-ACCESS not-accessible
                STATUS current
                DESCRIPTION "Row definition for the DS3 port statistics
                             table"
                INDEX { ds3PortStatsId }
                ::= { ds3PortStatsTable 1 }

Ds3PortStatsEntry ::= SEQUENCE {
                        ds3PortStatsId                        Integer32,
                        ds3PortStatsTimer                Integer32,
                        ds3PortStatsCurrentSEFSs        Integer32,
                        ds3PortStatsCurrentLCVs                Integer32,
                        ds3PortStatsCurrentLESs                Integer32
                        }

ds3PortStatsId        OBJECT-TYPE
                SYNTAX Integer32
                MAX-ACCESS not-accessible
                STATUS current
                DESCRIPTION "Port ID - Slot/Port (SSPP)"
                ::= { ds3PortStatsEntry 1 }

ds3PortStatsTimer OBJECT-TYPE
                SYNTAX Integer32 
                MAX-ACCESS read-only
                STATUS current
                DESCRIPTION "The number of seconds that have elapsed since the
                            beginning of the current error-measurement period."
                DEFVAL { 0 }
                ::= { ds3PortStatsEntry 2 }

ds3PortStatsCurrentSEFSs OBJECT-TYPE
                SYNTAX Integer32
                MAX-ACCESS read-only
                STATUS current
                DESCRIPTION "severely errored framing seconds"
                ::= { ds3PortStatsEntry 3 }

ds3PortStatsCurrentLCVs OBJECT-TYPE
                SYNTAX Integer32
                MAX-ACCESS read-only
                STATUS current
                DESCRIPTION "Line coding violations encountered"
                ::= { ds3PortStatsEntry 4 }

ds3PortStatsCurrentLESs OBJECT-TYPE
                SYNTAX Integer32
                MAX-ACCESS read-only
                STATUS current
                DESCRIPTION "Line errored seconds"
                ::= { ds3PortStatsEntry 5 }


ds1PortStatsTable OBJECT-TYPE
                SYNTAX SEQUENCE OF Ds1PortStatsEntry
                MAX-ACCESS not-accessible
                STATUS current
                DESCRIPTION "Table of statisics for a DS1 port"
                ::= { equipStatistics 2 }

ds1PortStatsEntry OBJECT-TYPE
                SYNTAX Ds1PortStatsEntry
                MAX-ACCESS not-accessible
                STATUS current
                DESCRIPTION "Row definition for the DS1 port statistics
                             table"
                INDEX { ds1PortStatsId }
                ::= { ds1PortStatsTable 1 }

Ds1PortStatsEntry ::= SEQUENCE {
                        ds1PortStatsId                Integer32,
                        ds1PortStatsTimer        Integer32,
                        ds1PortStatsCurrentESs        Integer32,
                        ds1PortStatsCurrentSESs        Integer32,
                        ds1PortStatsCurrentLCVs        Integer32
                        }

ds1PortStatsId        OBJECT-TYPE
                SYNTAX Integer32
                MAX-ACCESS not-accessible
                STATUS current
                DESCRIPTION "Port ID - Slot/Port (SSPP)"
                ::= { ds1PortStatsEntry 1 }

ds1PortStatsTimer         OBJECT-TYPE
                SYNTAX Integer32 
                MAX-ACCESS read-only
                STATUS current
                DESCRIPTION "The number of seconds that have elapsed since the
                            beginning of the current error-measurement period."
                DEFVAL { 0 }
                ::= { ds1PortStatsEntry 2 }

ds1PortStatsCurrentESs OBJECT-TYPE
                SYNTAX Integer32
                MAX-ACCESS read-only
                STATUS current
                DESCRIPTION "The number of Errored Seconds, encountered  by
                             a DS1 interface."
                ::= { ds1PortStatsEntry 3 }

ds1PortStatsCurrentSESs OBJECT-TYPE
                SYNTAX Integer32
                MAX-ACCESS read-only
                STATUS current
                DESCRIPTION "The number of Severely Errored Seconds encoun-
                             tered  by a DS1 interface."
                ::= { ds1PortStatsEntry 4 }

ds1PortStatsCurrentLCVs OBJECT-TYPE
                SYNTAX Integer32
                MAX-ACCESS read-only
                STATUS current
                DESCRIPTION "The number of Line Code Violations (LCVs)  en-
                             countered  by a DS1 interface."
                ::= { ds1PortStatsEntry 5 }


oc3PortStatsTable OBJECT-TYPE
                SYNTAX SEQUENCE OF Oc3PortStatsEntry
                MAX-ACCESS not-accessible
                STATUS current
                DESCRIPTION "Table of statisics for a OC3 port"
                ::= { equipStatistics 3 }

oc3PortStatsEntry OBJECT-TYPE
                SYNTAX Oc3PortStatsEntry
                MAX-ACCESS not-accessible
                STATUS current
                DESCRIPTION "Row definition for the OC3 port statistics
                             table"
                INDEX { oc3PortStatsId }
                ::= { oc3PortStatsTable 1 }

Oc3PortStatsEntry ::= SEQUENCE {
                        oc3PortStatsId                        Integer32,
                        oc3PortStatsSectionBip8Errs        Integer32,
                        oc3PortStatsLineBip8Errs        Integer32,
                        oc3PortStatsPathBip8Errs        Integer32,
                        oc3PortStatsLineFebeCount        Integer32,
                        oc3PortStatsPathFebeCount        Integer32,
                        oc3PortStatsTimer                Integer32
                        }

oc3PortStatsId        OBJECT-TYPE
                SYNTAX Integer32
                MAX-ACCESS not-accessible
                STATUS current
                DESCRIPTION "Port ID - Slot/Port (SSPP)"
                ::= { oc3PortStatsEntry 1 }

oc3PortStatsSectionBip8Errs OBJECT-TYPE
                SYNTAX Integer32
                MAX-ACCESS read-only
                STATUS current
                DESCRIPTION "section sublayer BIP8 errors. "
                ::= { oc3PortStatsEntry 2 }

oc3PortStatsLineBip8Errs OBJECT-TYPE
                SYNTAX Integer32
                MAX-ACCESS read-only
                STATUS current
                DESCRIPTION " line sublayer BIP8 errors.  "
                ::= { oc3PortStatsEntry 3 }

oc3PortStatsPathBip8Errs OBJECT-TYPE
                SYNTAX Integer32
                MAX-ACCESS read-only
                STATUS current
                DESCRIPTION " path sublayer BIP8 errors.  "
                ::= { oc3PortStatsEntry 4 }

oc3PortStatsLineFebeCount OBJECT-TYPE
                SYNTAX Integer32
                MAX-ACCESS read-only
                STATUS current
                DESCRIPTION " line sublayer FEBE count.  "
                ::= { oc3PortStatsEntry 5 }

oc3PortStatsPathFebeCount OBJECT-TYPE
                SYNTAX Integer32
                MAX-ACCESS read-only
                STATUS current
                DESCRIPTION " path sublayer FEBE count.  "
                ::= { oc3PortStatsEntry 6 }

oc3PortStatsTimer OBJECT-TYPE
                SYNTAX Integer32 
                MAX-ACCESS read-only
                STATUS current
                DESCRIPTION "The number of seconds that have elapsed since the
                            beginning of the current error-measurement period."
                DEFVAL { 0 }
                ::= { oc3PortStatsEntry 7 }

msPortStatsTable OBJECT-TYPE
                SYNTAX SEQUENCE OF MsPortStatsEntry
                MAX-ACCESS not-accessible
                STATUS current
                DESCRIPTION "Table of statisics for a MS port"
                ::= { equipStatistics 4 }
 
msPortStatsEntry OBJECT-TYPE
                SYNTAX MsPortStatsEntry
                MAX-ACCESS not-accessible
                STATUS current
                DESCRIPTION "Row definition for the MS port statistics
                             table"
                INDEX { msPortStatsId }
                ::= { msPortStatsTable 1 }
 
MsPortStatsEntry ::= SEQUENCE {
                        msPortStatsId                          Integer32,
                        msPortStatsFrameErrors                 Integer32,
                        msPortStatsOutOfFrameSeconds        Integer32,
                        msPortStatsTimer                Integer32
                        }
 
msPortStatsId  OBJECT-TYPE
                SYNTAX Integer32
                MAX-ACCESS not-accessible
                STATUS current
                DESCRIPTION "Port ID - Slot/Port (SSPP)"
                ::= { msPortStatsEntry 1 }
 

 
msPortStatsFrameErrors OBJECT-TYPE
                SYNTAX Integer32
                MAX-ACCESS read-only
                STATUS current
                DESCRIPTION "P-bit severely errored seconds"
                ::= { msPortStatsEntry 4 }

msPortStatsOutOfFrameSeconds OBJECT-TYPE
                SYNTAX Integer32
                MAX-ACCESS read-only
                STATUS current
                DESCRIPTION "severely errored framing seconds"
                ::= { msPortStatsEntry 5 }
 
msPortStatsTimer OBJECT-TYPE
                SYNTAX Integer32 
                MAX-ACCESS read-only
                STATUS current
                DESCRIPTION "The number of seconds that have elapsed since the
                            beginning of the current error-measurement period."
                DEFVAL { 0 }
                ::= { msPortStatsEntry 6 }

e3PortStatsTable OBJECT-TYPE
                SYNTAX SEQUENCE OF E3PortStatsEntry
                MAX-ACCESS not-accessible
                STATUS current
                DESCRIPTION "Table of statisics for a E3 port"
                ::= { equipStatistics 5 }

e3PortStatsEntry OBJECT-TYPE
                SYNTAX E3PortStatsEntry
                MAX-ACCESS not-accessible
                STATUS current
                DESCRIPTION "Row definition for the E3 port statistics
                             table"
                INDEX { e3PortStatsId }
                ::= { e3PortStatsTable 1 }

E3PortStatsEntry ::= SEQUENCE {
                        e3PortStatsId                Integer32,
                        e3PortStatsTimer        Integer32,
                        e3PortStatsCurrentSEFSs        Integer32,
                        e3PortStatsCurrentLCVs        Integer32,
                        e3PortStatsCurrentLESs        Integer32
                        }

e3PortStatsId        OBJECT-TYPE
                SYNTAX Integer32
                MAX-ACCESS not-accessible
                STATUS current
                DESCRIPTION "Port ID - Slot/Port (SSPP)"
                ::= { e3PortStatsEntry 1 }

e3PortStatsTimer OBJECT-TYPE
                SYNTAX Integer32 
                MAX-ACCESS read-only
                STATUS current
                DESCRIPTION "The number of seconds that have elapsed since the
                            beginning of the current error-measurement period."
                DEFVAL { 0 }
                ::= { e3PortStatsEntry 2 }

e3PortStatsCurrentSEFSs OBJECT-TYPE
                SYNTAX Integer32
                MAX-ACCESS read-only
                STATUS current
                DESCRIPTION "severely errored framing seconds"
                ::= { e3PortStatsEntry 3 }

e3PortStatsCurrentLCVs OBJECT-TYPE
                SYNTAX Integer32
                MAX-ACCESS read-only
                STATUS current
                DESCRIPTION "Line coding violations encountered"
                ::= { e3PortStatsEntry 4 }

e3PortStatsCurrentLESs OBJECT-TYPE
                SYNTAX Integer32
                MAX-ACCESS read-only
                STATUS current
                DESCRIPTION "Line errored seconds"
                ::= { e3PortStatsEntry 5 }

e1PortStatsTable OBJECT-TYPE
                SYNTAX SEQUENCE OF E1PortStatsEntry
                MAX-ACCESS not-accessible
                STATUS current
                DESCRIPTION "Table of statisics for a E1 port"
                ::= { equipStatistics 6 }

e1PortStatsEntry OBJECT-TYPE
                SYNTAX E1PortStatsEntry
                MAX-ACCESS not-accessible
                STATUS current
                DESCRIPTION "Row definition for the E1 port statistics
                             table"
                INDEX { e1PortStatsId }
                ::= { e1PortStatsTable 1 }

E1PortStatsEntry ::= SEQUENCE {
                        e1PortStatsId                Integer32,
                        e1PortStatsTimer        Integer32,
                        e1PortStatsCurrentESs        Integer32,
                        e1PortStatsCurrentSESs        Integer32,
                        e1PortStatsCurrentLCVs        Integer32
                        }

e1PortStatsId        OBJECT-TYPE
                SYNTAX Integer32
                MAX-ACCESS not-accessible
                STATUS current
                DESCRIPTION "Port ID - Slot/Port (SSPP)"
                ::= { e1PortStatsEntry 1 }

e1PortStatsTimer         OBJECT-TYPE
                SYNTAX Integer32 
                MAX-ACCESS read-only
                STATUS current
                DESCRIPTION "The number of seconds that have elapsed since the
                            beginning of the current error-measurement period."
                DEFVAL { 0 }
                ::= { e1PortStatsEntry 2 }

e1PortStatsCurrentESs OBJECT-TYPE
                SYNTAX Integer32
                MAX-ACCESS read-only
                STATUS current
                DESCRIPTION "The number of Errored Seconds, encountered  by
                             a E1 interface."
                ::= { e1PortStatsEntry 3 }

e1PortStatsCurrentSESs OBJECT-TYPE
                SYNTAX Integer32
                MAX-ACCESS read-only
                STATUS current
                DESCRIPTION "The number of Severely Errored Seconds encoun-
                             tered  by a E1 interface."
                ::= { e1PortStatsEntry 4 }

e1PortStatsCurrentLCVs OBJECT-TYPE
                SYNTAX Integer32
                MAX-ACCESS read-only
                STATUS current
                DESCRIPTION "The number of Line Code Violations (LCVs)  en-
                             countered  by a E1 interface."
                ::= { e1PortStatsEntry 5 }


ethernetPortStatsTable OBJECT-TYPE
                SYNTAX SEQUENCE OF EthernetPortStatsEntry
                MAX-ACCESS not-accessible
                STATUS current
                DESCRIPTION "Statisics for a collection of ethernet-like 
                             interfaces attached to a particular system."
                ::= { equipStatistics 7 }
 
ethernetPortStatsEntry OBJECT-TYPE
                SYNTAX EthernetPortStatsEntry
                MAX-ACCESS not-accessible
                STATUS current
                DESCRIPTION "Statistics for a particular interface to an
                             ethernet-like medium."
                INDEX { ethernetPortStatsId }
                ::= { ethernetPortStatsTable 1 }
 
EthernetPortStatsEntry ::= SEQUENCE {
                ethernetPortStatsId                                  Integer32,
                ethernetPortStatsTimer                                Integer32,
                ethernetPortStatsAlignmentErrors                Integer32,
                ethernetPortStatsFCSErrors                        Integer32,
                ethernetPortStatsSingleCollisionFrames                Integer32,
                ethernetPortStatsMultipleCollisionFrames        Integer32,
                ethernetPortStatsSQETestErrors                        Integer32,
                ethernetPortStatsDeferredTransmissions                Integer32,
                ethernetPortStatsLateCollisions                        Integer32,
                ethernetPortStatsExcessiveCollisions                Integer32,
                ethernetPortStatsInternalMacTransmitErrors        Integer32,
                ethernetPortStatsCarrierSenseErrors                Integer32,
                ethernetPortStatsFrameTooLongs                        Integer32,
                ethernetPortStatsInternalMacReceiveErrors        Integer32
                }
 
ethernetPortStatsId  OBJECT-TYPE
                SYNTAX Integer32
                MAX-ACCESS not-accessible
                STATUS current
                DESCRIPTION "An index value that uniquely identifies an 
                             interface to an ethernet-like medium.  The
                             interface identified by a particular value of
                             this index is the same interface as identified
                             by the same value of ethernetPortId."
                ::= { ethernetPortStatsEntry 1 }
 
ethernetPortStatsTimer OBJECT-TYPE
                SYNTAX Integer32
                MAX-ACCESS read-only
                STATUS current
                DESCRIPTION "Time, in seconds, since last reset."
                DEFVAL { 0 }
                ::= { ethernetPortStatsEntry 2 }
 
ethernetPortStatsAlignmentErrors OBJECT-TYPE
                SYNTAX Integer32
                MAX-ACCESS read-only
                STATUS current
                DESCRIPTION "A count of frames received on a particular
                             interface that are not an integral number of
                             octets in length and do not pass the FCS check.

                             The count represented by an instance of this
                             object is incremented when the alignmentError
                             status is returned by the MAC service to the
                             LLC (or other MAC user).  Received frames for 
                             which multiple error conditions obtain are,
                             according to the conventions of IEEE 802.3
                             Layer Management, counted exclusively according
                             to the error status presented to the LLC."
                REFERENCE "IEEE 802.3 Layer Management"
                DEFVAL { 0 }
                ::= { ethernetPortStatsEntry 3 }
 
ethernetPortStatsFCSErrors OBJECT-TYPE
                SYNTAX Integer32
                MAX-ACCESS read-only
                STATUS current
                DESCRIPTION "A count of frames received on a particular
                             interface that are an integral number of
                             octets in length but do not pass the FCS check.

                             The count represented by an instance of this
                             object is incremented when the frameCheckError
                             status is returned by the MAC service to the
                             LLC (or other MAC user).  Received frames for 
                             which multiple error conditions obtain are,
                             according to the conventions of IEEE 802.3
                             Layer Management, counted exclusively according
                             to the error status presented to the LLC."
                REFERENCE "IEEE 802.3 Layer Management"
                DEFVAL { 0 }
                ::= { ethernetPortStatsEntry 4 }
 
ethernetPortStatsSingleCollisionFrames OBJECT-TYPE
                SYNTAX Integer32
                MAX-ACCESS read-only
                STATUS current
                DESCRIPTION "A count of successfully transmitted frames on
                             a particular interface for which trnasmission
                             is inhibited by exactly one collision.

                             A frame that is counted by an instance of this
                             object is also counted by the corresponding
                             instance of either the ifOutUcastPkts,
                             IfOutMulticastPkts, or ifOutBroadcastPkts,
                             and is not counted by the corresponding
                             instance of the 
                             ethernetPortStatsMulitipleCollisionFrames object."
                REFERENCE "IEEE 802.3 Layer Management"
                DEFVAL { 0 }
                ::= { ethernetPortStatsEntry 5 }
 
ethernetPortStatsMultipleCollisionFrames OBJECT-TYPE
                SYNTAX Integer32
                MAX-ACCESS read-only
                STATUS current
                DESCRIPTION "A count of successfully transmitted frames on
                             a particular interface for which trnasmission
                             is inhibited by more than one collision.

                             A frame that is counted by an instance of this
                             object is also counted by the corresponding
                             instance of either the ifOutUcastPkts,
                             IfOutMulticastPkts, or ifOutBroadcastPkts,
                             and is not counted by the corresponding
                             instance of the 
                             ethernetPortStatsSingleCollisionFrames object."
                REFERENCE "IEEE 802.3 Layer Management"
                DEFVAL { 0 }
                ::= { ethernetPortStatsEntry 6 }
 
ethernetPortStatsSQETestErrors OBJECT-TYPE
                SYNTAX Integer32
                MAX-ACCESS read-only
                STATUS current
                DESCRIPTION "A count of times that the SQE TEST ERROR message
                             is generated by the PLS sublayer for a particular
                             interface.  The SQE TEST ERROR message is
                             defined in section 7.2.2.2.4 of ANSI/IEEE 
                             802.3-1985 and its generation is described
                             in section 7.2.4.6 of the same document."
                REFERENCE "ANSI/IEEE Std 802.3-1985 Carrier Sense Multiple
                           Access with Collision Detection Access Method
                           and Physical Layer Specifications" 
                DEFVAL { 0 }
                ::= { ethernetPortStatsEntry 7 }
 
ethernetPortStatsDeferredTransmissions OBJECT-TYPE
                SYNTAX Integer32
                MAX-ACCESS read-only
                STATUS current
                DESCRIPTION "A count of frames for which the first transmission
                             attempt on a particluar interface is delayed
                             because the medium is busy.

                             the count represented by an instance of this
                             object does not include frames involved in 
                             collisions."
                REFERENCE "IEEE 802.3 Layer Management"
                DEFVAL { 0 }
                ::= { ethernetPortStatsEntry 8 }
 
ethernetPortStatsLateCollisions OBJECT-TYPE
                SYNTAX Integer32
                MAX-ACCESS read-only
                STATUS current
                DESCRIPTION "The number of times that a collision is detected
                             on a particular interface later than 512 bit-times
                             into the transmission of a packet.

                             Five hundred and twelve bit-times corresponds to
                             51.2 microseconds on a 10 Mbit/s system.  A (late)
                             collision included in a count represented by an
                             instance of this object is also considered as a
                             (generic) collision for purposes of other 
                             collision-related statistics."
                REFERENCE "IEEE 802.3 Layer Management"
                DEFVAL { 0 }
                ::= { ethernetPortStatsEntry 9 }
 
ethernetPortStatsExcessiveCollisions OBJECT-TYPE
                SYNTAX Integer32
                MAX-ACCESS read-only
                STATUS current
                DESCRIPTION "A count of frames for which transmission on a
                             particular interface fails due to excessive
                             collisions."
                REFERENCE "IEEE 802.3 Layer Management"
                DEFVAL { 0 }
                ::= { ethernetPortStatsEntry 10 }
 
ethernetPortStatsInternalMacTransmitErrors OBJECT-TYPE
                SYNTAX Integer32
                MAX-ACCESS read-only
                STATUS current
                DESCRIPTION "A count of frames for which transmission on a
                             particular interface fails due to an internal
                             MAC sublayer transmit error.  A frame is only
                             counted by an instance of this object if it is
                             not counted by the corresponding instance of
                             either the ethernetPortStatsLateCollisions object,
                             the ethernetPortStatsExcessiveCollisions object,
                             or the ethernetPortStatsCarrierSenseErrors object.
                             The precise meaning of the count represented by
                             an instance of this object is implementation-
                             specific.  In particular, an instance of this
                             object may represent a count of transmission
                             errors on a particular interface that are not
                             otherwise counted."
                REFERENCE "IEEE 802.3 Layer Management"
                DEFVAL { 0 }
                ::= { ethernetPortStatsEntry 11 }
 
ethernetPortStatsCarrierSenseErrors OBJECT-TYPE
                SYNTAX Integer32
                MAX-ACCESS read-only
                STATUS current
                DESCRIPTION "The number of times that the carrier sense 
                             condition was lost or never asserted when
                             attempting to transmit a frame on a particular
                             interface.

                             The count represented by an instance of this 
                             object is incremented at most once per 
                             transmission attempt, even if the carrier sense
                             condition fluctuates during a transmission
                             attempt."
                REFERENCE "IEEE 802.3 Layer Management"
                DEFVAL { 0 }
                ::= { ethernetPortStatsEntry 12 }
 
ethernetPortStatsFrameTooLongs OBJECT-TYPE
                SYNTAX Integer32
                MAX-ACCESS read-only
                STATUS current
                DESCRIPTION "A count of frames received on a particular
                             interface that exceed the maximum permitted
                             frame size.

                             The count represented by an instance of this 
                             object is incremented when the frameTooLong status
                             is returned by the MAC service to the LLC (or 
                             other MAC user).  Received frames for which 
                             multiple error conditions obtain are, according
                             to the conventions of IEEE 802.3 Layer 
                             Management, counted exclusively according to the
                             error status presented to the LLC."
                REFERENCE "IEEE 802.3 Layer Management"
                DEFVAL { 0 }
                ::= { ethernetPortStatsEntry 13 }
 
ethernetPortStatsInternalMacReceiveErrors OBJECT-TYPE
                SYNTAX Integer32
                MAX-ACCESS read-only
                STATUS current
                DESCRIPTION "A count of frames for which reception on a 
                             particular interface fails due to an internal
                             MAC sublayer receive error.  A frame is only 
                             counted by an instance of this object if it is not
                             counted by the corresponding instance of either
                             the ethernetPortStatsFrameTooLongs object, the
                             ethernetPortStatsAlignmentErrors object, or the
                             ethernetPortStatsFCSErrors object.

                             The precise meaning of the count represented by
                             an instance of this object is implementation-
                             specific.  In particular, an instance of this
                             object may represent a count of receive errors
                             on a particular interface that are not 
                             otherwise counted."
                REFERENCE "IEEE 802.3 Layer Management"
                DEFVAL { 0 }
                ::= { ethernetPortStatsEntry 14 }
 

-- Interface Statistics Group intfStatistics

atmIfStatsTable OBJECT-TYPE
                SYNTAX SEQUENCE OF AtmIfStatsEntry
                MAX-ACCESS not-accessible
                STATUS current
                DESCRIPTION "Table of statistics for an atmUni interface"
                ::= { intfStatistics 1 }

atmIfStatsEntry OBJECT-TYPE
                SYNTAX AtmIfStatsEntry
                MAX-ACCESS not-accessible
                STATUS current
                DESCRIPTION "Row definition for the atmUni statistics
                             table"
                INDEX { atmIfStatsId }
                ::= { atmIfStatsTable 1}

AtmIfStatsEntry ::= SEQUENCE {
                atmIfStatsId IntfIndex,
                atmIfStatsValidCellsInHi        Integer32,
                atmIfStatsValidCellsInLo        Integer32,
                atmIfStatsErroredCellsIn        Integer32,
                atmIfStatsMismatchedCellsIn        Integer32,
                atmIfStatsNullCellsOutHi        Integer32,
                atmIfStatsNullCellsOutLo        Integer32,
                atmIfStatsValidCellsOutHi        Integer32,
                atmIfStatsValidCellsOutLo        Integer32,
                atmIfStatsTimer                        Integer32
                }

atmIfStatsId OBJECT-TYPE
                SYNTAX IntfIndex
                MAX-ACCESS not-accessible
                STATUS current
                DESCRIPTION "Interface index (SSPPCCC) to the atmUni 
                             statistics table"
                ::= { atmIfStatsEntry 1 }

atmIfStatsValidCellsInHi OBJECT-TYPE
                SYNTAX Integer32
                MAX-ACCESS read-only
                STATUS current
                DESCRIPTION "Number of valid cells received on the channel -
                             High Word"
                ::= { atmIfStatsEntry 2 }

atmIfStatsValidCellsInLo OBJECT-TYPE
                SYNTAX Integer32
                MAX-ACCESS read-only
                STATUS current
                DESCRIPTION "Number of valid cells received on the channel -
                             low Word"
                ::= { atmIfStatsEntry 3 }

atmIfStatsErroredCellsIn OBJECT-TYPE
                SYNTAX Integer32
                MAX-ACCESS read-only
                STATUS current
                DESCRIPTION "Number of errored cells received on the channel"
                ::= { atmIfStatsEntry 4 }

atmIfStatsMismatchedCellsIn OBJECT-TYPE
                SYNTAX Integer32
                MAX-ACCESS read-only
                STATUS current
                DESCRIPTION "Number of Vpi/Vci translation errors on input
                             cells."
                ::= { atmIfStatsEntry 5 }

atmIfStatsNullCellsOutHi OBJECT-TYPE
                SYNTAX Integer32
                MAX-ACCESS read-only
                STATUS current
                DESCRIPTION "Number of null cells sent out  on the channel -
                             High Word"
                ::= { atmIfStatsEntry 6 }

atmIfStatsNullCellsOutLo OBJECT-TYPE
                SYNTAX Integer32
                MAX-ACCESS read-only
                STATUS current
                DESCRIPTION "Number of null cells sent out  on the channel -
                             Low Word"
                ::= { atmIfStatsEntry 7 }

atmIfStatsValidCellsOutHi OBJECT-TYPE
                SYNTAX Integer32
                MAX-ACCESS read-only
                STATUS current
                DESCRIPTION "Number of valid cells sent out  on the channel -
                             High Word"
                ::= { atmIfStatsEntry 8 }

atmIfStatsValidCellsOutLo OBJECT-TYPE
                SYNTAX Integer32
                MAX-ACCESS read-only
                STATUS current
                DESCRIPTION "Number of valid cells sent out  on the channel -
                             Low Word"
                ::= { atmIfStatsEntry 9 }

atmIfStatsTimer OBJECT-TYPE
                SYNTAX Integer32 (1..899)
                MAX-ACCESS read-only
                STATUS current
                DESCRIPTION "Time, in seconds, since last reset."
                ::= { atmIfStatsEntry 10 }

frUniStatsTable OBJECT-TYPE
                SYNTAX SEQUENCE OF FrUniStatsEntry
                MAX-ACCESS not-accessible
                STATUS current
                DESCRIPTION "Table of statistics for a Frame Relay UNI 
                             Interface "
                ::= { intfStatistics 2 }

frUniStatsEntry OBJECT-TYPE
                SYNTAX FrUniStatsEntry
                MAX-ACCESS not-accessible
                STATUS current
                DESCRIPTION "Row definition for the Frame Realy UNI statistics
                             table"
                INDEX { frUniStatsId }
                ::= { frUniStatsTable 1}

FrUniStatsEntry ::= SEQUENCE {
                                frUniStatsId                        IntfIndex,
                                frUniStatsTimer                 INTEGER,
                                frUniStatsCellsMismatched       Integer32,
                                frUniStatsErroredFrames         Integer32,
                                frUniStatsCellsEncodedHi        Integer32,
                                frUniStatsCellsEncodedLo        Integer32,
                                frUniStatsFramesEncodedHi       Integer32,
                                frUniStatsFramesEncodedLo       Integer32,
                                frUniStatsCellsDecodedHi        Integer32,
                                frUniStatsCellsDecodedLo        Integer32,
                                frUniStatsFramesDecodedHi       Integer32,
                                frUniStatsFramesDecodedLo       Integer32,
                                frUniStatsAAL5Errors            Integer32

                             }

frUniStatsId OBJECT-TYPE
                SYNTAX IntfIndex
                MAX-ACCESS not-accessible
                STATUS current
                DESCRIPTION "Interface index (SSPPCCC) to the frame relay UNI
                             statistics table"
                ::= { frUniStatsEntry 1 }



frUniStatsTimer OBJECT-TYPE
                SYNTAX INTEGER (1..899)
                MAX-ACCESS read-only
                STATUS current
                DESCRIPTION "Time, in seconds, since last reset."
                ::= { frUniStatsEntry 9 }

frUniStatsCellsMismatched OBJECT-TYPE
                SYNTAX Integer32
                MAX-ACCESS read-only
                STATUS current
                DESCRIPTION "number of cells not matched to provisioned DLCIs."
                ::= { frUniStatsEntry 10 }

frUniStatsErroredFrames OBJECT-TYPE
                SYNTAX Integer32
                MAX-ACCESS read-only
                STATUS current
                DESCRIPTION "number of errored frames."
                ::= { frUniStatsEntry 11 }

frUniStatsCellsEncodedHi OBJECT-TYPE
                SYNTAX Integer32
                MAX-ACCESS read-only
                STATUS current
                DESCRIPTION "number of cells encoded - (High order portion)."
                ::= { frUniStatsEntry 12 }

frUniStatsCellsEncodedLo OBJECT-TYPE
                SYNTAX Integer32
                MAX-ACCESS read-only
                STATUS current
                DESCRIPTION "number of cells encoded - (Low order portion)."
                ::= { frUniStatsEntry 13 }

frUniStatsFramesEncodedHi OBJECT-TYPE
                SYNTAX Integer32
                MAX-ACCESS read-only
                STATUS current
                DESCRIPTION "number of frames encoded - (High order portion)."
                ::= { frUniStatsEntry 14 }

frUniStatsFramesEncodedLo OBJECT-TYPE
                SYNTAX Integer32
                MAX-ACCESS read-only
                STATUS current
                DESCRIPTION "number of frames encoded - (Low order portion)."
                ::= { frUniStatsEntry 15 }

frUniStatsCellsDecodedHi OBJECT-TYPE
                SYNTAX Integer32
                MAX-ACCESS read-only
                STATUS current
                DESCRIPTION "number of cells decoded - (High order portion)."
                ::= { frUniStatsEntry 16 }

frUniStatsCellsDecodedLo OBJECT-TYPE
                SYNTAX Integer32
                MAX-ACCESS read-only
                STATUS current
                DESCRIPTION "number of cells decoded - (Low order portion)."
                ::= { frUniStatsEntry 17 }

frUniStatsFramesDecodedHi OBJECT-TYPE
                SYNTAX Integer32
                MAX-ACCESS read-only
                STATUS current
                DESCRIPTION "number of frames decoded - (High order portion)."
                ::= { frUniStatsEntry 18 }

frUniStatsFramesDecodedLo OBJECT-TYPE
                SYNTAX Integer32
                MAX-ACCESS read-only
                STATUS current
                DESCRIPTION "number of frames decoded - (Low order portion)."
                ::= { frUniStatsEntry 19 }

frUniStatsAAL5Errors OBJECT-TYPE
                SYNTAX Integer32
                MAX-ACCESS read-only
                STATUS current
                DESCRIPTION " number of aal5 PDUs with invalid byte count 
                              or CRC-32."
                ::= { frUniStatsEntry 20 }



cirEmIfStatsTable OBJECT-TYPE
                SYNTAX SEQUENCE OF CirEmIfStatsEntry
                MAX-ACCESS not-accessible
                STATUS current
                DESCRIPTION "Table of statistics for an cirEm interface"
                ::= { intfStatistics 3 }

cirEmIfStatsEntry OBJECT-TYPE
                SYNTAX CirEmIfStatsEntry
                MAX-ACCESS not-accessible
                STATUS current
                DESCRIPTION "Row definition for the cirEm statistics
                             table"
                INDEX { cirEmIfStatsId }
                ::= { cirEmIfStatsTable 1}

CirEmIfStatsEntry ::= SEQUENCE {
                cirEmIfStatsId                         IntfIndex,
                cirEmIfStatsCellsEncodedHi        Integer32,
                cirEmIfStatsCellsEncodedLo        Integer32,
                cirEmIfStatsCellsDecodedHi        Integer32,
                cirEmIfStatsCellsDecodedLo        Integer32,
                cirEmIfStatsTimer                Integer32
                }

cirEmIfStatsId OBJECT-TYPE
                SYNTAX IntfIndex
                MAX-ACCESS not-accessible
                STATUS current
                DESCRIPTION "Interface index (SSPPCCC) to the cirEm 
                             statistics table"
                ::= { cirEmIfStatsEntry 1 }

cirEmIfStatsCellsEncodedHi OBJECT-TYPE
                SYNTAX Integer32
                MAX-ACCESS read-only
                STATUS current
                DESCRIPTION "Incoming cells from the outside media to the 
                             i/o port"
                ::= { cirEmIfStatsEntry 2 }

cirEmIfStatsCellsEncodedLo OBJECT-TYPE
                SYNTAX Integer32
                MAX-ACCESS read-only
                STATUS current
                DESCRIPTION "Incoming cells from the outside media to the 
                             i/o port"
                ::= { cirEmIfStatsEntry 3 }

cirEmIfStatsCellsDecodedHi OBJECT-TYPE
                SYNTAX Integer32
                MAX-ACCESS read-only
                STATUS current
                DESCRIPTION "Outgoing cells from the i/o port to the outside
                             media"
                ::= { cirEmIfStatsEntry 4 }

cirEmIfStatsCellsDecodedLo OBJECT-TYPE
                SYNTAX Integer32
                MAX-ACCESS read-only
                STATUS current
                DESCRIPTION "Outgoing cells from the i/o port to the outside
                             media"
                ::= { cirEmIfStatsEntry 5 }

cirEmIfStatsTimer OBJECT-TYPE
                SYNTAX Integer32 (1..899)
                MAX-ACCESS read-only
                STATUS current
                DESCRIPTION "Time, in seconds, since last reset."
                ::= { cirEmIfStatsEntry 6 }


vbrIfStatsTable OBJECT-TYPE
                SYNTAX SEQUENCE OF VbrIfStatsEntry
                MAX-ACCESS not-accessible
                STATUS current
                DESCRIPTION "Table of statistics for an vbr interface"
                ::= { intfStatistics 4 }

vbrIfStatsEntry OBJECT-TYPE
                SYNTAX VbrIfStatsEntry
                MAX-ACCESS not-accessible
                STATUS current
                DESCRIPTION "Row definition for the vbr statistics
                             table"
                INDEX { vbrIfStatsId }
                ::= { vbrIfStatsTable 1}

VbrIfStatsEntry ::= SEQUENCE {
                vbrIfStatsId                         IntfIndex,
                vbrIfStatsCellsEncodedHi        Integer32,
                vbrIfStatsCellsEncodedLo        Integer32,
                vbrIfStatsCellsDecodedHi        Integer32,
                vbrIfStatsCellsDecodedLo        Integer32,
                vbrIfStatsTimer                        Integer32
                }

vbrIfStatsId OBJECT-TYPE
                SYNTAX IntfIndex
                MAX-ACCESS not-accessible
                STATUS current
                DESCRIPTION "Interface index (SSPPCCC) to the vbr 
                             statistics table"
                ::= { vbrIfStatsEntry 1 }

vbrIfStatsCellsEncodedHi OBJECT-TYPE
                SYNTAX Integer32
                MAX-ACCESS read-only
                STATUS current
                DESCRIPTION "Incoming cells from the outside media to the 
                             i/o port"
                ::= { vbrIfStatsEntry 2 }

vbrIfStatsCellsEncodedLo OBJECT-TYPE
                SYNTAX Integer32
                MAX-ACCESS read-only
                STATUS current
                DESCRIPTION "Incoming cells from the outside media to the 
                             i/o port"
                ::= { vbrIfStatsEntry 3 }

vbrIfStatsCellsDecodedHi OBJECT-TYPE
                SYNTAX Integer32
                MAX-ACCESS read-only
                STATUS current
                DESCRIPTION "Outgoing cells from the i/o port to the outside
                             media"
                ::= { vbrIfStatsEntry 4 }

vbrIfStatsCellsDecodedLo OBJECT-TYPE
                SYNTAX Integer32
                MAX-ACCESS read-only
                STATUS current
                DESCRIPTION "Outgoing cells from the i/o port to the outside
                             media"
                ::= { vbrIfStatsEntry 5 }

vbrIfStatsTimer OBJECT-TYPE
                SYNTAX Integer32 (1..899)
                MAX-ACCESS read-only
                STATUS current
                DESCRIPTION "Time, in seconds, since last reset."
                ::= { vbrIfStatsEntry 6 }


frLmiStatsTable OBJECT-TYPE
                SYNTAX SEQUENCE OF FrLmiStatsEntry
                MAX-ACCESS not-accessible
                STATUS current
                DESCRIPTION "Table of statistics for a Frame Relay LMI 
                             Interface "
                ::= { intfStatistics 5 }

frLmiStatsEntry OBJECT-TYPE
                SYNTAX FrLmiStatsEntry
                MAX-ACCESS not-accessible
                STATUS current
                DESCRIPTION "Row definition for the Frame Realy LMI statistics
                             table"
                INDEX { frLmiStatsId }
                ::= { frLmiStatsTable 1 }

FrLmiStatsEntry ::= SEQUENCE {
                                frLmiStatsId                IntfIndex,
                                frLmiStatsEnqRx                Integer32,
                                frLmiStatsEnqTx                Integer32,
                                frLmiStatsStatusRx        Integer32,
                                frLmiStatsStatusTx        Integer32,
                                frLmiStatsAsyncRx        Integer32,
                                frLmiStatsAsyncTx        Integer32,
                                frLmiStatsPktDisc        Integer32,
                                frLmiStatsT391Exp        INTEGER,
                                frLmiStatsT392Exp        INTEGER,
                                frLmiStatsLinkReset        INTEGER,
                                frLmiStatsTimer                INTEGER
                             }

frLmiStatsId OBJECT-TYPE
                SYNTAX IntfIndex
                MAX-ACCESS not-accessible
                STATUS current
                DESCRIPTION "Interface index (SSPPCCC) to the frame relay LMI
                             statistics table"
                ::= { frLmiStatsEntry 1 }

frLmiStatsEnqRx OBJECT-TYPE
                SYNTAX Integer32
                MAX-ACCESS read-only
                STATUS current
                DESCRIPTION "number of STATUS ENQ messages received"
                ::= { frLmiStatsEntry 2 }

frLmiStatsEnqTx OBJECT-TYPE
                SYNTAX Integer32
                MAX-ACCESS read-only
                STATUS current
                DESCRIPTION "number of STATUS ENQ messages transmitted"
                ::= { frLmiStatsEntry 3 }

frLmiStatsStatusRx OBJECT-TYPE
                SYNTAX Integer32
                MAX-ACCESS read-only
                STATUS current
                DESCRIPTION "number of STATUS messages received"
                ::= { frLmiStatsEntry 4 }

frLmiStatsStatusTx OBJECT-TYPE
                SYNTAX Integer32
                MAX-ACCESS read-only
                STATUS current
                DESCRIPTION "number of STATUS messages transmitted"
                ::= { frLmiStatsEntry 5 }

frLmiStatsAsyncRx OBJECT-TYPE
                SYNTAX Integer32
                MAX-ACCESS read-only
                STATUS current
                DESCRIPTION "number of ASYNC STATUS messages received"
                ::= { frLmiStatsEntry 6 }
 
frLmiStatsAsyncTx OBJECT-TYPE
                SYNTAX Integer32
                MAX-ACCESS read-only
                STATUS current
                DESCRIPTION "number of ASYNC STATUS messages transmitted"
                ::= { frLmiStatsEntry 7 }
 
frLmiStatsPktDisc OBJECT-TYPE
                SYNTAX Integer32
                MAX-ACCESS read-only
                STATUS current
                DESCRIPTION "The number of lmi messages discarded due to
                             invalid length, receive sequence numbers, or
                             other error."
                ::= { frLmiStatsEntry 8 }

frLmiStatsT391Exp OBJECT-TYPE
                SYNTAX INTEGER (1..899)
                MAX-ACCESS read-only
                STATUS current
                DESCRIPTION "Link integrity verification polling timer expiry"
                ::= { frLmiStatsEntry 9 }

frLmiStatsT392Exp OBJECT-TYPE
                SYNTAX INTEGER (1..899)
                MAX-ACCESS read-only
                STATUS current
                DESCRIPTION "Polling verification timer expiry"
                ::= { frLmiStatsEntry 10 }

frLmiStatsLinkReset OBJECT-TYPE
                SYNTAX INTEGER (1..899)
                MAX-ACCESS read-only
                STATUS current
                DESCRIPTION "Number of times interface operational status was
                             in service after system startup."
                ::= { frLmiStatsEntry 11 }

frLmiStatsTimer OBJECT-TYPE
                SYNTAX INTEGER (1..899)
                MAX-ACCESS read-only
                STATUS current
                DESCRIPTION "Time since last reset for statistics - in seconds"
                ::= { frLmiStatsEntry 12 }


bridgeStatsTable OBJECT-TYPE
                SYNTAX SEQUENCE OF BridgeStatsEntry
                MAX-ACCESS not-accessible
                STATUS current
                DESCRIPTION "Table of statistics for a bridge interface."
                ::= { intfStatistics 6 }

bridgeStatsEntry OBJECT-TYPE
                SYNTAX BridgeStatsEntry
                MAX-ACCESS not-accessible
                STATUS current
                DESCRIPTION "Row definition for the bridge interface statistics
                             table"
                INDEX { bridgeStatsId }
                ::= { bridgeStatsTable 1 }

BridgeStatsEntry ::= SEQUENCE {
                bridgeStatsId                                        Integer32,
                bridgeStatsTimer                                Integer32,
                bridgeStatsBasePortDelayExceededDiscardsHi        Integer32,
                bridgeStatsBasePortDelayExceededDiscardsLo        Integer32,
                bridgeStatsBasePortMtuExceededDiscardsHi        Integer32,
                bridgeStatsBasePortMtuExceededDiscardsLo        Integer32,
                bridgeStatsTpPortInFramesHi                        Integer32,
                bridgeStatsTpPortInFramesLo                        Integer32,
                bridgeStatsTpPortOutFramesHi                        Integer32,
                bridgeStatsTpPortOutFramesLo                        Integer32,
                bridgeStatsTpPortInDiscardsHi                        Integer32,
                bridgeStatsTpPortInDiscardsLo                        Integer32
                }

bridgeStatsId OBJECT-TYPE
                SYNTAX Integer32
                MAX-ACCESS not-accessible
                STATUS current
                DESCRIPTION "Interface index (SSPPCCC) to the bridge"
                ::= { bridgeStatsEntry 1 }

bridgeStatsTimer OBJECT-TYPE
                SYNTAX Integer32
                MAX-ACCESS read-only
                STATUS current
                DESCRIPTION "Time, in seconds, since last reset."
                ::= { bridgeStatsEntry 2 }



bridgeStatsBasePortDelayExceededDiscardsHi OBJECT-TYPE
                SYNTAX Integer32
                MAX-ACCESS read-only
                STATUS current
                DESCRIPTION "The number of frames discarded by this port due
                             to excessive transit delay through the bridge.  It
                             is incremented by both transparent and source
                             route bridges. High-order 32 bits."
                REFERENCE "IEEE 802.1D-1990: Section 6.6.1.1.3"
                ::= { bridgeStatsEntry 8 }

bridgeStatsBasePortDelayExceededDiscardsLo OBJECT-TYPE
                SYNTAX Integer32
                MAX-ACCESS read-only
                STATUS current
                DESCRIPTION "The number of frames discarded by this port due
                             to excessive transit delay through the bridge.  It
                             is incremented by both transparent and source
                             route bridges.  Low-order 32 bits."
                REFERENCE "IEEE 802.1D-1990: Section 6.6.1.1.3"
                ::= { bridgeStatsEntry 9 }

bridgeStatsBasePortMtuExceededDiscardsHi OBJECT-TYPE
                SYNTAX Integer32
                MAX-ACCESS read-only
                STATUS current
                DESCRIPTION "The number of frames discarded by this port due
                             to an excessive size.  It is incremented by both
                             transparent and source route bridges.  High-order
                             32 bits."
                REFERENCE "IEEE 802.1D-1990: Section 6.6.1.1.3"
                ::= { bridgeStatsEntry 10 }

bridgeStatsBasePortMtuExceededDiscardsLo OBJECT-TYPE
                SYNTAX Integer32
                MAX-ACCESS read-only
                STATUS current
                DESCRIPTION "The number of frames discarded by this port due
                             to an excessive size.  It is incremented by both
                             transparent and source route bridges.  Low-order
                             32 bits."
                REFERENCE "IEEE 802.1D-1990: Section 6.6.1.1.3"
                ::= { bridgeStatsEntry 11 }

bridgeStatsTpPortInFramesHi OBJECT-TYPE
                SYNTAX Integer32
                MAX-ACCESS read-only
                STATUS current
                DESCRIPTION "The number of frames that have been received by
                             this port from its segment.  Note that a frame
                             received on the interface corresponding to this
                             port is only counted by this object if and only
                             if it is for a protocol being processed by the
                             local bridging function, including bridge 
                             management frames.  High-order 32 bits."
                REFERENCE "IEEE 802.1D-1990: Section 6.6.1.1.3"
                ::= { bridgeStatsEntry 12 }

bridgeStatsTpPortInFramesLo OBJECT-TYPE
                SYNTAX Integer32
                MAX-ACCESS read-only
                STATUS current
                DESCRIPTION "The number of frames that have been received by
                             this port from its segment.  Note that a frame
                             received on the interface corresponding to this
                             port is only counted by this object if and only
                             if it is for a protocol being processed by the
                             local bridging function, including bridge 
                             management frames.  Low-order 32 bits."
                REFERENCE "IEEE 802.1D-1990: Section 6.6.1.1.3"
                ::= { bridgeStatsEntry 13 }

bridgeStatsTpPortOutFramesHi OBJECT-TYPE
                SYNTAX Integer32
                MAX-ACCESS read-only
                STATUS current
                DESCRIPTION "The number of frames that have been transmitted
                             by this port to its segment.  Note that a frame
                             transmitted on the interface corresponding to this
                             port is only counted by this object if and only if
                             it is for a protocol being processed by the local
                             bridging function, including bridge management
                             frames.  High-order 32 bits."
                REFERENCE "IEEE 802.1D-1990: Section 6.6.1.1.3"
                ::= { bridgeStatsEntry 14 }

bridgeStatsTpPortOutFramesLo OBJECT-TYPE
                SYNTAX Integer32
                MAX-ACCESS read-only
                STATUS current
                DESCRIPTION "The number of frames that have been transmitted
                             by this port to its segment.  Note that a frame
                             transmitted on the interface corresponding to this
                             port is only counted by this object if and only if
                             it is for a protocol being processed by the local
                             bridging function, including bridge management
                             frames.  Low-order 32 bits."
                REFERENCE "IEEE 802.1D-1990: Section 6.6.1.1.3"
                ::= { bridgeStatsEntry 15 }

bridgeStatsTpPortInDiscardsHi OBJECT-TYPE
                SYNTAX Integer32
                MAX-ACCESS read-only
                STATUS current
                DESCRIPTION "Count of valid frames received which were
                             discarded (i.e., filtered) by the Forwarding
                             Process.  High-order 32 bits."
                REFERENCE "IEEE 802.1D-1990: Section 6.6.1.1.3"
                ::= { bridgeStatsEntry 16 }

bridgeStatsTpPortInDiscardsLo OBJECT-TYPE
                SYNTAX Integer32
                MAX-ACCESS read-only
                STATUS current
                DESCRIPTION "Count of valid frames received which were
                             discarded (i.e., filtered) by the Forwarding
                             Process.  Low-order 32 bits."
                REFERENCE "IEEE 802.1D-1990: Section 6.6.1.1.3"
                ::= { bridgeStatsEntry 17 }


dbCirEmIfStatsTable OBJECT-TYPE
                SYNTAX SEQUENCE OF DbCirEmIfStatsEntry
                MAX-ACCESS not-accessible
                STATUS current
                DESCRIPTION "Table of statistics for a dbCirEm interface."
                ::= { intfStatistics 7 }

dbCirEmIfStatsEntry OBJECT-TYPE
                SYNTAX DbCirEmIfStatsEntry
                MAX-ACCESS not-accessible
                STATUS current
                DESCRIPTION "Row definition for the dbCirEm statistics table."
                INDEX { dbCirEmIfStatsId }
                ::= { dbCirEmIfStatsTable 1}

DbCirEmIfStatsEntry ::= SEQUENCE {
                dbCirEmIfStatsId                 IntfIndex,
                dbCirEmIfStatsCellsEncodedHi        Integer32,
                dbCirEmIfStatsCellsEncodedLo        Integer32,
                dbCirEmIfStatsCellsDecodedHi        Integer32,
                dbCirEmIfStatsCellsDecodedLo        Integer32,
                dbCirEmIfStatsTimer                Integer32
                }

dbCirEmIfStatsId OBJECT-TYPE
                SYNTAX IntfIndex
                MAX-ACCESS not-accessible
                STATUS current
                DESCRIPTION "Interface index (SSPPCCC) to the dbCirEm 
                             statistics table."
                ::= { dbCirEmIfStatsEntry 1 }

dbCirEmIfStatsCellsEncodedHi OBJECT-TYPE
                SYNTAX Integer32
                MAX-ACCESS read-only
                STATUS current
                DESCRIPTION "Incoming cells from the outside media to the 
                             i/o port."
                ::= { dbCirEmIfStatsEntry 2 }

dbCirEmIfStatsCellsEncodedLo OBJECT-TYPE
                SYNTAX Integer32
                MAX-ACCESS read-only
                STATUS current
                DESCRIPTION "Incoming cells from the outside media to the 
                             i/o port."
                ::= { dbCirEmIfStatsEntry 3 }

dbCirEmIfStatsCellsDecodedHi OBJECT-TYPE
                SYNTAX Integer32
                MAX-ACCESS read-only
                STATUS current
                DESCRIPTION "Outgoing cells from the i/o port to the outside
                             media."
                ::= { dbCirEmIfStatsEntry 4 }

dbCirEmIfStatsCellsDecodedLo OBJECT-TYPE
                SYNTAX Integer32
                MAX-ACCESS read-only
                STATUS current
                DESCRIPTION "Outgoing cells from the i/o port to the outside
                             media."
                ::= { dbCirEmIfStatsEntry 5 }

dbCirEmIfStatsTimer OBJECT-TYPE
                SYNTAX Integer32 (1..899)
                MAX-ACCESS read-only
                STATUS current
                DESCRIPTION "Time, in seconds, since last reset."
                ::= { dbCirEmIfStatsEntry 6 }


atmImaStatsTable OBJECT-TYPE
                SYNTAX SEQUENCE OF AtmImaStatsEntry
                MAX-ACCESS not-accessible
                STATUS current
                DESCRIPTION "Table of statistics for an atmIma interface."
                ::= { intfStatistics 8 }

atmImaStatsEntry OBJECT-TYPE
                SYNTAX AtmImaStatsEntry
                MAX-ACCESS not-accessible
                STATUS current
                DESCRIPTION "Row definition for the atmIma statistics 
                             table."
                INDEX { atmImaStatsId }
                ::= { atmImaStatsTable 1 }


AtmImaStatsEntry ::= SEQUENCE {
                atmImaStatsId                   IntfIndex,
                atmImaStatsTimer                Integer32,        
                atmImaStatsImaViolations        Integer32,
                atmImaStatsOifAnomalies         Integer32,
                atmImaStatsNeTxNumFailures      Integer32,
                atmImaStatsNeRxNumFailures      Integer32,
                atmImaStatsFeTxNumFailures      Integer32,
                atmImaStatsFeRxNumFailures      Integer32,
                atmImaStatsTxStuffs             Integer32,
                atmImaStatsRxStuffs             Integer32
                }

atmImaStatsId        OBJECT-TYPE
                SYNTAX IntfIndex
                MAX-ACCESS not-accessible
                STATUS current
                DESCRIPTION "Interface index (SSPPCCC) to the atmIma
                             statistics table."
                ::= { atmImaStatsEntry 1 }

atmImaStatsTimer OBJECT-TYPE
                SYNTAX Integer32
                MAX-ACCESS read-only
                STATUS current
                DESCRIPTION "Time, in seconds, since last reset."
                ::= { atmImaStatsEntry 2 }

atmImaStatsImaViolations OBJECT-TYPE
                SYNTAX Integer32
                MAX-ACCESS read-only
                STATUS current
                DESCRIPTION
                  "ICP violations: count of errored, invalid or missing ICP
                   cells during non-SES-IMA condition."
                ::= { atmImaStatsEntry 3 }

atmImaStatsOifAnomalies OBJECT-TYPE
                SYNTAX Integer32
                MAX-ACCESS read-only
                STATUS current
                DESCRIPTION
                 "The number of OIF anomalies during non-SES-IMA condition at
                  the near-end."
                ::= { atmImaStatsEntry 4 }

atmImaStatsNeTxNumFailures OBJECT-TYPE
                SYNTAX Integer32
                MAX-ACCESS read-only
                STATUS current
                DESCRIPTION
                 "The number of times a near-end transmit failure alarm
                  condition has been entered on this link."
                ::= { atmImaStatsEntry 5 }

atmImaStatsNeRxNumFailures OBJECT-TYPE
                SYNTAX Integer32
                MAX-ACCESS read-only
                STATUS current
                DESCRIPTION
                 "The number of times a near-end receive failure alarm
                  condition has been entered on this link (i.e., LIF, LODS,
                  Mis-Connected, RDI-IMA)."
                ::= { atmImaStatsEntry 6 }

atmImaStatsFeTxNumFailures OBJECT-TYPE
                SYNTAX Integer32
                MAX-ACCESS read-only
                STATUS current
                DESCRIPTION
                 "The number of times a far-end transmit failure alarm
                  condition has been entered on this link."
                ::= { atmImaStatsEntry 7 }

atmImaStatsFeRxNumFailures OBJECT-TYPE
                SYNTAX Integer32
                MAX-ACCESS read-only
                STATUS current
                DESCRIPTION
                 "The number of times a far-end receive failure alarm condition
                  has been entered on this link (i.e. LIF, LODS, Mis-Connected,
                  RDI-IMA)."
                ::= { atmImaStatsEntry 8 }

atmImaStatsTxStuffs OBJECT-TYPE
                SYNTAX Integer32
                MAX-ACCESS read-only
                STATUS current
                DESCRIPTION
                 "Counts of stuff events inserted in the transmit direction."
                ::= { atmImaStatsEntry 9 }

atmImaStatsRxStuffs OBJECT-TYPE
                SYNTAX Integer32
                MAX-ACCESS read-only
                STATUS current
                DESCRIPTION
                 "Counts of stuff events detected in the receive direction."
                ::= { atmImaStatsEntry 10 }


ilmiStatsTable        OBJECT-TYPE
                SYNTAX SEQUENCE OF IlmiStatsEntry
                MAX-ACCESS not-accessible
                STATUS current
                DESCRIPTION "Table of statistics for an ILMI enabled interface."
                ::= { intfStatistics 9 }

ilmiStatsEntry        OBJECT-TYPE
                SYNTAX IlmiStatsEntry
                MAX-ACCESS not-accessible
                STATUS current
                DESCRIPTION "Row definition for the ILMI statistics table."
                INDEX { ilmiStatsId }
                ::= { ilmiStatsTable 1 }

IlmiStatsEntry        ::= SEQUENCE {
                ilmiStatsId                        IntfIndex,
                ilmiStatsTimer                        Integer32,
                ilmiStatsLinkResets                Integer32,
                ilmiStatsAttachPtChanged        Integer32,
                ilmiStatsAttachPtVerified        Integer32,
                ilmiStatsSecureLnkProcInit        Integer32,
                ilmiStatsColdStartRx                Integer32,
                ilmiStatsColdStartTx                Integer32,
                ilmiStatsPduRx                        Integer32,
                ilmiStatsPduTx                        Integer32,
                ilmiStatsReqTimeouts                Integer32,
                ilmiStatsPacketDisc                Integer32
                }

ilmiStatsId        OBJECT-TYPE
                SYNTAX IntfIndex
                MAX-ACCESS not-accessible
                STATUS current
                DESCRIPTION "Interface index (SSPPCCC) for the ILMI interface."
                ::= { ilmiStatsEntry 1 }

ilmiStatsTimer        OBJECT-TYPE
                SYNTAX Integer32
                MAX-ACCESS read-only
                STATUS current
                DESCRIPTION "Time, in seconds, since last statistics reset."
                ::= { ilmiStatsEntry 2 }

ilmiStatsLinkResets OBJECT-TYPE
                SYNTAX Integer32
                MAX-ACCESS read-only
                STATUS current
                DESCRIPTION "Times connectivity has toggled between down and 
                             up."
                ::= { ilmiStatsEntry 3 }

ilmiStatsAttachPtChanged OBJECT-TYPE
                SYNTAX Integer32
                MAX-ACCESS read-only
                STATUS current
                DESCRIPTION "Times Attachment Point change was detected."
                ::= { ilmiStatsEntry 4 }

ilmiStatsAttachPtVerified OBJECT-TYPE
                SYNTAX Integer32
                MAX-ACCESS read-only
                STATUS current
                DESCRIPTION "Times Attachment Point was verified successfully."
                ::= { ilmiStatsEntry 5 }

ilmiStatsSecureLnkProcInit OBJECT-TYPE
                SYNTAX Integer32
                MAX-ACCESS read-only
                STATUS current
                DESCRIPTION "Times Secure Link Procedure was initiated."
                ::= { ilmiStatsEntry 6 }

ilmiStatsColdStartRx OBJECT-TYPE
                SYNTAX Integer32
                MAX-ACCESS read-only
                STATUS current
                DESCRIPTION "Times Cold Start trap was received."
                ::= { ilmiStatsEntry 7 }

ilmiStatsColdStartTx OBJECT-TYPE
                SYNTAX Integer32
                MAX-ACCESS read-only
                STATUS current
                DESCRIPTION "Times Cold Start trap was transmitted."
                ::= { ilmiStatsEntry 8 }

ilmiStatsPduRx OBJECT-TYPE
                SYNTAX Integer32
                MAX-ACCESS read-only
                STATUS current
                DESCRIPTION "ilmi pdu received"
                ::= { ilmiStatsEntry 9 }

ilmiStatsPduTx OBJECT-TYPE
                SYNTAX Integer32
                MAX-ACCESS read-only
                STATUS current
                DESCRIPTION "ilmi pdu transmitted"
                ::= { ilmiStatsEntry 10 }

ilmiStatsReqTimeouts OBJECT-TYPE
                SYNTAX Integer32
                MAX-ACCESS read-only
                STATUS current
                DESCRIPTION "Times getRequest of any type timed out."
                ::= { ilmiStatsEntry 11 }

ilmiStatsPacketDisc OBJECT-TYPE
                SYNTAX Integer32
                MAX-ACCESS read-only
                STATUS current
                DESCRIPTION "Times a received packet was discarded."
                ::= { ilmiStatsEntry 12 }



-- Virtual UNI ILMI statistics table

vuniIlmiStatsTable        OBJECT-TYPE
                SYNTAX SEQUENCE OF VuniIlmiStatsEntry
                MAX-ACCESS not-accessible
                STATUS current
                DESCRIPTION "Table of statistics for an ILMI enabled interface."
                ::= { intfStatistics 12 }

vuniIlmiStatsEntry        OBJECT-TYPE
                SYNTAX VuniIlmiStatsEntry
                MAX-ACCESS not-accessible
                STATUS current
                DESCRIPTION "Row definition for the ILMI statistics table."
                INDEX { vuniIlmiStatsId, vuniIlmiVUNIId }
                ::= { vuniIlmiStatsTable 1 }

VuniIlmiStatsEntry        ::= SEQUENCE {
                vuniIlmiStatsId                        IntfIndex,
                vuniIlmiVUNIId        INTEGER,
                vuniIlmiStatsTimer                        Integer32,
                vuniIlmiStatsLinkResets                Integer32,
                vuniIlmiStatsAttachPtChanged        Integer32,
                vuniIlmiStatsAttachPtVerified        Integer32,
                vuniIlmiStatsSecureLnkProcInit        Integer32,
                vuniIlmiStatsColdStartRx                Integer32,
                vuniIlmiStatsColdStartTx                Integer32,
                vuniIlmiStatsPduRx                        Integer32,
                vuniIlmiStatsPduTx                        Integer32,
                vuniIlmiStatsReqTimeouts                Integer32,
                vuniIlmiStatsPacketDisc                Integer32,
        vuniResetIlmiStatistics     INTEGER
                }

vuniIlmiStatsId        OBJECT-TYPE
                SYNTAX IntfIndex
                MAX-ACCESS not-accessible
                STATUS current
                DESCRIPTION "Interface index (SSPPCCC) for the ILMI interface."
                ::= { vuniIlmiStatsEntry 1 }

vuniIlmiVUNIId        OBJECT-TYPE
                SYNTAX INTEGER (1..255)
                MAX-ACCESS not-accessible
                STATUS current
                DESCRIPTION "Virtual UNI number, second index to access the ILMI on
                     virtual UNI interface."
                DEFVAL { 1 }
                ::= { vuniIlmiStatsEntry 2 }

vuniIlmiStatsTimer        OBJECT-TYPE
                SYNTAX Integer32
                MAX-ACCESS read-only
                STATUS current
                DESCRIPTION "Time, in seconds, since last statistics reset."
                ::= { vuniIlmiStatsEntry 3 }

vuniIlmiStatsLinkResets OBJECT-TYPE
                SYNTAX Integer32
                MAX-ACCESS read-only
                STATUS current
                DESCRIPTION "Times connectivity has toggled between down and 
                             up."
                ::= { vuniIlmiStatsEntry 4 }

vuniIlmiStatsAttachPtChanged OBJECT-TYPE
                SYNTAX Integer32
                MAX-ACCESS read-only
                STATUS current
                DESCRIPTION "Times Attachment Point change was detected."
                ::= { vuniIlmiStatsEntry 5 }

vuniIlmiStatsAttachPtVerified OBJECT-TYPE
                SYNTAX Integer32
                MAX-ACCESS read-only
                STATUS current
                DESCRIPTION "Times Attachment Point was verified successfully."
                ::= { vuniIlmiStatsEntry 6 }

vuniIlmiStatsSecureLnkProcInit OBJECT-TYPE
                SYNTAX Integer32
                MAX-ACCESS read-only
                STATUS current
                DESCRIPTION "Times Secure Link Procedure was initiated."
                ::= { vuniIlmiStatsEntry 7 }

vuniIlmiStatsColdStartRx OBJECT-TYPE
                SYNTAX Integer32
                MAX-ACCESS read-only
                STATUS current
                DESCRIPTION "Times Cold Start trap was received."
                ::= { vuniIlmiStatsEntry 8 }

vuniIlmiStatsColdStartTx OBJECT-TYPE
                SYNTAX Integer32
                MAX-ACCESS read-only
                STATUS current
                DESCRIPTION "Times Cold Start trap was transmitted."
                ::= { vuniIlmiStatsEntry 9 }

vuniIlmiStatsPduRx OBJECT-TYPE
                SYNTAX Integer32
                MAX-ACCESS read-only
                STATUS current
                DESCRIPTION "vuniIlmi pdu received"
                ::= { vuniIlmiStatsEntry 10 }

vuniIlmiStatsPduTx OBJECT-TYPE
                SYNTAX Integer32
                MAX-ACCESS read-only
                STATUS current
                DESCRIPTION "vuniIlmi pdu transmitted"
                ::= { vuniIlmiStatsEntry 11 }

vuniIlmiStatsReqTimeouts OBJECT-TYPE
                SYNTAX Integer32
                MAX-ACCESS read-only
                STATUS current
                DESCRIPTION "Times getRequest of any type timed out."
                ::= { vuniIlmiStatsEntry 12 }

vuniIlmiStatsPacketDisc OBJECT-TYPE
                SYNTAX Integer32
                MAX-ACCESS read-only
                STATUS current
                DESCRIPTION "Times a received packet was discarded."
                ::= { vuniIlmiStatsEntry 13 }

vuniResetIlmiStatistics OBJECT-TYPE
                SYNTAX INTEGER
        {
          noAction (1),
          reset    (2)
        }
                MAX-ACCESS read-write
                STATUS current
                DESCRIPTION "Reset the ATM ILMI statistics counters for 
                             the given channel Id (SSPPCCC) and vuni Id"
        DEFVAL { noAction }
                ::= { vuniIlmiStatsEntry 14}



-- Connection Statistics Group connectionStatistics 

atmPvcVccStatsTable OBJECT-TYPE
                SYNTAX SEQUENCE OF AtmPvcVccStatsEntry
                MAX-ACCESS not-accessible
                STATUS current
                DESCRIPTION "Table of statistics for a channel connection"
                ::= { connectionStatistics 1 }

atmPvcVccStatsEntry OBJECT-TYPE
                SYNTAX AtmPvcVccStatsEntry
                MAX-ACCESS not-accessible
                STATUS current
                DESCRIPTION "Row definition for the connection statistics
                             table"
                INDEX { atmPvcVccStatsIfA, atmPvcVccStatsVpiA,
                        atmPvcVccStatsVciA, atmPvcVccStatsIfB,
                        atmPvcVccStatsVpiB, atmPvcVccStatsVciB }
                ::= { atmPvcVccStatsTable 1}

AtmPvcVccStatsEntry ::= SEQUENCE {
                atmPvcVccStatsIfA                         IntfIndex,
                atmPvcVccStatsVpiA                         INTEGER,
                atmPvcVccStatsVciA                        INTEGER,
                atmPvcVccStatsIfB                         IntfIndex,
                atmPvcVccStatsVpiB                         INTEGER,
                atmPvcVccStatsVciB                        INTEGER,
                atmPvcVccStatsInCellCountHiA                Integer32,
                atmPvcVccStatsInCellCountLoA                Integer32,
                atmPvcVccStatsOutCellCountHiA                 Integer32,
                atmPvcVccStatsOutCellCountLoA                 Integer32,
                atmPvcVccStatsInCellCountHiB                Integer32,
                atmPvcVccStatsInCellCountLoB                Integer32,
                atmPvcVccStatsOutCellCountHiB                 Integer32,
                atmPvcVccStatsOutCellCountLoB                 Integer32,
                atmPvcVccStatsTimer                        Integer32,
                atmPvcVccStatsFrwdErrCrrctnRateA2B         INTEGER,
                atmPvcVccStatsFrwdErrCrrctnRateB2A         INTEGER,
                atmPvcVccStatsInOdometerCellCountHiA        Integer32,
                atmPvcVccStatsInOdometerCellCountLoA        Integer32,
                atmPvcVccStatsOutOdometerCellCountHiA         Integer32,
                atmPvcVccStatsOutOdometerCellCountLoA         Integer32,
                atmPvcVccStatsInOdometerCellCountHiB        Integer32,
                atmPvcVccStatsInOdometerCellCountLoB        Integer32,
                atmPvcVccStatsOutOdometerCellCountHiB         Integer32,
                atmPvcVccStatsOutOdometerCellCountLoB         Integer32,
                atmPvcVccStatsOdometerTimer                Integer32,
                atmPvcVccStatsOdometerReset                 INTEGER,
                atmPvcVccStatsOamAisTxA                        Integer32,
                atmPvcVccStatsOamAisRxA                        Integer32,
                atmPvcVccStatsOamRdiTxA                        Integer32,
                atmPvcVccStatsOamRdiRxA                        Integer32,
                atmPvcVccStatsOamAisTxB                        Integer32,
                atmPvcVccStatsOamAisRxB                        Integer32,
                atmPvcVccStatsOamRdiTxB                        Integer32,
                atmPvcVccStatsOamRdiRxB                        Integer32,
                atmPvcVccStatsCellsDroppedA                  Integer32,
                atmPvcVccStatsCellsTaggedA                  Integer32,
                atmPvcVccStatsCellsDroppedB                  Integer32,
                atmPvcVccStatsCellsTaggedB                  Integer32
                }
atmPvcVccStatsIfA OBJECT-TYPE
                SYNTAX IntfIndex
                MAX-ACCESS not-accessible
                STATUS current
                DESCRIPTION "Interface index (SSPPCCC) on side A"
                ::= { atmPvcVccStatsEntry 1 }

atmPvcVccStatsVpiA OBJECT-TYPE
                SYNTAX INTEGER (0..4095)
                MAX-ACCESS not-accessible
                STATUS current
                DESCRIPTION "VPI on side A"
                ::= { atmPvcVccStatsEntry 2 }

atmPvcVccStatsVciA OBJECT-TYPE
                SYNTAX INTEGER (0..65535)
                MAX-ACCESS not-accessible
                STATUS current
                DESCRIPTION "VCI on side A"
                ::= { atmPvcVccStatsEntry 3 }

atmPvcVccStatsIfB OBJECT-TYPE
                SYNTAX IntfIndex
                MAX-ACCESS not-accessible
                STATUS current
                DESCRIPTION "Interface index (SSPPCCC) on side B"
                ::= { atmPvcVccStatsEntry 4 }

atmPvcVccStatsVpiB OBJECT-TYPE
                SYNTAX INTEGER (0..4095)
                MAX-ACCESS not-accessible
                STATUS current
                DESCRIPTION "VPI on side B"
                ::= { atmPvcVccStatsEntry 5 }

atmPvcVccStatsVciB OBJECT-TYPE
                SYNTAX INTEGER (0..65535)
                MAX-ACCESS not-accessible
                STATUS current
                DESCRIPTION "VCI on side B"
                ::= { atmPvcVccStatsEntry 6 }

atmPvcVccStatsInCellCountHiA OBJECT-TYPE
                SYNTAX Integer32
                MAX-ACCESS read-only
                STATUS current
                DESCRIPTION "Valid cells received (Input Billing Count)"
                ::= { atmPvcVccStatsEntry 7 }

atmPvcVccStatsInCellCountLoA OBJECT-TYPE
                SYNTAX Integer32
                MAX-ACCESS read-only
                STATUS current
                DESCRIPTION "Valid cells transmitted (Output Billing Count)"
                ::= { atmPvcVccStatsEntry 8 }

atmPvcVccStatsOutCellCountHiA OBJECT-TYPE
                SYNTAX Integer32
                MAX-ACCESS read-only
                STATUS current
                DESCRIPTION "Valid cells transmitted (Output Billing Count)"
                ::= { atmPvcVccStatsEntry 9 }

atmPvcVccStatsOutCellCountLoA OBJECT-TYPE
                SYNTAX Integer32
                MAX-ACCESS read-only
                STATUS current
                DESCRIPTION "Valid cells transmitted (Output Billing Count)"
                ::= { atmPvcVccStatsEntry 10 }

atmPvcVccStatsInCellCountHiB OBJECT-TYPE
                SYNTAX Integer32
                MAX-ACCESS read-only
                STATUS current
                DESCRIPTION "Valid cells received (Input Billing Count)"
                ::= { atmPvcVccStatsEntry 11 }

atmPvcVccStatsInCellCountLoB OBJECT-TYPE
                SYNTAX Integer32
                MAX-ACCESS read-only
                STATUS current
                DESCRIPTION "Valid cells transmitted (Output Billing Count)"
                ::= { atmPvcVccStatsEntry 12 }

atmPvcVccStatsOutCellCountHiB OBJECT-TYPE
                SYNTAX Integer32
                MAX-ACCESS read-only
                STATUS current
                DESCRIPTION "Valid cells transmitted (Output Billing Count)"
                ::= { atmPvcVccStatsEntry 13 }

atmPvcVccStatsOutCellCountLoB OBJECT-TYPE
                SYNTAX Integer32
                MAX-ACCESS read-only
                STATUS current
                DESCRIPTION "Valid cells transmitted (Output Billing Count)"
                ::= { atmPvcVccStatsEntry 14 }

atmPvcVccStatsTimer OBJECT-TYPE
                SYNTAX Integer32
                MAX-ACCESS read-only
                STATUS current
                DESCRIPTION "Number of seconds stats have been collecting"
                ::= { atmPvcVccStatsEntry 15 }

atmPvcVccStatsFrwdErrCrrctnRateA2B OBJECT-TYPE
                SYNTAX INTEGER {
                                none(1),
                                eighthRate(2),
                                quarterRate(3),
                                halfRate(4)
                               }
                MAX-ACCESS read-only
                STATUS current
                DESCRIPTION "Displays the Forward error correction rate being 
                             used by the FEC module in the A2B direction.  This
                             field is dynamic when Auto rates are selected.  In
                             other cases, it will display the rate set by the 
                             user."
                DEFVAL { none }
                ::= { atmPvcVccStatsEntry 16 }

atmPvcVccStatsFrwdErrCrrctnRateB2A OBJECT-TYPE
                SYNTAX INTEGER {
                                none(1),
                                eighthRate(2),
                                quarterRate(3),
                                halfRate(4)
                               }
                MAX-ACCESS read-only
                STATUS current
                DESCRIPTION "Displays the Forward error correction rate being 
                             used by the FEC module in the B2A direction.  This
                             field is dynamic when Auto rates are selected.  In
                             other cases, it will display the rate set by the 
                             user."
                DEFVAL { none }
                ::= { atmPvcVccStatsEntry 17 }

atmPvcVccStatsInOdometerCellCountHiA OBJECT-TYPE
                SYNTAX Integer32
                MAX-ACCESS read-only
                STATUS current
                DESCRIPTION "Valid cells received (Input Billing Count)"
                ::= { atmPvcVccStatsEntry 18 }

atmPvcVccStatsInOdometerCellCountLoA OBJECT-TYPE
                SYNTAX Integer32
                MAX-ACCESS read-only
                STATUS current
                DESCRIPTION "Valid cells transmitted (Output Billing Count)"
                ::= { atmPvcVccStatsEntry 19 }

atmPvcVccStatsOutOdometerCellCountHiA OBJECT-TYPE
                SYNTAX Integer32
                MAX-ACCESS read-only
                STATUS current
                DESCRIPTION "Valid cells transmitted (Output Billing Count)"
                ::= { atmPvcVccStatsEntry 20 }

atmPvcVccStatsOutOdometerCellCountLoA OBJECT-TYPE
                SYNTAX Integer32
                MAX-ACCESS read-only
                STATUS current
                DESCRIPTION "Valid cells transmitted (Output Billing Count)"
                ::= { atmPvcVccStatsEntry 21 }

atmPvcVccStatsInOdometerCellCountHiB OBJECT-TYPE
                SYNTAX Integer32
                MAX-ACCESS read-only
                STATUS current
                DESCRIPTION "Valid cells received (Input Billing Count)"
                ::= { atmPvcVccStatsEntry 22 }

atmPvcVccStatsInOdometerCellCountLoB OBJECT-TYPE
                SYNTAX Integer32
                MAX-ACCESS read-only
                STATUS current
                DESCRIPTION "Valid cells transmitted (Output Billing Count)"
                ::= { atmPvcVccStatsEntry 23 }

atmPvcVccStatsOutOdometerCellCountHiB OBJECT-TYPE
                SYNTAX Integer32
                MAX-ACCESS read-only
                STATUS current
                DESCRIPTION "Valid cells transmitted (Output Billing Count)"
                ::= { atmPvcVccStatsEntry 24 }

atmPvcVccStatsOutOdometerCellCountLoB OBJECT-TYPE
                SYNTAX Integer32
                MAX-ACCESS read-only
                STATUS current
                DESCRIPTION "Valid cells transmitted (Output Billing Count)"
                ::= { atmPvcVccStatsEntry 25 }

atmPvcVccStatsOdometerTimer OBJECT-TYPE
                SYNTAX Integer32
                MAX-ACCESS read-only
                STATUS current
                DESCRIPTION "Number of seconds since odometer was reset."
                ::= { atmPvcVccStatsEntry 26 }

atmPvcVccStatsOdometerReset OBJECT-TYPE
                SYNTAX INTEGER {
                                reset(1)
                               }
                MAX-ACCESS read-write
                STATUS current
                DESCRIPTION "Odometer reset button."
                ::= { atmPvcVccStatsEntry 27 }

atmPvcVccStatsOamAisTxA OBJECT-TYPE
                SYNTAX Integer32
                MAX-ACCESS read-only
                STATUS current
                DESCRIPTION "Number of AIS cells transmitted."
                ::= { atmPvcVccStatsEntry 28 }

atmPvcVccStatsOamAisRxA OBJECT-TYPE
                SYNTAX Integer32
                MAX-ACCESS read-only
                STATUS current
                DESCRIPTION "Number of AIS cells received."
                ::= { atmPvcVccStatsEntry 29 }

atmPvcVccStatsOamRdiTxA OBJECT-TYPE
                SYNTAX Integer32
                MAX-ACCESS read-only
                STATUS current
                DESCRIPTION "Number of RDI cells transmitted."
                ::= { atmPvcVccStatsEntry 30 }

atmPvcVccStatsOamRdiRxA OBJECT-TYPE
                SYNTAX Integer32
                MAX-ACCESS read-only
                STATUS current
                DESCRIPTION "Number of RDI cells received."
                ::= { atmPvcVccStatsEntry 31 }

atmPvcVccStatsOamAisTxB OBJECT-TYPE
                SYNTAX Integer32
                MAX-ACCESS read-only
                STATUS current
                DESCRIPTION "Number of AIS cells transmitted."
                ::= { atmPvcVccStatsEntry 32 }

atmPvcVccStatsOamAisRxB OBJECT-TYPE
                SYNTAX Integer32
                MAX-ACCESS read-only
                STATUS current
                DESCRIPTION "Number of AIS cells received."
                ::= { atmPvcVccStatsEntry 33 }

atmPvcVccStatsOamRdiTxB OBJECT-TYPE
                SYNTAX Integer32
                MAX-ACCESS read-only
                STATUS current
                DESCRIPTION "Number of RDI cells transmitted."
                ::= { atmPvcVccStatsEntry 34 }

atmPvcVccStatsOamRdiRxB OBJECT-TYPE
                SYNTAX Integer32
                MAX-ACCESS read-only
                STATUS current
                DESCRIPTION "Number of RDI cells received."
                ::= { atmPvcVccStatsEntry 35 }

atmPvcVccStatsCellsDroppedA OBJECT-TYPE
                  SYNTAX Integer32
                MAX-ACCESS read-only
                STATUS current
                DESCRIPTION "Cells Dropped on the Incoming side of A"
                ::= { atmPvcVccStatsEntry 36 }

atmPvcVccStatsCellsTaggedA OBJECT-TYPE
                SYNTAX Integer32
                MAX-ACCESS read-only
                STATUS current
                DESCRIPTION "Cells Tagged on the Incoming side of A"
                ::= { atmPvcVccStatsEntry 37 }

atmPvcVccStatsCellsDroppedB OBJECT-TYPE
                SYNTAX Integer32
                MAX-ACCESS read-only
                STATUS current
                DESCRIPTION "Cells Dropped on the Incoming side of B"
                ::= { atmPvcVccStatsEntry 38 }

atmPvcVccStatsCellsTaggedB OBJECT-TYPE
                SYNTAX Integer32
                MAX-ACCESS read-only
                STATUS current
                DESCRIPTION "Cells Tagged on the Incoming side of B"
                ::= { atmPvcVccStatsEntry 39 }

atmPvcVpcStatsTable OBJECT-TYPE
                SYNTAX SEQUENCE OF AtmPvcVpcStatsEntry
                MAX-ACCESS not-accessible
                STATUS current
                DESCRIPTION "Table of statistics for a channel connection"
                ::= { connectionStatistics 2 }

atmPvcVpcStatsEntry OBJECT-TYPE
                SYNTAX AtmPvcVpcStatsEntry
                MAX-ACCESS not-accessible
                STATUS current
                DESCRIPTION "Row definition for the connection statistics
                             table"
                INDEX { atmPvcVpcStatsIfA, atmPvcVpcStatsVpiA,
                        atmPvcVpcStatsIfB, atmPvcVpcStatsVpiB }
                ::= { atmPvcVpcStatsTable 1}

AtmPvcVpcStatsEntry ::= SEQUENCE {
                atmPvcVpcStatsIfA                         IntfIndex,
                atmPvcVpcStatsVpiA                         INTEGER,
                atmPvcVpcStatsIfB                         IntfIndex,
                atmPvcVpcStatsVpiB                         INTEGER,
                atmPvcVpcStatsInCellCountHiA                Integer32,
                atmPvcVpcStatsInCellCountLoA                Integer32,
                atmPvcVpcStatsOutCellCountHiA                 Integer32,
                atmPvcVpcStatsOutCellCountLoA                 Integer32,
                atmPvcVpcStatsInCellCountHiB                Integer32,
                atmPvcVpcStatsInCellCountLoB                Integer32,
                atmPvcVpcStatsOutCellCountHiB                 Integer32,
                atmPvcVpcStatsOutCellCountLoB                 Integer32,
                atmPvcVpcStatsTimer                        Integer32,
                atmPvcVpcStatsInOdometerCellCountHiA        Integer32,
                atmPvcVpcStatsInOdometerCellCountLoA        Integer32,
                atmPvcVpcStatsOutOdometerCellCountHiA         Integer32,
                atmPvcVpcStatsOutOdometerCellCountLoA         Integer32,
                atmPvcVpcStatsInOdometerCellCountHiB        Integer32,
                atmPvcVpcStatsInOdometerCellCountLoB        Integer32,
                atmPvcVpcStatsOutOdometerCellCountHiB         Integer32,
                atmPvcVpcStatsOutOdometerCellCountLoB         Integer32,
                atmPvcVpcStatsOdometerTimer                Integer32,
                atmPvcVpcStatsOdometerReset                INTEGER,
                atmPvcVpcStatsOamAisTxA                        Integer32,
                atmPvcVpcStatsOamAisRxA                        Integer32,
                atmPvcVpcStatsOamRdiTxA                        Integer32,
                atmPvcVpcStatsOamRdiRxA                        Integer32,
                atmPvcVpcStatsOamAisTxB                        Integer32,
                atmPvcVpcStatsOamAisRxB                        Integer32,
                atmPvcVpcStatsOamRdiTxB                        Integer32,
                atmPvcVpcStatsOamRdiRxB                        Integer32,
                atmPvcVpcStatsCellsDroppedA             Integer32,
                atmPvcVpcStatsCellsTaggedA              Integer32,
                atmPvcVpcStatsCellsDroppedB             Integer32,
                atmPvcVpcStatsCellsTaggedB                   Integer32
                }

atmPvcVpcStatsIfA OBJECT-TYPE
                SYNTAX IntfIndex
                MAX-ACCESS not-accessible
                STATUS current
                DESCRIPTION "Interface index (SSPPCCC) on side A"
                ::= { atmPvcVpcStatsEntry 1 }

atmPvcVpcStatsVpiA OBJECT-TYPE
                SYNTAX INTEGER (0..4095)
                MAX-ACCESS not-accessible
                STATUS current
                DESCRIPTION "VPI on side A"
                ::= { atmPvcVpcStatsEntry 2 }

atmPvcVpcStatsIfB OBJECT-TYPE
                SYNTAX IntfIndex
                MAX-ACCESS not-accessible
                STATUS current
                DESCRIPTION "Interface index (SSPPCCC) on side A"
                ::= { atmPvcVpcStatsEntry 3 }

atmPvcVpcStatsVpiB OBJECT-TYPE
                SYNTAX INTEGER (0..4095)
                MAX-ACCESS not-accessible
                STATUS current
                DESCRIPTION "VPI on side B"
                ::= { atmPvcVpcStatsEntry 4 }

atmPvcVpcStatsInCellCountHiA OBJECT-TYPE
                SYNTAX Integer32
                MAX-ACCESS read-only
                STATUS current
                DESCRIPTION "Valid cells received (Input Billing Count)"
                ::= { atmPvcVpcStatsEntry 5 }

atmPvcVpcStatsInCellCountLoA OBJECT-TYPE
                SYNTAX Integer32
                MAX-ACCESS read-only
                STATUS current
                DESCRIPTION "Valid cells received (Input Billing Count)"
                ::= { atmPvcVpcStatsEntry 6 }

atmPvcVpcStatsOutCellCountHiA OBJECT-TYPE
                SYNTAX Integer32
                MAX-ACCESS read-only
                STATUS current
                DESCRIPTION "Valid cells transmitted (Output Billing Count)"
                ::= { atmPvcVpcStatsEntry 7 }

atmPvcVpcStatsOutCellCountLoA OBJECT-TYPE
                SYNTAX Integer32
                MAX-ACCESS read-only
                STATUS current
                DESCRIPTION "Valid cells transmitted (Output Billing Count)"
                ::= { atmPvcVpcStatsEntry 8 }

atmPvcVpcStatsInCellCountHiB OBJECT-TYPE
                SYNTAX Integer32
                MAX-ACCESS read-only
                STATUS current
                DESCRIPTION "Valid cells received (Input Billing Count)"
                ::= { atmPvcVpcStatsEntry 9 }

atmPvcVpcStatsInCellCountLoB OBJECT-TYPE
                SYNTAX Integer32
                MAX-ACCESS read-only
                STATUS current
                DESCRIPTION "Valid cells received (Input Billing Count)"
                ::= { atmPvcVpcStatsEntry 10 }

atmPvcVpcStatsOutCellCountHiB OBJECT-TYPE
                SYNTAX Integer32
                MAX-ACCESS read-only
                STATUS current
                DESCRIPTION "Valid cells transmitted (Output Billing Count)"
                ::= { atmPvcVpcStatsEntry 11 }

atmPvcVpcStatsOutCellCountLoB OBJECT-TYPE
                SYNTAX Integer32
                MAX-ACCESS read-only
                STATUS current
                DESCRIPTION "Valid cells transmitted (Output Billing Count)"
                ::= { atmPvcVpcStatsEntry 12 }

atmPvcVpcStatsTimer OBJECT-TYPE
                SYNTAX Integer32
                MAX-ACCESS read-only
                STATUS current
                DESCRIPTION "Number of seconds stats have been collecting"
                ::= { atmPvcVpcStatsEntry 13 }

atmPvcVpcStatsInOdometerCellCountHiA OBJECT-TYPE
                SYNTAX Integer32
                MAX-ACCESS read-only
                STATUS current
                DESCRIPTION "Valid cells received (Input Billing Count)"
                ::= { atmPvcVpcStatsEntry 14 }

atmPvcVpcStatsInOdometerCellCountLoA OBJECT-TYPE
                SYNTAX Integer32
                MAX-ACCESS read-only
                STATUS current
                DESCRIPTION "Valid cells received (Input Billing Count)"
                ::= { atmPvcVpcStatsEntry 15 }

atmPvcVpcStatsOutOdometerCellCountHiA OBJECT-TYPE
                SYNTAX Integer32
                MAX-ACCESS read-only
                STATUS current
                DESCRIPTION "Valid cells transmitted (Output Billing Count)"
                ::= { atmPvcVpcStatsEntry 16 }

atmPvcVpcStatsOutOdometerCellCountLoA OBJECT-TYPE
                SYNTAX Integer32
                MAX-ACCESS read-only
                STATUS current
                DESCRIPTION "Valid cells transmitted (Output Billing Count)"
                ::= { atmPvcVpcStatsEntry 17 }

atmPvcVpcStatsInOdometerCellCountHiB OBJECT-TYPE
                SYNTAX Integer32
                MAX-ACCESS read-only
                STATUS current
                DESCRIPTION "Valid cells received (Input Billing Count)"
                ::= { atmPvcVpcStatsEntry 18 }

atmPvcVpcStatsInOdometerCellCountLoB OBJECT-TYPE
                SYNTAX Integer32
                MAX-ACCESS read-only
                STATUS current
                DESCRIPTION "Valid cells received (Input Billing Count)"
                ::= { atmPvcVpcStatsEntry 19 }

atmPvcVpcStatsOutOdometerCellCountHiB OBJECT-TYPE
                SYNTAX Integer32
                MAX-ACCESS read-only
                STATUS current
                DESCRIPTION "Valid cells transmitted (Output Billing Count)"
                ::= { atmPvcVpcStatsEntry 20 }

atmPvcVpcStatsOutOdometerCellCountLoB OBJECT-TYPE
                SYNTAX Integer32
                MAX-ACCESS read-only
                STATUS current
                DESCRIPTION "Valid cells transmitted (Output Billing Count)"
                ::= { atmPvcVpcStatsEntry 21 }

atmPvcVpcStatsOdometerTimer OBJECT-TYPE
                SYNTAX Integer32
                MAX-ACCESS read-only
                STATUS current
                DESCRIPTION "Number of seconds since odometer was reset."
                ::= { atmPvcVpcStatsEntry 22 }

atmPvcVpcStatsOdometerReset OBJECT-TYPE
                SYNTAX INTEGER {
                                reset(1)
                               }
                MAX-ACCESS read-write
                STATUS current
                DESCRIPTION "Odometer reset button."
                ::= { atmPvcVpcStatsEntry 23 }

atmPvcVpcStatsOamAisTxA OBJECT-TYPE
                SYNTAX Integer32
                MAX-ACCESS read-only
                STATUS current
                DESCRIPTION "Number of AIS cells transmitted."
                ::= { atmPvcVpcStatsEntry 24 }

atmPvcVpcStatsOamAisRxA OBJECT-TYPE
                SYNTAX Integer32
                MAX-ACCESS read-only
                STATUS current
                DESCRIPTION "Number of AIS cells received."
                ::= { atmPvcVpcStatsEntry 25 }

atmPvcVpcStatsOamRdiTxA OBJECT-TYPE
                SYNTAX Integer32
                MAX-ACCESS read-only
                STATUS current
                DESCRIPTION "Number of RDI cells transmitted."
                ::= { atmPvcVpcStatsEntry 26 }

atmPvcVpcStatsOamRdiRxA OBJECT-TYPE
                SYNTAX Integer32
                MAX-ACCESS read-only
                STATUS current
                DESCRIPTION "Number of RDI cells received."
                ::= { atmPvcVpcStatsEntry 27 }

atmPvcVpcStatsOamAisTxB OBJECT-TYPE
                SYNTAX Integer32
                MAX-ACCESS read-only
                STATUS current
                DESCRIPTION "Number of AIS cells transmitted."
                ::= { atmPvcVpcStatsEntry 28 }

atmPvcVpcStatsOamAisRxB OBJECT-TYPE
                SYNTAX Integer32
                MAX-ACCESS read-only
                STATUS current
                DESCRIPTION "Number of AIS cells received."
                ::= { atmPvcVpcStatsEntry 29 }

atmPvcVpcStatsOamRdiTxB OBJECT-TYPE
                SYNTAX Integer32
                MAX-ACCESS read-only
                STATUS current
                DESCRIPTION "Number of RDI cells transmitted."
                ::= { atmPvcVpcStatsEntry 30 }

atmPvcVpcStatsOamRdiRxB OBJECT-TYPE
                SYNTAX Integer32
                MAX-ACCESS read-only
                STATUS current
                DESCRIPTION "Number of RDI cells received."
                ::= { atmPvcVpcStatsEntry 31 }

atmPvcVpcStatsCellsDroppedA OBJECT-TYPE
                SYNTAX Integer32
                MAX-ACCESS read-only
                STATUS current
                DESCRIPTION "Cells Dropped on the Incoming side of A"
                ::= { atmPvcVpcStatsEntry 32 }

atmPvcVpcStatsCellsTaggedA OBJECT-TYPE
                SYNTAX Integer32
                MAX-ACCESS read-only
                STATUS current
                DESCRIPTION "Cells Tagged on the Incoming side of A"
                ::= { atmPvcVpcStatsEntry 33 }

atmPvcVpcStatsCellsDroppedB OBJECT-TYPE
                SYNTAX Integer32
                MAX-ACCESS read-only
                STATUS current
                DESCRIPTION "Cells Dropped on the Incoming side of B"
                ::= { atmPvcVpcStatsEntry 34 }

atmPvcVpcStatsCellsTaggedB OBJECT-TYPE
                SYNTAX Integer32
                MAX-ACCESS read-only
                STATUS current
                DESCRIPTION "Cells Tagged on the Incoming side of B"
                ::= { atmPvcVpcStatsEntry 35 }

atmSvcVccStatsTable OBJECT-TYPE
                SYNTAX SEQUENCE OF AtmSvcVccStatsEntry
                MAX-ACCESS not-accessible
                STATUS current
                DESCRIPTION "Table of statistics for a channel connection"
                ::= { connectionStatistics 3 }

atmSvcVccStatsEntry OBJECT-TYPE
                SYNTAX AtmSvcVccStatsEntry
                MAX-ACCESS not-accessible
                STATUS current
                DESCRIPTION "Row definition for the connection statistics
                             table"
                INDEX { atmSvcVccStatsIfA, atmSvcVccStatsVpiA,
                        atmSvcVccStatsVciA, atmSvcVccStatsIfB,
                        atmSvcVccStatsVpiB, atmSvcVccStatsVciB }
                ::= { atmSvcVccStatsTable 1}

AtmSvcVccStatsEntry ::= SEQUENCE {
                atmSvcVccStatsIfA                         IntfIndex,
                atmSvcVccStatsVpiA                         INTEGER,
                atmSvcVccStatsVciA                        INTEGER,
                atmSvcVccStatsIfB                         IntfIndex,
                atmSvcVccStatsVpiB                         INTEGER,
                atmSvcVccStatsVciB                        INTEGER,
                atmSvcVccStatsInCellCountHiA                Integer32,
                atmSvcVccStatsInCellCountLoA                Integer32,
                atmSvcVccStatsOutCellCountHiA                 Integer32,
                atmSvcVccStatsOutCellCountLoA                 Integer32,
                atmSvcVccStatsInCellCountHiB                Integer32,
                atmSvcVccStatsInCellCountLoB                Integer32,
                atmSvcVccStatsOutCellCountHiB                 Integer32,
                atmSvcVccStatsOutCellCountLoB                 Integer32,
                atmSvcVccStatsTimer                        Integer32,
                atmSvcVccStatsInOdometerCellCountHiA        Integer32,
                atmSvcVccStatsInOdometerCellCountLoA        Integer32,
                atmSvcVccStatsOutOdometerCellCountHiA         Integer32,
                atmSvcVccStatsOutOdometerCellCountLoA         Integer32,
                atmSvcVccStatsInOdometerCellCountHiB        Integer32,
                atmSvcVccStatsInOdometerCellCountLoB        Integer32,
                atmSvcVccStatsOutOdometerCellCountHiB         Integer32,
                atmSvcVccStatsOutOdometerCellCountLoB         Integer32,
                atmSvcVccStatsOdometerTimer                Integer32,
                atmSvcVccStatsOdometerReset                INTEGER,
                atmSvcVccStatsCellsDroppedA                  Integer32,
                atmSvcVccStatsCellsTaggedA                  Integer32,
                atmSvcVccStatsCellsDroppedB                  Integer32,
                atmSvcVccStatsCellsTaggedB                  Integer32
                }

atmSvcVccStatsIfA OBJECT-TYPE
                SYNTAX IntfIndex
                MAX-ACCESS not-accessible
                STATUS current
                DESCRIPTION "Interface index (SSPPCCC) on side A"
                ::= { atmSvcVccStatsEntry 1 }

atmSvcVccStatsVpiA OBJECT-TYPE
                SYNTAX INTEGER (0..4095)
                MAX-ACCESS not-accessible
                STATUS current
                DESCRIPTION "VPI on side A"
                ::= { atmSvcVccStatsEntry 2 }

atmSvcVccStatsVciA OBJECT-TYPE
                SYNTAX INTEGER (0..65535)
                MAX-ACCESS not-accessible
                STATUS current
                DESCRIPTION "VCI on side A"
                ::= { atmSvcVccStatsEntry 3 }

atmSvcVccStatsIfB OBJECT-TYPE
                SYNTAX IntfIndex
                MAX-ACCESS not-accessible
                STATUS current
                DESCRIPTION "Interface index (SSPPCCC) on side A"
                ::= { atmSvcVccStatsEntry 4 }

atmSvcVccStatsVpiB OBJECT-TYPE
                SYNTAX INTEGER (0..4095)
                MAX-ACCESS not-accessible
                STATUS current
                DESCRIPTION "VPI on side B"
                ::= { atmSvcVccStatsEntry 5 }

atmSvcVccStatsVciB OBJECT-TYPE
                SYNTAX INTEGER (0..65535)
                MAX-ACCESS not-accessible
                STATUS current
                DESCRIPTION "VCI on side B"
                ::= { atmSvcVccStatsEntry 6 }

atmSvcVccStatsInCellCountHiA OBJECT-TYPE
                SYNTAX Integer32
                MAX-ACCESS read-only
                STATUS current
                DESCRIPTION "Valid cells received (Input Billing Count)"
                ::= { atmSvcVccStatsEntry 7 }

atmSvcVccStatsInCellCountLoA OBJECT-TYPE
                SYNTAX Integer32
                MAX-ACCESS read-only
                STATUS current
                DESCRIPTION "Valid cells received (Input Billing Count)"
                ::= { atmSvcVccStatsEntry 8 }

atmSvcVccStatsOutCellCountHiA OBJECT-TYPE
                SYNTAX Integer32
                MAX-ACCESS read-only
                STATUS current
                DESCRIPTION "Valid cells transmitted (Output Billing Count)"
                ::= { atmSvcVccStatsEntry 9 }

atmSvcVccStatsOutCellCountLoA OBJECT-TYPE
                SYNTAX Integer32
                MAX-ACCESS read-only
                STATUS current
                DESCRIPTION "Valid cells transmitted (Output Billing Count)"
                ::= { atmSvcVccStatsEntry 10 }

atmSvcVccStatsInCellCountHiB OBJECT-TYPE
                SYNTAX Integer32
                MAX-ACCESS read-only
                STATUS current
                DESCRIPTION "Valid cells received (Input Billing Count)"
                ::= { atmSvcVccStatsEntry 11 }

atmSvcVccStatsInCellCountLoB OBJECT-TYPE
                SYNTAX Integer32
                MAX-ACCESS read-only
                STATUS current
                DESCRIPTION "Valid cells received (Input Billing Count)"
                ::= { atmSvcVccStatsEntry 12 }

atmSvcVccStatsOutCellCountHiB OBJECT-TYPE
                SYNTAX Integer32
                MAX-ACCESS read-only
                STATUS current
                DESCRIPTION "Valid cells transmitted (Output Billing Count)"
                ::= { atmSvcVccStatsEntry 13 }

atmSvcVccStatsOutCellCountLoB OBJECT-TYPE
                SYNTAX Integer32
                MAX-ACCESS read-only
                STATUS current
                DESCRIPTION "Valid cells transmitted (Output Billing Count)"
                ::= { atmSvcVccStatsEntry 14 }

atmSvcVccStatsTimer OBJECT-TYPE
                SYNTAX Integer32
                MAX-ACCESS read-only
                STATUS current
                DESCRIPTION "Number of seconds stats have been collecting"
                ::= { atmSvcVccStatsEntry 15 }

atmSvcVccStatsInOdometerCellCountHiA OBJECT-TYPE
                SYNTAX Integer32
                MAX-ACCESS read-only
                STATUS current
                DESCRIPTION "Valid cells received (Input Billing Count)"
                ::= { atmSvcVccStatsEntry 16 }

atmSvcVccStatsInOdometerCellCountLoA OBJECT-TYPE
                SYNTAX Integer32
                MAX-ACCESS read-only
                STATUS current
                DESCRIPTION "Valid cells received (Input Billing Count)"
                ::= { atmSvcVccStatsEntry 17 }

atmSvcVccStatsOutOdometerCellCountHiA OBJECT-TYPE
                SYNTAX Integer32
                MAX-ACCESS read-only
                STATUS current
                DESCRIPTION "Valid cells transmitted (Output Billing Count)"
                ::= { atmSvcVccStatsEntry 18 }

atmSvcVccStatsOutOdometerCellCountLoA OBJECT-TYPE
                SYNTAX Integer32
                MAX-ACCESS read-only
                STATUS current
                DESCRIPTION "Valid cells transmitted (Output Billing Count)"
                ::= { atmSvcVccStatsEntry 19 }

atmSvcVccStatsInOdometerCellCountHiB OBJECT-TYPE
                SYNTAX Integer32
                MAX-ACCESS read-only
                STATUS current
                DESCRIPTION "Valid cells received (Input Billing Count)"
                ::= { atmSvcVccStatsEntry 20 }

atmSvcVccStatsInOdometerCellCountLoB OBJECT-TYPE
                SYNTAX Integer32
                MAX-ACCESS read-only
                STATUS current
                DESCRIPTION "Valid cells received (Input Billing Count)"
                ::= { atmSvcVccStatsEntry 21 }

atmSvcVccStatsOutOdometerCellCountHiB OBJECT-TYPE
                SYNTAX Integer32
                MAX-ACCESS read-only
                STATUS current
                DESCRIPTION "Valid cells transmitted (Output Billing Count)"
                ::= { atmSvcVccStatsEntry 22 }

atmSvcVccStatsOutOdometerCellCountLoB OBJECT-TYPE
                SYNTAX Integer32
                MAX-ACCESS read-only
                STATUS current
                DESCRIPTION "Valid cells transmitted (Output Billing Count)"
                ::= { atmSvcVccStatsEntry 23 }

atmSvcVccStatsOdometerTimer OBJECT-TYPE
                SYNTAX Integer32
                MAX-ACCESS read-only
                STATUS current
                DESCRIPTION "Number of seconds since odometer was reset."
                ::= { atmSvcVccStatsEntry 24 }

atmSvcVccStatsOdometerReset OBJECT-TYPE
                SYNTAX INTEGER {
                                reset(1)
                               }
                MAX-ACCESS read-write
                STATUS current
                DESCRIPTION "Odometer reset button."
                ::= { atmSvcVccStatsEntry 25 }

atmSvcVccStatsCellsDroppedA OBJECT-TYPE
                SYNTAX Integer32
                MAX-ACCESS read-only
                STATUS current
                DESCRIPTION "Cells Dropped on the Incoming side of A"
                ::= { atmSvcVccStatsEntry 26 }

atmSvcVccStatsCellsTaggedA OBJECT-TYPE 
                SYNTAX Integer32
                MAX-ACCESS read-only
                STATUS current
                DESCRIPTION "Cells Tagged on the Incoming side of A"
                ::= { atmSvcVccStatsEntry 27 }

atmSvcVccStatsCellsDroppedB OBJECT-TYPE
                SYNTAX Integer32
                MAX-ACCESS read-only
                STATUS current
                DESCRIPTION "Cells Dropped on the Incoming side of B"
                ::= { atmSvcVccStatsEntry 28 }

atmSvcVccStatsCellsTaggedB OBJECT-TYPE
                SYNTAX Integer32
                MAX-ACCESS read-only
                STATUS current
                DESCRIPTION "Cells Tagged on the Incoming side of B"
                ::= { atmSvcVccStatsEntry 29 }

ipAtmAppPvcVccStatsTable OBJECT-TYPE
                SYNTAX SEQUENCE OF IpAtmAppPvcVccStatsEntry
                MAX-ACCESS not-accessible
                STATUS current
                DESCRIPTION "Table of Statistics entries"
                ::= { connectionStatistics 4 }

ipAtmAppPvcVccStatsEntry OBJECT-TYPE
                SYNTAX IpAtmAppPvcVccStatsEntry
                MAX-ACCESS not-accessible
                STATUS current
                DESCRIPTION "Row definition for statistics attribution."
                INDEX { ipAtmAppPvcVccStatsDestAddrA, 
                        ipAtmAppPvcVccStatsSubnetMaskA, ipAtmAppPvcVccStatsIfB,
                        ipAtmAppPvcVccStatsVpiB, ipAtmAppPvcVccStatsVciB }
                ::= { ipAtmAppPvcVccStatsTable 1}

IpAtmAppPvcVccStatsEntry ::= SEQUENCE {
                ipAtmAppPvcVccStatsDestAddrA                        IpAddress,
                ipAtmAppPvcVccStatsSubnetMaskA                        IpAddress,
                ipAtmAppPvcVccStatsIfB                                 IntfIndex,
                ipAtmAppPvcVccStatsVpiB                                 INTEGER,
                ipAtmAppPvcVccStatsVciB                                INTEGER,
                ipAtmAppPvcVccStatsInCellCountHiA                Integer32,
                ipAtmAppPvcVccStatsInCellCountLoA                Integer32,
                ipAtmAppPvcVccStatsOutCellCountHiA                 Integer32,
                ipAtmAppPvcVccStatsOutCellCountLoA                 Integer32,
                ipAtmAppPvcVccStatsFramesInB                        Integer32,
                ipAtmAppPvcVccStatsFramesOutB                        Integer32,
                ipAtmAppPvcVccStatsInCellCountHiB                Integer32,
                ipAtmAppPvcVccStatsInCellCountLoB                Integer32,
                ipAtmAppPvcVccStatsOutCellCountHiB                 Integer32,
                ipAtmAppPvcVccStatsOutCellCountLoB                 Integer32,
                ipAtmAppPvcVccStatsTimer                        Integer32,
                ipAtmAppPvcVccStatsInOdometerCellCountHiA        Integer32,
                ipAtmAppPvcVccStatsInOdometerCellCountLoA        Integer32,
                ipAtmAppPvcVccStatsOutOdometerCellCountHiA         Integer32,
                ipAtmAppPvcVccStatsOutOdometerCellCountLoA         Integer32,
                ipAtmAppPvcVccStatsOdometerFramesInB                Integer32,
                ipAtmAppPvcVccStatsOdometerFramesOutB                Integer32,
                ipAtmAppPvcVccStatsInOdometerCellCountHiB        Integer32,
                ipAtmAppPvcVccStatsInOdometerCellCountLoB        Integer32,
                ipAtmAppPvcVccStatsOutOdometerCellCountHiB         Integer32,
                ipAtmAppPvcVccStatsOutOdometerCellCountLoB         Integer32,
                ipAtmAppPvcVccStatsOdometerTimer                Integer32,
                ipAtmAppPvcVccStatsOdometerReset                INTEGER,
                ipAtmAppPvcVccStatsCellsDroppedB                 Integer32,
                ipAtmAppPvcVccStatsCellsTaggedB                  Integer32
                }

ipAtmAppPvcVccStatsDestAddrA OBJECT-TYPE
                SYNTAX IpAddress
                MAX-ACCESS not-accessible
                STATUS current
                DESCRIPTION "Statistics destination IP address"
                ::= { ipAtmAppPvcVccStatsEntry 1 }

ipAtmAppPvcVccStatsSubnetMaskA OBJECT-TYPE
                SYNTAX IpAddress
                MAX-ACCESS not-accessible
                STATUS current
                DESCRIPTION "The subnet mask of the destination IP address.
                             Value is an IP address."
                ::= { ipAtmAppPvcVccStatsEntry 2 }

ipAtmAppPvcVccStatsIfB OBJECT-TYPE
                SYNTAX IntfIndex
                MAX-ACCESS not-accessible
                STATUS current
                DESCRIPTION "Interface index (SSPPCCC) on side B"
                ::= { ipAtmAppPvcVccStatsEntry 3 }

ipAtmAppPvcVccStatsVpiB OBJECT-TYPE
                SYNTAX INTEGER (0..4095)
                MAX-ACCESS not-accessible
                STATUS current
                DESCRIPTION "VPI on side B"
                ::= { ipAtmAppPvcVccStatsEntry 4 }

ipAtmAppPvcVccStatsVciB OBJECT-TYPE
                SYNTAX INTEGER (0..65535)
                MAX-ACCESS not-accessible
                STATUS current
                DESCRIPTION "VCI on side B"
                ::= { ipAtmAppPvcVccStatsEntry 5 }

ipAtmAppPvcVccStatsInCellCountHiA OBJECT-TYPE
                SYNTAX Integer32
                MAX-ACCESS read-only
                STATUS current
                DESCRIPTION "Valid cells received (Input Billing Count)"
                ::= { ipAtmAppPvcVccStatsEntry 6 }

ipAtmAppPvcVccStatsInCellCountLoA OBJECT-TYPE
                SYNTAX Integer32
                MAX-ACCESS read-only
                STATUS current
                DESCRIPTION "Valid cells received (Input Billing Count)"
                ::= { ipAtmAppPvcVccStatsEntry 7 }

ipAtmAppPvcVccStatsOutCellCountHiA OBJECT-TYPE
                SYNTAX Integer32
                MAX-ACCESS read-only
                STATUS current
                DESCRIPTION "Valid cells transmitted (Output Billing Count)"
                ::= { ipAtmAppPvcVccStatsEntry 8 }

ipAtmAppPvcVccStatsOutCellCountLoA OBJECT-TYPE
                SYNTAX Integer32
                MAX-ACCESS read-only
                STATUS current
                DESCRIPTION "Valid cells transmitted (Output Billing Count)"
                ::= { ipAtmAppPvcVccStatsEntry 9 }

ipAtmAppPvcVccStatsFramesInB OBJECT-TYPE
                SYNTAX Integer32
                MAX-ACCESS read-only
                STATUS current
                DESCRIPTION "number of frames received on side B."
                ::= { ipAtmAppPvcVccStatsEntry 10 }

ipAtmAppPvcVccStatsFramesOutB OBJECT-TYPE
                SYNTAX Integer32
                MAX-ACCESS read-only
                STATUS current
                DESCRIPTION "number of frames sent from side B."
                ::= { ipAtmAppPvcVccStatsEntry 11 }

ipAtmAppPvcVccStatsInCellCountHiB OBJECT-TYPE
                SYNTAX Integer32
                MAX-ACCESS read-only
                STATUS current
                DESCRIPTION "Valid cells received (Input Billing Count)"
                ::= { ipAtmAppPvcVccStatsEntry 12 }

ipAtmAppPvcVccStatsInCellCountLoB OBJECT-TYPE
                SYNTAX Integer32
                MAX-ACCESS read-only
                STATUS current
                DESCRIPTION "Valid cells received (Input Billing Count)"
                ::= { ipAtmAppPvcVccStatsEntry 13 }

ipAtmAppPvcVccStatsOutCellCountHiB OBJECT-TYPE
                SYNTAX Integer32
                MAX-ACCESS read-only
                STATUS current
                DESCRIPTION "Valid cells transmitted (Output Billing Count)"
                ::= { ipAtmAppPvcVccStatsEntry 14 }

ipAtmAppPvcVccStatsOutCellCountLoB OBJECT-TYPE
                SYNTAX Integer32
                MAX-ACCESS read-only
                STATUS current
                DESCRIPTION "Valid cells transmitted (Output Billing Count)"
                ::= { ipAtmAppPvcVccStatsEntry 15 }

ipAtmAppPvcVccStatsTimer OBJECT-TYPE
                SYNTAX Integer32
                MAX-ACCESS read-only
                STATUS current
                DESCRIPTION "Number of seconds stats have been collecting"
                ::= { ipAtmAppPvcVccStatsEntry 16 }

ipAtmAppPvcVccStatsInOdometerCellCountHiA OBJECT-TYPE
                SYNTAX Integer32
                MAX-ACCESS read-only
                STATUS current
                DESCRIPTION "Valid cells received (Input Billing Count)"
                ::= { ipAtmAppPvcVccStatsEntry 17 }

ipAtmAppPvcVccStatsInOdometerCellCountLoA OBJECT-TYPE
                SYNTAX Integer32
                MAX-ACCESS read-only
                STATUS current
                DESCRIPTION "Valid cells received (Input Billing Count)"
                ::= { ipAtmAppPvcVccStatsEntry 18 }

ipAtmAppPvcVccStatsOutOdometerCellCountHiA OBJECT-TYPE
                SYNTAX Integer32
                MAX-ACCESS read-only
                STATUS current
                DESCRIPTION "Valid cells transmitted (Output Billing Count)"
                ::= { ipAtmAppPvcVccStatsEntry 19 }

ipAtmAppPvcVccStatsOutOdometerCellCountLoA OBJECT-TYPE
                SYNTAX Integer32
                MAX-ACCESS read-only
                STATUS current
                DESCRIPTION "Valid cells transmitted (Output Billing Count)"
                ::= { ipAtmAppPvcVccStatsEntry 20 }

ipAtmAppPvcVccStatsOdometerFramesInB OBJECT-TYPE
                SYNTAX Integer32
                MAX-ACCESS read-only
                STATUS current
                DESCRIPTION "Valid frames received at side B."
                ::= { ipAtmAppPvcVccStatsEntry 21 }

ipAtmAppPvcVccStatsOdometerFramesOutB OBJECT-TYPE
                SYNTAX Integer32
                MAX-ACCESS read-only
                STATUS current
                DESCRIPTION "Valid frames transmitted from side B."
                ::= { ipAtmAppPvcVccStatsEntry 22 }

ipAtmAppPvcVccStatsInOdometerCellCountHiB OBJECT-TYPE
                SYNTAX Integer32
                MAX-ACCESS read-only
                STATUS current
                DESCRIPTION "Valid cells received (Input Billing Count)"
                ::= { ipAtmAppPvcVccStatsEntry 23 }

ipAtmAppPvcVccStatsInOdometerCellCountLoB OBJECT-TYPE
                SYNTAX Integer32
                MAX-ACCESS read-only
                STATUS current
                DESCRIPTION "Valid cells received (Input Billing Count)"
                ::= { ipAtmAppPvcVccStatsEntry 24 }

ipAtmAppPvcVccStatsOutOdometerCellCountHiB OBJECT-TYPE
                SYNTAX Integer32
                MAX-ACCESS read-only
                STATUS current
                DESCRIPTION "Valid cells transmitted (Output Billing Count)"
                ::= { ipAtmAppPvcVccStatsEntry 25 }

ipAtmAppPvcVccStatsOutOdometerCellCountLoB OBJECT-TYPE
                SYNTAX Integer32
                MAX-ACCESS read-only
                STATUS current
                DESCRIPTION "Valid cells transmitted (Output Billing Count)"
                ::= { ipAtmAppPvcVccStatsEntry 26 }

ipAtmAppPvcVccStatsOdometerTimer OBJECT-TYPE
                SYNTAX Integer32
                MAX-ACCESS read-only
                STATUS current
                DESCRIPTION "Number of seconds since odometer was reset."
                ::= { ipAtmAppPvcVccStatsEntry 27 }

ipAtmAppPvcVccStatsOdometerReset OBJECT-TYPE
                SYNTAX INTEGER {
                                reset(1)
                               }
                MAX-ACCESS read-write
                STATUS current
                DESCRIPTION "Odometer reset button."
                ::= { ipAtmAppPvcVccStatsEntry 28 }

ipAtmAppPvcVccStatsCellsDroppedB OBJECT-TYPE
                SYNTAX Integer32
                MAX-ACCESS read-only
                STATUS current
                DESCRIPTION "Cells Dropped on the Incoming side of B"
                ::= { ipAtmAppPvcVccStatsEntry 29 }

ipAtmAppPvcVccStatsCellsTaggedB OBJECT-TYPE
                SYNTAX Integer32
                MAX-ACCESS read-only
                STATUS current
                DESCRIPTION "Cells Tagged on the Incoming side of B"
                ::= { ipAtmAppPvcVccStatsEntry 30 }

ipAtmAppSvcVccStatsTable OBJECT-TYPE
                SYNTAX SEQUENCE OF IpAtmAppSvcVccStatsEntry
                MAX-ACCESS not-accessible
                STATUS current
                DESCRIPTION "Table of statistics entries"
                ::= { connectionStatistics 5 }

ipAtmAppSvcVccStatsEntry OBJECT-TYPE
                SYNTAX IpAtmAppSvcVccStatsEntry
                MAX-ACCESS not-accessible
                STATUS current
                DESCRIPTION "Row definition of statistics attributes."
                INDEX { ipAtmAppSvcVccStatsDestAddrA,
                        ipAtmAppSvcVccStatsSubnetMaskA, ipAtmAppSvcVccStatsIfB,
                        ipAtmAppSvcVccStatsVpiB, ipAtmAppSvcVccStatsVciB }
                ::= { ipAtmAppSvcVccStatsTable 1}

IpAtmAppSvcVccStatsEntry ::= SEQUENCE {
                ipAtmAppSvcVccStatsDestAddrA                IpAddress,
                ipAtmAppSvcVccStatsSubnetMaskA                IpAddress,
                ipAtmAppSvcVccStatsIfB                         IntfIndex,
                ipAtmAppSvcVccStatsVpiB                         INTEGER,
                ipAtmAppSvcVccStatsVciB                        INTEGER,
                ipAtmAppSvcVccStatsInCellCountHiA        Integer32,
                ipAtmAppSvcVccStatsInCellCountLoA        Integer32,
                ipAtmAppSvcVccStatsOutCellCountHiA         Integer32,
                ipAtmAppSvcVccStatsOutCellCountLoA         Integer32,
                ipAtmAppSvcVccStatsFramesInB                Integer32,
                ipAtmAppSvcVccStatsFramesOutB                Integer32,
                ipAtmAppSvcVccStatsInCellCountHiB        Integer32,
                ipAtmAppSvcVccStatsInCellCountLoB        Integer32,
                ipAtmAppSvcVccStatsOutCellCountHiB         Integer32,
                ipAtmAppSvcVccStatsOutCellCountLoB         Integer32,
                ipAtmAppSvcVccStatsTimer                Integer32,
                ipAtmAppSvcVccStatsCellsDroppedB         Integer32, 
                ipAtmAppSvcVccStatsCellsTaggedB          Integer32
                }

ipAtmAppSvcVccStatsDestAddrA OBJECT-TYPE
                SYNTAX IpAddress
                MAX-ACCESS not-accessible
                STATUS current
                DESCRIPTION "Statistics destination IP address "
                ::= { ipAtmAppSvcVccStatsEntry 1 }

ipAtmAppSvcVccStatsSubnetMaskA OBJECT-TYPE
                SYNTAX IpAddress
                MAX-ACCESS not-accessible
                STATUS current
                DESCRIPTION "The subnet mask of the destination IP address.
                             Value is an IP address."
                ::= { ipAtmAppSvcVccStatsEntry 2 }

ipAtmAppSvcVccStatsIfB OBJECT-TYPE
                SYNTAX IntfIndex
                MAX-ACCESS not-accessible
                STATUS current
                DESCRIPTION "Interface index (SSPPCCC) on side B"
                ::= { ipAtmAppSvcVccStatsEntry 3 }

ipAtmAppSvcVccStatsVpiB OBJECT-TYPE
                SYNTAX INTEGER (0..4095)
                MAX-ACCESS not-accessible
                STATUS current
                DESCRIPTION "VPI on side B"
                ::= { ipAtmAppSvcVccStatsEntry 4 }

ipAtmAppSvcVccStatsVciB OBJECT-TYPE
                SYNTAX INTEGER (0..65535)
                MAX-ACCESS not-accessible
                STATUS current
                DESCRIPTION "VCI on side B"
                ::= { ipAtmAppSvcVccStatsEntry 5 }

ipAtmAppSvcVccStatsInCellCountHiA OBJECT-TYPE
                SYNTAX Integer32
                MAX-ACCESS read-only
                STATUS current
                DESCRIPTION "Valid cells received (Input Billing Count)"
                ::= { ipAtmAppSvcVccStatsEntry 6 }

ipAtmAppSvcVccStatsInCellCountLoA OBJECT-TYPE
                SYNTAX Integer32
                MAX-ACCESS read-only
                STATUS current
                DESCRIPTION "Valid cells received (Input Billing Count)"
                ::= { ipAtmAppSvcVccStatsEntry 7 }

ipAtmAppSvcVccStatsOutCellCountHiA OBJECT-TYPE
                SYNTAX Integer32
                MAX-ACCESS read-only
                STATUS current
                DESCRIPTION "Valid cells transmitted (Output Billing Count)"
                ::= { ipAtmAppSvcVccStatsEntry 8 }

ipAtmAppSvcVccStatsOutCellCountLoA OBJECT-TYPE
                SYNTAX Integer32
                MAX-ACCESS read-only
                STATUS current
                DESCRIPTION "Valid cells transmitted (Output Billing Count)"
                ::= { ipAtmAppSvcVccStatsEntry 9 }

ipAtmAppSvcVccStatsFramesInB OBJECT-TYPE
                SYNTAX Integer32
                MAX-ACCESS read-only
                STATUS current
                DESCRIPTION "Frames received at side B."
                ::= { ipAtmAppSvcVccStatsEntry 10 }

ipAtmAppSvcVccStatsFramesOutB OBJECT-TYPE
                SYNTAX Integer32
                MAX-ACCESS read-only
                STATUS current
                DESCRIPTION "Frames transmitted from side B."
                ::= { ipAtmAppSvcVccStatsEntry 11 }

ipAtmAppSvcVccStatsInCellCountHiB OBJECT-TYPE
                SYNTAX Integer32
                MAX-ACCESS read-only
                STATUS current
                DESCRIPTION "Valid cells received (Input Billing Count)"
                ::= { ipAtmAppSvcVccStatsEntry 12 }

ipAtmAppSvcVccStatsInCellCountLoB OBJECT-TYPE
                SYNTAX Integer32
                MAX-ACCESS read-only
                STATUS current
                DESCRIPTION "Valid cells received (Input Billing Count)"
                ::= { ipAtmAppSvcVccStatsEntry 13 }

ipAtmAppSvcVccStatsOutCellCountHiB OBJECT-TYPE
                SYNTAX Integer32
                MAX-ACCESS read-only
                STATUS current
                DESCRIPTION "Valid cells transmitted (Output Billing Count)"
                ::= { ipAtmAppSvcVccStatsEntry 14 }

ipAtmAppSvcVccStatsOutCellCountLoB OBJECT-TYPE
                SYNTAX Integer32
                MAX-ACCESS read-only
                STATUS current
                DESCRIPTION "Valid cells transmitted (Output Billing Count)"
                ::= { ipAtmAppSvcVccStatsEntry 15 }

ipAtmAppSvcVccStatsTimer OBJECT-TYPE
                SYNTAX Integer32
                MAX-ACCESS read-only
                STATUS current
                DESCRIPTION "Number of seconds stats have been collecting"
                ::= { ipAtmAppSvcVccStatsEntry 16 }

ipAtmAppSvcVccStatsCellsDroppedB OBJECT-TYPE
                SYNTAX Integer32
                MAX-ACCESS read-only
                STATUS current
                DESCRIPTION "Cells Dropped on the Incoming side of B"
                ::= { ipAtmAppSvcVccStatsEntry 17 }

ipAtmAppSvcVccStatsCellsTaggedB OBJECT-TYPE
                SYNTAX Integer32
                MAX-ACCESS read-only
                STATUS current
                DESCRIPTION "Cells Tagged on the Incoming side of B"
                ::= { ipAtmAppSvcVccStatsEntry 18 }

cirEmAtmPvcVccStatsTable OBJECT-TYPE
                SYNTAX SEQUENCE OF CirEmAtmPvcVccStatsEntry
                MAX-ACCESS not-accessible
                STATUS current
                DESCRIPTION "Table of statistics for a channel connection"
                ::= { connectionStatistics 6 }

cirEmAtmPvcVccStatsEntry OBJECT-TYPE
                SYNTAX CirEmAtmPvcVccStatsEntry
                MAX-ACCESS not-accessible
                STATUS current
                DESCRIPTION "Row definition for the connection statistics
                             table"
                INDEX { cirEmAtmPvcVccStatsIfA, cirEmAtmPvcVccStatsIfB,
                        cirEmAtmPvcVccStatsVpiB, cirEmAtmPvcVccStatsVciB }
                ::= { cirEmAtmPvcVccStatsTable 1}

CirEmAtmPvcVccStatsEntry ::= SEQUENCE {
                cirEmAtmPvcVccStatsIfA                                IntfIndex,
                cirEmAtmPvcVccStatsIfB                                 IntfIndex,
                cirEmAtmPvcVccStatsVpiB                                 INTEGER,
                cirEmAtmPvcVccStatsVciB                                INTEGER,
                cirEmAtmPvcVccStatsCellsEncodedHiA                Integer32,
                cirEmAtmPvcVccStatsCellsEncodedLoA                Integer32,
                cirEmAtmPvcVccStatsCellsDecodedHiA                Integer32,
                cirEmAtmPvcVccStatsCellsDecodedLoA                Integer32,
                cirEmAtmPvcVccStatsInCellCountHiB                Integer32,
                cirEmAtmPvcVccStatsInCellCountLoB                Integer32,
                cirEmAtmPvcVccStatsOutCellCountHiB                 Integer32,
                cirEmAtmPvcVccStatsOutCellCountLoB                 Integer32,
                cirEmAtmPvcVccStatsTimer                        Integer32,
                cirEmAtmPvcVccStatsOdometerCellsEncodedHiA        Integer32,
                cirEmAtmPvcVccStatsOdometerCellsEncodedLoA        Integer32,
                cirEmAtmPvcVccStatsOdometerCellsDecodedHiA        Integer32,
                cirEmAtmPvcVccStatsOdometerCellsDecodedLoA        Integer32,
                cirEmAtmPvcVccStatsInOdometerCellCountHiB        Integer32,
                cirEmAtmPvcVccStatsInOdometerCellCountLoB        Integer32,
                cirEmAtmPvcVccStatsOutOdometerCellCountHiB         Integer32,
                cirEmAtmPvcVccStatsOutOdometerCellCountLoB         Integer32,
                cirEmAtmPvcVccStatsOdometerTimer                Integer32,
                cirEmAtmPvcVccStatsOdometerReset                INTEGER,
                cirEmAtmPvcVccStatsOamAisTx                        Integer32,
                cirEmAtmPvcVccStatsOamAisRx                        Integer32,
                cirEmAtmPvcVccStatsOamRdiTx                        Integer32,
                cirEmAtmPvcVccStatsOamRdiRx                        Integer32,
                cirEmAtmPvcVccStatsCellsDroppedB                 Integer32,
                cirEmAtmPvcVccStatsCellsTaggedB                  Integer32
                }

cirEmAtmPvcVccStatsIfA OBJECT-TYPE
                SYNTAX IntfIndex
                MAX-ACCESS not-accessible
                STATUS current
                DESCRIPTION "Interface index (SSPPCCC) on side A"
                ::= { cirEmAtmPvcVccStatsEntry 1 }

cirEmAtmPvcVccStatsIfB OBJECT-TYPE
                SYNTAX IntfIndex
                MAX-ACCESS not-accessible
                STATUS current
                DESCRIPTION "Interface index (SSPPCCC) on side A"
                ::= { cirEmAtmPvcVccStatsEntry 2 }

cirEmAtmPvcVccStatsVpiB OBJECT-TYPE
                SYNTAX INTEGER (0..4095)
                MAX-ACCESS not-accessible
                STATUS current
                DESCRIPTION "VPI on side B"
                ::= { cirEmAtmPvcVccStatsEntry 3 }

cirEmAtmPvcVccStatsVciB OBJECT-TYPE
                SYNTAX INTEGER (0..65535)
                MAX-ACCESS not-accessible
                STATUS current
                DESCRIPTION "VCI on side B"
                ::= { cirEmAtmPvcVccStatsEntry 4 }

cirEmAtmPvcVccStatsCellsEncodedHiA OBJECT-TYPE
                SYNTAX Integer32
                MAX-ACCESS read-only
                STATUS current
                DESCRIPTION " Cells encoded on side A- (High order portion)"
                ::= { cirEmAtmPvcVccStatsEntry 5 }

cirEmAtmPvcVccStatsCellsEncodedLoA OBJECT-TYPE
                SYNTAX Integer32
                MAX-ACCESS read-only
                STATUS current
                DESCRIPTION "Cells encoded on side A- (Low order portion) "
                ::= { cirEmAtmPvcVccStatsEntry 6 }

cirEmAtmPvcVccStatsCellsDecodedHiA OBJECT-TYPE
                SYNTAX Integer32
                MAX-ACCESS read-only
                STATUS current
                DESCRIPTION "Cells decoded on side A- (High order portion) "
                ::= { cirEmAtmPvcVccStatsEntry 7 }

cirEmAtmPvcVccStatsCellsDecodedLoA OBJECT-TYPE
                SYNTAX Integer32
                MAX-ACCESS read-only
                STATUS current
                DESCRIPTION "Cells decoded on side A- (Low order portion) "
                ::= { cirEmAtmPvcVccStatsEntry 8 }

cirEmAtmPvcVccStatsInCellCountHiB OBJECT-TYPE
                SYNTAX Integer32
                MAX-ACCESS read-only
                STATUS current
                DESCRIPTION "Valid cells received (Input Billing Count)"
                ::= { cirEmAtmPvcVccStatsEntry 9 }

cirEmAtmPvcVccStatsInCellCountLoB OBJECT-TYPE
                SYNTAX Integer32
                MAX-ACCESS read-only
                STATUS current
                DESCRIPTION "Valid cells received (Input Billing Count)"
                ::= { cirEmAtmPvcVccStatsEntry 10 }

cirEmAtmPvcVccStatsOutCellCountHiB OBJECT-TYPE
                SYNTAX Integer32
                MAX-ACCESS read-only
                STATUS current
                DESCRIPTION "Valid cells transmitted (Output Billing Count)"
                ::= { cirEmAtmPvcVccStatsEntry 11 }

cirEmAtmPvcVccStatsOutCellCountLoB OBJECT-TYPE
                SYNTAX Integer32
                MAX-ACCESS read-only
                STATUS current
                DESCRIPTION "Valid cells transmitted (Output Billing Count)"
                ::= { cirEmAtmPvcVccStatsEntry 12 }

cirEmAtmPvcVccStatsTimer OBJECT-TYPE
                SYNTAX Integer32
                MAX-ACCESS read-only
                STATUS current
                DESCRIPTION "Number of seconds stats have been collecting"
                ::= { cirEmAtmPvcVccStatsEntry 13 }

cirEmAtmPvcVccStatsOdometerCellsEncodedHiA OBJECT-TYPE
                SYNTAX Integer32
                MAX-ACCESS read-only
                STATUS current
                DESCRIPTION "Cells encoded on side A- (High order portion) "
                ::= { cirEmAtmPvcVccStatsEntry 14 }

cirEmAtmPvcVccStatsOdometerCellsEncodedLoA OBJECT-TYPE
                SYNTAX Integer32
                MAX-ACCESS read-only
                STATUS current
                DESCRIPTION "Cells encoded on side A- (Low order portion) "
                ::= { cirEmAtmPvcVccStatsEntry 15 }

cirEmAtmPvcVccStatsOdometerCellsDecodedHiA OBJECT-TYPE
                SYNTAX Integer32
                MAX-ACCESS read-only
                STATUS current
                DESCRIPTION "Cells decoded on side A- (High order portion) "
                ::= { cirEmAtmPvcVccStatsEntry 16 }

cirEmAtmPvcVccStatsOdometerCellsDecodedLoA OBJECT-TYPE
                SYNTAX Integer32
                MAX-ACCESS read-only
                STATUS current
                DESCRIPTION "Cells decoded on side A- (Low order portion) "
                ::= { cirEmAtmPvcVccStatsEntry 17 }

cirEmAtmPvcVccStatsInOdometerCellCountHiB OBJECT-TYPE
                SYNTAX Integer32
                MAX-ACCESS read-only
                STATUS current
                DESCRIPTION "Valid cells received (Input Billing Count)"
                ::= { cirEmAtmPvcVccStatsEntry 18 }

cirEmAtmPvcVccStatsInOdometerCellCountLoB OBJECT-TYPE
                SYNTAX Integer32
                MAX-ACCESS read-only
                STATUS current
                DESCRIPTION "Valid cells received (Input Billing Count)"
                ::= { cirEmAtmPvcVccStatsEntry 19 }

cirEmAtmPvcVccStatsOutOdometerCellCountHiB OBJECT-TYPE
                SYNTAX Integer32
                MAX-ACCESS read-only
                STATUS current
                DESCRIPTION "Valid cells transmitted (Output Billing Count)"
                ::= { cirEmAtmPvcVccStatsEntry 20 }

cirEmAtmPvcVccStatsOutOdometerCellCountLoB OBJECT-TYPE
                SYNTAX Integer32
                MAX-ACCESS read-only
                STATUS current
                DESCRIPTION "Valid cells transmitted (Output Billing Count)"
                ::= { cirEmAtmPvcVccStatsEntry 21 }

cirEmAtmPvcVccStatsOdometerTimer OBJECT-TYPE
                SYNTAX Integer32
                MAX-ACCESS read-only
                STATUS current
                DESCRIPTION "Number of seconds since odometer was reset."
                ::= { cirEmAtmPvcVccStatsEntry 22 }

cirEmAtmPvcVccStatsOdometerReset OBJECT-TYPE
                SYNTAX INTEGER {
                                reset(1)
                               }
                MAX-ACCESS read-write
                STATUS current
                DESCRIPTION "Odometer reset button."
                ::= { cirEmAtmPvcVccStatsEntry 23 }

cirEmAtmPvcVccStatsOamAisTx OBJECT-TYPE
                SYNTAX Integer32
                MAX-ACCESS read-only
                STATUS current
                DESCRIPTION "Number of AIS cells transmitted."
                ::= { cirEmAtmPvcVccStatsEntry 24 }

cirEmAtmPvcVccStatsOamAisRx OBJECT-TYPE
                SYNTAX Integer32
                MAX-ACCESS read-only
                STATUS current
                DESCRIPTION "Number of AIS cells received."
                ::= { cirEmAtmPvcVccStatsEntry 25 }

cirEmAtmPvcVccStatsOamRdiTx OBJECT-TYPE
                SYNTAX Integer32
                MAX-ACCESS read-only
                STATUS current
                DESCRIPTION "Number of RDI cells transmitted."
                ::= { cirEmAtmPvcVccStatsEntry 26 }

cirEmAtmPvcVccStatsOamRdiRx OBJECT-TYPE
                SYNTAX Integer32
                MAX-ACCESS read-only
                STATUS current
                DESCRIPTION "Number of RDI cells received."
                ::= { cirEmAtmPvcVccStatsEntry 27 }

cirEmAtmPvcVccStatsCellsDroppedB OBJECT-TYPE
                SYNTAX Integer32
                MAX-ACCESS read-only
                STATUS current
                DESCRIPTION "Cells Dropped on the Incoming side of B"
                ::= { cirEmAtmPvcVccStatsEntry 28 }

cirEmAtmPvcVccStatsCellsTaggedB OBJECT-TYPE
                SYNTAX Integer32
                MAX-ACCESS read-only
                STATUS current
                DESCRIPTION "Cells Tagged on the Incoming side of B"
                ::= { cirEmAtmPvcVccStatsEntry 29 }

frAtmPvcVccStatsTable OBJECT-TYPE
                SYNTAX SEQUENCE OF FrAtmPvcVccStatsEntry
                MAX-ACCESS not-accessible
                STATUS current
                DESCRIPTION "Table of statistics for a channel connection"
                ::= { connectionStatistics 7 }

frAtmPvcVccStatsEntry OBJECT-TYPE
                SYNTAX FrAtmPvcVccStatsEntry
                MAX-ACCESS not-accessible
                STATUS current
                DESCRIPTION "Row definition for the connection statistics
                             table"
                INDEX { frAtmPvcVccStatsIfA, frAtmPvcVccStatsDlciA,
                        frAtmPvcVccStatsIfB, frAtmPvcVccStatsVpiB, 
                        frAtmPvcVccStatsVciB }
                ::= { frAtmPvcVccStatsTable 1}

FrAtmPvcVccStatsEntry ::= SEQUENCE {
                frAtmPvcVccStatsIfA                         IntfIndex,
                frAtmPvcVccStatsDlciA                         INTEGER,
                frAtmPvcVccStatsIfB                         IntfIndex,
                frAtmPvcVccStatsVpiB                         INTEGER,
                frAtmPvcVccStatsVciB                        INTEGER,
                frAtmPvcVccStatsCellsEncodedHiA                Integer32,
                frAtmPvcVccStatsCellsEncodedLoA                Integer32,
                frAtmPvcVccStatsCellsDecodedHiA                Integer32,
                frAtmPvcVccStatsCellsDecodedLoA                Integer32,
                frAtmPvcVccStatsInCellCountHiB                Integer32,
                frAtmPvcVccStatsInCellCountLoB                Integer32,
                frAtmPvcVccStatsOutCellCountHiB                Integer32,
                frAtmPvcVccStatsOutCellCountLoB                Integer32,
                frAtmPvcVccStatsTimer                        Integer32,
                frAtmPvcVccStatsFramesDroppedA                Integer32,
                frAtmPvcVccStatsOdometerCellsEncodedHiA        Integer32,
                frAtmPvcVccStatsOdometerCellsEncodedLoA        Integer32,
                frAtmPvcVccStatsOdometerCellsDecodedHiA        Integer32,
                frAtmPvcVccStatsOdometerCellsDecodedLoA        Integer32,
                frAtmPvcVccStatsInOdometerCellCountHiB        Integer32,
                frAtmPvcVccStatsInOdometerCellCountLoB        Integer32,
                frAtmPvcVccStatsOutOdometerCellCountHiB        Integer32,
                frAtmPvcVccStatsOutOdometerCellCountLoB        Integer32,
                frAtmPvcVccStatsOdometerTimer                Integer32,
                frAtmPvcVccStatsOdometerFramesDroppedA        Integer32,
                frAtmPvcVccStatsOdometerReset                INTEGER,
                frAtmPvcVccStatsOamAisTx                Integer32,
                frAtmPvcVccStatsOamAisRx                Integer32,
                frAtmPvcVccStatsOamRdiTx                Integer32,
                frAtmPvcVccStatsOamRdiRx                Integer32,
                frAtmPvcVccStatsAal5ErrFramesA              Integer32,
                frAtmPvcVccStatsFramesTaggedA                Integer32,
                frAtmPvcVccStatsCellsDroppedB                 Integer32,
                frAtmPvcVccStatsCellsTaggedB                  Integer32
                }


frAtmPvcVccStatsIfA OBJECT-TYPE
                SYNTAX IntfIndex
                MAX-ACCESS not-accessible
                STATUS current
                DESCRIPTION "Interface index (SSPPCCC) on side A"
                ::= { frAtmPvcVccStatsEntry 1 }

frAtmPvcVccStatsDlciA OBJECT-TYPE
                SYNTAX INTEGER (0..1023)
                MAX-ACCESS not-accessible
                STATUS current
                DESCRIPTION "dlci - side A "
                ::= { frAtmPvcVccStatsEntry 2 }

frAtmPvcVccStatsIfB OBJECT-TYPE
                SYNTAX IntfIndex
                MAX-ACCESS not-accessible
                STATUS current
                DESCRIPTION "Interface index (SSPPCCC) on side B"
                ::= { frAtmPvcVccStatsEntry 3 }

frAtmPvcVccStatsVpiB OBJECT-TYPE
                SYNTAX INTEGER (0..4095)
                MAX-ACCESS not-accessible
                STATUS current
                DESCRIPTION "VPI on side B"
                ::= { frAtmPvcVccStatsEntry 4 }

frAtmPvcVccStatsVciB OBJECT-TYPE
                SYNTAX INTEGER (0..65535)
                MAX-ACCESS not-accessible
                STATUS current
                DESCRIPTION "VCI on side B"
                ::= { frAtmPvcVccStatsEntry 5 }

frAtmPvcVccStatsCellsEncodedHiA OBJECT-TYPE
                SYNTAX Integer32
                MAX-ACCESS read-only
                STATUS current
                DESCRIPTION "Cells encoded on side A- (High order portion) "
                ::= { frAtmPvcVccStatsEntry 6 }

frAtmPvcVccStatsCellsEncodedLoA OBJECT-TYPE
                SYNTAX Integer32
                MAX-ACCESS read-only
                STATUS current
                DESCRIPTION "Cells encoded on side A- (Low order portion)"
                ::= { frAtmPvcVccStatsEntry 7 }

frAtmPvcVccStatsCellsDecodedHiA OBJECT-TYPE
                SYNTAX Integer32
                MAX-ACCESS read-only
                STATUS current
                DESCRIPTION "Cells decoded on side A- (High order portion)"
                ::= { frAtmPvcVccStatsEntry 8 }

frAtmPvcVccStatsCellsDecodedLoA OBJECT-TYPE
                SYNTAX Integer32
                MAX-ACCESS read-only
                STATUS current
                DESCRIPTION "Cells decoded on side A- (Low order portion)"
                ::= { frAtmPvcVccStatsEntry 9 }

frAtmPvcVccStatsInCellCountHiB OBJECT-TYPE
                SYNTAX Integer32
                MAX-ACCESS read-only
                STATUS current
                DESCRIPTION "Valid cells received (Input Billing Count)"
                ::= { frAtmPvcVccStatsEntry 10 }

frAtmPvcVccStatsInCellCountLoB OBJECT-TYPE
                SYNTAX Integer32
                MAX-ACCESS read-only
                STATUS current
                DESCRIPTION "Valid cells received (Input Billing Count)"
                ::= { frAtmPvcVccStatsEntry 11 }

frAtmPvcVccStatsOutCellCountHiB OBJECT-TYPE
                SYNTAX Integer32
                MAX-ACCESS read-only
                STATUS current
                DESCRIPTION "Valid cells transmitted (Output Billing Count)"
                ::= { frAtmPvcVccStatsEntry 12 }

frAtmPvcVccStatsOutCellCountLoB OBJECT-TYPE
                SYNTAX Integer32
                MAX-ACCESS read-only
                STATUS current
                DESCRIPTION "Valid cells transmitted (Output Billing Count)"
                ::= { frAtmPvcVccStatsEntry 13 }

frAtmPvcVccStatsTimer OBJECT-TYPE
                SYNTAX Integer32
                MAX-ACCESS read-only
                STATUS current
                DESCRIPTION "Number of seconds stats have been collecting"
                ::= { frAtmPvcVccStatsEntry 14 }

frAtmPvcVccStatsFramesDroppedA OBJECT-TYPE
                SYNTAX Integer32
                MAX-ACCESS read-only
                STATUS current
                DESCRIPTION "Number of frames dropped for a given DLCI for A2B
                             direction, only applicable to the input side."
                ::= { frAtmPvcVccStatsEntry 15 }

frAtmPvcVccStatsOdometerCellsEncodedHiA OBJECT-TYPE
                SYNTAX Integer32
                MAX-ACCESS read-only
                STATUS current
                DESCRIPTION "Cells encoded on side A- (High order portion)"
                ::= { frAtmPvcVccStatsEntry 16 }

frAtmPvcVccStatsOdometerCellsEncodedLoA OBJECT-TYPE
                SYNTAX Integer32
                MAX-ACCESS read-only
                STATUS current
                DESCRIPTION "Cells encoded on side A- (Low order portion)"
                ::= { frAtmPvcVccStatsEntry 17 }

frAtmPvcVccStatsOdometerCellsDecodedHiA OBJECT-TYPE
                SYNTAX Integer32
                MAX-ACCESS read-only
                STATUS current
                DESCRIPTION "Cells decoded on side A- (High order portion)"
                ::= { frAtmPvcVccStatsEntry 18 }

frAtmPvcVccStatsOdometerCellsDecodedLoA OBJECT-TYPE
                SYNTAX Integer32
                MAX-ACCESS read-only
                STATUS current
                DESCRIPTION "Cells decoded on side A- (Low order portion)"
                ::= { frAtmPvcVccStatsEntry 19 }

frAtmPvcVccStatsInOdometerCellCountHiB OBJECT-TYPE
                SYNTAX Integer32
                MAX-ACCESS read-only
                STATUS current
                DESCRIPTION "Valid cells received (Input Billing Count)"
                ::= { frAtmPvcVccStatsEntry 20 }

frAtmPvcVccStatsInOdometerCellCountLoB OBJECT-TYPE
                SYNTAX Integer32
                MAX-ACCESS read-only
                STATUS current
                DESCRIPTION "Valid cells received (Input Billing Count)"
                ::= { frAtmPvcVccStatsEntry 21 }

frAtmPvcVccStatsOutOdometerCellCountHiB OBJECT-TYPE
                SYNTAX Integer32
                MAX-ACCESS read-only
                STATUS current
                DESCRIPTION "Valid cells transmitted (Output Billing Count)"
                ::= { frAtmPvcVccStatsEntry 22 }

frAtmPvcVccStatsOutOdometerCellCountLoB OBJECT-TYPE
                SYNTAX Integer32
                MAX-ACCESS read-only
                STATUS current
                DESCRIPTION "Valid cells transmitted (Output Billing Count)"
                ::= { frAtmPvcVccStatsEntry 23 }

frAtmPvcVccStatsOdometerTimer OBJECT-TYPE
                SYNTAX Integer32
                MAX-ACCESS read-only
                STATUS current
                DESCRIPTION "Number of seconds since odometer was reset."
                ::= { frAtmPvcVccStatsEntry 24 }

frAtmPvcVccStatsOdometerFramesDroppedA OBJECT-TYPE
                SYNTAX Integer32
                MAX-ACCESS read-only
                STATUS current
                DESCRIPTION "Number of frames dropped for a given DLCI for A2B
                             direction, only applicable to the input side."
                ::= { frAtmPvcVccStatsEntry 25 }

frAtmPvcVccStatsOdometerReset OBJECT-TYPE
                SYNTAX INTEGER {
                                reset(1)
                               }
                MAX-ACCESS read-write
                STATUS current
                DESCRIPTION "Odometer reset button."
                ::= { frAtmPvcVccStatsEntry 26 }

frAtmPvcVccStatsOamAisTx OBJECT-TYPE
                SYNTAX Integer32
                MAX-ACCESS read-only
                STATUS current
                DESCRIPTION "Number of AIS cells transmitted."
                ::= { frAtmPvcVccStatsEntry 27 }

frAtmPvcVccStatsOamAisRx OBJECT-TYPE
                SYNTAX Integer32
                MAX-ACCESS read-only
                STATUS current
                DESCRIPTION "Number of AIS cells received."
                ::= { frAtmPvcVccStatsEntry 28 }

frAtmPvcVccStatsOamRdiTx OBJECT-TYPE
                SYNTAX Integer32
                MAX-ACCESS read-only
                STATUS current
                DESCRIPTION "Number of RDI cells transmitted."
                ::= { frAtmPvcVccStatsEntry 29 }

frAtmPvcVccStatsOamRdiRx OBJECT-TYPE
                SYNTAX Integer32
                MAX-ACCESS read-only
                STATUS current
                DESCRIPTION "Number of RDI cells received."
                ::= { frAtmPvcVccStatsEntry 30 }

frAtmPvcVccStatsAal5ErrFramesA OBJECT-TYPE 
                SYNTAX Integer32
                MAX-ACCESS read-only
                STATUS current
                DESCRIPTION "Number of Aal5 Errored Frames, which are not
                                dropped due to UPC in A2B dir, 
                                only applicable to Input Side"
                ::= { frAtmPvcVccStatsEntry 31 }

frAtmPvcVccStatsFramesTaggedA OBJECT-TYPE
                SYNTAX Integer32
                MAX-ACCESS read-only
                STATUS current
                DESCRIPTION "Number of  Frames tagged due to UPC in A2B
                                dir, only applicable to Input Side"
                ::= { frAtmPvcVccStatsEntry 32 }

frAtmPvcVccStatsCellsDroppedB OBJECT-TYPE
                SYNTAX Integer32
                MAX-ACCESS read-only
                STATUS current
                DESCRIPTION "Cells Dropped on the Incoming side of B"
                ::= { frAtmPvcVccStatsEntry 33 }

frAtmPvcVccStatsCellsTaggedB OBJECT-TYPE
                SYNTAX Integer32
                MAX-ACCESS read-only
                STATUS current
                DESCRIPTION "Cells Tagged on the Incoming side of B"
                ::= { frAtmPvcVccStatsEntry 34 }

frFrPvcStatsTable OBJECT-TYPE
                SYNTAX SEQUENCE OF FrFrPvcStatsEntry
                MAX-ACCESS not-accessible
                STATUS current
                DESCRIPTION "Table of statistics for a channel connection"
                ::= { connectionStatistics 8 }

frFrPvcStatsEntry OBJECT-TYPE
                SYNTAX FrFrPvcStatsEntry
                MAX-ACCESS not-accessible
                STATUS current
                DESCRIPTION "Row definition for the connection statistics
                             table"
                INDEX { frFrPvcStatsIfA, frFrPvcStatsDlciA,
                        frFrPvcStatsIfB, frFrPvcStatsDlciB }
                ::= { frFrPvcStatsTable 1}

FrFrPvcStatsEntry ::= SEQUENCE {
                frFrPvcStatsIfA                         IntfIndex,
                frFrPvcStatsDlciA                         INTEGER,
                frFrPvcStatsIfB                         IntfIndex,
                frFrPvcStatsDlciB                        INTEGER,
                frFrPvcStatsCellsEncodedHiA                Integer32,
                frFrPvcStatsCellsEncodedLoA                Integer32,
                frFrPvcStatsCellsDecodedHiA                Integer32,
                frFrPvcStatsCellsDecodedLoA                Integer32,
                frFrPvcStatsCellsEncodedHiB                Integer32,
                frFrPvcStatsCellsEncodedLoB                Integer32,
                frFrPvcStatsCellsDecodedHiB                Integer32,
                frFrPvcStatsCellsDecodedLoB                Integer32,
                frFrPvcStatsTimer                        Integer32,
                frFrPvcStatsFramesDroppedA                Integer32,
                frFrPvcStatsFramesDroppedB                Integer32,
                frFrPvcStatsOdometerCellsEncodedHiA        Integer32,
                frFrPvcStatsOdometerCellsEncodedLoA        Integer32,
                frFrPvcStatsOdometerCellsDecodedHiA        Integer32,
                frFrPvcStatsOdometerCellsDecodedLoA        Integer32,
                frFrPvcStatsOdometerCellsEncodedHiB        Integer32,
                frFrPvcStatsOdometerCellsEncodedLoB        Integer32,
                frFrPvcStatsOdometerCellsDecodedHiB        Integer32,
                frFrPvcStatsOdometerCellsDecodedLoB        Integer32,
                frFrPvcStatsOdometerTimer                Integer32,
                frFrPvcStatsOdometerFramesDroppedA        Integer32,
                frFrPvcStatsOdometerFramesDroppedB        Integer32,
                frFrPvcStatsOdometerReset                INTEGER,
                frFrPvcStatsAal5ErrFramesA                  Integer32,
                frFrPvcStatsAal5ErrFramesB                  Integer32,
                frFrPvcStatsFramesTaggedA                  Integer32,
                frFrPvcStatsFramesTaggedB                  Integer32
                }

frFrPvcStatsIfA OBJECT-TYPE
                SYNTAX IntfIndex
                MAX-ACCESS not-accessible
                STATUS current
                DESCRIPTION "Interface index (SSPPCCC) on side A"
                ::= { frFrPvcStatsEntry 1 }

frFrPvcStatsDlciA OBJECT-TYPE
                SYNTAX INTEGER (0..1023)
                MAX-ACCESS not-accessible
                STATUS current
                DESCRIPTION "dlci - side A"
                ::= { frFrPvcStatsEntry 2 }

frFrPvcStatsIfB OBJECT-TYPE
                SYNTAX IntfIndex
                MAX-ACCESS not-accessible
                STATUS current
                DESCRIPTION "Interface index (SSPPCCC) on side B"
                ::= { frFrPvcStatsEntry 3 }

frFrPvcStatsDlciB OBJECT-TYPE
                SYNTAX INTEGER (0..1023)
                MAX-ACCESS not-accessible
                STATUS current
                DESCRIPTION "dlci - side B"
                ::= { frFrPvcStatsEntry 4 }

frFrPvcStatsCellsEncodedHiA OBJECT-TYPE
                SYNTAX Integer32
                MAX-ACCESS read-only
                STATUS current
                DESCRIPTION "Cells encoded on side A- (High order portion) "
                ::= { frFrPvcStatsEntry 5 }

frFrPvcStatsCellsEncodedLoA OBJECT-TYPE
                SYNTAX Integer32
                MAX-ACCESS read-only
                STATUS current
                DESCRIPTION "Cells encoded on side A- (Low order portion) "
                ::= { frFrPvcStatsEntry 6 }

frFrPvcStatsCellsDecodedHiA OBJECT-TYPE
                SYNTAX Integer32
                MAX-ACCESS read-only
                STATUS current
                DESCRIPTION "Cells decoded on side A- (High order portion) "
                ::= { frFrPvcStatsEntry 7 }

frFrPvcStatsCellsDecodedLoA OBJECT-TYPE
                SYNTAX Integer32
                MAX-ACCESS read-only
                STATUS current
                DESCRIPTION "Cells decoded on side A- (Low order portion) "
                ::= { frFrPvcStatsEntry 8 }

frFrPvcStatsCellsEncodedHiB OBJECT-TYPE
                SYNTAX Integer32
                MAX-ACCESS read-only
                STATUS current
                DESCRIPTION "Cells encoded on side B- (High order portion)"
                ::= { frFrPvcStatsEntry 9 }

frFrPvcStatsCellsEncodedLoB OBJECT-TYPE
                SYNTAX Integer32
                MAX-ACCESS read-only
                STATUS current
                DESCRIPTION "Cells encoded on side B- (Low order portion) "
                ::= { frFrPvcStatsEntry 10 }

frFrPvcStatsCellsDecodedHiB OBJECT-TYPE
                SYNTAX Integer32
                MAX-ACCESS read-only
                STATUS current
                DESCRIPTION "Cells decoded on side B- (High order portion) "
                ::= { frFrPvcStatsEntry 11 }

frFrPvcStatsCellsDecodedLoB OBJECT-TYPE
                SYNTAX Integer32
                MAX-ACCESS read-only
                STATUS current
                DESCRIPTION "Cells decoded on side B- (Low order portion) "
                ::= { frFrPvcStatsEntry 12 }

frFrPvcStatsTimer OBJECT-TYPE
                SYNTAX Integer32
                MAX-ACCESS read-only
                STATUS current
                DESCRIPTION "Number of seconds stats have been collecting"
                ::= { frFrPvcStatsEntry 13 }

frFrPvcStatsFramesDroppedA OBJECT-TYPE
                SYNTAX Integer32
                MAX-ACCESS read-only
                STATUS current
                DESCRIPTION "Number of frames dropped for a given DLCI for A2B
                             direction, only applicable to the input side."
                ::= { frFrPvcStatsEntry 14 }

frFrPvcStatsFramesDroppedB OBJECT-TYPE
                SYNTAX Integer32
                MAX-ACCESS read-only
                STATUS current
                DESCRIPTION "Number of frames dropped for a given DLCI for B2A
                             direction, only applicable to the input side."
                ::= { frFrPvcStatsEntry 15 }

frFrPvcStatsOdometerCellsEncodedHiA OBJECT-TYPE
                SYNTAX Integer32
                MAX-ACCESS read-only
                STATUS current
                DESCRIPTION "Cells encoded on side A- (High order portion) "
                ::= { frFrPvcStatsEntry 16 }

frFrPvcStatsOdometerCellsEncodedLoA OBJECT-TYPE
                SYNTAX Integer32
                MAX-ACCESS read-only
                STATUS current
                DESCRIPTION "Cells encoded on side A- (Low order portion) "
                ::= { frFrPvcStatsEntry 17 }

frFrPvcStatsOdometerCellsDecodedHiA OBJECT-TYPE
                SYNTAX Integer32
                MAX-ACCESS read-only
                STATUS current
                DESCRIPTION "Cells decoded on side A- (High order portion) "
                ::= { frFrPvcStatsEntry 18 }

frFrPvcStatsOdometerCellsDecodedLoA OBJECT-TYPE
                SYNTAX Integer32
                MAX-ACCESS read-only
                STATUS current
                DESCRIPTION "Cells decoded on side A- (Low order portion) "
                ::= { frFrPvcStatsEntry 19 }

frFrPvcStatsOdometerCellsEncodedHiB OBJECT-TYPE
                SYNTAX Integer32
                MAX-ACCESS read-only
                STATUS current
                DESCRIPTION "Cells encoded on side B- (High order portion) "
                ::= { frFrPvcStatsEntry 20 }

frFrPvcStatsOdometerCellsEncodedLoB OBJECT-TYPE
                SYNTAX Integer32
                MAX-ACCESS read-only
                STATUS current
                DESCRIPTION "Cells encoded on side B- (Low order portion) "
                ::= { frFrPvcStatsEntry 21 }

frFrPvcStatsOdometerCellsDecodedHiB OBJECT-TYPE
                SYNTAX Integer32
                MAX-ACCESS read-only
                STATUS current
                DESCRIPTION "Cells decoded on side B- (High order portion) "
                ::= { frFrPvcStatsEntry 22 }

frFrPvcStatsOdometerCellsDecodedLoB OBJECT-TYPE
                SYNTAX Integer32
                MAX-ACCESS read-only
                STATUS current
                DESCRIPTION "Cells decoded on side B- (Low order portion) "
                ::= { frFrPvcStatsEntry 23 }

frFrPvcStatsOdometerTimer OBJECT-TYPE
                SYNTAX Integer32
                MAX-ACCESS read-only
                STATUS current
                DESCRIPTION "Number of seconds since odometer was reset."
                ::= { frFrPvcStatsEntry 24 }

frFrPvcStatsOdometerFramesDroppedA OBJECT-TYPE
                SYNTAX Integer32
                MAX-ACCESS read-only
                STATUS current
                DESCRIPTION "Number of frames dropped for a given DLCI for A2B
                             direction, only applicable to the input side."
                ::= { frFrPvcStatsEntry 25 }

frFrPvcStatsOdometerFramesDroppedB OBJECT-TYPE
                SYNTAX Integer32
                MAX-ACCESS read-only
                STATUS current
                DESCRIPTION "Number of frames dropped for a given DLCI for B2A
                             direction, only applicable to the input side."
                ::= { frFrPvcStatsEntry 26 }

frFrPvcStatsOdometerReset OBJECT-TYPE
                SYNTAX INTEGER {
                                reset(1)
                               }
                MAX-ACCESS read-write
                STATUS current
                DESCRIPTION "Odometer reset button."
                ::= { frFrPvcStatsEntry 27 }


frFrPvcStatsAal5ErrFramesA OBJECT-TYPE
                SYNTAX Integer32
                MAX-ACCESS read-only
                STATUS current
                DESCRIPTION "Number of Aal5 Errored Frames, which are not 
                                dropped due to UPC in A2B dir, only 
                                applicable to Input Side"
                ::= { frFrPvcStatsEntry 28 }


frFrPvcStatsAal5ErrFramesB OBJECT-TYPE
                SYNTAX Integer32
                MAX-ACCESS read-only
                STATUS current
                DESCRIPTION "Number of Aal5 Errored Frames, which are not 
                                dropped due to UPC in B2A dir, 
                                only applicable to Input Side"
                ::= { frFrPvcStatsEntry 29 }

frFrPvcStatsFramesTaggedA OBJECT-TYPE
                SYNTAX Integer32
                MAX-ACCESS read-only
                STATUS current
                DESCRIPTION "Number of  Frames tagged due to UPC in A2B 
                        dir, only applicable to Input Side"
                ::= { frFrPvcStatsEntry 30 }


frFrPvcStatsFramesTaggedB OBJECT-TYPE
                SYNTAX Integer32
                MAX-ACCESS read-only
                STATUS current
                DESCRIPTION "Number of  Frames tagged due to UPC in B2A 
                                dir, only applicable to Input Side"
                ::= { frFrPvcStatsEntry 31 }


vbrAtmPvcVccStatsTable OBJECT-TYPE
                SYNTAX SEQUENCE OF VbrAtmPvcVccStatsEntry
                MAX-ACCESS not-accessible
                STATUS current
                DESCRIPTION "Table of statistics for a channel connection"
                ::= { connectionStatistics 9 }

vbrAtmPvcVccStatsEntry OBJECT-TYPE
                SYNTAX VbrAtmPvcVccStatsEntry
                MAX-ACCESS not-accessible
                STATUS current
                DESCRIPTION "Row definition for the connection statistics
                             table"
                INDEX { vbrAtmPvcVccStatsIfA, vbrAtmPvcVccStatsIfB,
                        vbrAtmPvcVccStatsVpiB, vbrAtmPvcVccStatsVciB }
                ::= { vbrAtmPvcVccStatsTable 1}

VbrAtmPvcVccStatsEntry ::= SEQUENCE {
                vbrAtmPvcVccStatsIfA                                 IntfIndex,
                vbrAtmPvcVccStatsIfB                                 IntfIndex,
                vbrAtmPvcVccStatsVpiB                                 INTEGER,
                vbrAtmPvcVccStatsVciB                                 INTEGER,
                vbrAtmPvcVccStatsCellsEncodedHiA                Integer32,
                vbrAtmPvcVccStatsCellsEncodedLoA                Integer32,
                vbrAtmPvcVccStatsCellsDecodedHiA                Integer32,
                vbrAtmPvcVccStatsCellsDecodedLoA                Integer32,
                vbrAtmPvcVccStatsInCellCountHiB                        Integer32,
                vbrAtmPvcVccStatsInCellCountLoB                        Integer32,
                vbrAtmPvcVccStatsOutCellCountHiB                Integer32,
                vbrAtmPvcVccStatsOutCellCountLoB                Integer32,
                vbrAtmPvcVccStatsTimer                                Integer32,
                vbrAtmPvcVccStatsOdometerCellsEncodedHiA        Integer32,
                vbrAtmPvcVccStatsOdometerCellsEncodedLoA        Integer32,
                vbrAtmPvcVccStatsOdometerCellsDecodedHiA        Integer32,
                vbrAtmPvcVccStatsOdometerCellsDecodedLoA        Integer32,
                vbrAtmPvcVccStatsInOdometerCellCountHiB                Integer32,
                vbrAtmPvcVccStatsInOdometerCellCountLoB                Integer32,
                vbrAtmPvcVccStatsOutOdometerCellCountHiB        Integer32,
                vbrAtmPvcVccStatsOutOdometerCellCountLoB        Integer32,
                vbrAtmPvcVccStatsOdometerTimer                        Integer32,
                vbrAtmPvcVccStatsOdometerReset                        INTEGER,
                vbrAtmPvcVccStatsOamAisTx                        Integer32,
                vbrAtmPvcVccStatsOamAisRx                        Integer32,
                vbrAtmPvcVccStatsOamRdiTx                        Integer32,
                vbrAtmPvcVccStatsOamRdiRx                        Integer32,
                vbrAtmPvcVccStatsCellsDroppedB                         Integer32, 
                vbrAtmPvcVccStatsCellsTaggedB                          Integer32
                }

vbrAtmPvcVccStatsIfA OBJECT-TYPE
                SYNTAX IntfIndex
                MAX-ACCESS not-accessible
                STATUS current
                DESCRIPTION "Interface index (SSPPCCC) on side A"
                ::= { vbrAtmPvcVccStatsEntry 1 }

vbrAtmPvcVccStatsIfB OBJECT-TYPE
                SYNTAX IntfIndex
                MAX-ACCESS not-accessible
                STATUS current
                DESCRIPTION "Interface index (SSPPCCC) on side A"
                ::= { vbrAtmPvcVccStatsEntry 2 }

vbrAtmPvcVccStatsVpiB OBJECT-TYPE
                SYNTAX INTEGER (0..4095)
                MAX-ACCESS not-accessible
                STATUS current
                DESCRIPTION "vpi - side B "
                ::= { vbrAtmPvcVccStatsEntry 3 }

vbrAtmPvcVccStatsVciB OBJECT-TYPE
                SYNTAX INTEGER (0..65535)
                MAX-ACCESS not-accessible
                STATUS current
                DESCRIPTION "vci - side B "
                ::= { vbrAtmPvcVccStatsEntry 4 }

vbrAtmPvcVccStatsCellsEncodedHiA OBJECT-TYPE
                SYNTAX Integer32
                MAX-ACCESS read-only
                STATUS current
                DESCRIPTION "Cells encoded on side A- (High order portion)  "
                ::= { vbrAtmPvcVccStatsEntry 5 }

vbrAtmPvcVccStatsCellsEncodedLoA OBJECT-TYPE
                SYNTAX Integer32
                MAX-ACCESS read-only
                STATUS current
                DESCRIPTION "Cells encoded on side A- (Low order portion) "
                ::= { vbrAtmPvcVccStatsEntry 6 }

vbrAtmPvcVccStatsCellsDecodedHiA OBJECT-TYPE
                SYNTAX Integer32
                MAX-ACCESS read-only
                STATUS current
                DESCRIPTION "Cells decoded on side A- (High order portion)"
                ::= { vbrAtmPvcVccStatsEntry 7 }

vbrAtmPvcVccStatsCellsDecodedLoA OBJECT-TYPE
                SYNTAX Integer32
                MAX-ACCESS read-only
                STATUS current
                DESCRIPTION "Cells decoded on side A- (Low order portion)"
                ::= { vbrAtmPvcVccStatsEntry 8 }



vbrAtmPvcVccStatsInCellCountHiB OBJECT-TYPE
                SYNTAX Integer32
                MAX-ACCESS read-only
                STATUS current
                DESCRIPTION "Valid cells received (Input Billing Count)"
                ::= { vbrAtmPvcVccStatsEntry 10 }

vbrAtmPvcVccStatsInCellCountLoB OBJECT-TYPE
                SYNTAX Integer32
                MAX-ACCESS read-only
                STATUS current
                DESCRIPTION "Valid cells received (Input Billing Count)"
                ::= { vbrAtmPvcVccStatsEntry 11 }

vbrAtmPvcVccStatsOutCellCountHiB OBJECT-TYPE
                SYNTAX Integer32
                MAX-ACCESS read-only
                STATUS current
                DESCRIPTION "Valid cells transmitted (Output Billing Count)"
                ::= { vbrAtmPvcVccStatsEntry 12 }

vbrAtmPvcVccStatsOutCellCountLoB OBJECT-TYPE
                SYNTAX Integer32
                MAX-ACCESS read-only
                STATUS current
                DESCRIPTION "Valid cells transmitted (Output Billing Count)"
                ::= { vbrAtmPvcVccStatsEntry 13 }

vbrAtmPvcVccStatsTimer OBJECT-TYPE
                SYNTAX Integer32
                MAX-ACCESS read-only
                STATUS current
                DESCRIPTION "Number of seconds stats have been collecting"
                ::= { vbrAtmPvcVccStatsEntry 14 }

vbrAtmPvcVccStatsOdometerCellsEncodedHiA OBJECT-TYPE
                SYNTAX Integer32
                MAX-ACCESS read-only
                STATUS current
                DESCRIPTION "Cells encoded on side A- (High order portion)"
                ::= { vbrAtmPvcVccStatsEntry 15 }

vbrAtmPvcVccStatsOdometerCellsEncodedLoA OBJECT-TYPE
                SYNTAX Integer32
                MAX-ACCESS read-only
                STATUS current
                DESCRIPTION "Cells encoded on side A- (Low order portion)"
                ::= { vbrAtmPvcVccStatsEntry 16 }

vbrAtmPvcVccStatsOdometerCellsDecodedHiA OBJECT-TYPE
                SYNTAX Integer32
                MAX-ACCESS read-only
                STATUS current
                DESCRIPTION "Cells decoded on side A- (High order portion)"
                ::= { vbrAtmPvcVccStatsEntry 17 }

vbrAtmPvcVccStatsOdometerCellsDecodedLoA OBJECT-TYPE
                SYNTAX Integer32
                MAX-ACCESS read-only
                STATUS current
                DESCRIPTION " Cells decoded on side A- (Low order portion)"
                ::= { vbrAtmPvcVccStatsEntry 18 }

vbrAtmPvcVccStatsInOdometerCellCountHiB OBJECT-TYPE
                SYNTAX Integer32
                MAX-ACCESS read-only
                STATUS current
                DESCRIPTION "Valid cells received (Input Billing Count)"
                ::= { vbrAtmPvcVccStatsEntry 19 }

vbrAtmPvcVccStatsInOdometerCellCountLoB OBJECT-TYPE
                SYNTAX Integer32
                MAX-ACCESS read-only
                STATUS current
                DESCRIPTION "Valid cells received (Input Billing Count)"
                ::= { vbrAtmPvcVccStatsEntry 20 }

vbrAtmPvcVccStatsOutOdometerCellCountHiB OBJECT-TYPE
                SYNTAX Integer32
                MAX-ACCESS read-only
                STATUS current
                DESCRIPTION "Valid cells transmitted (Output Billing Count)"
                ::= { vbrAtmPvcVccStatsEntry 21 }

vbrAtmPvcVccStatsOutOdometerCellCountLoB OBJECT-TYPE
                SYNTAX Integer32
                MAX-ACCESS read-only
                STATUS current
                DESCRIPTION "Valid cells transmitted (Output Billing Count)"
                ::= { vbrAtmPvcVccStatsEntry 22 }

vbrAtmPvcVccStatsOdometerTimer OBJECT-TYPE
                SYNTAX Integer32
                MAX-ACCESS read-only
                STATUS current
                DESCRIPTION "Number of seconds since odometer was reset."
                ::= { vbrAtmPvcVccStatsEntry 23 }

vbrAtmPvcVccStatsOdometerReset OBJECT-TYPE
                SYNTAX INTEGER {
                                reset(1)
                               }
                MAX-ACCESS read-write
                STATUS current
                DESCRIPTION "Odometer reset button."
                ::= { vbrAtmPvcVccStatsEntry 24 }

vbrAtmPvcVccStatsOamAisTx OBJECT-TYPE
                SYNTAX Integer32
                MAX-ACCESS read-only
                STATUS current
                DESCRIPTION "Number of AIS cells transmitted."
                ::= { vbrAtmPvcVccStatsEntry 25 }

vbrAtmPvcVccStatsOamAisRx OBJECT-TYPE
                SYNTAX Integer32
                MAX-ACCESS read-only
                STATUS current
                DESCRIPTION "Number of AIS cells received."
                ::= { vbrAtmPvcVccStatsEntry 26 }

vbrAtmPvcVccStatsOamRdiTx OBJECT-TYPE
                SYNTAX Integer32
                MAX-ACCESS read-only
                STATUS current
                DESCRIPTION "Number of RDI cells transmitted."
                ::= { vbrAtmPvcVccStatsEntry 27 }

vbrAtmPvcVccStatsOamRdiRx OBJECT-TYPE
                SYNTAX Integer32
                MAX-ACCESS read-only
                STATUS current
                DESCRIPTION "Number of RDI cells received."
                ::= { vbrAtmPvcVccStatsEntry 28 }

vbrAtmPvcVccStatsCellsDroppedB OBJECT-TYPE
                SYNTAX Integer32
                MAX-ACCESS read-only
                STATUS current
                DESCRIPTION "Cells Dropped on the Incoming side of B"
                ::= { vbrAtmPvcVccStatsEntry 29 }

vbrAtmPvcVccStatsCellsTaggedB OBJECT-TYPE
                SYNTAX Integer32
                MAX-ACCESS read-only
                STATUS current
                DESCRIPTION "Cells Tagged on the Incoming side of B"
                ::= { vbrAtmPvcVccStatsEntry 30 }

cirEmCirEmPvcStatsTable OBJECT-TYPE
                SYNTAX SEQUENCE OF CirEmCirEmPvcStatsEntry
                MAX-ACCESS not-accessible
                STATUS current
                DESCRIPTION "Table of statistics for a channel connection"
                ::= { connectionStatistics 10 }
 
cirEmCirEmPvcStatsEntry OBJECT-TYPE
                SYNTAX CirEmCirEmPvcStatsEntry
                MAX-ACCESS not-accessible
                STATUS current
                DESCRIPTION "Row definition for the connection statistics
                             table"
                INDEX { cirEmCirEmPvcStatsIfA, cirEmCirEmPvcStatsIfB
                      }
                ::= { cirEmCirEmPvcStatsTable 1}
 
CirEmCirEmPvcStatsEntry ::= SEQUENCE {
                cirEmCirEmPvcStatsIfA                            IntfIndex,
                cirEmCirEmPvcStatsIfB                            IntfIndex,
                cirEmCirEmPvcStatsCellsEncodedHiA                Integer32,
                cirEmCirEmPvcStatsCellsEncodedLoA                Integer32,
                cirEmCirEmPvcStatsCellsDecodedHiA                Integer32,
                cirEmCirEmPvcStatsCellsDecodedLoA                Integer32,
                cirEmCirEmPvcStatsCellsEncodedHiB                Integer32,
                cirEmCirEmPvcStatsCellsEncodedLoB                Integer32,
                cirEmCirEmPvcStatsCellsDecodedHiB                Integer32,
                cirEmCirEmPvcStatsCellsDecodedLoB                Integer32,
                cirEmCirEmPvcStatsTimer                          Integer32,
                cirEmCirEmPvcStatsOdometerCellsEncodedHiA        Integer32,
                cirEmCirEmPvcStatsOdometerCellsEncodedLoA        Integer32,
                cirEmCirEmPvcStatsOdometerCellsDecodedHiA        Integer32,
                cirEmCirEmPvcStatsOdometerCellsDecodedLoA        Integer32,
                cirEmCirEmPvcStatsOdometerCellsEncodedHiB        Integer32,
                cirEmCirEmPvcStatsOdometerCellsEncodedLoB        Integer32,
                cirEmCirEmPvcStatsOdometerCellsDecodedHiB        Integer32,
                cirEmCirEmPvcStatsOdometerCellsDecodedLoB        Integer32,
                cirEmCirEmPvcStatsOdometerTimer                  Integer32,
                cirEmCirEmPvcStatsOdometerReset                  INTEGER
                }
 
cirEmCirEmPvcStatsIfA OBJECT-TYPE
                SYNTAX IntfIndex
                MAX-ACCESS not-accessible
                STATUS current
                DESCRIPTION "Interface index (SSPPCCC) on side A"
                ::= { cirEmCirEmPvcStatsEntry 1 }
 
cirEmCirEmPvcStatsIfB OBJECT-TYPE
                SYNTAX IntfIndex
                MAX-ACCESS not-accessible
                STATUS current
                DESCRIPTION "Interface index (SSPPCCC) on side A"
                ::= { cirEmCirEmPvcStatsEntry 2 }
 
cirEmCirEmPvcStatsCellsEncodedHiA OBJECT-TYPE
                SYNTAX Integer32
                MAX-ACCESS read-only
                STATUS current
                DESCRIPTION "Valid cells received (Input Billing Count)"
                ::= { cirEmCirEmPvcStatsEntry 3 }
 
cirEmCirEmPvcStatsCellsEncodedLoA OBJECT-TYPE
                SYNTAX Integer32
                MAX-ACCESS read-only
                STATUS current
                DESCRIPTION "Valid cells received (Input Billing Count)"
                ::= { cirEmCirEmPvcStatsEntry 4 }
 
cirEmCirEmPvcStatsCellsDecodedHiA OBJECT-TYPE
                SYNTAX Integer32
                MAX-ACCESS read-only
                STATUS current
                DESCRIPTION "Valid cells transmitted (Output Billing Count)"
                ::= { cirEmCirEmPvcStatsEntry 5 }

cirEmCirEmPvcStatsCellsDecodedLoA OBJECT-TYPE
                SYNTAX Integer32
                MAX-ACCESS read-only
                STATUS current
                DESCRIPTION "Valid cells transmitted (Output Billing Count)"
                ::= { cirEmCirEmPvcStatsEntry 6 }

cirEmCirEmPvcStatsCellsEncodedHiB OBJECT-TYPE
                SYNTAX Integer32
                MAX-ACCESS read-only
                STATUS current
                DESCRIPTION "Valid cells received (Input Billing Count)"
                ::= { cirEmCirEmPvcStatsEntry 7 }
 
cirEmCirEmPvcStatsCellsEncodedLoB OBJECT-TYPE
                SYNTAX Integer32
                MAX-ACCESS read-only
                STATUS current
                DESCRIPTION "Valid cells received (Input Billing Count)"
                ::= { cirEmCirEmPvcStatsEntry 8 }
 
cirEmCirEmPvcStatsCellsDecodedHiB OBJECT-TYPE
                SYNTAX Integer32
                MAX-ACCESS read-only
                STATUS current
                DESCRIPTION "Valid cells transmitted (Output Billing Count)"
                ::= { cirEmCirEmPvcStatsEntry 9 }

cirEmCirEmPvcStatsCellsDecodedLoB OBJECT-TYPE
                SYNTAX Integer32
                MAX-ACCESS read-only
                STATUS current
                DESCRIPTION "Valid cells transmitted (Output Billing Count)"
                ::= { cirEmCirEmPvcStatsEntry 10 }

cirEmCirEmPvcStatsTimer OBJECT-TYPE
                SYNTAX Integer32
                MAX-ACCESS read-only
                STATUS current
                DESCRIPTION "Number of seconds stats have been collecting"
                ::= { cirEmCirEmPvcStatsEntry 11 }

cirEmCirEmPvcStatsOdometerCellsEncodedHiA OBJECT-TYPE
                SYNTAX Integer32
                MAX-ACCESS read-only
                STATUS current
                DESCRIPTION "Valid cells received (Input Billing Count)"
                ::= { cirEmCirEmPvcStatsEntry 12 }
 
cirEmCirEmPvcStatsOdometerCellsEncodedLoA OBJECT-TYPE
                SYNTAX Integer32
                MAX-ACCESS read-only
                STATUS current
                DESCRIPTION "Valid cells received (Input Billing Count)"
                ::= { cirEmCirEmPvcStatsEntry 13 }
 
cirEmCirEmPvcStatsOdometerCellsDecodedHiA OBJECT-TYPE
                SYNTAX Integer32
                MAX-ACCESS read-only
                STATUS current
                DESCRIPTION "Valid cells transmitted (Output Billing Count)"
                ::= { cirEmCirEmPvcStatsEntry 14 }

cirEmCirEmPvcStatsOdometerCellsDecodedLoA OBJECT-TYPE
                SYNTAX Integer32
                MAX-ACCESS read-only
                STATUS current
                DESCRIPTION "Valid cells transmitted (Output Billing Count)"
                ::= { cirEmCirEmPvcStatsEntry 15 }

cirEmCirEmPvcStatsOdometerCellsEncodedHiB OBJECT-TYPE
                SYNTAX Integer32
                MAX-ACCESS read-only
                STATUS current
                DESCRIPTION "Valid cells received (Input Billing Count)"
                ::= { cirEmCirEmPvcStatsEntry 16 }
 
cirEmCirEmPvcStatsOdometerCellsEncodedLoB OBJECT-TYPE
                SYNTAX Integer32
                MAX-ACCESS read-only
                STATUS current
                DESCRIPTION "Valid cells received (Input Billing Count)"
                ::= { cirEmCirEmPvcStatsEntry 17 }
 
cirEmCirEmPvcStatsOdometerCellsDecodedHiB OBJECT-TYPE
                SYNTAX Integer32
                MAX-ACCESS read-only
                STATUS current
                DESCRIPTION "Valid cells transmitted (Output Billing Count)"
                ::= { cirEmCirEmPvcStatsEntry 18 }

cirEmCirEmPvcStatsOdometerCellsDecodedLoB OBJECT-TYPE
                SYNTAX Integer32
                MAX-ACCESS read-only
                STATUS current
                DESCRIPTION "Valid cells transmitted (Output Billing Count)"
                ::= { cirEmCirEmPvcStatsEntry 19 }

cirEmCirEmPvcStatsOdometerTimer OBJECT-TYPE
                SYNTAX Integer32
                MAX-ACCESS read-only
                STATUS current
                DESCRIPTION "Number of seconds since odometer was reset."
                ::= { cirEmCirEmPvcStatsEntry 20 }

cirEmCirEmPvcStatsOdometerReset OBJECT-TYPE
                SYNTAX INTEGER {
                                reset(1)
                               }
                MAX-ACCESS read-write
                STATUS current
                DESCRIPTION "Odometer reset button."
                ::= { cirEmCirEmPvcStatsEntry 21 }


vbrVbrPvcStatsTable OBJECT-TYPE
                SYNTAX SEQUENCE OF VbrVbrPvcStatsEntry
                MAX-ACCESS not-accessible
                STATUS current
                DESCRIPTION "Table of statistics for a channel connection"
                ::= { connectionStatistics 11 }
 
vbrVbrPvcStatsEntry OBJECT-TYPE
                SYNTAX VbrVbrPvcStatsEntry
                MAX-ACCESS not-accessible
                STATUS current
                DESCRIPTION "Row definition for the connection statistics
                             table"
                INDEX { vbrVbrPvcStatsIfA, vbrVbrPvcStatsIfB
                      }
                ::= { vbrVbrPvcStatsTable 1}
 
VbrVbrPvcStatsEntry ::= SEQUENCE {
                vbrVbrPvcStatsIfA                        IntfIndex,
                vbrVbrPvcStatsIfB                        IntfIndex,
                vbrVbrPvcStatsCellsEncodedHiA                Integer32,
                vbrVbrPvcStatsCellsEncodedLoA                Integer32,
                vbrVbrPvcStatsCellsDecodedHiA                Integer32,
                vbrVbrPvcStatsCellsDecodedLoA                Integer32,
                vbrVbrPvcStatsCellsEncodedHiB                Integer32,
                vbrVbrPvcStatsCellsEncodedLoB                Integer32,
                vbrVbrPvcStatsCellsDecodedHiB                Integer32,
                vbrVbrPvcStatsCellsDecodedLoB                Integer32,
                vbrVbrPvcStatsTimer                     Integer32,
                vbrVbrPvcStatsOdometerCellsEncodedHiA        Integer32,
                vbrVbrPvcStatsOdometerCellsEncodedLoA        Integer32,
                vbrVbrPvcStatsOdometerCellsDecodedHiA        Integer32,
                vbrVbrPvcStatsOdometerCellsDecodedLoA        Integer32,
                vbrVbrPvcStatsOdometerCellsEncodedHiB        Integer32,
                vbrVbrPvcStatsOdometerCellsEncodedLoB        Integer32,
                vbrVbrPvcStatsOdometerCellsDecodedHiB        Integer32,
                vbrVbrPvcStatsOdometerCellsDecodedLoB        Integer32,
                vbrVbrPvcStatsOdometerTimer             Integer32,
                vbrVbrPvcStatsOdometerReset             INTEGER
                }
 
vbrVbrPvcStatsIfA OBJECT-TYPE
                SYNTAX IntfIndex
                MAX-ACCESS not-accessible
                STATUS current
                DESCRIPTION "Interface index (SSPPCCC) on side A"
                ::= { vbrVbrPvcStatsEntry 1 }
 
vbrVbrPvcStatsIfB OBJECT-TYPE
                SYNTAX IntfIndex
                MAX-ACCESS not-accessible
                STATUS current
                DESCRIPTION "Interface index (SSPPCCC) on side A"
                ::= { vbrVbrPvcStatsEntry 2 }
 

 
vbrVbrPvcStatsCellsEncodedHiA OBJECT-TYPE
                SYNTAX Integer32
                MAX-ACCESS read-only
                STATUS current
                DESCRIPTION "Cells encoded on side A- (High order portion) "
                ::= { vbrVbrPvcStatsEntry 4 }
 
vbrVbrPvcStatsCellsEncodedLoA OBJECT-TYPE
                SYNTAX Integer32
                MAX-ACCESS read-only
                STATUS current
                DESCRIPTION "Cells encoded on side A- (Low order portion)"
                ::= { vbrVbrPvcStatsEntry 5 }
 
vbrVbrPvcStatsCellsDecodedHiA OBJECT-TYPE
                SYNTAX Integer32
                MAX-ACCESS read-only
                STATUS current
                DESCRIPTION "Cells decoded on side A- (High order portion)"
                ::= { vbrVbrPvcStatsEntry 6 }
 
vbrVbrPvcStatsCellsDecodedLoA OBJECT-TYPE
                SYNTAX Integer32
                MAX-ACCESS read-only
                STATUS current
                DESCRIPTION "Cells decoded on side A- (Low order portion) "
                ::= { vbrVbrPvcStatsEntry 7 }


 
vbrVbrPvcStatsCellsEncodedHiB OBJECT-TYPE
                SYNTAX Integer32
                MAX-ACCESS read-only
                STATUS current
                DESCRIPTION "Cells encoded on side B- (High order portion) "
                ::= { vbrVbrPvcStatsEntry 9 }
 
vbrVbrPvcStatsCellsEncodedLoB OBJECT-TYPE
                SYNTAX Integer32
                MAX-ACCESS read-only
                STATUS current
                DESCRIPTION "Cells encoded on side B- (Low order portion)"
                ::= { vbrVbrPvcStatsEntry 10 }
 
vbrVbrPvcStatsCellsDecodedHiB OBJECT-TYPE
                SYNTAX Integer32
                MAX-ACCESS read-only
                STATUS current
                DESCRIPTION "Cells decoded on side B- (High order portion)"
                ::= { vbrVbrPvcStatsEntry 11 }
 
vbrVbrPvcStatsCellsDecodedLoB OBJECT-TYPE
                SYNTAX Integer32
                MAX-ACCESS read-only
                STATUS current
                DESCRIPTION "Cells decoded on side B- (Low order portion)"
                ::= { vbrVbrPvcStatsEntry 12 }

vbrVbrPvcStatsTimer OBJECT-TYPE
                SYNTAX Integer32
                MAX-ACCESS read-only
                STATUS current
                DESCRIPTION "Number of seconds stats have been collecting"
                ::= { vbrVbrPvcStatsEntry 13 }

vbrVbrPvcStatsOdometerCellsEncodedHiA OBJECT-TYPE
                SYNTAX Integer32
                MAX-ACCESS read-only
                STATUS current
                DESCRIPTION "Cells encoded on side A- (High order portion) "
                ::= { vbrVbrPvcStatsEntry 14 }
 
vbrVbrPvcStatsOdometerCellsEncodedLoA OBJECT-TYPE
                SYNTAX Integer32
                MAX-ACCESS read-only
                STATUS current
                DESCRIPTION "Cells encoded on side A- (Low order portion)"
                ::= { vbrVbrPvcStatsEntry 15 }
 
vbrVbrPvcStatsOdometerCellsDecodedHiA OBJECT-TYPE
                SYNTAX Integer32
                MAX-ACCESS read-only
                STATUS current
                DESCRIPTION "Cells decoded on side A- (High order portion)"
                ::= { vbrVbrPvcStatsEntry 16 }
 
vbrVbrPvcStatsOdometerCellsDecodedLoA OBJECT-TYPE
                SYNTAX Integer32
                MAX-ACCESS read-only
                STATUS current
                DESCRIPTION "Cells decoded on side A- (Low order portion) "
                ::= { vbrVbrPvcStatsEntry 17 }

vbrVbrPvcStatsOdometerCellsEncodedHiB OBJECT-TYPE
                SYNTAX Integer32
                MAX-ACCESS read-only
                STATUS current
                DESCRIPTION "Cells encoded on side B- (High order portion) "
                ::= { vbrVbrPvcStatsEntry 18 }
 
vbrVbrPvcStatsOdometerCellsEncodedLoB OBJECT-TYPE
                SYNTAX Integer32
                MAX-ACCESS read-only
                STATUS current
                DESCRIPTION "Cells encoded on side B- (Low order portion) "
                ::= { vbrVbrPvcStatsEntry 19 }
 
vbrVbrPvcStatsOdometerCellsDecodedHiB OBJECT-TYPE
                SYNTAX Integer32
                MAX-ACCESS read-only
                STATUS current
                DESCRIPTION "Cells decoded on side B- (High order portion)"
                ::= { vbrVbrPvcStatsEntry 20 }
 
vbrVbrPvcStatsOdometerCellsDecodedLoB OBJECT-TYPE
                SYNTAX Integer32
                MAX-ACCESS read-only
                STATUS current
                DESCRIPTION "Cells decoded on side B- (Low order portion) "
                ::= { vbrVbrPvcStatsEntry 21 }

vbrVbrPvcStatsOdometerTimer OBJECT-TYPE
                SYNTAX Integer32
                MAX-ACCESS read-only
                STATUS current
                DESCRIPTION "Number of seconds since odometer was reset."
                ::= { vbrVbrPvcStatsEntry 22 }

vbrVbrPvcStatsOdometerReset OBJECT-TYPE
                SYNTAX INTEGER {
                                reset(1)
                               }
                MAX-ACCESS read-write
                STATUS current
                DESCRIPTION "Odometer reset button."
                ::= { vbrVbrPvcStatsEntry 23 }


bridgeBridgePvcStatsTable OBJECT-TYPE
                SYNTAX SEQUENCE OF BridgeBridgePvcStatsEntry
                MAX-ACCESS not-accessible
                STATUS current
                DESCRIPTION "Table of bridge-bridge PVC connection
                             statistics"
                ::= { connectionStatistics 12 }
 
bridgeBridgePvcStatsEntry OBJECT-TYPE
                SYNTAX BridgeBridgePvcStatsEntry
                MAX-ACCESS not-accessible
                STATUS current
                DESCRIPTION "Row definition of statistics attributes"
                INDEX { bridgeBridgePvcStatsIfA, 
                        bridgeBridgePvcStatsIfB
                      }
                ::= { bridgeBridgePvcStatsTable 1}
 
BridgeBridgePvcStatsEntry ::= SEQUENCE {
                bridgeBridgePvcStatsIfA                                IntfIndex,
                bridgeBridgePvcStatsIfB                                IntfIndex,
                bridgeBridgePvcStatsCellsEncodedHiA                Integer32,
                bridgeBridgePvcStatsCellsEncodedLoA                Integer32,
                bridgeBridgePvcStatsCellsDecodedHiA                Integer32,
                bridgeBridgePvcStatsCellsDecodedLoA                Integer32,
                bridgeBridgePvcStatsCellsEncodedHiB                Integer32,
                bridgeBridgePvcStatsCellsEncodedLoB                Integer32,
                bridgeBridgePvcStatsCellsDecodedHiB                Integer32,
                bridgeBridgePvcStatsCellsDecodedLoB                Integer32,
                bridgeBridgePvcStatsTimer                        Integer32,
                bridgeBridgePvcStatsOdometerCellsEncodedHiA        Integer32,
                bridgeBridgePvcStatsOdometerCellsEncodedLoA        Integer32,
                bridgeBridgePvcStatsOdometerCellsDecodedHiA        Integer32,
                bridgeBridgePvcStatsOdometerCellsDecodedLoA        Integer32,
                bridgeBridgePvcStatsOdometerCellsEncodedHiB        Integer32,
                bridgeBridgePvcStatsOdometerCellsEncodedLoB        Integer32,
                bridgeBridgePvcStatsOdometerCellsDecodedHiB        Integer32,
                bridgeBridgePvcStatsOdometerCellsDecodedLoB        Integer32,
                bridgeBridgePvcStatsOdometerTimer                Integer32,
                bridgeBridgePvcStatsOdometerReset                INTEGER
                }
 
bridgeBridgePvcStatsIfA OBJECT-TYPE
                SYNTAX IntfIndex
                MAX-ACCESS not-accessible
                STATUS current
                DESCRIPTION " Interface index (SSPPCCC) on side A"
                ::= { bridgeBridgePvcStatsEntry 1 }

bridgeBridgePvcStatsIfB OBJECT-TYPE
                SYNTAX IntfIndex
                MAX-ACCESS not-accessible
                STATUS current
                DESCRIPTION "Interface index (SSPPCCC) on side B"
                ::= { bridgeBridgePvcStatsEntry 2 }

bridgeBridgePvcStatsCellsEncodedHiA OBJECT-TYPE
                SYNTAX Integer32
                MAX-ACCESS read-only
                STATUS current
                DESCRIPTION "Cells encoded on side A  - (High order portion )"
                ::= { bridgeBridgePvcStatsEntry 3 }
 
bridgeBridgePvcStatsCellsEncodedLoA OBJECT-TYPE
                SYNTAX Integer32
                MAX-ACCESS read-only
                STATUS current
                DESCRIPTION " Cells encoded on side A - ( Low order portion)  "
                ::= { bridgeBridgePvcStatsEntry 4 }
 
bridgeBridgePvcStatsCellsDecodedHiA OBJECT-TYPE
                SYNTAX Integer32
                MAX-ACCESS read-only
                STATUS current
                DESCRIPTION "Cells decoded on side A - ( High order portion)"
                ::= { bridgeBridgePvcStatsEntry 5 }
 
bridgeBridgePvcStatsCellsDecodedLoA OBJECT-TYPE
                SYNTAX Integer32
                MAX-ACCESS read-only
                STATUS current
                DESCRIPTION "Cells decoded on side A -  (Low order portion) "
                ::= { bridgeBridgePvcStatsEntry 6 }

bridgeBridgePvcStatsCellsEncodedHiB OBJECT-TYPE
                SYNTAX Integer32
                MAX-ACCESS read-only
                STATUS current
                DESCRIPTION "Cells encoded on side B  - (High order portion ) "
                ::= { bridgeBridgePvcStatsEntry 7 }
 
bridgeBridgePvcStatsCellsEncodedLoB OBJECT-TYPE
                SYNTAX Integer32
                MAX-ACCESS read-only
                STATUS current
                DESCRIPTION "Cells encoded on side B  - (Low order portion ) "
                ::= { bridgeBridgePvcStatsEntry 8 }
 
bridgeBridgePvcStatsCellsDecodedHiB OBJECT-TYPE
                SYNTAX Integer32
                MAX-ACCESS read-only
                STATUS current
                DESCRIPTION "Cells decoded on side B  - (High order portion )"
                ::= { bridgeBridgePvcStatsEntry 9 }
 
bridgeBridgePvcStatsCellsDecodedLoB OBJECT-TYPE
                SYNTAX Integer32
                MAX-ACCESS read-only
                STATUS current
                DESCRIPTION "Cells decoded on side B  -(Low order portion ) "
                ::= { bridgeBridgePvcStatsEntry 10 }

bridgeBridgePvcStatsTimer OBJECT-TYPE
                SYNTAX Integer32
                MAX-ACCESS read-only
                STATUS current
                DESCRIPTION "Number of seconds stats have been collecting"
                ::= { bridgeBridgePvcStatsEntry 11 }

bridgeBridgePvcStatsOdometerCellsEncodedHiA OBJECT-TYPE
                SYNTAX Integer32
                MAX-ACCESS read-only
                STATUS current
                DESCRIPTION "Cells encoded on side A- (High order portion) "
                ::= { bridgeBridgePvcStatsEntry 12 }
 
bridgeBridgePvcStatsOdometerCellsEncodedLoA OBJECT-TYPE
                SYNTAX Integer32
                MAX-ACCESS read-only
                STATUS current
                DESCRIPTION " Cells encoded on side A- (Low order portion)"
                ::= { bridgeBridgePvcStatsEntry 13 }
 
bridgeBridgePvcStatsOdometerCellsDecodedHiA OBJECT-TYPE
                SYNTAX Integer32
                MAX-ACCESS read-only
                STATUS current
                DESCRIPTION "Cells decoded on side A- (High order portion)"
                ::= { bridgeBridgePvcStatsEntry 14 }
 
bridgeBridgePvcStatsOdometerCellsDecodedLoA OBJECT-TYPE
                SYNTAX Integer32
                MAX-ACCESS read-only
                STATUS current
                DESCRIPTION "Cells decoded on side A- (Low order portion) "
                ::= { bridgeBridgePvcStatsEntry 15 }

bridgeBridgePvcStatsOdometerCellsEncodedHiB OBJECT-TYPE
                SYNTAX Integer32
                MAX-ACCESS read-only
                STATUS current
                DESCRIPTION "Cells encoded on side B - (High order portion)"
                ::= { bridgeBridgePvcStatsEntry 16 }
 
bridgeBridgePvcStatsOdometerCellsEncodedLoB OBJECT-TYPE
                SYNTAX Integer32
                MAX-ACCESS read-only
                STATUS current
                DESCRIPTION "Cells encoded on side B - (Low order portion)"
                ::= { bridgeBridgePvcStatsEntry 17 }
 
bridgeBridgePvcStatsOdometerCellsDecodedHiB OBJECT-TYPE
                SYNTAX Integer32
                MAX-ACCESS read-only
                STATUS current
                DESCRIPTION " Cells decoded on side B - (High order portion)  "
                ::= { bridgeBridgePvcStatsEntry 18 }
 
bridgeBridgePvcStatsOdometerCellsDecodedLoB OBJECT-TYPE
                SYNTAX Integer32
                MAX-ACCESS read-only
                STATUS current
                DESCRIPTION " Cells decoded on side B - (Low order portion)"
                ::= { bridgeBridgePvcStatsEntry 19 }

bridgeBridgePvcStatsOdometerTimer OBJECT-TYPE
                SYNTAX Integer32
                MAX-ACCESS read-only
                STATUS current
                DESCRIPTION "Number of seconds since odometer was reset."
                ::= { bridgeBridgePvcStatsEntry 20 }

bridgeBridgePvcStatsOdometerReset OBJECT-TYPE
                SYNTAX INTEGER {
                                reset(1)
                               }
                MAX-ACCESS read-write
                STATUS current
                DESCRIPTION "Odometer reset button."
                ::= { bridgeBridgePvcStatsEntry 21 }


bridgeAtmPvcVccStatsTable OBJECT-TYPE
                SYNTAX SEQUENCE OF BridgeAtmPvcVccStatsEntry
                MAX-ACCESS not-accessible
                STATUS current
                DESCRIPTION "Table of statisics"
                ::= { connectionStatistics 13 }

bridgeAtmPvcVccStatsEntry OBJECT-TYPE
                SYNTAX BridgeAtmPvcVccStatsEntry
                MAX-ACCESS not-accessible
                STATUS current
                DESCRIPTION "Row definition for the connection statistics
                             table"
                INDEX { bridgeAtmPvcVccStatsIfA, bridgeAtmPvcVccStatsIfB, 
                        bridgeAtmPvcVccStatsVpiB, bridgeAtmPvcVccStatsVciB }
                ::= { bridgeAtmPvcVccStatsTable 1}

BridgeAtmPvcVccStatsEntry ::= SEQUENCE {
                bridgeAtmPvcVccStatsIfA                                IntfIndex,
                bridgeAtmPvcVccStatsIfB                         IntfIndex,
                bridgeAtmPvcVccStatsVpiB                         INTEGER,
                bridgeAtmPvcVccStatsVciB                         INTEGER,
                bridgeAtmPvcVccStatsCellsEncodedHiA                Integer32,
                bridgeAtmPvcVccStatsCellsEncodedLoA                Integer32,
                bridgeAtmPvcVccStatsCellsDecodedHiA                Integer32,
                bridgeAtmPvcVccStatsCellsDecodedLoA                Integer32,
                bridgeAtmPvcVccStatsInCellCountHiB                Integer32,
                bridgeAtmPvcVccStatsInCellCountLoB                Integer32,
                bridgeAtmPvcVccStatsOutCellCountHiB                Integer32,
                bridgeAtmPvcVccStatsOutCellCountLoB                Integer32,
                bridgeAtmPvcVccStatsTimer                        Integer32,
                bridgeAtmPvcVccStatsOdometerCellsEncodedHiA        Integer32,
                bridgeAtmPvcVccStatsOdometerCellsEncodedLoA        Integer32,
                bridgeAtmPvcVccStatsOdometerCellsDecodedHiA        Integer32,
                bridgeAtmPvcVccStatsOdometerCellsDecodedLoA        Integer32,
                bridgeAtmPvcVccStatsInOdometerCellCountHiB        Integer32,
                bridgeAtmPvcVccStatsInOdometerCellCountLoB        Integer32,
                bridgeAtmPvcVccStatsOutOdometerCellCountHiB        Integer32,
                bridgeAtmPvcVccStatsOutOdometerCellCountLoB        Integer32,
                bridgeAtmPvcVccStatsOdometerTimer                Integer32,
                bridgeAtmPvcVccStatsOdometerReset                INTEGER,
                bridgeAtmPvcVccStatsOamAisTx                        Integer32,
                bridgeAtmPvcVccStatsOamAisRx                        Integer32,
                bridgeAtmPvcVccStatsOamRdiTx                        Integer32,
                bridgeAtmPvcVccStatsOamRdiRx                        Integer32,
                bridgeAtmPvcVccStatsCellsDroppedB                 Integer32,
                bridgeAtmPvcVccStatsCellsTaggedB                  Integer32
                }

bridgeAtmPvcVccStatsIfA OBJECT-TYPE
                SYNTAX IntfIndex
                MAX-ACCESS not-accessible
                STATUS current
                DESCRIPTION " Interface index (SSPPCCC) on side A"
                ::= { bridgeAtmPvcVccStatsEntry 1 }

bridgeAtmPvcVccStatsIfB OBJECT-TYPE
                SYNTAX IntfIndex
                MAX-ACCESS not-accessible
                STATUS current
                DESCRIPTION "Interface index (SSPPCCC) on side B"
                ::= { bridgeAtmPvcVccStatsEntry 2 }

bridgeAtmPvcVccStatsVpiB OBJECT-TYPE
                SYNTAX INTEGER (0..4095)
                MAX-ACCESS not-accessible
                STATUS current
                DESCRIPTION "vpi - side B "
                ::= { bridgeAtmPvcVccStatsEntry 3 }

bridgeAtmPvcVccStatsVciB OBJECT-TYPE
                SYNTAX INTEGER (0..65535)
                MAX-ACCESS not-accessible
                STATUS current
                DESCRIPTION "vci - side B "
                ::= { bridgeAtmPvcVccStatsEntry 4 }

bridgeAtmPvcVccStatsCellsEncodedHiA OBJECT-TYPE
                SYNTAX Integer32
                MAX-ACCESS read-only
                STATUS current
                DESCRIPTION "number of cells encoded on side A
                             - (High order portion).  "
                ::= { bridgeAtmPvcVccStatsEntry 5 }

bridgeAtmPvcVccStatsCellsEncodedLoA OBJECT-TYPE
                SYNTAX Integer32
                MAX-ACCESS read-only
                STATUS current
                DESCRIPTION "number of cells encoded on side A
                             - (Low order portion).  "
                ::= { bridgeAtmPvcVccStatsEntry 6 }

bridgeAtmPvcVccStatsCellsDecodedHiA OBJECT-TYPE
                SYNTAX Integer32
                MAX-ACCESS read-only
                STATUS current
                DESCRIPTION " number of cells decoded on side A
                              - (High order portion). "
                ::= { bridgeAtmPvcVccStatsEntry 7 }

bridgeAtmPvcVccStatsCellsDecodedLoA OBJECT-TYPE
                SYNTAX Integer32
                MAX-ACCESS read-only
                STATUS current
                DESCRIPTION " number of cells decoded on side A
                              - (Low order portion).  "
                ::= { bridgeAtmPvcVccStatsEntry 8 }

bridgeAtmPvcVccStatsInCellCountHiB OBJECT-TYPE
                SYNTAX Integer32
                MAX-ACCESS read-only
                STATUS current
                DESCRIPTION "Valid cells received (Input Billing Count)"
                ::= { bridgeAtmPvcVccStatsEntry 9 }

bridgeAtmPvcVccStatsInCellCountLoB OBJECT-TYPE
                SYNTAX Integer32
                MAX-ACCESS read-only
                STATUS current
                DESCRIPTION "Valid cells received (Input Billing Count)"
                ::= { bridgeAtmPvcVccStatsEntry 10 }

bridgeAtmPvcVccStatsOutCellCountHiB OBJECT-TYPE
                SYNTAX Integer32
                MAX-ACCESS read-only
                STATUS current
                DESCRIPTION "Valid cells transmitted (Output Billing Count)"
                ::= { bridgeAtmPvcVccStatsEntry 11 }

bridgeAtmPvcVccStatsOutCellCountLoB OBJECT-TYPE
                SYNTAX Integer32
                MAX-ACCESS read-only
                STATUS current
                DESCRIPTION "Valid cells transmitted (Output Billing Count)"
                ::= { bridgeAtmPvcVccStatsEntry 12 }

bridgeAtmPvcVccStatsTimer OBJECT-TYPE
                SYNTAX Integer32
                MAX-ACCESS read-only
                STATUS current
                DESCRIPTION "Number of seconds stats have been collecting"
                ::= { bridgeAtmPvcVccStatsEntry 13 }

bridgeAtmPvcVccStatsOdometerCellsEncodedHiA OBJECT-TYPE
                SYNTAX Integer32
                MAX-ACCESS read-only
                STATUS current
                DESCRIPTION " Cells encoded on side A- (High order portion)"
                ::= { bridgeAtmPvcVccStatsEntry 14 }

bridgeAtmPvcVccStatsOdometerCellsEncodedLoA OBJECT-TYPE
                SYNTAX Integer32
                MAX-ACCESS read-only
                STATUS current
                DESCRIPTION "Cells encoded on side A- (Low order portion)"
                ::= { bridgeAtmPvcVccStatsEntry 15 }

bridgeAtmPvcVccStatsOdometerCellsDecodedHiA OBJECT-TYPE
                SYNTAX Integer32
                MAX-ACCESS read-only
                STATUS current
                DESCRIPTION "Cells decoded on side A- (High order portion)"
                ::= { bridgeAtmPvcVccStatsEntry 16 }

bridgeAtmPvcVccStatsOdometerCellsDecodedLoA OBJECT-TYPE
                SYNTAX Integer32
                MAX-ACCESS read-only
                STATUS current
                DESCRIPTION "Cells decoded on side A- (Low order portion)"
                ::= { bridgeAtmPvcVccStatsEntry 17 }

bridgeAtmPvcVccStatsInOdometerCellCountHiB OBJECT-TYPE
                SYNTAX Integer32
                MAX-ACCESS read-only
                STATUS current
                DESCRIPTION "Valid cells received (Input Billing Count)"
                ::= { bridgeAtmPvcVccStatsEntry 18 }

bridgeAtmPvcVccStatsInOdometerCellCountLoB OBJECT-TYPE
                SYNTAX Integer32
                MAX-ACCESS read-only
                STATUS current
                DESCRIPTION "Valid cells received (Input Billing Count)"
                ::= { bridgeAtmPvcVccStatsEntry 19 }

bridgeAtmPvcVccStatsOutOdometerCellCountHiB OBJECT-TYPE
                SYNTAX Integer32
                MAX-ACCESS read-only
                STATUS current
                DESCRIPTION "Valid cells transmitted (Output Billing Count)"
                ::= { bridgeAtmPvcVccStatsEntry 20 }

bridgeAtmPvcVccStatsOutOdometerCellCountLoB OBJECT-TYPE
                SYNTAX Integer32
                MAX-ACCESS read-only
                STATUS current
                DESCRIPTION "Valid cells transmitted (Output Billing Count)"
                ::= { bridgeAtmPvcVccStatsEntry 21 }

bridgeAtmPvcVccStatsOdometerTimer OBJECT-TYPE
                SYNTAX Integer32
                MAX-ACCESS read-only
                STATUS current
                DESCRIPTION "Number of seconds since odometer was reset."
                ::= { bridgeAtmPvcVccStatsEntry 22 }

bridgeAtmPvcVccStatsOdometerReset OBJECT-TYPE
                SYNTAX INTEGER {
                                reset(1)
                               }
                MAX-ACCESS read-write
                STATUS current
                DESCRIPTION "Odometer reset button."
                ::= { bridgeAtmPvcVccStatsEntry 23 }

bridgeAtmPvcVccStatsOamAisTx OBJECT-TYPE
                SYNTAX Integer32
                MAX-ACCESS read-only
                STATUS current
                DESCRIPTION "Number of AIS cells transmitted."
                ::= { bridgeAtmPvcVccStatsEntry 24 }

bridgeAtmPvcVccStatsOamAisRx OBJECT-TYPE
                SYNTAX Integer32
                MAX-ACCESS read-only
                STATUS current
                DESCRIPTION "Number of AIS cells received."
                ::= { bridgeAtmPvcVccStatsEntry 25 }

bridgeAtmPvcVccStatsOamRdiTx OBJECT-TYPE
                SYNTAX Integer32
                MAX-ACCESS read-only
                STATUS current
                DESCRIPTION "Number of RDI cells transmitted."
                ::= { bridgeAtmPvcVccStatsEntry 26 }

bridgeAtmPvcVccStatsOamRdiRx OBJECT-TYPE
                SYNTAX Integer32
                MAX-ACCESS read-only
                STATUS current
                DESCRIPTION "Number of RDI cells received."
                ::= { bridgeAtmPvcVccStatsEntry 27 }

bridgeAtmPvcVccStatsCellsDroppedB OBJECT-TYPE
                SYNTAX Integer32
                MAX-ACCESS read-only
                STATUS current
                DESCRIPTION "Cells Dropped on the Incoming side of B"
                ::= { bridgeAtmPvcVccStatsEntry 28 }

bridgeAtmPvcVccStatsCellsTaggedB OBJECT-TYPE
                SYNTAX Integer32
                MAX-ACCESS read-only
                STATUS current
                DESCRIPTION "Cells Tagged on the Incoming side of B" 
                ::= { bridgeAtmPvcVccStatsEntry 29 }



cirEmAtmSpvcVccStatsTable OBJECT-TYPE
                SYNTAX SEQUENCE OF CirEmAtmSpvcVccStatsEntry
                MAX-ACCESS not-accessible
                STATUS current
                DESCRIPTION "Table of statistics for a CES SPVC channel 
                             connection"
                ::= { connectionStatistics 14 }

cirEmAtmSpvcVccStatsEntry OBJECT-TYPE
                SYNTAX CirEmAtmSpvcVccStatsEntry
                MAX-ACCESS not-accessible
                STATUS current
                DESCRIPTION "Row definition for the CES SPVC connection 
                             statistics table"
                INDEX { cirEmAtmSpvcVccStatsIfA, cirEmAtmSpvcVccStatsIfB,
                        cirEmAtmSpvcVccStatsVpiB, cirEmAtmSpvcVccStatsVciB }
                ::= { cirEmAtmSpvcVccStatsTable 1}

CirEmAtmSpvcVccStatsEntry ::= SEQUENCE {
                cirEmAtmSpvcVccStatsIfA                                IntfIndex,
                cirEmAtmSpvcVccStatsIfB                                IntfIndex,
                cirEmAtmSpvcVccStatsVpiB                         INTEGER,
                cirEmAtmSpvcVccStatsVciB                        INTEGER,
                cirEmAtmSpvcVccStatsCellsEncodedHiA                Integer32,
                cirEmAtmSpvcVccStatsCellsEncodedLoA                Integer32,
                cirEmAtmSpvcVccStatsCellsDecodedHiA                Integer32,
                cirEmAtmSpvcVccStatsCellsDecodedLoA                Integer32,
                cirEmAtmSpvcVccStatsInCellCountHiB                Integer32,
                cirEmAtmSpvcVccStatsInCellCountLoB                Integer32,
                cirEmAtmSpvcVccStatsOutCellCountHiB                 Integer32,
                cirEmAtmSpvcVccStatsOutCellCountLoB                 Integer32,
                cirEmAtmSpvcVccStatsTimer                        Integer32,
                cirEmAtmSpvcVccStatsOdometerCellsEncodedHiA        Integer32,
                cirEmAtmSpvcVccStatsOdometerCellsEncodedLoA        Integer32,
                cirEmAtmSpvcVccStatsOdometerCellsDecodedHiA        Integer32,
                cirEmAtmSpvcVccStatsOdometerCellsDecodedLoA        Integer32,
                cirEmAtmSpvcVccStatsInOdometerCellCountHiB        Integer32,
                cirEmAtmSpvcVccStatsInOdometerCellCountLoB        Integer32,
                cirEmAtmSpvcVccStatsOutOdometerCellCountHiB         Integer32,
                cirEmAtmSpvcVccStatsOutOdometerCellCountLoB         Integer32,
                cirEmAtmSpvcVccStatsOdometerTimer                Integer32,
                cirEmAtmSpvcVccStatsOdometerReset                INTEGER,
                cirEmAtmSpvcVccStatsCellsDroppedB                 Integer32,
                cirEmAtmSpvcVccStatsCellsTaggedB                  Integer32
                }

cirEmAtmSpvcVccStatsIfA OBJECT-TYPE
                SYNTAX IntfIndex
                MAX-ACCESS not-accessible
                STATUS current
                DESCRIPTION "Interface index for side A, the circuit emulation
                             side, of a circuit emulation-atm SPVC VCC 
                             connection.  Number value is interpreted as an 
                             interface of the form, SSPPCCC, where SS is the 
                             card slot, PP is the port number, and CCC is the 
                             channel number."
                ::= { cirEmAtmSpvcVccStatsEntry 1 }

cirEmAtmSpvcVccStatsIfB OBJECT-TYPE
                SYNTAX IntfIndex
                MAX-ACCESS not-accessible
                STATUS current
                DESCRIPTION "Interface index for side B, the atm side, of a 
                             circuit emulation-atm SPVC VCC connection.  Number 
                             value is interpreted as an interface of the form, 
                             SSPPCCC, where SS is the card slot, PP is the port 
                             number, and CCC is the channel number."
                ::= { cirEmAtmSpvcVccStatsEntry 2 }

cirEmAtmSpvcVccStatsVpiB OBJECT-TYPE
                SYNTAX INTEGER (0..4095)
                MAX-ACCESS not-accessible
                STATUS current
                DESCRIPTION "VPI value for side B, the atm side,  of a
                             circuit emulation-atm SPVC VCC connection.  Valid 
                             range is a number between 0 and 4095."
                ::= { cirEmAtmSpvcVccStatsEntry 3 }

cirEmAtmSpvcVccStatsVciB OBJECT-TYPE
                SYNTAX INTEGER (0..65535)
                MAX-ACCESS not-accessible
                STATUS current
                DESCRIPTION "VCI value for side B, the atm side,  of a
                             circuit emulation-atm SPVC VCC connection.  Valid 
                             range is a number between 0 and 65535."
                ::= { cirEmAtmSpvcVccStatsEntry 4 }

cirEmAtmSpvcVccStatsCellsEncodedHiA OBJECT-TYPE
                SYNTAX Integer32
                MAX-ACCESS read-only
                STATUS current
                DESCRIPTION "Cells encoded on side A - (High order portion )"
                ::= { cirEmAtmSpvcVccStatsEntry 5 }

cirEmAtmSpvcVccStatsCellsEncodedLoA OBJECT-TYPE
                SYNTAX Integer32
                MAX-ACCESS read-only
                STATUS current
                DESCRIPTION "Cells encoded on side A - ( Low order portion) "
                ::= { cirEmAtmSpvcVccStatsEntry 6 }

cirEmAtmSpvcVccStatsCellsDecodedHiA OBJECT-TYPE
                SYNTAX Integer32
                MAX-ACCESS read-only
                STATUS current
                DESCRIPTION "Cells decoded on side A - ( High order portion) "
                ::= { cirEmAtmSpvcVccStatsEntry 7 }

cirEmAtmSpvcVccStatsCellsDecodedLoA OBJECT-TYPE
                SYNTAX Integer32
                MAX-ACCESS read-only
                STATUS current
                DESCRIPTION "Cells decoded on side A -  (Low order portion) "
                ::= { cirEmAtmSpvcVccStatsEntry 8 }

cirEmAtmSpvcVccStatsInCellCountHiB OBJECT-TYPE
                SYNTAX Integer32
                MAX-ACCESS read-only
                STATUS current
                DESCRIPTION "Valid Cells received on B - (High order portion)"
                ::= { cirEmAtmSpvcVccStatsEntry 9 }

cirEmAtmSpvcVccStatsInCellCountLoB OBJECT-TYPE
                SYNTAX Integer32
                MAX-ACCESS read-only
                STATUS current
                DESCRIPTION "Valid Cells received on B - (Low order portion) "
                ::= { cirEmAtmSpvcVccStatsEntry 10 }

cirEmAtmSpvcVccStatsOutCellCountHiB OBJECT-TYPE
                SYNTAX Integer32
                MAX-ACCESS read-only
                STATUS current
                DESCRIPTION "Valid cells transmitted on B - (High order portion)"
                ::= { cirEmAtmSpvcVccStatsEntry 11 }

cirEmAtmSpvcVccStatsOutCellCountLoB OBJECT-TYPE
                SYNTAX Integer32
                MAX-ACCESS read-only
                STATUS current
                DESCRIPTION "Valid cells transmitted on B - (Low order portion)"
                ::= { cirEmAtmSpvcVccStatsEntry 12 }

cirEmAtmSpvcVccStatsTimer OBJECT-TYPE
                SYNTAX Integer32
                MAX-ACCESS read-only
                STATUS current
                DESCRIPTION "Number of seconds since stats have been collecting"
                ::= { cirEmAtmSpvcVccStatsEntry 13 }

cirEmAtmSpvcVccStatsOdometerCellsEncodedHiA OBJECT-TYPE
                SYNTAX Integer32
                MAX-ACCESS read-only
                STATUS current
                DESCRIPTION "Cells encoded on side A- (High order portion) "
                ::= { cirEmAtmSpvcVccStatsEntry 14 }

cirEmAtmSpvcVccStatsOdometerCellsEncodedLoA OBJECT-TYPE
                SYNTAX Integer32
                MAX-ACCESS read-only
                STATUS current
                DESCRIPTION "Cells encoded on side A- (Low order portion) "
                ::= { cirEmAtmSpvcVccStatsEntry 15 }

cirEmAtmSpvcVccStatsOdometerCellsDecodedHiA OBJECT-TYPE
                SYNTAX Integer32
                MAX-ACCESS read-only
                STATUS current
                DESCRIPTION "Cells decoded on side A- (High order portion) "
                ::= { cirEmAtmSpvcVccStatsEntry 16 }

cirEmAtmSpvcVccStatsOdometerCellsDecodedLoA OBJECT-TYPE
                SYNTAX Integer32
                MAX-ACCESS read-only
                STATUS current
                DESCRIPTION "Cells decoded on side A- (Low order portion) "
                ::= { cirEmAtmSpvcVccStatsEntry 17 }

cirEmAtmSpvcVccStatsInOdometerCellCountHiB OBJECT-TYPE
                SYNTAX Integer32
                MAX-ACCESS read-only
                STATUS current
                DESCRIPTION "Valid cells received (Input Billing Count)"
                ::= { cirEmAtmSpvcVccStatsEntry 18 }

cirEmAtmSpvcVccStatsInOdometerCellCountLoB OBJECT-TYPE
                SYNTAX Integer32
                MAX-ACCESS read-only
                STATUS current
                DESCRIPTION "Valid cells received (Input Billing Count)"
                ::= { cirEmAtmSpvcVccStatsEntry 19 }

cirEmAtmSpvcVccStatsOutOdometerCellCountHiB OBJECT-TYPE
                SYNTAX Integer32
                MAX-ACCESS read-only
                STATUS current
                DESCRIPTION "Valid cells transmitted (Output Billing Count)"
                ::= { cirEmAtmSpvcVccStatsEntry 20 }

cirEmAtmSpvcVccStatsOutOdometerCellCountLoB OBJECT-TYPE
                SYNTAX Integer32
                MAX-ACCESS read-only
                STATUS current
                DESCRIPTION "Valid cells transmitted (Output Billing Count)"
                ::= { cirEmAtmSpvcVccStatsEntry 21 }

cirEmAtmSpvcVccStatsOdometerTimer OBJECT-TYPE
                SYNTAX Integer32
                MAX-ACCESS read-only
                STATUS current
                DESCRIPTION "Number of seconds since odometer was reset."
                ::= { cirEmAtmSpvcVccStatsEntry 22 }

cirEmAtmSpvcVccStatsOdometerReset OBJECT-TYPE
                SYNTAX INTEGER {
                                reset(1)
                               }
                MAX-ACCESS read-write
                STATUS current
                DESCRIPTION "Odometer reset button."
                ::= { cirEmAtmSpvcVccStatsEntry 23 }

cirEmAtmSpvcVccStatsCellsDroppedB OBJECT-TYPE
                SYNTAX Integer32
                MAX-ACCESS read-only
                STATUS current
                DESCRIPTION "Cells Dropped on the Incoming side of B"
                ::= { cirEmAtmSpvcVccStatsEntry 24 }

cirEmAtmSpvcVccStatsCellsTaggedB OBJECT-TYPE
                SYNTAX Integer32
                MAX-ACCESS read-only
                STATUS current
                DESCRIPTION "Cells Tagged on the Incoming side of B"
                ::= { cirEmAtmSpvcVccStatsEntry 25 }

vbrAtmSpvcVccStatsTable OBJECT-TYPE
                SYNTAX SEQUENCE OF VbrAtmSpvcVccStatsEntry
                MAX-ACCESS not-accessible
                STATUS current
                DESCRIPTION "Table of statistics for a TE SPVC channel 
                             connection."
                ::= { connectionStatistics 15 }

vbrAtmSpvcVccStatsEntry OBJECT-TYPE
                SYNTAX VbrAtmSpvcVccStatsEntry
                MAX-ACCESS not-accessible
                STATUS current
                DESCRIPTION "Row definition for the TE SPVC connection 
                             statistics table."
                INDEX { vbrAtmSpvcVccStatsIfA, vbrAtmSpvcVccStatsIfB,
                        vbrAtmSpvcVccStatsVpiB, vbrAtmSpvcVccStatsVciB }
                ::= { vbrAtmSpvcVccStatsTable 1}

VbrAtmSpvcVccStatsEntry ::= SEQUENCE {
                vbrAtmSpvcVccStatsIfA                                 IntfIndex,
                vbrAtmSpvcVccStatsIfB                                 IntfIndex,
                vbrAtmSpvcVccStatsVpiB                                 INTEGER,
                vbrAtmSpvcVccStatsVciB                                 INTEGER,
                vbrAtmSpvcVccStatsCellsEncodedHiA                Integer32,
                vbrAtmSpvcVccStatsCellsEncodedLoA                Integer32,
                vbrAtmSpvcVccStatsCellsDecodedHiA                Integer32,
                vbrAtmSpvcVccStatsCellsDecodedLoA                Integer32,
                vbrAtmSpvcVccStatsInCellCountHiB                Integer32,
                vbrAtmSpvcVccStatsInCellCountLoB                Integer32,
                vbrAtmSpvcVccStatsOutCellCountHiB                Integer32,
                vbrAtmSpvcVccStatsOutCellCountLoB                Integer32,
                vbrAtmSpvcVccStatsTimer                                Integer32,
                vbrAtmSpvcVccStatsOdometerCellsEncodedHiA        Integer32,
                vbrAtmSpvcVccStatsOdometerCellsEncodedLoA        Integer32,
                vbrAtmSpvcVccStatsOdometerCellsDecodedHiA        Integer32,
                vbrAtmSpvcVccStatsOdometerCellsDecodedLoA        Integer32,
                vbrAtmSpvcVccStatsInOdometerCellCountHiB        Integer32,
                vbrAtmSpvcVccStatsInOdometerCellCountLoB        Integer32,
                vbrAtmSpvcVccStatsOutOdometerCellCountHiB        Integer32,
                vbrAtmSpvcVccStatsOutOdometerCellCountLoB        Integer32,
                vbrAtmSpvcVccStatsOdometerTimer                        Integer32,
                vbrAtmSpvcVccStatsOdometerReset                        INTEGER,
                vbrAtmSpvcVccStatsCellsDroppedB                 Integer32,
                vbrAtmSpvcVccStatsCellsTaggedB                  Integer32
                }

vbrAtmSpvcVccStatsIfA OBJECT-TYPE
                SYNTAX IntfIndex
                MAX-ACCESS not-accessible
                STATUS current
                DESCRIPTION "Interface index for side A, the variable bit rate
                             side, of a variable bit rate-atm SPVC VCC 
                             connection.  Number value is interpreted as an 
                             interface of the form, SSPPCCC, where SS is the 
                             card slot, PP is the port number, and CCC is the 
                             channel number."
                ::= { vbrAtmSpvcVccStatsEntry 1 }

vbrAtmSpvcVccStatsIfB OBJECT-TYPE
                SYNTAX IntfIndex
                MAX-ACCESS not-accessible
                STATUS current
                DESCRIPTION "Interface index for side B, the atm side, of a 
                             variable bit rate-atm SPVC VCC connection.  Number 
                             value is interpreted as an interface of the form, 
                             SSPPCCC, where SS is the card slot, PP is the port 
                             number, and CCC is the channel number."
                ::= { vbrAtmSpvcVccStatsEntry 2 }

vbrAtmSpvcVccStatsVpiB OBJECT-TYPE
                SYNTAX INTEGER (0..4095)
                MAX-ACCESS not-accessible
                STATUS current
                DESCRIPTION "VPI value for side B, the atm side,  of a
                             variable bit rate-atm SPVC VCC connection.  Valid 
                             range is a number between 0 and 4095."
                ::= { vbrAtmSpvcVccStatsEntry 3 }

vbrAtmSpvcVccStatsVciB OBJECT-TYPE
                SYNTAX INTEGER (0..65535)
                MAX-ACCESS not-accessible
                STATUS current
                DESCRIPTION "VCI value for side B, the atm side,  of a
                             variable bit rate-atm SPVC VCC connection.  Valid 
                             range is a number between 0 and 65535."
                ::= { vbrAtmSpvcVccStatsEntry 4 }

vbrAtmSpvcVccStatsCellsEncodedHiA OBJECT-TYPE
                SYNTAX Integer32
                MAX-ACCESS read-only
                STATUS current
                DESCRIPTION "Cells encoded on side A- (High order portion)"
                ::= { vbrAtmSpvcVccStatsEntry 5 }

vbrAtmSpvcVccStatsCellsEncodedLoA OBJECT-TYPE
                SYNTAX Integer32
                MAX-ACCESS read-only
                STATUS current
                DESCRIPTION "ells encoded on side A - (Low order portion)"
                ::= { vbrAtmSpvcVccStatsEntry 6 }

vbrAtmSpvcVccStatsCellsDecodedHiA OBJECT-TYPE
                SYNTAX Integer32
                MAX-ACCESS read-only
                STATUS current
                DESCRIPTION "Cells decoded on side A - (High order portion)"
                ::= { vbrAtmSpvcVccStatsEntry 7 }

vbrAtmSpvcVccStatsCellsDecodedLoA OBJECT-TYPE
                SYNTAX Integer32
                MAX-ACCESS read-only
                STATUS current
                DESCRIPTION "Cells decoded on side A - (Low order portion)"
                ::= { vbrAtmSpvcVccStatsEntry 8 }

vbrAtmSpvcVccStatsInCellCountHiB OBJECT-TYPE
                SYNTAX Integer32
                MAX-ACCESS read-only
                STATUS current
                DESCRIPTION "Valid Cells received on  B - (High order portion)"
                ::= { vbrAtmSpvcVccStatsEntry 9}

vbrAtmSpvcVccStatsInCellCountLoB OBJECT-TYPE
                SYNTAX Integer32
                MAX-ACCESS read-only
                STATUS current
                DESCRIPTION "Valid Cells received on B - (Low order portion)"
                ::= { vbrAtmSpvcVccStatsEntry 10 }

vbrAtmSpvcVccStatsOutCellCountHiB OBJECT-TYPE
                SYNTAX Integer32
                MAX-ACCESS read-only
                STATUS current
                DESCRIPTION "Valid cells transmitted on B -(High order portion)"
                ::= { vbrAtmSpvcVccStatsEntry 11 }

vbrAtmSpvcVccStatsOutCellCountLoB OBJECT-TYPE
                SYNTAX Integer32
                MAX-ACCESS read-only
                STATUS current
                DESCRIPTION "Valid cells transmitted on B - (Low order portion)"
                ::= { vbrAtmSpvcVccStatsEntry 12 }

vbrAtmSpvcVccStatsTimer OBJECT-TYPE
                SYNTAX Integer32
                MAX-ACCESS read-only
                STATUS current
                DESCRIPTION "Number of seconds stats have been collecting"
                ::= { vbrAtmSpvcVccStatsEntry 13 }

vbrAtmSpvcVccStatsOdometerCellsEncodedHiA OBJECT-TYPE
                SYNTAX Integer32
                MAX-ACCESS read-only
                STATUS current
                DESCRIPTION "Cells encoded on side A- (High order portion)"
                ::= { vbrAtmSpvcVccStatsEntry 14 }

vbrAtmSpvcVccStatsOdometerCellsEncodedLoA OBJECT-TYPE
                SYNTAX Integer32
                MAX-ACCESS read-only
                STATUS current
                DESCRIPTION "Cells encoded on side A- (Low order portion)"
                ::= { vbrAtmSpvcVccStatsEntry 15 }

vbrAtmSpvcVccStatsOdometerCellsDecodedHiA OBJECT-TYPE
                SYNTAX Integer32
                MAX-ACCESS read-only
                STATUS current
                DESCRIPTION "Cells decoded on side A- (High order portion)"
                ::= { vbrAtmSpvcVccStatsEntry 16 }

vbrAtmSpvcVccStatsOdometerCellsDecodedLoA OBJECT-TYPE
                SYNTAX Integer32
                MAX-ACCESS read-only
                STATUS current
                DESCRIPTION "Cells decoded on side A- (Low order portion)"
                ::= { vbrAtmSpvcVccStatsEntry 17 }

vbrAtmSpvcVccStatsInOdometerCellCountHiB OBJECT-TYPE
                SYNTAX Integer32
                MAX-ACCESS read-only
                STATUS current
                DESCRIPTION "Valid Cells received on  B - (High order portion)"
                ::= { vbrAtmSpvcVccStatsEntry 18 }

vbrAtmSpvcVccStatsInOdometerCellCountLoB OBJECT-TYPE
                SYNTAX Integer32
                MAX-ACCESS read-only
                STATUS current
                DESCRIPTION "Valid Cells received on  B - (Low order portion)"
                ::= { vbrAtmSpvcVccStatsEntry 19 }

vbrAtmSpvcVccStatsOutOdometerCellCountHiB OBJECT-TYPE
                SYNTAX Integer32
                MAX-ACCESS read-only
                STATUS current
                DESCRIPTION "Valid Cells transmitted on B -(High order portion)"
                ::= { vbrAtmSpvcVccStatsEntry 20 }

vbrAtmSpvcVccStatsOutOdometerCellCountLoB OBJECT-TYPE
                SYNTAX Integer32
                MAX-ACCESS read-only
                STATUS current
                DESCRIPTION "Valid Cells transmitted on B -(Low order portion)"
                ::= { vbrAtmSpvcVccStatsEntry 21 }

vbrAtmSpvcVccStatsOdometerTimer OBJECT-TYPE
                SYNTAX Integer32
                MAX-ACCESS read-only
                STATUS current
                DESCRIPTION "Number of seconds since odometer was reset."
                ::= { vbrAtmSpvcVccStatsEntry 22 }

vbrAtmSpvcVccStatsOdometerReset OBJECT-TYPE
                SYNTAX INTEGER {
                                reset(1)
                               }
                MAX-ACCESS read-write
                STATUS current
                DESCRIPTION "Odometer reset button."
                ::= { vbrAtmSpvcVccStatsEntry 23 }

vbrAtmSpvcVccStatsCellsDroppedB OBJECT-TYPE
                SYNTAX Integer32
                MAX-ACCESS read-only
                STATUS current
                DESCRIPTION "Cells Dropped on the Incoming side of B"
                ::= { vbrAtmSpvcVccStatsEntry 24 }

vbrAtmSpvcVccStatsCellsTaggedB OBJECT-TYPE
                SYNTAX Integer32
                MAX-ACCESS read-only
                STATUS current
                DESCRIPTION "Cells Tagged on the Incoming side of B"
                ::= { vbrAtmSpvcVccStatsEntry 25 }

atmSpvcVccStatsTable OBJECT-TYPE
                SYNTAX SEQUENCE OF AtmSpvcVccStatsEntry
                MAX-ACCESS not-accessible
                STATUS current
                DESCRIPTION "Table of statistics for a ATM SPVC channel 
                             connection"
                ::= { connectionStatistics 16 }

atmSpvcVccStatsEntry OBJECT-TYPE
                SYNTAX AtmSpvcVccStatsEntry
                MAX-ACCESS not-accessible
                STATUS current
                DESCRIPTION "Row definition for the ATM SPVC connection 
                             statistics table"
                INDEX { atmSpvcVccStatsIfA, atmSpvcVccStatsVpiA,
                        atmSpvcVccStatsVciA, atmSpvcVccStatsIfB,
                        atmSpvcVccStatsVpiB, atmSpvcVccStatsVciB }
                ::= { atmSpvcVccStatsTable 1 }

AtmSpvcVccStatsEntry ::= SEQUENCE {
                atmSpvcVccStatsIfA                         IntfIndex,
                atmSpvcVccStatsVpiA                         INTEGER,
                atmSpvcVccStatsVciA                        INTEGER,
                atmSpvcVccStatsIfB                         IntfIndex,
                atmSpvcVccStatsVpiB                         INTEGER,
                atmSpvcVccStatsVciB                        INTEGER,
                atmSpvcVccStatsInCellCountHiA                Integer32,
                atmSpvcVccStatsInCellCountLoA                Integer32,
                atmSpvcVccStatsOutCellCountHiA                 Integer32,
                atmSpvcVccStatsOutCellCountLoA                 Integer32,
                atmSpvcVccStatsInCellCountHiB                Integer32,
                atmSpvcVccStatsInCellCountLoB                Integer32,
                atmSpvcVccStatsOutCellCountHiB                 Integer32,
                atmSpvcVccStatsOutCellCountLoB                 Integer32,
                atmSpvcVccStatsTimer                        Integer32,
                atmSpvcVccStatsFrwdErrCrrctnRateA2B        INTEGER,
                atmSpvcVccStatsFrwdErrCrrctnRateB2A        INTEGER,
                atmSpvcVccStatsInOdometerCellCountHiA        Integer32,
                atmSpvcVccStatsInOdometerCellCountLoA        Integer32,
                atmSpvcVccStatsOutOdometerCellCountHiA         Integer32,
                atmSpvcVccStatsOutOdometerCellCountLoA         Integer32,
                atmSpvcVccStatsInOdometerCellCountHiB        Integer32,
                atmSpvcVccStatsInOdometerCellCountLoB        Integer32,
                atmSpvcVccStatsOutOdometerCellCountHiB         Integer32,
                atmSpvcVccStatsOutOdometerCellCountLoB         Integer32,
                atmSpvcVccStatsOdometerTimer                Integer32,
                atmSpvcVccStatsOdometerReset                 INTEGER,
                atmSpvcVccStatsCellsDroppedA                  Integer32,
                atmSpvcVccStatsCellsTaggedA                  Integer32,
                atmSpvcVccStatsCellsDroppedB                  Integer32,
                atmSpvcVccStatsCellsTaggedB                  Integer32
                }

atmSpvcVccStatsIfA OBJECT-TYPE
                SYNTAX IntfIndex
                MAX-ACCESS not-accessible
                STATUS current
                DESCRIPTION "Interface index for side A of an ATM-to-ATM PVC VCC
                             connection.  Number value is interpreted as an
                             interface of the form, SSPPCCC, where SS is the 
                             card slot, PP is the port number, and CCC is the 
                             channel number."
                ::= { atmSpvcVccStatsEntry 1 }

atmSpvcVccStatsVpiA OBJECT-TYPE
                SYNTAX INTEGER (0..4095)
                MAX-ACCESS not-accessible
                STATUS current
                DESCRIPTION "VPI value for side A of an ATM-to-ATM PVC VCC 
                             connection.  Valid range is a number between 0 and 
                             4095."
                ::= { atmSpvcVccStatsEntry 2 }

atmSpvcVccStatsVciA OBJECT-TYPE
                SYNTAX INTEGER (0..65535)
                MAX-ACCESS not-accessible
                STATUS current
                DESCRIPTION "VCI value for side A of an ATM-to-ATM PVC VCC 
                             connection.  Valid range is a number between 0 and 
                             65535."
                ::= { atmSpvcVccStatsEntry 3 }

atmSpvcVccStatsIfB OBJECT-TYPE
                SYNTAX IntfIndex
                MAX-ACCESS not-accessible
                STATUS current
                DESCRIPTION "Interface index for side B of an ATM-to-ATM PVC VCC
                             connection.  Number value is interpreted as an
                             interface of the form, SSPPCCC, where SS is the 
                             card slot, PP is the port number, and CCC is the 
                             channel number."
                ::= { atmSpvcVccStatsEntry 4 }

atmSpvcVccStatsVpiB OBJECT-TYPE
                SYNTAX INTEGER (0..4095)
                MAX-ACCESS not-accessible
                STATUS current
                DESCRIPTION "VPI value for side B of an ATM-to-ATM PVC VCC 
                             connection.  Valid range is a number between 0 and 
                             4095."
                ::= { atmSpvcVccStatsEntry 5 }

atmSpvcVccStatsVciB OBJECT-TYPE
                SYNTAX INTEGER (0..65535)
                MAX-ACCESS not-accessible
                STATUS current
                DESCRIPTION "VCI value for side B of an ATM-to-ATM PVC VCC 
                             connection.  Valid range is a number between 0 and 
                             65535."
                ::= { atmSpvcVccStatsEntry 6 }

atmSpvcVccStatsInCellCountHiA OBJECT-TYPE
                SYNTAX Integer32
                MAX-ACCESS read-only
                STATUS current
                DESCRIPTION "Valid Cells received on A - (High order portion)"
                ::= { atmSpvcVccStatsEntry 7 }

atmSpvcVccStatsInCellCountLoA OBJECT-TYPE
                SYNTAX Integer32
                MAX-ACCESS read-only
                STATUS current
                DESCRIPTION "Valid Cells received on A - (Low order portion) "
                ::= { atmSpvcVccStatsEntry 8 }

atmSpvcVccStatsOutCellCountHiA OBJECT-TYPE
                SYNTAX Integer32
                MAX-ACCESS read-only
                STATUS current
                DESCRIPTION "Valid cells transmitted on A -(High order portion)"
                ::= { atmSpvcVccStatsEntry 9 }

atmSpvcVccStatsOutCellCountLoA OBJECT-TYPE
                SYNTAX Integer32
                MAX-ACCESS read-only
                STATUS current
                DESCRIPTION "Valid cells transmitted on A -(Low order portion)"
                ::= { atmSpvcVccStatsEntry 10 }

atmSpvcVccStatsInCellCountHiB OBJECT-TYPE
                SYNTAX Integer32
                MAX-ACCESS read-only
                STATUS current
                DESCRIPTION "Valid Cells received on B - (High order portion)"
                ::= { atmSpvcVccStatsEntry 11 }

atmSpvcVccStatsInCellCountLoB OBJECT-TYPE
                SYNTAX Integer32
                MAX-ACCESS read-only
                STATUS current
                DESCRIPTION "Valid Cells received on B - (Low order portion) "
                ::= { atmSpvcVccStatsEntry 12 }

atmSpvcVccStatsOutCellCountHiB OBJECT-TYPE
                SYNTAX Integer32
                MAX-ACCESS read-only
                STATUS current
                DESCRIPTION "Valid cells transmitted on B -(High order portion)"
                ::= { atmSpvcVccStatsEntry 13 }

atmSpvcVccStatsOutCellCountLoB OBJECT-TYPE
                SYNTAX Integer32
                MAX-ACCESS read-only
                STATUS current
                DESCRIPTION "Valid cells transmitted on B -(Low order portion)"
                ::= { atmSpvcVccStatsEntry 14 }

atmSpvcVccStatsTimer OBJECT-TYPE
                SYNTAX Integer32
                MAX-ACCESS read-only
                STATUS current
                DESCRIPTION "Number of seconds stats have been collecting"
                ::= { atmSpvcVccStatsEntry 15 }

atmSpvcVccStatsFrwdErrCrrctnRateA2B OBJECT-TYPE
                SYNTAX INTEGER {
                                none(1),
                                eighthRate(2),
                                quarterRate(3),
                                halfRate(4)
                               }
                MAX-ACCESS read-only
                STATUS current
                DESCRIPTION "Displays the Forward error correction rate being 
                             used by the FEC module in the A2B direction.  This
                             field is dynamic when Auto rates are selected.  In
                             other cases, it will display the rate set by the 
                             user."
                DEFVAL { none }
                ::= { atmSpvcVccStatsEntry 16 }

atmSpvcVccStatsFrwdErrCrrctnRateB2A OBJECT-TYPE
                SYNTAX INTEGER {
                                none(1),
                                eighthRate(2),
                                quarterRate(3),
                                halfRate(4)
                               }
                MAX-ACCESS read-only
                STATUS current
                DESCRIPTION "Displays the Forward error correction rate being 
                             used by the FEC module in the B2A direction.  This
                             field is dynamic when Auto rates are selected.  In
                             other cases, it will display the rate set by the 
                             user."
                DEFVAL { none }
                ::= { atmSpvcVccStatsEntry 17 }

atmSpvcVccStatsInOdometerCellCountHiA OBJECT-TYPE
                SYNTAX Integer32
                MAX-ACCESS read-only
                STATUS current
                DESCRIPTION "Valid cells received (Input Billing Count)"
                ::= { atmSpvcVccStatsEntry 18 }

atmSpvcVccStatsInOdometerCellCountLoA OBJECT-TYPE
                SYNTAX Integer32
                MAX-ACCESS read-only
                STATUS current
                DESCRIPTION "Valid cells transmitted (Output Billing Count)"
                ::= { atmSpvcVccStatsEntry 19 }

atmSpvcVccStatsOutOdometerCellCountHiA OBJECT-TYPE
                SYNTAX Integer32
                MAX-ACCESS read-only
                STATUS current
                DESCRIPTION "Valid cells transmitted (Output Billing Count)"
                ::= { atmSpvcVccStatsEntry 20 }

atmSpvcVccStatsOutOdometerCellCountLoA OBJECT-TYPE
                SYNTAX Integer32
                MAX-ACCESS read-only
                STATUS current
                DESCRIPTION "Valid cells transmitted (Output Billing Count)"
                ::= { atmSpvcVccStatsEntry 21 }

atmSpvcVccStatsInOdometerCellCountHiB OBJECT-TYPE
                SYNTAX Integer32
                MAX-ACCESS read-only
                STATUS current
                DESCRIPTION "Valid cells received (Input Billing Count)"
                ::= { atmSpvcVccStatsEntry 22 }

atmSpvcVccStatsInOdometerCellCountLoB OBJECT-TYPE
                SYNTAX Integer32
                MAX-ACCESS read-only
                STATUS current
                DESCRIPTION "Valid cells transmitted (Output Billing Count)"
                ::= { atmSpvcVccStatsEntry 23 }

atmSpvcVccStatsOutOdometerCellCountHiB OBJECT-TYPE
                SYNTAX Integer32
                MAX-ACCESS read-only
                STATUS current
                DESCRIPTION "Valid cells transmitted (Output Billing Count)"
                ::= { atmSpvcVccStatsEntry 24 }

atmSpvcVccStatsOutOdometerCellCountLoB OBJECT-TYPE
                SYNTAX Integer32
                MAX-ACCESS read-only
                STATUS current
                DESCRIPTION "Valid cells transmitted (Output Billing Count)"
                ::= { atmSpvcVccStatsEntry 25 }

atmSpvcVccStatsOdometerTimer OBJECT-TYPE
                SYNTAX Integer32
                MAX-ACCESS read-only
                STATUS current
                DESCRIPTION "Number of seconds since odometer was reset."
                ::= { atmSpvcVccStatsEntry 26 }

atmSpvcVccStatsOdometerReset OBJECT-TYPE
                SYNTAX INTEGER {
                                reset(1)
                               }
                MAX-ACCESS read-write
                STATUS current
                DESCRIPTION "Odometer reset button."
                ::= { atmSpvcVccStatsEntry 27 }

atmSpvcVccStatsCellsDroppedA OBJECT-TYPE
                SYNTAX Integer32
                MAX-ACCESS read-only
                STATUS current
                DESCRIPTION "Cells Dropped on the Incoming side of A"
                ::= { atmSpvcVccStatsEntry 28 }

atmSpvcVccStatsCellsTaggedA OBJECT-TYPE
                SYNTAX Integer32
                MAX-ACCESS read-only
                STATUS current
                DESCRIPTION "Cells Tagged on the Incoming side of A"
                ::= { atmSpvcVccStatsEntry 29 }

atmSpvcVccStatsCellsDroppedB OBJECT-TYPE
                SYNTAX Integer32
                MAX-ACCESS read-only
                STATUS current
                DESCRIPTION "Cells Dropped on the Incoming side of B"
                ::= { atmSpvcVccStatsEntry 30 }

atmSpvcVccStatsCellsTaggedB OBJECT-TYPE
                SYNTAX Integer32
                MAX-ACCESS read-only
                STATUS current
                DESCRIPTION "Cells Tagged on the Incoming side of B"
                ::= { atmSpvcVccStatsEntry 31 }




-- IP over ATM Group

ipAtmArpSrvConnType OBJECT-TYPE
                SYNTAX INTEGER  {
                                pvc(1),
                                svc(2),
                                none(3)
                                }
                MAX-ACCESS read-write
                STATUS current
                DESCRIPTION "type of Arp Server connection"
                ::= { ipAtmGroup 1 }

ipAtmIpAddr        OBJECT-TYPE
                SYNTAX IpAddress
                MAX-ACCESS read-write
                STATUS current
                DESCRIPTION "Local IP Address" 
                ::= { ipAtmGroup 2 }
                
ipAtmIpMask        OBJECT-TYPE
                SYNTAX IpAddress
                MAX-ACCESS read-write
                STATUS current
                DESCRIPTION "Local IP Mask" 
                ::= { ipAtmGroup 3 }


atmArpTable        OBJECT-TYPE
                SYNTAX SEQUENCE OF AtmArpEntry
                MAX-ACCESS not-accessible
                STATUS current
                DESCRIPTION "ARP Table"
                ::= { ipAtmGroup 4 }

atmArpEntry        OBJECT-TYPE
                SYNTAX AtmArpEntry
                MAX-ACCESS not-accessible
                STATUS current
                DESCRIPTION "ARP Table entry"
                INDEX { atmArpIpAddress }
                ::= { atmArpTable 1 }

AtmArpEntry        ::= SEQUENCE {
                              atmArpIpAddress                IpAddress,
                        atmArpAtmAddress        OCTET STRING,
                        atmArpAddrType                INTEGER,
                        atmArpEntryState        INTEGER,
                        atmArpEntryRowStatus        RowStatus
                        }

atmArpIpAddress        OBJECT-TYPE
                SYNTAX IpAddress
                MAX-ACCESS not-accessible
                STATUS current
                DESCRIPTION "IP address of the IP host described in APR table
                             entry."
                ::= { atmArpEntry 1 }

atmArpAtmAddress OBJECT-TYPE
                SYNTAX OCTET STRING (SIZE(20))
                MAX-ACCESS read-write
                STATUS current
                DESCRIPTION "ATM address of the IP host."
                ::= { atmArpEntry 2 }

atmArpAddrType        OBJECT-TYPE
                SYNTAX INTEGER {
                                nsap(1),
                                e164(2),
                                e164nsap(3)
                               }
                MAX-ACCESS read-write
                STATUS current
                DESCRIPTION "Type of ATM address value of atmArp address."
                DEFVAL { nsap }
                ::= { atmArpEntry 3 }

atmArpEntryState OBJECT-TYPE
                SYNTAX INTEGER {
                                valid(1),
                                invalid(2),
                                unconnected(3),
                                permanent(4),
                                pendingAtmAddr(5),
                                pendingIpAddr(6),
                                pendingConnect(7)
                               }
                MAX-ACCESS read-only
                STATUS current
                DESCRIPTION "State of this entry."
                DEFVAL { valid }
                ::= { atmArpEntry 4 }

atmArpEntryRowStatus OBJECT-TYPE
                SYNTAX RowStatus
                MAX-ACCESS read-write
                STATUS current
                DESCRIPTION "RowStatus of this entry."
                ::= { atmArpEntry 5 }


appIpRouteTable OBJECT-TYPE
              SYNTAX  SEQUENCE OF AppIpRouteEntry
              MAX-ACCESS  not-accessible
              STATUS  current
              DESCRIPTION "Application IP Routing table."
              ::= { ipAtmGroup  5 }

appIpRouteEntry OBJECT-TYPE
              SYNTAX  AppIpRouteEntry
              MAX-ACCESS  not-accessible
              STATUS  current
              DESCRIPTION "A route to a particular destination."
              INDEX   { appIpRouteDest, appIpRouteMask, appIpRouteMetric1 }
              ::= { appIpRouteTable 1 }

AppIpRouteEntry ::=
              SEQUENCE {
                  appIpRouteDest
                      IpAddress,
                  appIpRouteMask
                      IpAddress,
                  appIpRouteMetric1
                      INTEGER,
                  appIpRouteNextHop
                      IpAddress,
                  appIpRouteState
                     INTEGER
              }

appIpRouteDest OBJECT-TYPE
              SYNTAX  IpAddress
              MAX-ACCESS  not-accessible
              STATUS  current
              DESCRIPTION
                      "The destination IP address of this route.  An
                      entry with a value of 0.0.0.0 is not valid
                      route. "
              ::= { appIpRouteEntry 1 }

appIpRouteMask OBJECT-TYPE
              SYNTAX  IpAddress
              MAX-ACCESS not-accessible
              STATUS  current
              DESCRIPTION
                      "Mask for Ip route, usefull only for SENS stack 
                       VxWorks"
              ::= { appIpRouteEntry 2 }


appIpRouteMetric1 OBJECT-TYPE
              SYNTAX  INTEGER (1..255)
              MAX-ACCESS not-accessible
              STATUS  current
              DESCRIPTION
                      "The primary routing metric for this route.  The
                      semantics of this metric are determined by the
                      routing-protocol specified in the routes
                      appIpRouteProto value.  If this metric is not used,
                      its value should be set to 1."
              ::= { appIpRouteEntry 3 }

appIpRouteNextHop OBJECT-TYPE
              SYNTAX  IpAddress
              MAX-ACCESS  read-write
              STATUS  current
              DESCRIPTION
                      "The IP address of the next hop of this route.
                      (In the case of a route bound to an interface
                      which is realized via a broadcast media, the value
                      of this field is the agent's IP address on that
                      interface.)"
              ::= { appIpRouteEntry 4 }

appIpRouteState OBJECT-TYPE
                SYNTAX INTEGER {
                                invalid(0),
                                inuse(1),
                                notinuse(2),
                                error(3)
                               }
                MAX-ACCESS read-only
                STATUS current
                DESCRIPTION "Current state of route"
                ::= { appIpRouteEntry  5 }

-- Iisp Routing Group iispRouting

iispCbrRoutTable OBJECT-TYPE
                SYNTAX SEQUENCE OF IispCbrRoutEntry
                MAX-ACCESS not-accessible
                STATUS current
                DESCRIPTION "IISP CBR Routing Table"
                ::= { iispRouting 1 }

iispCbrRoutEntry OBJECT-TYPE
                SYNTAX IispCbrRoutEntry
                MAX-ACCESS not-accessible
                STATUS current
                DESCRIPTION "IISP CBR Table Entry"
                INDEX { iispCbrRoutLength,
                        iispCbrRoutNsapAddr }
                ::= { iispCbrRoutTable 1 }

IispCbrRoutEntry ::= SEQUENCE {
                              iispCbrRoutLength             Integer32,
                              iispCbrRoutNsapAddr        OCTET STRING,
                              iispCbrRoutIfIndex        IntfIndex,
                              iispCbrRoutRowStatus        RowStatus
                              }

iispCbrRoutLength OBJECT-TYPE
               SYNTAX Integer32
               MAX-ACCESS not-accessible
               STATUS current
               DESCRIPTION "length in bits"
               ::= { iispCbrRoutEntry 1 }

iispCbrRoutNsapAddr OBJECT-TYPE
               SYNTAX OCTET STRING (SIZE(1..20))
               MAX-ACCESS not-accessible
               STATUS current
               DESCRIPTION "nsap address"
               ::= { iispCbrRoutEntry 2 }

iispCbrRoutIfIndex OBJECT-TYPE
               SYNTAX IntfIndex
               MAX-ACCESS read-write
               STATUS current
               DESCRIPTION "Interface index - SSPPCCC"
               ::= { iispCbrRoutEntry 3 }

iispCbrRoutRowStatus OBJECT-TYPE
              SYNTAX RowStatus
              MAX-ACCESS read-write
              STATUS current
              DESCRIPTION "row status"
              ::= { iispCbrRoutEntry 4 }


iispVbrRoutTable OBJECT-TYPE
             SYNTAX SEQUENCE OF IispVbrRoutEntry
             MAX-ACCESS not-accessible
             STATUS current
             DESCRIPTION "IISP CBR Routing Table"
             ::= { iispRouting 2 }

iispVbrRoutEntry OBJECT-TYPE
            SYNTAX IispVbrRoutEntry
            MAX-ACCESS not-accessible
            STATUS current
            DESCRIPTION "IISP CBR Table Entry"
            INDEX { iispVbrRoutLength, iispVbrRoutNsapAddr }
            ::= { iispVbrRoutTable 1 }

IispVbrRoutEntry::= SEQUENCE {
                              iispVbrRoutLength             Integer32,
                              iispVbrRoutNsapAddr        OCTET STRING,
                              iispVbrRoutIfIndex        IntfIndex,
                              iispVbrRoutRowStatus        RowStatus
                             }

iispVbrRoutLength OBJECT-TYPE
                SYNTAX Integer32
                MAX-ACCESS not-accessible
                STATUS current
                DESCRIPTION "length in bits"
                ::= { iispVbrRoutEntry 1 }

iispVbrRoutNsapAddr OBJECT-TYPE
                SYNTAX OCTET STRING (SIZE(1..20))
                MAX-ACCESS not-accessible
                STATUS current
                DESCRIPTION "nsap address"
                ::= { iispVbrRoutEntry 2 }

iispVbrRoutIfIndex OBJECT-TYPE
                SYNTAX IntfIndex
                MAX-ACCESS read-write
                STATUS current
                DESCRIPTION "Interface index - SSPPCCC"
                ::= { iispVbrRoutEntry 3 }

iispVbrRoutRowStatus OBJECT-TYPE
                SYNTAX RowStatus
                MAX-ACCESS read-write
                STATUS current
                DESCRIPTION "row status"
                ::= { iispVbrRoutEntry 4 }



-- the following two tables are almost same as two iisp mib 
-- table above. They only diff at the number of the INDEX keys

iispCbrRouteTable  OBJECT-TYPE
                SYNTAX SEQUENCE OF IispCbrRouteEntry
                  MAX-ACCESS not-accessible
                STATUS current
                DESCRIPTION "IISP CBR Routing Table"
                ::= { iispRouting 3 }

iispCbrRouteEntry  OBJECT-TYPE
                SYNTAX IispCbrRouteEntry
                MAX-ACCESS not-accessible
                STATUS current
                DESCRIPTION "IISP CBR Route Entry"
                INDEX { iispCbrRouteLength,
                        iispCbrRouteNsapAddr, iispCbrRouteIfIndex

                        ,iispCbrRouteIfVuniId 

                        }
                  ::= { iispCbrRouteTable 1 }

IispCbrRouteEntry ::= SEQUENCE {
                iispCbrRouteLength        Integer32,
                iispCbrRouteNsapAddr      OCTET STRING,
                iispCbrRouteIfIndex        IntfIndex,
                iispCbrRouteRowStatus  RowStatus

        ,iispCbrRouteIfVuniId    INTEGER,



                iispCbrRouteDest        Integer32,
                iispCbrRouteType        Integer32
                }

iispCbrRouteLength   OBJECT-TYPE
                SYNTAX Integer32
                MAX-ACCESS not-accessible
                STATUS current
                DESCRIPTION "length in bits"
                ::= { iispCbrRouteEntry 1 }

iispCbrRouteNsapAddr  OBJECT-TYPE
                SYNTAX OCTET STRING (SIZE(1..20))
                MAX-ACCESS not-accessible
                STATUS current
                DESCRIPTION "nsap address"
                ::= { iispCbrRouteEntry 2 }

iispCbrRouteIfIndex  OBJECT-TYPE
                SYNTAX IntfIndex
                MAX-ACCESS not-accessible
                STATUS current
                DESCRIPTION "Interface index - SSPPCCC"
                ::= { iispCbrRouteEntry 3 }

iispCbrRouteRowStatus OBJECT-TYPE
                SYNTAX RowStatus
                MAX-ACCESS read-write
                STATUS current
                DESCRIPTION "row status"
                ::= { iispCbrRouteEntry 4 }


iispCbrRouteIfVuniId OBJECT-TYPE
                SYNTAX INTEGER (0..255)
                MAX-ACCESS not-accessible
                STATUS current
                  DESCRIPTION "Virtual UNI interface VUNI Id"
        DEFVAL { 0 }
                ::= { iispCbrRouteEntry 5 }


-- The following 2 objects are defined according to the definition in the
-- header file atmRoute.h under atmRoute/inc. For backward compatibility and
-- minimal code changes, the values have been retained in dito
 
iispCbrRouteType OBJECT-TYPE
                SYNTAX INTEGER {
                        drmRouteTypeAny (0),
                        drmRouteTypeAtm (1),
                        drmRouteTypeIisp (2),
                        drmRouteTypeIlmiUser (3),
                        drmRouteTypeIsdn (11),
                        drmRouteTypeCe (21),
                        drmRouteTypeSs7 (31),
                        drmRouteTypeFr (41),
                        drmRouteTypeCasTrunk (51),
                        drmRouteTypeEndPtAtm (132),
                        drmRouteTypeEndPtCe (133),
                        drmRouteTypeEndPtTe (134),
                        drmRouteTypeEndPtIsdn (135),
                        drmRouteTypeEndPtIp (136),
                        drmRouteTypeEndPtFr (137)
                }
                MAX-ACCESS read-write
                STATUS current
                DESCRIPTION "Type of Route, Categorisation of an Endpoint
                             Route or an intermediate Route"
                DEFVAL { 0 }

                ::= { iispCbrRouteEntry 6 }



 
iispCbrRouteDest OBJECT-TYPE
                SYNTAX INTEGER {
                        drmRouteDestAny (0),
                        drmRouteDestAtm (1),
                        drmRouteDestIsdn (2),
                        drmRouteDestCe (3),
                        drmRouteDestSs7 (4),
                        drmRouteDestFr (5),
                        drmRouteDestAalIwf (6),
                        drmRouteDestEndPtAtm (15),
                        drmRouteDestEndPtCe (16),
                        drmRouteDestEndPtTe (17),
                        drmRouteDestEndPtIsdn (18),
                        drmRouteTypeEndPtIp (19),
                        drmRouteTypeEndPtFr (20),
                        drmRouteTypeEndPtCas (21)
                }
                MAX-ACCESS read-write
                STATUS current
                DESCRIPTION "Type of Destination, Categorisation of an
                             Endpoint destination or an intermediate
                             destination"
                DEFVAL { 0 }

                ::= { iispCbrRouteEntry 7 }




iispVbrRouteTable  OBJECT-TYPE
                SYNTAX SEQUENCE OF IispVbrRouteEntry
                MAX-ACCESS not-accessible
                STATUS current
                DESCRIPTION "IISP CBR Routing Table"
                ::= { iispRouting 4 }

iispVbrRouteEntry  OBJECT-TYPE
                SYNTAX IispVbrRouteEntry
                MAX-ACCESS not-accessible
                STATUS current
                DESCRIPTION "IISP CBR Table Entry"
                INDEX { iispVbrRouteLength, iispVbrRouteNsapAddr,
                        iispVbrRouteIfIndex

                        , iispVbrRouteIfVuniId

                        }
                  ::= { iispVbrRouteTable 1 }

IispVbrRouteEntry ::= SEQUENCE {
                iispVbrRouteLength       Integer32,
                iispVbrRouteNsapAddr     OCTET STRING,
                iispVbrRouteIfIndex        IntfIndex,
                iispVbrRouteRowStatus     RowStatus

        ,iispVbrRouteIfVuniId    INTEGER,



                iispVbrRouteDest        Integer32,
                iispVbrRouteType        Integer32
                }

iispVbrRouteLength  OBJECT-TYPE
                SYNTAX Integer32
                MAX-ACCESS not-accessible
                STATUS current
                DESCRIPTION "length in bits"
                ::= { iispVbrRouteEntry 1 }

iispVbrRouteNsapAddr  OBJECT-TYPE
                SYNTAX OCTET STRING (SIZE(1..20))
                MAX-ACCESS not-accessible
                STATUS current
                DESCRIPTION "nsap address"
                ::= { iispVbrRouteEntry 2 }

iispVbrRouteIfIndex OBJECT-TYPE
                SYNTAX IntfIndex
                MAX-ACCESS not-accessible
                STATUS current
                  DESCRIPTION "In most cases, it is the I/O Interface index - 
                             SSPPCCC. However, in case of ATM Trunking's 
                             Narrowband routing and Broadband routing, this
                             is either the CAS trunk group ID, or the remote 
                             IWF ID, which are 1 to 3 digits decimal numbers"
                ::= { iispVbrRouteEntry 3 }

iispVbrRouteRowStatus OBJECT-TYPE
                SYNTAX RowStatus
                MAX-ACCESS read-write
                STATUS current
                DESCRIPTION "row status"
                ::= { iispVbrRouteEntry 4 }


iispVbrRouteIfVuniId OBJECT-TYPE
                SYNTAX INTEGER (0..255)
                MAX-ACCESS not-accessible
                STATUS current
                  DESCRIPTION "Virtual UNI interface VUNI Id"
        DEFVAL { 0 }
                ::= { iispVbrRouteEntry 5 }


-- The following 2 objects are defined according to the definition in the
-- header file atmRoute.h under atmRoute/inc. For backward compatibility and
-- minimal code changes, the values have been retained in dito
 
iispVbrRouteType OBJECT-TYPE
                SYNTAX INTEGER {
                        drmRouteTypeAny (0),
                        drmRouteTypeAtm (1),
                        drmRouteTypeIisp (2),
                        drmRouteTypeIlmiUser (3),
                        drmRouteTypeIsdn (11),
                        drmRouteTypeCe (21),
                        drmRouteTypeSs7 (31),
                        drmRouteTypeFr (41),
                        drmRouteTypeCasTrunk (51),
                        drmRouteTypeIwfTrunk (61),
                        drmRouteTypeEndPtAtm (132),
                        drmRouteTypeEndPtCe (133),
                        drmRouteTypeEndPtTe (134),
                        drmRouteTypeEndPtIsdn (135),
                        drmRouteTypeEndPtIp (136),
                        drmRouteTypeEndPtFr (137)
                }
                MAX-ACCESS read-write
                STATUS current
                DESCRIPTION "Type of Route, Categorisation of an Endpoint
                             Route or an intermediate Route"
                DEFVAL { 0 }

                ::= { iispVbrRouteEntry 6 }



 
iispVbrRouteDest OBJECT-TYPE
                SYNTAX INTEGER {
                        drmRouteDestAny (0),
                        drmRouteDestAtm (1),
                        drmRouteDestIsdn (2),
                        drmRouteDestCe (3),
                        drmRouteDestSs7 (4),
                        drmRouteDestFr (5),
                        drmRouteDestAalIwf (6),
                        drmRouteDestEndPtAny (14),
                        drmRouteDestEndPtAtm (15),
                        drmRouteDestEndPtCe (16),
                        drmRouteDestEndPtTe (17),
                        drmRouteDestEndPtIsdn (18),
                        drmRouteTypeEndPtIp (19),
                        drmRouteTypeEndPtFr (20),
                        drmRouteTypeEndPtCas (21),
                        drmRouteTypeEndPtTrkIwf (22)
                }
                MAX-ACCESS read-write
                STATUS current
                DESCRIPTION "Type of Destination, Categorisation of an
                             Endpoint destination or an intermediate
                             destination"
                DEFVAL { 0 }

                ::= { iispVbrRouteEntry 7 }



 
-- Return Code Group returnCode

pvcFailureReasonCode    OBJECT-TYPE
                SYNTAX INTEGER  {
                                 vpiVciUnavailableA2B(1),
                                 vpiVciUnavailableB2A(2),
                                 bandwidthUnavailableA2B(3),
                                 bandwidthUnavailableB2A(4),
                                 qosUnavailableA2B(5),
                                 qosUnavailableB2A(6),
                                 internalResourceUnavailable(7),
                                 cantUseSignalingChnlIgrsA2B(8),
                                 cantUseSignalingChnlEgrsA2B(9),
                                 cantUseSignalingChnlIgrsB2A(10),
                                 cantUseSignalingChnlEgrsB2A(11),
                                 cantUseManagementChnlIgrsA2B(12),
                                 cantUseManagementChnlEgrsA2B(13),
                                 cantUseManagementChnlIgrsB2A(14),
                                 cantUseManagementChnlEgrsB2A(15),
                                 vcLessThanVcMinIgrsA2B(16),
                                 vcLessThanVcMinEgrsA2B(17),
                                 vcLessThanVcMinIgrsB2A(18),
                                 vcLessThanVcMinEgrsB2A(19),
                                 vcGreaterThanVcMaxIgrsA2B(20),
                                 vcGreaterThanVcMaxEgrsA2B(21),
                                 vcGreaterThanVcMaxIgrsB2A(22),
                                 vcGreaterThanVcMaxEgrsB2A(23),
                                 vpLessThanVpMinIgrsA2B(24),
                                 vpLessThanVpMinEgrsA2B(25),
                                 vpLessThanVpMinIgrsB2A(26),
                                 vpLessThanVpMinEgrsB2A(27),
                                 vpGreaterThanVpMaxIgrsA2B(28),
                                 vpGreaterThanVpMaxEgrsA2B(29),
                                 vpGreaterThanVpMaxIgrsB2A(30),
                                 vpGreaterThanVpMaxEgrsB2A(31),
                                 vpGreaterThanVpMaxIispIgrsA2B(32),
                                 vpGreaterThanVpMaxIispEgrsA2B(33),
                                 vpGreaterThanVpMaxIispIgrsB2A(34),
                                 vpGreaterThanVpMaxIispEgrsB2A(35),
                                 rsvdChnlRangeIgrsA2B(36),
                                 rsvdChnlRangeEgrsA2B(37),
                                 rsvdChnlRangeIgrsB2A(38),
                                 rsvdChnlRangeEgrsB2A(39),
                                 internalSrvcTypeUnavailableA2B(40),
                                 internalSrvcTypeUnavailableB2A(41),
                                 unrecognizableBindTypeEgrsA2B(42),
                                 unrecognizableBindTypeEgrsB2A(43),
                                 callWithoutConnections(44),
                                 callDataStructuresUnavailable(45),
                                 cnctnDataStructuresUnavailable(46),
                                 nullTrafficParametersRejectedA2B(47),
                                 nullTrafficParametersRejectedB2A(48),
                                 vpiWithinSvcRangeIgrsA2B(49),
                                 vpiWithinSvcRangeEgrsA2B(50),
                                 vpiWithinSvcRangeIgrsB2A(51),
                                 vpiWithinSvcRangeEgrsB2A(52),
                                 vpiInReservedListA2B(53),
                                 vpiInReservedListB2A(54),
                                 vpiInPvcListA2B(55),
                                 vpiInPvcListB2A(56),
                                 vpiInReleasedListA2B(57),
                                 vpiInReleasedListB2A(58),
                                 vciIsNotNullInVpcIgrsA2B(59),
                                 vciIsNotNullInVpcEgrsA2B(60),
                                 vciIsNotNullInVpcIgrsB2A(61),
                                 vciIsNotNullInVpcEgrsB2A(62),
                                 vpiInVpcReservedListA2B(63),
                                 vpiInVpcReservedListB2A(64),
                                 vpiVciInReservedListA2B(65),
                                 vpiVciInReservedListB2A(66),
                                 vpiInVpcPvcListA2B(67),
                                 vpiInVpcPvcListB2A(68),
                                 vpiVciInPvcListA2B(69),
                                 vpiVciInPvcListB2A(70),
                                 vpiInVpcReleasedListA2B(71),
                                 vpiInVpcReleasedListB2A(72),
                                 vpiVciInReleasedListA2B(73),
                                 vpiVciInReleasedListB2A(74),
                                 illegalMulticaseIdA2B(75),
                                 illegalMulticaseIdB2A(76),
                                 unsupportedConnectionA2B(77),
                                 unsupportedConnectionB2A(78),
                                 connectionsUnavailableInModuleA2B(79),
                                 connectionsUnavailableInModuleB2A(80),
                                 cbrBandwidthUnavailableIgrsA2B(81),
                                 cbrBandwidthUnavailableEgrsA2B(82),
                                 cbrBandwidthUnavailableIgrsB2A(83),
                                 cbrBandwidthUnavailableEgrsB2A(84),
                                 vbrBandwidthUnavailableIgrsA2B(85),
                                 vbrBandwidthUnavailableEgrsA2B(86),
                                 vbrBandwidthUnavailableIgrsB2A(87),
                                 vbrBandwidthUnavailableEgrsB2A(88),
                                 vpiVciWithinSvcRangeIgrsA2B(89),
                                 vpiVciWithinSvcRangeEgrsA2B(90),
                                 vpiVciWithinSvcRangeIgrsB2A(91),
                                 vpiVciWithinSvcRangeEgrsB2A(92),
                                 multicastDataStructuresUnavailable(93),
                                 semaphoreTimeout(94),
                                 dlciFoundInReservedList(95),
                                 dlciFoundInPvcList(96),
                                 dlciFoundInReleasedList(97),
                                 invalidDlci(98),
                                 slotA-OutOfRange(99),
                                 portA-OutOfRange(100),
                                 channelA-OutOfRange(101),
                                 moduleA-Uninitialized(102),
                                 physicalPortA-Uninitialized(103),
                                 channelA-NotBound(104),
                                 moduleA-UnrecognizablePortType(105),
                                 slotB-OutOfRange(106),
                                 portB-OutOfRange(107),
                                 channelB-OutOfRange(108),
                                 moduleB-Uninitialized(109),
                                 physicalPortB-Uninitialized(110),
                                 channelB-NotBound(111),
                                 moduleB-UnrecognizablePortType(112),
                                 interfaceA-NotAtm(113),
                                 interfaceB-NotAtm(114),
                                 unrecognizableServiceTypeA2B(115),
                                 unrecognizableServiceTypeB2A(116),
                                 unrecognizableSarTypeA2B(117),
                                 unrecognizableSarTypeB2A(118),
                                 interfaceA-NotCircuitEmulation(119),
                                 interfaceB-NotCircuitEmulation(120),
                                 unrecognizableSilenceDetectionMode(121),
                                 unrecognizableEchoCancellationMode(122),
                                 unrecognizableVoiceCompressionMode(123),
                                 interfaceA-NotVbr(124),
                                 interfaceB-NotVbr(125),
                                 interfaceA-NotFrameRelay(126),
                                 interfaceB-NotFrameRelay(127),
                                 interfaceA-InHdlcPvcList(128),
                                 interfaceA-InHdlcReleasedList(129),
                                 interfaceA-InHdlcReservedList(130),
                                 interfaceA-InTerminalEmulationPvcList(131),
                                interfaceA-InTerminalEmulationReleasedList(132),
                                interfaceA-InTerminalEmulationReservedList(133),
                                 interfaceA-InCircuitEmulationPvcList(134),
                                 interfaceA-InCircuitEmulationReleasedList(135),
                                 interfaceA-InCircuitEmulationReservedList(136),
                                 notNullVpcInNoisyLinkA2BIgrs(137),
                                 notNullVpcInNoisyLinkA2BEgrs(138),
                                 invalidVccInNoisyLinkA2BIgrs(139),
                                 invalidVccInNoisyLinkA2BEgrs(140),
                                 unsupportedFrwdErrCorrectValueA2B(141),
                                 interfaceB-InHdlcPvcList(142),
                                 interfaceB-InHdlcReleasedList(143),
                                 interfaceB-InHdlcReservedList(144),
                                 interfaceB-InTerminalEmulationPvcList(145),
                                interfaceB-InTerminalEmulationReleasedList(146),
                                interfaceB-InTerminalEmulationReservedList(147),
                                 interfaceB-InCircuitEmulationPvcList(148),
                                 interfaceB-InCircuitEmulationReleasedList(149),
                                 interfaceB-InCircuitEmulationReservedList(150),
                                 notNullVpcInNoisyLinkB2AIgrs(151),
                                 notNullVpcInNoisyLinkB2AEgrs(152),
                                 invalidVccInNoisyLinkB2AIgrs(153),
                                 invalidVccInNoisyLinkB2AEgrs(154),
                                 unsupportedFrwdErrCorrectValueB2A(155),
                                 interfaceInUse(156),
                                 unsupportedFrwdErrCorrectSettings(157),
                                 unsupportedFlowSettings(158),
                                 frwdErrCorrectResourceInternalError(159),
                                 unsupportedConnection(160),
                                 ipDestAddrSubnetAInReservedList(161),
                                 ipDestAddrSubnetAInPvcList(162),
                                 ipDestAddrSubnetAInReleasedList(163),
                                 ipDestAddrSubnetBInReservedList(164),
                                 ipDestAddrSubnetBInPvcList(165),
                                 ipDestAddrSubnetBInReleasedList(166),
                                 notCpuIpInterfaceA(167),
                                 ipResourceUnavailable(168),
                                 fecAutoInSimplexNotValid(169),
                                 fecResourceUnavailable(170),
                                 notBridgeInterfaceA(171),
                                 notBridgeInterfaceB(172),
                                 invalidBridgePortA2B(173),
                                 invalidBridgePortB2A(174),
                                 interfaceAInBridgePvcList(175),
                                 interfaceBInBridgePvcList(176),
                                 interfaceAInBridgeReleasedList(177),
                                 interfaceBInBridgeReleasedList(178),
                                 interfaceAInBridgeReservedList(179),
                                 interfaceBInBridgeReservedList(180),
                                 invalidDlciA(181),
                                 invalidDlciB(182),
                                 unrecognizableServiceType(183),
                                 moduleAMcstNotSupported(184),
                                 moduleBMcstNotSupported(185),
                                 moduleAMultiPortMcstNotSupported(186),
                                 moduleBMultiPortMcstNotSupported(187),
                                 bcBeCirCannotBeNullA2B(188),
                                 bcBeCirCannotBeNullB2A(189),
                                 bcBeOrCirValTooHiA2B(190),
                                 bcBeOrCirValTooHiB2A(191),
                                 bcNotValidA2B(192),
                                 bcNotValidB2A(193),
                                 beNotValidA2B(194),
                                 beNotValidB2A(195),
                                 bcOrCirNotValidA2B(196),
                                 bcOrCirNotValidB2A(197),
                                 iWF-NotSupportedModuleA(198),
                                 iWF-NotSupportedModuleB(199),
                                 invalidMaxFrSizeA2B(200),
                                 invalidMaxFrSizeB2A(201),
                                 invalidSARType(202),
                                 unrecognizableSilenceDetectionModeA2B(203),
                                 unrecognizableEchoCancellationModeA2B(204),
                                 unrecognizableVoiceCompressionModeA2B(205),
                                 unrecognizableCallingToneDetectionA2B(206),
                                 unrecognizableCodingTranslationA2B(207),
                                 unrecognizableSilenceDetectionModeB2A(208),
                                 unrecognizableEchoCancellationModeB2A(209),
                                 unrecognizableVoiceCompressionModeB2A(210),
                                 unrecognizableCallingToneDetectionB2A(211),
                                 unrecognizableCodingTranslationB2A(212),
                                 dspUnsupportedForMultiCastConns(213),
                                 dspResourceUnavailable(214),
                                 destOrSrcCannotBeDSPCard(215),
                                 internalDSPResourceError(216),
                                 echoCancellationOnlySupportedForDuplex(217),
                                 cirEmCirEm-ThruPutMismatch(218),
                                 vi-Cannot-Be-0(219),
                                 vi-OOR(220),
                                 vi-Mod-Limit-Exceeded(221),
                                 vi-Resource-Unavail(222),
                                 vi-Already-Exists(223),
                                 vi-Does-Not-Exist(224),
                                 vi-0-Non-Ubr-Conn-Not-Supp(225),
                                 vi-OS-Cannot-Be-0(226),
                                 vi-OS-OOR(227),
                                 vi-CellRate-Too-Lo(228),
                                 vi-CellRate-Too-Hi(229),
                                 intf-CBR-CellRate-Exceeded(230),
                                 intf-VBR-CellRate-Exceeded(231),
                                 vi-Conn-CellRate-Exceeded(232),
                                 vi-Not-Enabled(233),
                                 vi-Should-Be-0(234),
                                 vi-OOR-A(235),
                                 vi-OOR-B(236),
                                 vi-0-Non-Ubr-Conn-Not-SuppA2B(237),
                                 vi-0-Non-Ubr-Conn-Not-SuppB2A(238),
                                 vi-Should-Be-0-A(239),
                                 vi-Should-Be-0-B(240),
                                 vi-Cbr-Bw-Unavailable-Egrs(241),
                                 vi-Cbr-Bw-Unavailable-Egrs-A(242),
                                 vi-Cbr-Bw-Unavailable-Egrs-B(243),
                                 vi-Vbr-Bw-Unavailable-Egrs(244),
                                 vi-Vbr-Bw-Unavailable-Egrs-A(245),
                                 vi-Vbr-Bw-Unavailable-Egrs-B(246),
                                 vi-Not-Enabled-A(247),
                                 vi-Not-Enabled-B(248),
                                 pcrLessThanScr(249),
                                 cnfrmTypeNotValidA2B(250),
                                 cnfrmTypeNotValidB2A(251),
                                 cnfrmType-ServiceType-Mismatch-A2B(252),
                                 cnfrmType-ServiceType-Mismatch-B2A(253),
                                 vuni-Should-Be-0(254),        
                                 vuni-Not-Enabled(255),                        
                                 vuni-OOR(256),
                                 vuni-Already-Exists(257),
                                 vuni-Does-Not-Exist(258),
                                 vuni-Does-Not-Match-vi(259),
                                 vuni-Should-Be-0-A(260),        
                                  vuni-Not-Enabled-A(261),
                                 vuni-OOR-A(262),
                                 vuni-Already-Exists-A(263),
                                 vuni-Does-Not-Exist-A(264),
                                 vuni-Does-Not-Match-vi-A(265),
                                 vuni-Should-Be-0-B(266),
                                 vuni-Not-Enabled-B(267),
                                 vuni-OOR-B(268),
                                 vuni-Already-Exists-B(269),
                                 vuni-Does-Not-Exist-B(270),
                                 vuni-Does-Not-Match-vi-B(271),
                                 vuni-Vpi-OOR(272),
                                 vuni-Vpi-OOR-A(273),
                                 vuni-Vpi-OOR-B(274),
                                 stdAal2TrunkResourceUnavailable(275),
                                 stdAal2Dsp2ResourceUnavailable(276),
                                 slotStdAal2ResourceUavailable(277),
                                 stdAal2CIDAlreadyInUse(278),
                                 stdAal2TrunkBWUavailableEgrs(279),
                                 stdAal2TrunkBWUavailableIgrs(280),
                                 stdAal2CIDInRsvRange(281),
                                 stdAal2TrunkNotSetup(282),
                                 aal2CIDOutOfRange(283),
                                 dhpvcSwitchOver-PrimToBkup(284),
                                 dhpvcSwitchOver-PrimToNone(285),
                                 dhpvcSwitchOver-NoneToPrim(286),
                                 dhpvcSwitchOver-NoneToBkup(287),
                                 dhpvcSwitchOver-BkupToNone(288),
                                 dhpvcSwitchOver-BkupToPrim(289),
                                 dhpvcState-Prim-Pass-Fail-Bkup-Act-NoFail(290),
                              dhpvcState-Prim-Pass-NoFail-Bkup-Act-NoFail(291),
                              dhpvcState-Prim-Act-NoFail-Bkup-Pass-Fail(292),
                              dhpvcState-Prim-Act-NoFail-Bkup-Pass-NoFail(293),
                              pcrGreaterThanLinkSpeedIngrA2B(294),
                              pcrGreaterThanLinkSpeedIngrB2A(295),
                              pcrGreaterThanLinkSpeedEgrA2B(296),
                              pcrGreaterThanLinkSpeedEgrB2A(297),
                              aal2CuTimerOutOfRange(298),
                              unrecognizableDigitCollectTypeA2B(299),
                              unrecognizableDigitCollectTypeB2A(300),
                              queueTypeSarTypeMismatchA2B(301),
                              queueTypeSarTypeMismatchB2A(302),
                              pcrLessThanOrEqualToMcrA2B(303),
                              pcrLessThanOrEqualToMcrB2A(304)
                                }
                MAX-ACCESS read-only
                STATUS current
                DESCRIPTION "An identified reason why an ATM PVC connection 
                             request failed.
                             aal2CuTimerOutOfRange(298):   this error code is 
                                  generated when the aal2CuTimer value is out
                                  of range and the valid reanges is 0 to 8 
                                  (0 - 40 msec of delay).
                             unrecognizableDigitCollectTypeA2B(299): 
                                  unrecognizable digital tone set in
                                  connection A2B direction.
                             unrecognizableDigitCollectTypeB2A(300): 
                                  unrecognizable digital tone set in
                                  connection B2A direction.
                            "
                ::= { returnCode 1 }

interfaceIndex        OBJECT-TYPE
                SYNTAX IntfIndex
                MAX-ACCESS read-only
                STATUS current
                DESCRIPTION "Interface index used for identifcation in traps.
                             Number value is interpreted as an interface of the 
                             form, SSPPCCC, where SS is the card slot, PP is 
                             the port number, and CCC is the channel number."
                ::= { returnCode 2 }

interfaceType   OBJECT-TYPE
            SYNTAX INTEGER  {
                atmUni3-0(1),
                atmUni3-1(2),

                iispUser(3),
                iispNetwork(4),

                circuitEmulation(5),
                frameRelayUni(6),

                pri-isdn-user(7),
                pri-isdn-network(8),

                terminalEmulation(9),
                dsp(10),
                hdlcPassThrough(11),
                bridge(12),
                routing(13),
                dbCirEm(14),
                frameRelayNni(15),
                dsp2(16),
                atmIma(17),
                atmPnni1-0(18),
                atmUni4-0(19),

                atmVnnUni3-1(20),

                casTrunkLine(21),
                toneAnnce(22),
                gr303(23)
            }
                MAX-ACCESS read-only
                STATUS current
                DESCRIPTION "Interface type used for identification in traps.
                             A specific interface is associated with each
                             number.
                        atmUni3-0(1)         ATM User Network Interface version 3.0
                        atmUni3-1(2)         ATM User Network Interface version 3.1
                        iispUser(3)          Interim Inter Switch Protocol User Side
                        iispNetwork(4)       Interim Inter Switch Protocol Network
                                             Side
                        circuitEmulation(5)  ATM Circuit Emulation
                        frameRelayUni(6)     Frame Relay User Network Interface
                        pri-isdn-user(7)     Integrated Services Digital Network
                                             Primary
                                             Rate Interface User Interface
                        pri-isdn-network(8)  Integrated Services Digital Network
                                             Primary
                                             Rate Interface Network Interface
                        terminalEmulation(9) Terminal Emulation
                        dsp(10)              DSP
                        hdlcPassThrough(11)  High Level Data Link Control Pass
                                             Through Interface
                        bridge(12)           Ethernet Bridge
                        routing(13)          Ethernet Routing
                        dbCirEm(14)          Dynamic Bandwidth Circuit Emulation
                        frameRelayNni(15)    Frame Relay Network Network Interface
                        dsp2(16)             DSP2
                        atmIma(17)           ATM Inverse Multiplexing over ATM (IMA)
                        atmPnni1-0(18)       ATM Private Network Network Interface
                                             Version 1.0
                        atmUni4-0(19)        ATM User Network Interface Version 4.0
                        atmVnnUni3-1(20)     ATM Virtual Network Navigator User 
                                             Network Interface Version 3.1
                        casTrunkLine(21)     Channel Associated Signaling Trunk
                                             Line Interface
                        toneAnnce(22)        Tone Announcement Interface
                        gr303(23)            GR303"
                ::= { returnCode 3 }

interfaceFailureReasonCode        OBJECT-TYPE
                SYNTAX INTEGER  {
                interfaceInService(1),
                interfaceNotNew(2),
                interfaceExists(3),
                bridgeGroupActive(4),
                signalingNotEnabled(5),
                firmwareOutOfDate(6),

                t1SigEnableInterfaceNotSupported(7),

                ts16ForData(8),
                dbcesConfigured(9),
                signalingEnabled(10),






                channelizationEnabled(15),
                unstructuredCEConfigured(16),
                firmwareOutOfDate-ts16CAS-unsupported(17),
                firmwareOutOfDate-interfaceType-unsupported(18),
                firmwareOutOfDate-ts16-unsupported(19),
                invalidPortMap(20),

                otherInterfacesExistOnThisPort(21),

                intfInIMAgroup(22),
                errorCTC-portTxClkSrc-notLocal(23),
                different-LoopbackConfig-on-Ports(24),
                imaGChanNeTxClkMode-unsupported(25),
                intfChange-Disallowed-on-APS-ProtectionPort(26),
                intferfaceCurrentlyNotSupported(27),
                failure-at-call-handler(28),
                unstructuredCE-payloadloop(29),
                channelConfigModeNotConforming(30),
                usageOfReservedTimeSlot(31),
                virtualIntf-and-AtmSignaling-bothCannotBeEnabled(32),
                virtualUni-and-AtmSignaling-bothCannotBeEnabled(33),
                virtualUni-notSupported(34),
                atmUni-UbrLoadBalSupp-cannotBeEnabled-whenSignalingDisabled(35),
                virtualInterface-notSupported(36),
                card-doesNotSupport-UPC(37),
                atmUni-SvcVpiVci-RangeCheck-Failure(38),
                atmUni-SigVpiVci-Within-Svc-Range(39),
                atmUni-Ilmi-Svc-Sig-VpiVci-Clash(40), 
                virtualUNI-VpiNotAvailable(41),
                virtualUNI-InvalidVUNIId(42),
                intfNotSupported-with-ds1LineType-d4(43),
                intfNotSupported-with-ds1LineCoding-ami(44),
                onlyCEsupported-with-msBitStuffing-enabled(45),
                vISuppConnTrafficShapingMutuallyExclusive(46),
                tS16onPortNotCAS(47),
                channelizationDisabled(48),

                primaryDS1InterfaceNotConfigured(49),
                primaryTMCChanNotConfigured(50),
                primaryTMCIntfAlreadyConfiguredInAnotherIg(51),
                primaryTMCIntfCantBeChanged(52),

                primaryEOCChanNotConfigured(53),
                primaryEOCIntfAlreadyConfiguredInAnotherIg(54),
                primaryTMC-EOCIntfShouldBeSame(55),
                primaryEOCIntfCantBeChanged(56),
                primaryTMC-BackupTMCIntfCantBeSame(57),

                backupDS1InterfaceNotConfigured(58),
                backupTMCChanNotConfigured(59),
                backupTMCIntfAlreadyConfiguredInAnotherIg(60),
                backupTMCIntfCantBeChanged(61),

                primaryEOC-BackupEOCIntfCantBeSame(62),
                backupEOCChanNotConfigured(63),
                backupEOCIntfAlreadyConfiguredInAnotherIg(64),
                backupTMC-EOCIntfShouldBeSame(65),
                backupEOCIntfCantBeChanged(66),
                newBWBelowCurrentAllocated(67),
                newBWBelowCurrentAllocated-SvcsBeingDeleted(68),
                newBWBelowCurrentAllocated-DeletePvcs(69),
                newBWAboveCurrentAllocated(70),
                primaryInactive-or-SecondaryActive-In-IntfProtTable(71),
                onlyCEsupported-with-msLOSDetection-enabled(72),
                nonMuxNotAllowed-with-FaxRelay(73),
                invalid-DSPmode-and-AALmode-combination(74),
                noBandwidth-For-SignalingConns(75)

                                }
                MAX-ACCESS read-only
                STATUS current
                DESCRIPTION "Identification of cause for failure in changing
                             the status of an interface.
                interfaceInService(1) 
                        Most, if not all, modifications require
                        that the interface be out of service.
                interfaceNotNew(2)  
                        Some modifications require that the
                        interface must never have been in service.
                interfaceExists(3)  
                        Some modifications, such as setting the
                        interface type, require that no interface
                        exists. (type must be unconfigured).
                bridgeGroupActive(4)  
                        For setting the bridgeDomainNumber in
                        bridge or router interfaces.  to add an
                        interface to a bridgeGroup, the bridgeGroup
                        must be in service.
                signalingNotEnabled(5)  
                        For this interface to be created,
                        signaling must be enabled.
                firmwareOutOfDate(6)  
                        The firmware for the i/o card does not
                         work with this interface.
                t1SigEnableInterfaceNotSupported(7)
                        The interface is not supported if T1 signaling is enabled
                ts16ForData(8)  
                        ts16 has been set for passing data and the
                        user attempts to turn on signaling.
                dbcesConfigured(9)  
                        Signaling cannot be disabled because this
                        interface is configured as dbces.
                signalingEnabled(10) 
                        Signaling is on for at least one of the
                        channels while trying to change e1 TS16
                        from CAS to CCS.
                cmCardTypeNotSupported(11)  
                        CM_NET interface is only supported by 
                        DS3 DS1 OC3 and SUPER_DS1 cards
                cmMultipleIntfNotSupported(12)  
                        only one interface can be configured as CM_NET
                cmIntfInService(13)         
                        CM_NET interface is in-service
                cmInterfaceConfigured(14)   
                        CM_NET interface is configured
                channelizationEnabled(15)   
                        A port can not be channelized in order
                        to support unstructured CE.
                unstructuredCEConfigured(16)   
                        A port which has been channelized can not
                        be configured to support unstructured CE.
                firmwareOutOfDate-ts16CAS-unsupported(17)  
                        ts16CAS is not supported by the firmware
                firmwareOutOfDate-interfaceType-unsupported(18)  
                        interface type is not supported by the firmware
                firmwareOutOfDate-ts16-unsupported(19)
                        ts16 is not supported by the firmware
                invalidPortMap(20)
                        invalid port map
                otherInterfacesExistOnThisPort(21)
                        ISDN interface needs all 24 channels on the port. If 
                        any of the channels on that interface are already configured,
                        the ISDN interface can not be defined on that port.
                intfInIMAgroup(22)  
                        chanId bit in portMap is 1
                errorCTC-portTxClkSrc-notLocal(23)
                        if imaGrpChannelNeTxClkMode is set to ctc then all ports 
                        should have the transmitClockSource as localTiming
                different-LoopbackConfig-on-Ports(24)
                        all physical ports included in the portMap
                        must have the same loopback configuration
                imaGChanNeTxClkMode-unsupported(25)
                        ima group channel near-end Tx clock mode is not supported
                intfChange-Disallowed-on-APS-ProtectionPort(26)
                        an interface cannot be manipulated via protection port
                        in an APS setup
                intferfaceCurrentlyNotSupported(27)
                        the interface type is not support currently
                failure-at-call-handler(28)
                        interface creation failure due to call handler
                unstructuredCE-payloadloop(29)
                        Unstructured CE should not have payload loopback as a
                        loop back option
                channelConfigModeNotConforming(30)
                        There was a limitation on the channel mode of DSP_2D card:
                        if there is a channel is already inService, all the
                        channel mode of configured channels must be the same as
                        that of the channel inService; all the channel mode of
                        unconfigured channels can only be configured the same as
                        that of the channel inService.
                usageOfReservedTimeSlot(31)
                        for HD_E1, do not allow any configuration to be SET on 
                        channel number 1 or 17 (base 1) or chan 0 or 16 (base 0).
                virtualIntf-and-AtmSignaling-bothCannotBeEnabled(32)
                        vitual interface and signalling cannot both be enabled
                        at the same time
                virtualUni-and-AtmSignaling-bothCannotBeEnabled(33)
                        vitual UNI and signalling cannot both be enabled at the
                        same time
                virtualUni-notSupported(34)
                        virtual UNI is not supported
                atmUni-UbrLoadBalSupp-cannotBeEnabled-whenSignalingDisabled(35)
                        ubr load balancing cannot be enabled when signaling is
                        disabled
                virtualInterface-notSupported(36)
                        virtual interface support only allowed on APS type of cards
                card-doesNotSupport-UPC(37)
                        only some cardTypes support UPC
                atmUni-SvcVpiVci-RangeCheck-Failure(38)
                        Do range check provided atmSignaling is enabled
                        vciMinSvc <= vciMaxSvc and vpiMinSvc <= vpiMaxSvc
                atmUni-SigVpiVci-Within-Svc-Range(39)
                        atmUni{Vpi,Vci}Sig should not be within svc range
                atmUni-Ilmi-Svc-Sig-VpiVci-Clash(40)
                        if IlmiProtocol status and atmUniSignaling are both enabled
                        then the Ilmi Vpi/Vci should not fall in the Svc range and 
                        should not be equal to signaling vpi/vci
                virtualUNI-VpiNotAvailable(41)
                        vpi is not available for the virtual UNI
                virtualUNI-InvalidVUNIId(42)
                        vitural UNI Index is invalid
                intfNotSupported-with-ds1LineType-d4(43)
                        if dsx1LineType is DSX1_D4 channel, interface type can't
                        be atmIma
                intfNotSupported-with-ds1LineCoding-ami(44)
                        if dsx1LineCoding is DSX1_AMI channel interface type can't
                        be atmIma
                onlyCEsupported-with-msBitStuffing-enabled(45)
                        if msBitStuffing is enabled only interface type circuit
                        emulation is supported
                vISuppConnTrafficShapingMutuallyExclusive(46)
                        The VI support flag and Traffic Shaping flag are mutually
                        exclusive
                tS16onPortNotCAS(47)
                        must have cas on port for channel to have cas trunk line
                        interface
                channelizationDisabled(48)
                        should have channelization enabled to have cas trunk line

                primaryDS1InterfaceNotConfigured(49)
                        primary DS1 interface is not configured
                primaryTMCChanNotConfigured(50)
                        primary timeslot management channel is not configured
                primaryTMCIntfAlreadyConfiguredInAnotherIg(51)
                        primary timeslot management channel interface is already 
                        configured in another interface group
                primaryTMCIntfCantBeChanged(52)
                        primary timeslot management channel interfance can't be
                        changed

                primaryEOCChanNotConfigured(53)
                        primary embeded operation channel is not configured
                primaryEOCIntfAlreadyConfiguredInAnotherIg(54)
                        primary embeded operation channel interface is already 
                        configured in another interface group
                primaryTMC-EOCIntfShouldBeSame(55)
                        primary timeslot management channel and embeded operation 
                        channel interfaces should be the same
                primaryEOCIntfCantBeChanged(56)
                        primary embeded operation channel inteface can't be changed
                primaryTMC-BackupTMCIntfCantBeSame(57)
                        primary and backup timeslot management channel
                        interfaces can't be the same

                backupDS1InterfaceNotConfigured(58)
                        backup DS1 interface is not configured
                backupTMCChanNotConfigured(59)
                        backup timeslot management channel is not configured
                backupTMCIntfAlreadyConfiguredInAnotherIg(60)
                        backup timeslot management channel interface is already 
                        configured in another interface group
                backupTMCIntfCantBeChanged(61)
                        backup timeslot management channel interfance can't be
                        changed

                primaryEOC-BackupEOCIntfCantBeSame(62)
                        primary and backup embeded operation channel interfaces
                        can't be the same
                backupEOCChanNotConfigured(63)
                        backup embeded operation channel is not configured
                backupEOCIntfAlreadyConfiguredInAnotherIg(64)
                        backup embeded operation channel interface is already 
                        configured in another interface group
                backupTMC-EOCIntfShouldBeSame(65)
                        backup timeslot management channel and embeded operation 
                        channel interfaces should be the same
                backupEOCIntfCantBeChanged(66)
                        backup embeded operation channel inteface can't be changed

                newBWBelowCurrentAllocated(67)
                        new bandwidth is below the current allocated bandwidth
                newBWBelowCurrentAllocated-SvcsBeingDeleted(68)
                        new bandwidth is below the current allocated bandwidth
                        svc is being deleted
                newBWBelowCurrentAllocated-DeletePvcs(69)
                        new bandwidth is below the current allocated bandwidth
                        delete pvc
                newBWAboveCurrentAllocated(70)
                        new bandwidth is above the current allocated bandwidth
                primaryInactive-or-SecondaryActive-In-IntfProtTable(71)
                        an interface can't be deleted if it is in interface
                        protection group which is primary/inactive or secondry/active
                onlyCEsupported-with-msLOSDetection-enabled(72)
                        if msLOSDetection is enabled, only interface type circuit
                        emulation is supported
                nonMuxNotAllowed-with-FaxRelay(73)
                        DSP2 cards: if channelMode is CFG_DSP2_FAX_RELAY, aalMode
                        can't be D_dsp2AalMode_aal2_non_multiplexed,
                invalid-DSPmode-and-AALmode-combination(74)
                        DSP2 cards: such DSP mode and AAL mode combination is not
                        allowed
                noBandwidth-For-SignalingConns(75)
                        no bandwidth for signal connections"
                ::= { returnCode 4 }


powerSupplyReasonCode                OBJECT-TYPE
                SYNTAX INTEGER  {
                                overload(1),
                                overloadCleared(2),
                                plus5vFailed(3),
                                plus5vCleared(4),
                                plus120vFailed(5),
                                plus120vCleared(6),
                                minus48vFailed(7),
                                minus48vCleared(8)
                                }
                MAX-ACCESS read-only
                STATUS current
                DESCRIPTION "Identification for change in status of a power supply.
                                overload(1)             overload
                                overloadCleared(2)      overload cleared
                                plus5vFailed(3)         +5V power supply failed
                                plus5vCleared(4)        +5V power supply cleared
                                plus120vFailed(5)       +120V power supply failed
                                plus120vCleared(6)      +120V power supply cleared
                                minus48vFailed(7)       -48V power supply failed
                                minus48vCleared(8)      -48V power supply failed
                                "
                ::= { returnCode 5 }

portId                                OBJECT-TYPE
                SYNTAX Integer32
                MAX-ACCESS read-only
                STATUS current
                DESCRIPTION "Port ID used for identification in traps.  Number
                             value is interpreted as a port of the form, SSPP,
                             where SS is the card slot and PP is the port
                             number."
                ::= { returnCode 6 }

lineStatus                        OBJECT-TYPE
                SYNTAX Integer32
                MAX-ACCESS read-only
                STATUS current
                DESCRIPTION "Bit map of the status of a line connected to a 
                             port."
                ::= { returnCode 7 }

firmwareDownloadReasonCode        OBJECT-TYPE
                SYNTAX INTEGER  {
                                cardInService(1),
                                errorInFile(2),
                                otherFailure(3),
                                wrongCardSubType(4),
                                driverUnavailable(5),
                                driverInvalidHeaderChecksum(6),
                                driverInvalidRecordChecksum(7),
                                requestReplyTimeout(8),
                                completeReplyTimeout(9),
                                mapFileCorrupted(10),
                                mapFileUnavailable(11),
                                mapFileInvalidChecksum(12),
                                mapFileNameImproper(13),
                                cfgFileCorrupted(14),
                                cfgFileUnavailable(15),
                                cfgFileInvalidChecksum(16),
                                wrongCardType(17),
                                removeCardBeforeFinish(18),
                                ioUnsupported(19)
                                }
                MAX-ACCESS read-only
                STATUS current
                DESCRIPTION "The suspected reasons of why a firmware download
                             would fail."
                ::= { returnCode 8 }

remoteRebootReasonCode                OBJECT-TYPE
                SYNTAX INTEGER  {
                        ioCard1Reboot-OK(1),
                        ioCard2Reboot-OK(2),
                        ioCard3Reboot-OK(3),
                        ioCard4Reboot-OK(4),
                        ioCard5Reboot-OK(5),
                        ioCard6Reboot-OK(6),
                        ioCard7Reboot-OK(7),
                        ioCard8Reboot-OK(8),
                        ioCard9Reboot-OK(9),
                        ioCard10Reboot-OK(10),
                        ioCard11Reboot-OK(11),
                        ioCard12Reboot-OK(12),
                        ioCard13Reboot-OK(13),
                        ioCard14Reboot-OK(14),
                        ioCard15Reboot-OK(15),
                        ioCard16Reboot-OK(16),
                        ioCard1Reboot-NoCardInSlot(17),
                        ioCard2Reboot-NoCardInSlot(18),
                        ioCard3Reboot-NoCardInSlot(19),
                        ioCard4Reboot-NoCardInSlot(20),
                        ioCard5Reboot-NoCardInSlot(21),
                        ioCard6Reboot-NoCardInSlot(22),
                        ioCard7Reboot-NoCardInSlot(23),
                        ioCard8Reboot-NoCardInSlot(24),
                        ioCard9Reboot-NoCardInSlot(25),
                        ioCard10Reboot-NoCardInSlot(26),
                        ioCard11Reboot-NoCardInSlot(27),
                        ioCard12Reboot-NoCardInSlot(28),
                        ioCard13Reboot-NoCardInSlot(29),
                        ioCard14Reboot-NoCardInSlot(30),
                        ioCard15Reboot-NoCardInSlot(31),
                        ioCard16Reboot-NoCardInSlot(32),
                        allIOCardReboot-OK(33),
                        allIOCardReboot-NoIOCards(34),
                        chassisReboot-Proceeding(35),
                        backupCpuReboot-Proceeding(36),
                        backupCpuReboot-NoBackup(37),
                        primaryCpuReboot-Proceeding(38),
                        primaryCpuSwitchover-Proceeding(39),
                        primaryCpuSwitchover-NoBackup(40),
                        chassisReboot-Fail-VersionControlInProgress(41),
                        backupCpuReboot-Fail-VersionControlInProgress(42),
                        primaryCpuReboot-Fail-VersionControlInProgress(43),
                        primaryCpuSwitchover-Fail-VersionControlInProgress(44),
                        primaryCpuSwitchover-Fail-BkCPUDataBaseNotNew(45),
                        primaryCpuSwitchover-Fail-BkCPUBuildNotGood(46),
            primaryCpuSwitchover-Fail-BkCPU-NotReady(47)
                       }
                MAX-ACCESS read-only
                STATUS current
                DESCRIPTION "The result of a remote reboot request."
                ::= { returnCode 9 }

saveConfigurationReasonCode OBJECT-TYPE
                SYNTAX INTEGER  {
                        equipment-OK(1),
                        equipment-Fail-VersionControlInProgress(2),
                        equipment-Fail(3),
                        connections-OK(4),
                        connections-Fail-VersionControlInProgress(5),
                        connections-Fail(6),
                        routing-OK(7),
                        routing-Fail-VersionControlInProgress(8),
                        routing-Fail(9),
                        all-OK(10),
                        all-Fail-VersionControlInProgress(11),
                        all-Fail(12),
                        fileTransferFailed(13),
                        fileTransferCompleted(14),
                        unSupportedOption(15),
                        fail-backupCpuInitializationInProgress(16),
                        expect2ndCPURebootAfterSave(17), 
                        expect2ndCPUCardFailedOrRemoved(18)
                       } 
                MAX-ACCESS read-only
                STATUS current
                DESCRIPTION "The result of a save configuration request.
                             equipment-OK(1) - Save of equipment configuration
                                             completed. 
                equipment-Fail-VersionControlInProgress(2) 
                                - Save of equipment configuration failed
                                 due to ongoing version control operation.
                equipment-Fail(3) - Save of equipment configuration failed.
                connections-OK(4) - Save of connection configuration 
                                    completed. 
                connections-Fail-VersionControlInProgress(5) - 
                                 - Save of connection configuration failed
                                   due to ongoing version control operation.
                connections-Fail(6) - Save of connection configuration failed.
                routing-OK(7)       - Save of routing  configuration completed.
                routing-Fail-VersionControlInProgress(8) - 
                                 - Save of routing configuration failed
                                   due to ongoing version control operation.
                routing-Fail(9)     - Save of routing configuration failed.
                all-OK(10)          - Saving of all configurations completed.
                all-Fail-VersionControlInProgress(11) - 
                                    - Saving of all configurations failed
                                      due to ongoing version control operation.
                all-Fail(12)        - Saving of all configurations failed.
                fileTransferFailed(13) - Saving of configurations to secondary
                                        CPU failed. 
                fileTransferCompleted(14) - Saving of configurations to 
                                            secondary CPU completed. 
                unSupportedOption(15) - Unsupported save option received.
                fail-backupCpuInitializationInProgress(16) - 
                                        - Save operation failed due to ongoing
                                          secondary cpu initialization. 
                expect2ndCPURebootAfterSave(17) - 
                                         - Notification to expect reboot of
                                           secondary CPU after a save operation.
                expect2ndCPUCardFailedOrRemoved(18) 
                                 - Notification to expect trap indicating
                                   removal/failure of secondary CPU after a
                                   save operation. "
                ::= { returnCode 10 }

versionConfigurationReasonCode OBJECT-TYPE
                SYNTAX INTEGER  {
                        upgrade-Start(1),
                        upgrade-Completed(2),
                        upgrade-Fail(3),
                        downgrade-Start(4),
                        downgrade-Completed(5),
                        downgrade-Fail(6),
                        upgrade-Fail-NoVersion(7),
                        upgrade-Fail-VersionControlInProgress(8),
                        downgrade-Fail-NoVersion(9),
                        downgrade-Fail-VersionControlInProgress(10),
                        upgrade-InProgress(11),
                        downgrade-InProgress(12),
                        upgrade-sanityCheck-InProgress(13),
                        downgrade-sanityCheck-InProgress(14),
                        upgrade-sanityCheck-Completed(15),
                        downgrade-sanityCheck-Completed(16),
                        upgrade-Fail-SanityCheckFail(17),
                        downgrade-Fail-SanityCheckFail(18),
                        upgrade-Fail-BkCPUFailedToRespond(19),
                        downgrade-Fail-BkCPUFailedToRespond(20),
                        upgrade-Fail-UserAbort(21),
                        downgrade-Fail-UserAbort(22),
                        synch-Start(23), 
                        synch-InProgress(24), 
                        synch-Completed(25),
                        synch-Fail(26),
                        synch-Fail-NoBkCPU(27),
                        synch-Fail-SameVersion(28),
                        synch-Fail-FileCRCFailed(29),
                        synch-Fail-VersionControlInProgress(30),
                        synch-Fail-UserAbort(31),
                        synch-Fail-SanityCheckFail(32),
                        synch-Fail-BkCPUFailedToRespond(33),
                        synch-sanityCheck-InProgress(34),
                        synch-sanityCheck-Completed(35),
                        failedToAbort(36) 
                        } 
                MAX-ACCESS read-only
                STATUS current
                DESCRIPTION "Indicated status and results of version changing.
                        upgrade-Start(1)        upgrade starts
                        upgrade-Completed(2)    upgrade completed
                        upgrade-Fail(3)         upgrade failed
                        downgrade-Start(4)      downgrade starts
                        downgrade-Completed(5)  downgrade completed
                        downgrade-Fail(6)       downgrade failed
                        upgrade-Fail-NoVersion(7)       
                                upgrade failed, no version
                        upgrade-Fail-VersionControlInProgress(8)
                                upgrade failed, version control is in progress
                        downgrade-Fail-NoVersion(9)     
                                downgrade failed, no version
                        downgrade-Fail-VersionControlInProgress(10)
                                downgrade failed, version control is in progress
                        upgrade-InProgress(11)  upgrade is in progress
                        downgrade-InProgress(12)downgrade is in progress
                        upgrade-sanityCheck-InProgress(13)
                                upgrade sanity check is in progress
                        downgrade-sanityCheck-InProgress(14)
                                downgrade sanity check is in progress
                        upgrade-sanityCheck-Completed(15),
                                upgrade sanity check is completed
                        downgrade-sanityCheck-Completed(16),
                                downgrade sanity check is completed
                        upgrade-Fail-SanityCheckFail(17)
                                upgrade failed due to sanity check failure
                        downgrade-Fail-SanityCheckFail(18)
                                downgrade failed due to sanity check failure
                        upgrade-Fail-BkCPUFailedToRespond(19)
                                upgrade failed since backup CPU failed to respond
                        downgrade-Fail-BkCPUFailedToRespond(20)
                                downgrade failed since backup CPU failed to respond
                        upgrade-Fail-UserAbort(21)
                                upgrade failed since user aborted
                        downgrade-Fail-UserAbort(22)
                                downgrade failed since user aborted
                        synch-Start(23)         synchronization starts
                        synch-InProgress(24)    synchronization is in progress
                        synch-Completed(25)     synchronization is completed
                        synch-Fail(26)          synchronization failed
                        synch-Fail-NoBkCPU(27) 
                                synchronization failed since no backup CPU
                        synch-Fail-SameVersion(28)
                                synchronization failed due to the same version
                        synch-Fail-FileCRCFailed(29)
                                synchronization failed due to file CRC failure
                        synch-Fail-VersionControlInProgress(30)
                                synchronization failed since version control 
                                is in progress
                        synch-Fail-UserAbort(31)
                                synchronization failed since user aborted
                        synch-Fail-SanityCheckFail(32)
                                synchronization failed due to sanity 
                                check failure
                        synch-Fail-BkCPUFailedToRespond(33)
                                synchronization failed since backup CPU 
                                failed to respond
                        synch-sanityCheck-InProgress(34)
                                synchronization sanity check is in progress
                        synch-sanityCheck-Completed(35)
                                synchronization sanity check is completed
                        failedToAbort(36)       failed to abort
                        "
                ::= { returnCode 11 }

percentComplete        OBJECT-TYPE
                SYNTAX Integer32
                MAX-ACCESS read-only
                STATUS current
                DESCRIPTION "Used for trap fileTransferStatusNotify and 
                             value equals the percent of the upgrade,
                             downgrade, or ftp download completed."
                ::= { returnCode 12 }

ipTypeReasonCode OBJECT-TYPE
                SYNTAX INTEGER  {
                        siteEtherIpAddr(1),
                        siteEtherIpMask(2),
                        siteGatewayAddr(3),
                        siteRemoteMgrAddr1(4),
                        siteRemoteMgrAddr2(5),
                        siteRemoteMgrAddr3(6),
                        siteRemoteMgrAddr4(7),
                        siteRemoteMgrAddr5(8),
                        inBandPrimaryIpAddress(9),
                        inBandPrimaryIpMask(10),
                        inBandBackupIpAddress(11),
                        inBandBackupIpMask(12),
                        siteIncorrectGatewaySubnet(13),
                        siteGatewayInbandAddrMatch(14),
                        siteIncorrectInbandSubnet(15),
                        siteIncorrectEthernetSubnet(16),
                        cpuIpSameAsSwitchIpAddr(17),
                        cpuIpAddrInvalid(18),
                        cpuAndIpMaskInvalid(19),
                        switchAndCpuIpSubnetMismatch(20),
                        switchIpAddrInvalid(21),
                        switchAndIpMaskInvalid(22),
                        cpuIpMaskClashWithInbandSubnet(23),
                        switchIpMaskClashWithInbandSubnet(24),
                        siteGatewayAddrInvalid(25),
                        siteGatewayInbandAddrClash(26),
                        unableToApplyGatewayIpAddr(27),
                        unableToSetCpuIpInEPROM(28),
                        unableToApplyCpuIpAddr(29),
                        unableToApplySwitchIpAddr(30),
                        unableToRevertBackToCpuIpAddr(31),
                        gatewayAndCpuIpSubnetMismatch(32)
                       } 
                MAX-ACCESS read-only
                STATUS current
                DESCRIPTION "Indicator of which ip address had the problem."
                ::= { returnCode 13 }

timingReasonCode OBJECT-TYPE
                SYNTAX INTEGER  {
                        invalidForwardDelay-MaxAge(1),
                        invalidHelloTime-MaxAge(2)
                       } 
                MAX-ACCESS read-only
                STATUS current
                DESCRIPTION "Indicator of type of relationship violated."
                ::= { returnCode 14 }

alarmCardReasonCode OBJECT-TYPE
                SYNTAX INTEGER  {
                        inputContactClosed(1),
                        inputContactOpen(2),
                        outputActivated(3),
                        outputDactivated(4),
                        audibleLocalAlarmEnable(5),
                        audibleLocalAlarmCutoff(6),
                        audibleRemoteAlarmEnable(7),
                        audibleRemoteAlarmCutoff(8)
                       } 
                MAX-ACCESS read-only
                STATUS current
                DESCRIPTION " Configuration status of the alarm inputs and
                outputs.  cutoff - alarm turned off. There are two ways to
                turn off the audible alarm, locally via the pushbutton switch
                on the alarm module, and remotely, via the remote alarm
                cutoff, one of the alarm card inputs.
                "
                ::= { returnCode 15 }

removeConfigFiles OBJECT-TYPE
                SYNTAX INTEGER  {
                        from-PrimaryCPU(1),
                        from-BackupCPU(2),
                        chassisReboot(3),
                        failed-VersionControlInProgress(4)
                       } 
                MAX-ACCESS read-only
                STATUS current
                DESCRIPTION "Used to indicate the status of a remove 
                             configuration files request.
                from-PrimaryCPU(1)
                     configuration files are removed from primary CPU
                from-BackupCPU(2)
                     configuration files are removed from backup CPU
                chassisReboot(3)
                     chassis reboot being done after removing
                     configuration files
                failed-VersionControlInProgress(4)
                     configuration file removal failed due to ongoing
                     version conflict
                "
                ::= { returnCode 16 }


spvcConfigFailureCode OBJECT-TYPE
                SYNTAX INTEGER  {
                                noSpvcConfigured(1),
                                spvcAlreadyConfigured(2),
                                noInterfaceConfigured(3),
                                interfaceNotConfiguredAsRequired(4),
                                notActiveSpvc(6),
                                slotA-OutofRange(7),
                                portA-OutofRange(8),
                                channelA-OutofRange(9),
                                vpiVciWithInSvcRange(10),
                                retryIntervalExceedsTheLimit(11),
                                interfaceNotConfiguredAsCE(12),
                                interfaceNotConfiguredAsVbr(13),
                                interfaceNotConfiguredAsAtm(14),
                                noAddressConfiguredOnTheInterface(15),
                                localAddressNotValid(16),
                                vpiVciUnavailable(17),
                                pvcAlreadySetupOnVpiVci(18),
                                pvcAlreadySetupOnInterface(19),
                                retryIntervalTooSmall(20),
                                interfaceNotConfiguredAsFr(21),
                                dlciUnavailable(22),
                                pvcAlreadySetupOnDlci(23),
                                frTrafficParamsUnsupp(24),
                                dsp2ParamsUnsupp(25),
                                sarNotConfigReq(26),
                                vuniNotMatch(27)
                                }
                MAX-ACCESS read-only
                STATUS current
                DESCRIPTION "An identified reason for failure while
             configuring/modifying SPVC parameters.
             noSpvcConfigured(1) : There endpoint has not been configured
             as SPVC, so SPVC parameters cannot be modified.
             spvcAlreadyConfigured(2) : SPVC is already configured so it cannot
             be configured again as SPVC endpoint.
             noInterfaceConfigured(3) : There is no interface configured on the
             particular SSPPCCC.
             interfaceNotConfiguredAsRequired(4) : While configuring an SPVC
             endpoint, the interface is not as desired (e.g.it is not CE,
             while trying to configure CES SPVC).
             notActiveSpvc(6) : If the endpoint is configured with flowType
             ptToMptA2B the connType has to be activeSvc.
             slotA-OutofRange(7) : A-side of SPVC connection has slot number
             out of range.
             portA-OutofRange(8): A-side of SPVC connection has port number
             out of range.
             channelA-OutofRange(9): A-side of SPVC connection has channel number
             out of range.
             vpiVciWithInSvcRange(10) : A-side side of SPVC connection has vpi/vci
             configured in the SVC range of the A-side ATM interface.
             retryIntervalExceedsTheLimit(11) : retryInterval exceeds 3600s.
             interfaceNotConfiguredAsCE(12) : SPVC endpoint is configured as
             something other than CE.
             interfaceNotConfiguredAsVbr(13) : SPVC endpoint is configured as
             something other than TE.
             interfaceNotConfiguredAsAtm(14) : SPVC endpoint is configured as
             something other than ATM.
             noAddressConfiguredOnTheInterface(15) : Local address not configured
             for the particular SPVC being configured.
             localAddressNotValid(16) : invalid NSAP address format
             vpiVciUnavailable(17) : SPVC already setup on particular vpi/vci.
             pvcAlreadySetupOnVpiVci(18) : vpi/vci being used by another pvc.
             pvcAlreadySetupOnInterface(19) : redundant, same as above.
             interfaceNotConfiguredAsFr(21) : SPVC endpoint is configured as
             something other than Fr
             dlciUnavailable(22) : dlci not available at Passive endpoint.
             pvcAlreadySetupOnDlci(23) : dlci being used by another pvc.
             frTrafficParamsUnsupp(24) : fr-atm traffic mapping failure.
             dsp2ParamsUnsupp(25) : dsp2 params not supported for the call.
             sarNotConfigReq(26) : sarType not configured as required."
		::= { returnCode 17 }


imaGrpChannelStatus OBJECT-TYPE
                SYNTAX INTEGER  {
                        startupFe(1),
                        cfgAbort(2),
                        cfgAbortFe(3),
                        insuffLinks(4),
                        insuffLinksFe(5),
                        blockedNe(6),
                        blockedFe(7),
                        timingSynch(8)
                       } 
                MAX-ACCESS read-only
                STATUS current
                DESCRIPTION "
                 The return value for the imaGrpChannelFailNotify trap.
                 startupFe(1)     Far-end is in the state of start-up
                 cfgAbort(2)      this state is entered when the far-end tries to
                                  use unacceptable configuration parameters including
                                  invalid frame length and incompatable symmetry
                 cfgAbortFe(3)    Far-end reported unacceptable configuration
                                  parameters including invalid frame length and
                                  incompatable symmetry
                 insuffLinks(4)   Near-end reported less than the min number of 
                                  Tx links are active or less than the min number
                                  of Rx links are active
                 insuffLinksFe(5) Far-end reported less than the min number of
                                  Rx links are active or less than thenmin number 
                                  of Tx links are active
                 blockedNe(6)     Near-end is administratively out-of-service
                 blockedFe(7)     Far-end  is administratively out-of-service
                 timingSynch(8)   A possible configuration mismatch has
                                  occurred (CTC and CTC modes are not the same
                                  at both ends of the IMA virtual links."
                ::= { returnCode 18 }

atmImaIntfStatus OBJECT-TYPE
                SYNTAX INTEGER  {
                        lif(1),
                        lods(2),
                        txMisConnect(3),
                        rfi(4),
                        fault(5),
                        txUnusableFe(6),
                        rxUnusableFe(7)
                       } 
                MAX-ACCESS read-only
                STATUS current
                DESCRIPTION "
                 The return value for the atmImaIntfFailNotify trap. 
                 lif          -- Persistence of LIF defect at near-end 
                                 (Loss of IMA Frame)
                 lods         -- Persistence of LODS defect at near-end 
                                 (Link Out of Delay Synchronization)
                 txMisConnect -- The link is mis-connected (not connected to
                                 the same far-end as the other links in the
                                 group.)
                 rfi          -- Persistence of RDI-IMA defect at near-end
                                 (Remote Failure Indicator)
                 fault        -- Implementation specific fault at near-end
                 txUnusableFe -- Tx link forced to unusable due to far-end
                                 behavior
                 rxUnusableFe -- Rx link forced to unusable due to far-end 
                                 behavior"
                ::= { returnCode 19 }

deviceId        OBJECT-TYPE
                SYNTAX Integer32
                MAX-ACCESS read-only
                STATUS current
                DESCRIPTION "device ID is used as the number of external 
                             devices.  Each device can be an external input 
                             device or control output device."
                ::= { returnCode 20 }

oamTestFailureReasonCode OBJECT-TYPE
                SYNTAX INTEGER  {
                        invalidSPCforOAM(1),
                        invalidIntfForOAM(2),
                        invalidLocationLength(3),
                        oamNotSupportedForThisConnection(4),
                        loopbackTestAlreadyRunning(5),
                        loopbackTestNotRunning(6),
                        oamLocalResourcesUnavailable(7)
                       } 
                MAX-ACCESS read-only
                STATUS current
                DESCRIPTION "An identified reason why an OAM Loopback Test 
                             request has failed.
		
			    invalidSPCforOAM: There is no such slot/port/channel 				in this box.
			    invalidIntfForOAM: There is no such interface that
				OAM enabled.
			    invalidLocationLength: The length of the Loopback Lo				cation ID id not valid.
			    oamNotSupportedForThisConnection: This connection is
				not OAM enabled.so OAM loopback is invalid test.
			    loopbackTestAlreadyRunning: OAM loopback is waiting 
				for response,not expect for another test.
			    loopbackTestNotRunning: Invalid Test Actio.
			    oamLocalResourcesUnavailable: Memery Alloc Fail."
			    
                ::= { returnCode 21 }


pnniCode OBJECT-TYPE
                SYNTAX INTEGER  {
                        pnniInvEndSysPortId(1),
                        pnniNodeAdmStatNotUp(2),
                        pnniProtLnkStatDown(3),
                        pnniProtLnkStatUpNotAdv(4),
                        pnniProtLinkStatUpAdv(5),
                        pnniIntfAdmStatUp(6),
                         pnniNodeNotCfg(7),        
                         pnniRtAddrAddedByIlmi(8),        
                         pnniRtAddrDelByIlmi(9),        
                        pnniLvlMismatchInNodeId(10),
                        pnniLvlMismatchInPGId(11),
                        pnniATMAddrInvInNodeId(12),
                        pnniATMAddrInvInPGId(13),
                        pnniIntfAdmStatNotDel(14),
                        pnniNodeAdmStatUp(15),
                        pnniNodeRowStatNotActive(16),
                        pnniNewRtAddrAdded(17),
                        pnniRtAddrMod(18),
                        pnniAdvtNodeIdNotMine(19),
                        pnniFeatureNotSupported(20)
                } 
                MAX-ACCESS read-only
                STATUS current
                DESCRIPTION "An identified reason for Miscellaneous Reasons in PNNI Configuration
                            pnniInvEndSysPortId(1) : Invalid EndSystem PortId.
            pnniNodeAdmStatNotUp(2) : Admin Status of Node is not up.
            pnniProtLnkStatDown(3) : Pnni Lnk status is down.
            pnniProtLnkStatUpNotAdv(4) :  Pnni Lnk status up but not advertised.
            pnniProtLinkStatUpAdv(5) : Pnni Lnk status up and advertised.
            pnniIntfAdmStatUp(6) : Pnni Intf Admin Status up.
            pnniNodeNotCfg(7) : Pnni Node not configured in the switch.
            pnniRtAddrAddedByIlmi(8) : Pnni Route added succesfully from ILMI.
            pnniRtAddrDelByIlmi(9) : Pnni Route deleted succesfully from ILMI.
            pnniLvlMismatchInNodeId(10) : Level mismatch in Node Id.
            pnniLvlMismatchInPGId(11) : Level mismatch in Peer Group Id.
            pnniATMAddrInvInNodeId(12) : ATM Address entered in Node Id invalid.
            pnniATMAddrInvInPGId(13) : ATM Address entered in Peer Group Id invalid.
            pnniIntfAdmStatNotDel(14) : Pnni Intf Admin Status Not deleted.
            pnniNodeAdmStatUp(15) : Pnni Node Admin Status up.
            pnniNodeRowStatNotActive(16) : Pnni Node Row Status not active - cannot
            modify
            pnniNewRtAddrAdded(17) : New route added into pnni route address table.
            pnniRtAddrMod(18) : Route modified in pnni Address table.
            pnniAdvtNodeIdNotMine(19) : Advertised NodeId does not belong to this psax.
            pnniFeatureNotSupported(20) : pnni feature unsupported."
                ::= { returnCode 22 }

swtchNodeIndx OBJECT-TYPE
                SYNTAX Integer32
                MAX-ACCESS read-only
                STATUS current
                DESCRIPTION "Switch Node Index for PNNI."
                ::= { returnCode 23 }

oc3APSPairPortIndex OBJECT-TYPE
                  SYNTAX Integer32
                  MAX-ACCESS not-accessible
                  STATUS current
                  DESCRIPTION "APS Pair Port index - SSPP"
                  ::= { returnCode 24 }

oc3APSReasonCode OBJECT-TYPE
                SYNTAX INTEGER {
                        localprotectDoNotRevert(1),
                        localprotectManualSw(8),
                        localprotectSD(10),
                        localprotectSF(12),
                        localprotectForced(14),
                        localprotectLockOut(15),
                        localworkingDoNotRevert(17),
                        localworkingManualSw(24),
                        localworkingSD(26),
                        localworkingSF(28),
                        localworkingForced(30),
                        remoteprotectDoNotRevert(33), 
                        remoteprotectManualSw(40), 
                        remoteprotectSD(42),
                        remoteprotectSF(44),
                        remoteprotectForced(46),
                        remoteprotectLockOut(47),
                        noRequest(48),
                        remoteworkingDoNotRevert(49),
                        remoteworkingManualSw(56),
                        remoteworkingSD(58),
                        remoteworkingSF(60),
                        remoteworkingForced(62)
                }
                MAX-ACCESS read-only
                STATUS current
                DESCRIPTION "Enumerated values of the outcome of previous
                             apsPair UserCommand or alarms on the line
                        local       - near-end
                        remote      - far-end
                        working     - working port
                        protect     - protecting port
                        DoNotRevert - after switching from working line to
                                      protection line, don't revert to working
                                      line even it returns to work
                        ManualSw    - switch over by user command
                        SD          - signal degradation
                        SF          - signal failure
                        Forced      - force switch over
                        LockOut     - don't allow switch over to a line
                        "
                ::= { returnCode 25 }


oc3APSK1K2Rx OBJECT-TYPE
                SYNTAX OCTET STRING (SIZE(2))
                MAX-ACCESS read-only
                STATUS current
                DESCRIPTION "Rx K1/K2 followed by hex value of K1, K2"
                ::= { returnCode 26 }

oc3APSK1K2Tx OBJECT-TYPE
                SYNTAX OCTET STRING (SIZE(2))
                MAX-ACCESS read-only
                STATUS current
                DESCRIPTION "Tx K1/K2 followed by hex value of K1, K2"
                ::= { returnCode 27 }

oc3APSSelectorState OBJECT-TYPE
                SYNTAX INTEGER {
                                w-active-p-standby(1),
                                w-standby-p-active(2)
                                }
                MAX-ACCESS read-only
                STATUS current
                DESCRIPTION "Working port: active/standby Protection port:
                             standby/active"
                ::= { returnCode 28 }


oc3APSWorkingLineSignalStatus OBJECT-TYPE
                SYNTAX INTEGER {
                        noAlarm(1),
                        signalDegradation(2),
                        signalFailure(4),
                        lostCellDelineation(8),
                        switchByteFailure(16),
                        ais-l(32),
                        ais-p(64),
                        lop(128),
                        lof(256),
                        los(512),
                        moduleFailure(1024)
                }
                MAX-ACCESS read-only
                STATUS current
                DESCRIPTION "Line Status of the working port sent in a trap
                        enumeration explanations are the same as those of
                        oc3APSProtectionLineSignalStatus
                        "
                ::= { returnCode 29 }

oc3APSProtectionLineSignalStatus OBJECT-TYPE
                SYNTAX INTEGER {
                        noAlarm(1),
                        signalDegradation(2),
                        signalFailure(4),
                        lostCellDelineation(8),
                        switchByteFailure(16),
                        ais-l(32),
                        ais-p(64),
                        lop(128),
                        lof(256),
                        los(512),
                        moduleFailure(1024)
                }
                MAX-ACCESS read-only
                STATUS current
                DESCRIPTION "Line Status of the protection port sent in a trap.
                        noAlarm(1)              no alarm
                        signalDegradation(2)    signal bit error rate is higher than
                                                the specified threshold
                        signalFailure(4)        signal bit error rate is much higher
                                                than the specified threshold
                        lostCellDelineation(8)  unable to identify cell boundary
                        switchByteFailure(16)   switch bytes(k1,k2) of SONET header
                                                have invalid code
                        ais-l(32)               line header of SONET frame gives
                                                alarm indication signal
                        ais-p(64)               path header of SONET frame gives
                                                alarm indication signal
                        lop(128)                1)a valid STS or VT pointer can't be
                                                obtained by using the pointer
                                                interpretation rules and the pointer
                                                word doesn't contain all-ones;
                                                2)a number of consecutive with the
                                                NDF set to 1001 but not indicating
                                                concatenation is received
                        lof(256)                loss of frame
                        los(512)                loss of signal
                        moduleFailure(1024)     module failure"
                ::= { returnCode 30 }


arpStatus       OBJECT-TYPE
                SYNTAX INTEGER  {
                                success(1),
                                noArpEntries(2),
                                tryAgain(3)
                                }
                MAX-ACCESS read-only 
                STATUS current
                DESCRIPTION " Success:  Arp Data is Available.
                              Failure:  Reply from RS Card timed-out.
                              TryAgain: The request was not honoured as it came
                              too soon (within a sec). Try again after 1 sec
                              and we will return either Success or Noroutes."
                ::= { returnCode 31 }
                
routingStatus   OBJECT-TYPE 
                SYNTAX INTEGER  { 
                                success(1),
                                noRoutes(2),
                                tryAgain(3)
                                }
                MAX-ACCESS read-only
                STATUS current
                DESCRIPTION " Success:  Routing Data is Available.
                              Failure:  Reply from RS Card timed-out.
                              TryAgain: The request was not honoured as it came
                              too soon (within a sec). Try again after 1 sec
                              and we will return either Success or Noroutes."
                ::= { returnCode 32 }

vpnTrapStatus   OBJECT-TYPE
                SYNTAX INTEGER  {
                        vpnAddOk(1),
                        vpnInternalFailure(2),
                        vpnTooMany(3),
                        vpnBadSlot(4),
                        vpnBadId(5),
                        vpnBadState(6),
                        vpnBadTimerVal(7),
                        vpnAlreadyExists(8),
                        vpnCantLocate(9),
                        vpnDelInProgress(10),
                        vpnLockedIdle(11),
                        vpnGeneralFailure(12),
                        vpnNotAllowed(13),
                        vpnShutting(14),
                        vpnDisabled(15),
                        vpnModifyOk(16)
                       }
                MAX-ACCESS read-only
                STATUS current
                DESCRIPTION "Return codes for route server VPN level
                             operations.
			vpnAddOk(1)             VPN Creation OK
                        vpnInternalFailure(2)   Memory Corruption Failure
                        vpnTooMany(3)           Exceeded Max # of VPNs
                        vpnBadSlot(4)           Impossible Slot Number
                        vpnBadId(5)             VPN ID Must Be Between 1-6
                        vpnBadState(6)          VPN State Machine Confused
                        vpnBadTimerVal(7)       Bad Timer Value: State Machine
                        vpnAlreadyExists(8)     VPN Already Exists
                        vpnCantLocate(9),       Cannot Find Referenced VPN
                        vpnDelInProgress(10)    Deletion In Progress -Must Wait
                        vpnLockedIdle(11)       VPN Taken Out Of Service
                        vpnGeneralFailure(12)   Reference Prev.Trap For Reason
                        vpnNotAllowed(13)       Operation Not Allowed
                        vpnShutting(14)         Shutting Down VPN -Must Wait
                        vpnDisabled(15)         Some VPN SubSystem Not Working
                        vpnModifyOk(16)         Modify Operation OK"
                ::= { returnCode 33 }

ipIntfStatus   OBJECT-TYPE
                SYNTAX INTEGER  {
                        intOK(1),
                        intIntFailure(2),
                        intTooMany(3),
                        intBadSlot(4),
                        intBadId(5),
                        intBadState(6),
                        intBadTimer(7),
                        intExists(8),
                        intCantFind(9),
                        intDelInProgress(10),
                        intLockedIdle(11),
                        intBadNetMask(12),
                        intShutting(13),
                        intDisabled(14),
                        intNotHostAddr(15),
                        intBadIpAddr(16),
                        intBadRouterId(17),
                        intBadIntfId(18),
                        intCantFindRouter(19),
                        intCantFindIntf(20),
                        intCantOnSameSubnet(21),
                        intCantModIntfAddr(22),
                        intCantModIntfMask(23),
                        intCantModIntfRipVer(24)
                       }
                MAX-ACCESS read-only
                STATUS current
                DESCRIPTION "Return codes for route server IP interface
                              operations.
			intOK(1)                Interface OK.
                        intIntFailure(2)        Memory Corruption
                        intTooMany(3)           Exceeded Max # Of Interfaces
                        intBadSlot(4)           Impossible Slot Number
                        intBadId(5),            Impossible Interface ID
                        intBadState(6)          State Machine Confused
                        intBadTimer(7)          Bad Timer Value: State Machine
                        intExists(8)            Interface Already Exists
                        intCantFind(9)          Unused
                        intDelInProgress(10)    Deleting: -Must Wait
                        intLockedIdle(11)       Interface Taken Out Of Service
                        intBadNetMask(12)       Illegal Network Mask
                        intShutting(13)         Shutting Down -Must Wait
                        intDisabled(14)         Some Subsystem Not Working
                        intNotHostAddr(15)      Host Address Is Missing
                        intBadIpAddr(16)        Illegal IP Address
                        intBadRouterId(17)      Illegal VPN/Router ID
                        intBadIntfId(18)        Illegal Interface ID
                        intCantFindRouter(19)   No Corresponding VPN
                        intCantFindIntf(20)     Interface Does Not Exist
                        intCantOnSameSubnet(21) Interface Already On This Subnet
                        intCantModIntfAddr(22)  Cannot Change Interface Addr
                        intCantModIntfMask(23)  Cannot Change Interface Mask
                        intCantModIntfRipVer(24) Cannot Change Rip Ver #"
                ::= { returnCode 34 }

subChanStatus   OBJECT-TYPE
                SYNTAX INTEGER  {
                        scOK(1),
                        scIntFailure(2),
                        scTooMany(3),
                        scBadSlot(4),
                        scBadId(5),
                        scBadState(6),
                        scBadTimerVal(7),
                        scExists(8),
                        scCantFind(9),
                        scDelInProgress(10),
                        scLockedIdle(12),
                        scSameVc(13),
                        scFailedSetup(14),
                        scShutting(15),
                        scDisabled(16),
                        scSetupErr(17),
                        scRemvErr(18),
                        scBadPortNo(19),
                        scBadImIpAddr(20),
                        scBadRouterId(21),
                        scBadIntfId(22),
                        scBadChanId(23),
                        scCantFindRouter(24),
                        scCantFindIntf(25),
                        scCantFindChan(26)
                       }
                MAX-ACCESS read-only
                STATUS current
                DESCRIPTION "Return codes for route server sub channel
                              connections operations.
			scOK(1)                 SubChannel OK
                        scIntFailure(2)         Memory Corruption
                        scTooMany(3)            Too Many SubChannels
                        scBadSlot(4)            Impossible Slot Number
                        scBadId(5)              Bad VPN ID
                        scBadState(6),          State Machine Confusion
                        scBadTimerVal(7)        Bad Timer Value: State Machine
                        scExists(8)             SubChannel Already Exists
                        scCantFind(9)           Unused
                        scDelInProgress(10)     Deleting: -Must Wait
                        scLockedIdle(12)        SubChannel Taken Out Of Serv.
                        scSameVc(13)            Connection In Use Already
                        scFailedSetup(14)       Referene Previous Trap
                        scShutting(15)          Shutting Down: -Must Wait
                        scDisabled(16)          SubSystem Disabled.
                        scSetupErr(17)
                        scRemvErr(18)           Error Removing SubChannel
                        scBadPortNo(19)         Bad Port Specified
                        scBadImIpAddr(20)       Bad InBand IP Address
                        scBadRouterId(21)       Bad VPN/Router ID
                        scBadIntfId(22)         Impossible Interface ID
                        scBadChanId(23)         Impossible Channel ID
                        scCantFindRouter(24)    Cannot Find VPN
                        scCantFindIntf(25)      Cannot Find Interface
                        scCantFindChan(26)      Cannot Find SubChannel"
                ::= { returnCode 35 }


routeSrvStatus   OBJECT-TYPE
                SYNTAX INTEGER  {
                        rsCardOK(1),
                        rsModInitFail(2),
                        rsIntfInitFail(3),
                        rsPortInitFail(4),
                        rsRipUpdateIntOK(5),
                        rsRipUpdateIntFail(6)
                       }
                MAX-ACCESS read-only
                STATUS current
                DESCRIPTION "Return codes for basic route server task
                             operations not related to any specific VPN
                             or IP/Connection operation.
			rsCardOK(1)             Route Server OK
                        rsModInitFail(2)        Route Server Failed Module Init.
                        rsIntfInitFail(3)       Route Server Failed Intf. Init.
                        rsPortInitFail(4)       Route Server Failed Port Init
                        rsRipUpdateIntOK(5)     Rip Update Interval was updated
                                                ok for the route server card.
                        rsRipUpdateIntFail(6)   Rip Update Interval was not
                                                updated mostly because of
                                                some VPN's still in service."
                ::= { returnCode 36 }


apsFailureReasonCode OBJECT-TYPE
                 SYNTAX INTEGER {
                         protectionCard-notPresent(1), 
                         protectionCardType-notAPS(2),
                         protectionCardType-incompatible(3),
                         protectionCard-notInUnconfiguredState(4),
                         protectionCard-notUnprotected(5),
                         resource-access-failure(6),
                         incorrect-APSconfiguration(7),
                         protectionPort-Active(8),
                         workingPort-localLoop-notAllowed(9),
                         protectionPort-localLoop-notAllowed(10)
                         }
                 MAX-ACCESS read-only
                 STATUS current
                 DESCRIPTION " Identification of cause for automatic 
                               protection switching failure.
                 protectionCard-notPresent(1)    protection card doesn't exist
                 protectionCardType-notAPS(2)
                              card type of protection card is not APS
                 protectionCardType-incompatible(3)  
                              card types of protection card and 
                              working card are incompatible
                 protectionCard-notInUnconfiguredState(4)  
                              protection card is already configured 
                 protectionCard-notUnprotected(5)
                              protection card is not unprotected
                 resource-access-failure(6)      internal failure application
                 incorrect-APSconfiguration(7)   
                              correct aps configuration: 1)oc3APSConfiguration 
                              of working port is working and oc3APSConfiguration
                              of protection port is protection
                              2) oc3APSConfiguration of working and protection 
                              ports are unprotected
                 protectionPort-Active(8)
                              protection port must be inactive when breaking 
                              aps pair
                 workingPort-localLoop-notAllowed(9)  
                              working port can't be configured as localLoop
                 protectionPort-localLoop-notAllowed(10)  
                              protection port can't be configured as 
                              localLoop either"
                 ::={ returnCode 37 }

statRtStatus   OBJECT-TYPE
                 SYNTAX INTEGER  {
                       statRtOk(1),
                       statRtIntFailure(2),
                       statRtMany(3),
                       statRtSlot(4),
                       statRtBadId(5),
                       statRtBadState(6),
                       statRtBadTimer(7),
                       statRtExists(8),
                       statRtCantFind(9),
                       statRtDelInProgress(10),
                       statRtLockedIdle(11),
                       statRtBadNetMask(12),
                       statRtCorrelation(13),
                       statRtShutting(14),
                       statRtDisabled(15),
                       statRtBadMetric(16),
                       statRtBadIPAddr(17),
                       intfRtExists(18),
                       statRtBadSlot(19),
                       statRtBadRouterId(20),
                       statRtBadRouteId(21),
                       statRtBadRouteNetMask(22),
                       statRtBadRouteIpAddr(23),
                       statRtBadGtwyIpAddr(24),
                       statRtBadDestIpAddr(25),
                       statRtBadDestNetMask(26),
                       statRtCantFindRouter(27),
                       statRtCantFindRoute(28)
                       }
                 MAX-ACCESS read-only
                 STATUS current
                 DESCRIPTION "Return codes for route server static route
                            condititions.
                       statRtOk(1)              Static Rt OK
                       statRtIntFailure(2)      Memory Corruption
                       statRtMany(3)            Too Many Static Routes
                       statRtSlot(4)            Impossible Slot ID
                       statRtBadId(5)           Bad VPN ID
                       statRtBadState(6)        State Machine Confusion
                       statRtBadTimer(7)        Bad Timer Value: State Machine
                       statRtExists(8)          Static Rt Already Exists
                       statRtCantFind(9)        Unused
                       statRtDelInProgress(10)  Deleting: -Must Wait
                       statRtLockedIdle(11)     Static Rt Taken Out Of Service
                       statRtBadNetMask(12)     Bad Network Mask
                       statRtCorrelation(13)    Internal Correlation Error
                       statRtShutting(14)       Shutting Down: -Must Wait
                       statRtDisabled(15)       SubSystem Failure
                       statRtBadMetric(16)      Illegal Metric Value
                       statRtBadIPAddr(17)      Bad Static Route IP Address
                       intfRtExists(18)         Static Route On Different Intf.
                       statRtBadSlot(19)        Impossible Slot ID
                       statRtBadRouterId(20)    Bad VPN/Router ID
                       statRtBadRouteId(21)     Illegal Static Route ID
                       statRtBadRouteNetMask(22) Bad Stat Route Network Mask
                       statRtBadRouteIpAddr(23) Bad Interface IP Address
                       statRtBadGtwyIpAddr(24)  Bad Gateway IP Address
                       statRtBadDestIpAddr(25)  Bad Destination IP Address
                       statRtBadDestNetMask(26) Bad Destination IP Mask
                       statRtCantFindRouter(27) Cannot Find VPN
                       statRtCantFindRoute(28)  Cannot Find Static Route"
                 ::= { returnCode 38 }

portFailureReasonCode        OBJECT-TYPE
                SYNTAX INTEGER  {
                                insufficientModuleBandwidth(1),
                                localLoopNotAllowedWhenInAPS(2),
                msBitStuffingEnabledOnlyForCE(3),
                invalidOption(4),
                hasInterfaceInService(5),
                unsupportedBaudRate(6),
                msLOSDetectionNotEnabled(7)

                                }
                MAX-ACCESS read-only
                STATUS current
                DESCRIPTION "Identification of cause for failure in changing
                             the parameters of a port
                        insufficientModuleBandwidth(1)
                                insufficient module bandwidth
                        localLoopNotAllowedWhenInAPS(2)
                                local loop is not allowed when a port
                                is in an automatic switching pair.
                        msBitStuffingEnabledOnlyForCE(3)
                                if msBitStuffing is enabled, only interface
                                type circuit emulation is allowed
                        invalidOption(4)            invalid option
                        hasInterfaceInService(5)    interface is in-service
                        unsupportedBaudRate(6)      the baud rate is not supported
                        msLOSDetectionNotEnabled(7) msLOSDetection is not enabled
                        "
                ::= { returnCode 39 }
 
dlciNumber      OBJECT-TYPE
                SYNTAX Integer32
                MAX-ACCESS read-only
                STATUS current
                DESCRIPTION "The number of the dlci being used."
                ::= { returnCode 40 }

ipAddrNumber    OBJECT-TYPE
                SYNTAX IpAddress
                MAX-ACCESS read-only
                STATUS current
                DESCRIPTION "The IP address of the host/network to be echoed"
                ::= { returnCode 41 }

pingStatusReasonCode   OBJECT-TYPE
                SYNTAX INTEGER {
                       alive(1),
                       not-Alive(2)
                }
                MAX-ACCESS read-only
                STATUS current
                DESCRIPTION "The response value - 
                        Alive           destination can be reached
                        Not Alive       destination can't be reached"
                ::= { returnCode 42 }

primarySoftwareVersion OBJECT-TYPE
                SYNTAX OCTET STRING (SIZE(20))
                MAX-ACCESS read-only
                STATUS current
                DESCRIPTION "Software version running on primary cpu."
                ::= { returnCode 43 }

backupSoftwareVersion OBJECT-TYPE
                SYNTAX OCTET STRING (SIZE(20))
                MAX-ACCESS read-only
                STATUS current
                DESCRIPTION "Software version running on backup cpu."
                ::= { returnCode 44 }

oamActDeactResultCode OBJECT-TYPE
                SYNTAX INTEGER  {
                        eteCCActSuccTowardsFarEnd(1),
                        eteCCActSuccTowardsNearEnd(2),
                        eteCCActSuccTowardsBothEnd(3),
                        eteCCActDeniedTowardsFarEnd(4),
                        eteCCActDeniedTowardsNearEnd(5),
                        eteCCActDeniedTowardsBothEnd(6),
                        eteCCActFailedTowardsFarEnd(7),
                        eteCCActFailedTowardsNearEnd(8),
                        eteCCActFailedTowardsBothEnd(9),
                        eteCCDeactSuccTowardsFarEnd(10),
                        eteCCDeactSuccTowardsNearEnd(11),
                        eteCCDeactSuccTowardsBothEnd(12),
                        eteCCDeactDeniedTowardsFarEnd(13),
                        eteCCDeactDeniedTowardsNearEnd(14),
                        eteCCDeactDeniedTowardsBothEnd(15),
                        eteCCDeactFailedTowardsFarEnd(16),
                        eteCCDeactFailedTowardsNearEnd(17),
                        eteCCDeactFailedTowardsBothEnd(18),
                        segCCActSuccTowardsFarEnd(19),
                        segCCActSuccTowardsNearEnd(20),
                        segCCActSuccTowardsBothEnd(21),
                        segCCActDeniedTowardsFarEnd(22),
                        segCCActDeniedTowardsNearEnd(23),
                        segCCActDeniedTowardsBothEnd(24),
                        segCCActFailedTowardsFarEnd(25),
                        segCCActFailedTowardsNearEnd(26),
                        segCCActFailedTowardsBothEnd(27),
                        segCCDeactSuccTowardsFarEnd(28),
                        segCCDeactSuccTowardsNearEnd(29),
                        segCCDeactSuccTowardsBothEnd(30),
                        oamReqFunctionNotImplemented(31),
                        oamReqFailLocRsrcUnavl(32),
                        oamActDeactPrevReqInProgress(33),
                        oamActDeactInvalidParams(34),
                        oamActDeactInvalidIntf(35),
                        oamNotSupportedForThisConnection(36),
                        oamCCnotSupportedForThisConnection(37),
                        oamPrevActDeactReqFailed(38),
                        oamEteLossOfContinuitySet(39),
                        oamEteLossOfContinuityCleared(40),
                        oamSegLossOfContinuitySet(41),
                        oamSegLossOfContinuityCleared(42),
                        oamActDeactPMOnlySupportOC3(43),
                        oamPMnotSupportedForThisConnection(44),
                        oamPMBRnotSupportedForThisConnection(45),
                        etePMActSuccTowardsFarEnd(46),
                        etePMActSuccTowardsNearEnd(47),
                        etePMActSuccTowardsBothEnd(48),                
                        etePMActDeniedTowardsFarEnd(49),
                        etePMActDeniedTowardsNearEnd(50),
                        etePMActDeniedTowardsBothEnd(51),
                        etePMActFailedTowardsFarEnd(52),
                        etePMActFailedTowardsNearEnd(53),
                        etePMActFailedTowardsBothEnd(54),
                        etePMDeactSuccTowardsFarEnd(55),
                        etePMDeactSuccTowardsNearEnd(56),
                        etePMDeactSuccTowardsBothEnd(57),
                        etePMBRActSuccTowardsFarEnd(58),
                        etePMBRActSuccTowardsNearEnd(59), 
                        etePMBRActSuccTowardsBothEnd(60), 
                        etePMBRActDeniedTowardsFarEnd(61),
                        etePMBRActDeniedTowardsNearEnd(62),
                        etePMBRActDeniedTowardsBothEnd(63),
                        etePMBRActFailedTowardsFarEnd(64),
                        etePMBRActFailedTowardsNearEnd(65),
                        etePMBRActFailedTowardsBothEnd(66),
                        etePMBRDeactSuccTowardsFarEnd(67),
                        etePMBRDeactSuccTowardsNearEnd(68),
                        etePMBRDeactSuccTowardsBothEnd(69),
                        segPMActSuccTowardsFarEnd(70),
                        segPMActSuccTowardsNearEnd(71),
                        segPMActSuccTowardsBothEnd(72),
                        segPMActDeniedTowardsFarEnd(73),
                        segPMActDeniedTowardsNearEnd(74),
                        segPMActDeniedTowardsBothEnd(75),
                        segPMActFailedTowardsFarEnd(76),
                        segPMActFailedTowardsNearEnd(77),
                        segPMActFailedTowardsBothEnd(78),
                        segPMDeactSuccTowardsFarEnd(79),
                        segPMDeactSuccTowardsNearEnd(80),
                        segPMDeactSuccTowardsBothEnd(81),
                        segPMBRActSuccTowardsFarEnd(82),
                        segPMBRActSuccTowardsNearEnd(83),
                        segPMBRActSuccTowardsBothEnd(84),
                        segPMBRActDeniedTowardsFarEnd(85),
                        segPMBRActDeniedTowardsNearEnd(86),
                        segPMBRActDeniedTowardsBothEnd(87),
                        segPMBRActFailedTowardsFarEnd(88),
                        segPMBRActFailedTowardsNearEnd(89),
                        segPMBRActFailedTowardsBothEnd(90),
                        segPMBRDeactSuccTowardsFarEnd(91),
                        segPMBRDeactSuccTowardsNearEnd(92),
                        segPMBRDeactSuccTowardsBothEnd(93),
                        eteSendPMCell(94),
                        eteReceiveBRErrMessage(95),
                        receiveBRErrMessage(96),
                          receiveFPMErrMessage(97),
                          sendPMCell(98)
                        }
                MAX-ACCESS read-only
                STATUS current
                DESCRIPTION "Various result codes for the operator's 
                        command for OAM Activation-Deactivation.
		
			eteCCActSuccTowardsFarEnd:
			eteCCActSuccTowardsNearEnd:
			eteCCActSuccTowardsBothEnd:
			eteCCDeactSuccTowardsFarEnd:
			eteCCDeactSuccTowardsNearEnd:
			eteCCDeactSuccTowardsBothEnd:
				ete CC Act/Deact-request send out to far/near/both end
			eteCCActDeniedTowardsFarEnd:
			eteCCActDeniedTowardsNearEnd:
			eteCCActDeniedTowardsBothEnd:
			eteCCDeactDeniedTowardsFarEnd:
			eteCCDeactDeniedTowardsNearEnd:
			eteCCDeactDeniedTowardsBothEnd:
				ete CC Act/Deact-request is denied.
			eteCCActFailedTowardsFarEnd:
			eteCCActFailedTowardsNearEnd:
			eteCCActFailedTowardsBothEnd:
			eteCCDeactFailedTowardsFarEnd:
			eteCCDeactFailedTowardsNearEnd:
			eteCCDeactFailedTowardsBothEnd:
				ete CC Act/Deact-request is failed sent out 

			segCCActSuccTowardsFarEnd:
			segCCActSuccTowardsNearEnd:
			segCCActSuccTowardsBothEnd:
			segCCDeactSuccTowardsFarEnd:
			segCCDeactSuccTowardsNearEnd:
			segCCDeactSuccTowardsBothEnd:
				segment CC Act/Deact-request send out to far/near/both end.
			segCCActDeniedTowardsFarEnd:
			segCCActDeniedTowardsNearEnd:
			segCCActDeniedTowardsBothEnd:
				segment CC Act-request is denied.
			segCCActFailedTowardsFarEnd:
			segCCActFailedTowardsNearEnd:
			segCCActFailedTowardsBothEnd:
				ete CC Act-request is failed sent out.

			oamReqFunctionNotImplemented: The function user issued is not impemeted.
			oamActDeactPrevReqInProgress: this interface is in wait for response 
							state.
			SendPMCell: a management cell has been sent out to IO card indicating 
					PM cell need to be sent.
			eteReceiveBRErrMessage: a BR message has been forwarded to CPU indicating 
					BR error.
			receiveFPMErrMessage: a FPM message has been forwarded to CPU indicating
					FPM error."
			
		
                ::= { returnCode 45 }

tasCmprsAnnceReasonCode OBJECT-TYPE
                SYNTAX INTEGER  {
                        cmprs-success(1),
                        cmprs-Fail-equipment-Fail(2),
                        cmprs-Fail-connections-Fail(3),
                        cmprs-Fail-resource-busy(4),
                        cmprs-Fail-resource-unavail(5)
                       }
                MAX-ACCESS read-only
                STATUS current
                DESCRIPTION "The result of a compress announcement request."
                ::= { returnCode 46 }

tasTstLineReasonCode OBJECT-TYPE
                SYNTAX INTEGER  {
                        tst-success(1),
                        tst-Fail-equipment-Fail(2),
                        tst-Fail-invalid-params(3),
                        tst-Fail-resource-unavail(4),
                        tst-Fail-resource-busy(5)
                       }
                MAX-ACCESS read-only
                STATUS current
                DESCRIPTION "The result of a test line request."
                ::= { returnCode 47 }

gr303PPSReasonCode OBJECT-TYPE
                SYNTAX INTEGER  {
                        forced(1),
                        normal(2),
                        userCommandFailed-inhibited(3),
                        userCommandFailed-PathOos(4),
                        userCommandFailed-badPathId(5),
                        userCommandFailed-maxRetry(6),
                        userCommandFailed-inprogress(7),
                        userCommandFailed-unknown(8)
                       }
                MAX-ACCESS read-only
                STATUS current
                DESCRIPTION "These reason codes are the result of GR303
                Path Protection Switching (PPS) command issued by user"
                ::= { returnCode 48 }

gr303PPSSource OBJECT-TYPE
                SYNTAX INTEGER  {
                        none(1),
                        byIdt(2),
                        byUser(3),
                        byLocalAgent(4),
                        suspendedByIdt(5),
                        suspendedByLocalAgent(6)
                       }
                MAX-ACCESS read-only
                STATUS current
                DESCRIPTION "Indicates the initiator of the PPS switching"
                ::= { returnCode 49 }

tasMemReasonCode OBJECT-TYPE
                SYNTAX INTEGER  {
                        mem-init-success(1),
                        mem-init-Fail(2)
                       }
                MAX-ACCESS read-only
                STATUS current
                DESCRIPTION "The result of a memory init request."
                ::= { returnCode 50 }

tasTrapTstId OBJECT-TYPE
                SYNTAX INTEGER (1..100)
                MAX-ACCESS read-only
                STATUS current
                DESCRIPTION "Announcement ID for trap."
                ::= { returnCode 51 }

tasTrapAnnceId OBJECT-TYPE
                SYNTAX INTEGER  (1..100)
                MAX-ACCESS read-only
                STATUS current
                DESCRIPTION "test id for trap."
                ::= { returnCode 52 }


atmVpi          OBJECT-TYPE
                SYNTAX INTEGER (0..4095)
                MAX-ACCESS read-only
                STATUS current
                DESCRIPTION "Vpi is used in identification of Traps "
                ::= { returnCode 53 }

atmVci                 OBJECT-TYPE
                SYNTAX INTEGER (0..65535)
                MAX-ACCESS read-only
                STATUS current
                DESCRIPTION "Vci is used in identification of Traps "
                ::= { returnCode 54 }

iptResultCode OBJECT-TYPE
                SYNTAX INTEGER  {
                interfaceProtectioniptAlreadyExistInterface(1),
                interfaceProtectioniptInvalidInterface (2),
                 interfaceProtectioniptInvalidParams(3),
                interfaceProtectioniptTryToDeleteEmptyTable(4),
                interfaceProtectioniptInvalidConfiguation(5),
                interfaceProtectioniptSuccessfulSwichOver(6),
                interfaceProtectioniptSuccessfulSwichBack(7),
                interfaceProtectioniptFailedSwichOver(8),
                interfaceProtectioniptFailedSwichBack(9)
                }

          MAX-ACCESS read-only
                STATUS current
                DESCRIPTION "Various result codes for the operator's 
                        command forsetting/deleting interface protection group.
			  
			interfaceProtectioniptAlreadyExistInterface: Expect 
				another interface to be protected.
			interfaceProtectioniptInvalidInterface:interface invalid 
			interfaceProtectioniptInvalidParams: invalid Parameters
			interfaceProtectioniptTryToDeleteEmptyTable:Table is 
			    	already empty,can not be deleted .
			interfaceProtectioniptInvalidConfiguation: 
			interfaceProtectioniptSuccessfulSwichOver: interface 
				is switched over to the secondry interface.
			interfaceProtectioniptSuccessfulSwichBack: interface 
				is switched back from secondry interface.
			interfaceProtectioniptFailedSwichOver: interface
				is failed switched over to the secondry interface.
			interfaceProtectioniptFailedSwichBack: interface 
				is failed switched back from secondry interface."
                ::= { returnCode 55 }

pgtResultCode OBJECT-TYPE
                SYNTAX INTEGER  {
                interfaceProtectionpgtAlreadyExistInterface(1),
                interfaceProtectionpgtInvalidInterface (2),
                 interfaceProtectionpgtInvalidParams(3),
                interfaceProtectionpgtryToDeleteEmptyTable(4),
                interfaceProtectionpgtSuccessfulSwichOver(5),
                 interfaceProtectionpgtSuccessfulSwichBack(6),
                interfaceProtectionpgtFailedSwichOver(7),
                interfaceProtectionpgtFailedSwichBack(8),
                interfaceProtectionpgtInvalidConfiguation(9)
                }
                
          MAX-ACCESS read-only
                STATUS current
                DESCRIPTION "Various result codes for the operator's 
                        command for interface protection ."

                ::= { returnCode 56 }

tasmControlBlockAllocFailReasonCode OBJECT-TYPE
                SYNTAX INTEGER  {
                        res-alloc-success(1),
                        res-alloc-Fail-announce-control-blocks-mem-unavail(2),
                        res-alloc-Fail-digit-control-blocks-mem-unavail(3),
                        res-alloc-Fail-line-test-control-blocks-mem-unavail(4)
                       }
                MAX-ACCESS read-only
                STATUS current
                DESCRIPTION "The result of a tasm control block memory 
                             allocation request."
                ::= { returnCode 57}

tasmCacheMemAllocFailReasonCode OBJECT-TYPE
                SYNTAX INTEGER  {
                        res-alloc-success(1),
                        res-alloc-Fail-announce-cache-mem-unavail(2)
                       }
                MAX-ACCESS read-only
                STATUS current
                DESCRIPTION "The result of a tasm control block memory 
                             allocation request."
                ::= { returnCode 58}


atmTrunkingConfigFailureCode OBJECT-TYPE
                SYNTAX INTEGER  {
                    localIWFAlreadyConfigured(1),
                    localIWFAtmAddressError(2),
                    localIWFIdOutOfRange(3),
                    maxNumberRmtIWFOutOfRange(4),
                    rmtIWFAlreadyConfigured(5),
                    rmtIWFIdOutOfRange(6),
                    rmtIWFAtmAddressError(7),
                    vccIdError(8),
                    vccPvcParameterNotAcceptable(9),
                    vccTrafficParameterNotValid(10),
                    vccViVuniNotValid(11),
                    vccTrunkParameterNotValid(12),
                    vccTrunkFeatureParameterNotValid(13),
                    localIwfNotConfigured(14),
                    localIwfIdNotMatch(15),
                    localIwfStatus(16),
                    rmtIwfNotConfigured(17),
                    rmtIwfModeNotCompatible(18),
                    rmtIwfStatus(19),
                    vccAlreadyConfigured(20),
                    vccPvcCacReject(21),
                    requiredFieldMissing(22),
                    outOfResource(23),
                    rowStatusError(24),
                    generalErrorUnspecified(25)
                    
                }
                MAX-ACCESS read-only
                STATUS current
                DESCRIPTION "An identified reason for failure while 
                             configuring/modifying 
                             ATM Trunking parameters:
                             localIWFAlreadyConfigured(1) : Local IWF has 
                             already been configured, the
                             parameters can not be changed or apply again.
                             localIWFAtmAddressError(2): the ATM Address for 
                             Local IWF is not valid or
                             this address has been used by someone else.
                             localIWFIdOutOfRange(3): the Identification of 
                             Local IWF is out of range.
                             maxNumberRmtIWFOutOfRange(4): the maximum number 
                             of Remote IWF is out of range.
                             rmtIWFAlreadyConfigured(5): this remote IWF has 
                             already been configured(
                             with index atmTrunkingRmtIWFIdentifier).
                             rmtIWFIdOutOfRange: the identifier for the remote 
                             IWF is out of range.
                             rmtIWFAtmAddressError: the ATM Address for remote 
                             IWF is not valid or
                             this address has been used by someone else.
                             vccIdError: the VCC ID for the SigVcc or BrVcc 
                             is 0, or this VCC ID is out of range
                             or it has been used by someone else.
                             vccPvcParameterNotAcceptable: the parameters 
                             of PVC side, including slot, port, channel,
                             vpi, vci, are not acceptable.
                             vccTrafficParameterNotValid: the VCC traffic 
                             parameters are not acceptable,
                             including FwPcr01, BwPcr01, FwScr01, BwScr01, 
                             FWMbs01, BwMbs01, BrVccServiceType, BrVccSarType.
                             vccViVuniNotValid: the configuration of Egress 
                             Vi/VUNI is not acceptable.
                             vccTrunkParameterNotValid: the parameters for the 
                             Trunk is not supported,
                             including BrVccMaxAal2ChanId, 
                             BrVccCircuitModeDataSupp,
                             BrVccFrameModeSupp, BrVccFaxModeSupp, 
                             CASPktXportSupp,
                             BrVccDTMFPktXportSupp, BrVccMFR1PktXportSupp,
                             BrVccMFR2PktXportSupp, BrVccPCMEncoding, 
                             BrVccMaxFrameLength,
                             BrVccIdleChannSuprSupp, BrVccSilenceDetSupp,
                             BrVccCompressionSpec,AudioProfileId,
                             SigVccSignaling.
                             vccTrunkFeatureParameterNotValid: PSAX proprietary 
                             feature parameters not supported
                             including SigVccInactiveTimer, SigVccRetryTimer, 
                             SigVccRetryLimit,
                             BrVccInactiveTimer, BrVccRetryTimer, 
                             BrVccRetryLimit,  BrVccGr303Supp, BrVccOamStatus.
                             localIwfNotConfigured(14) :
                                                     Local IWF not Configured
                             localIwfIdNotMatch(15): 
                                                specified Local IWF not match
                             localIwfStatus(16): this operation is not supported
                                 because of the status of Local IWF
                             rmtIwfNotConfigured(17): Remote IWF Not Configured
                             rmtIwfModeNotCompatible(18): the Mode of Remote IWF
                                 is not compatiable
                             rmtIwfStatus(19): this operation is not support
                                 because of the Status of Remote IWF
                             vccAlreadyConfigured(20): 
                                                   This VCC has been configured
                             vccPvcCacReject(21): PVC Configuration rejected by
                                 Cac Reservation Function
                             requiredFieldMissing(22): mandatory fields missing
                             outOfResource(23): Atm Trunking Task or System
                                 out of resource for this configuration
                             rowStatusError(24):Row Status Error with the SNMP
                                 command
                             generalErrorUnspecified(25): all other unspecified
                                 failure cause.
                             "
                ::= { returnCode 59 }


sapphireIntfAddressFailReasonCode OBJECT-TYPE
                SYNTAX INTEGER  {
                      address-assign-ok(1),
                      fail-Ilegal-IP-address(2),
                      fail-not-match-InBandManagement-Switch-Cpu-IP-Address(3),
                      fail-Switch-or-Cpu-IP-Address-unconfigured(4),
                      fail-InBandManagement-IP-Address-unconfigured(5)
                       }
                MAX-ACCESS read-only
                STATUS current
                DESCRIPTION "The result of assigning the Sapphire
                             Interface address when PSAX is Sapphire client.
                  address-ok(1),        Address assignment succeeded
                  fail-Ilegal-IP-address(2),
                          Illegal IP address assigned address not matching
                  fail-not-match-InBandManagement-Switch-CPU-IP-Address(3)
                          In-Band Management IP or Switch IP or CPU IP address
                  fail-Switch-or-CPU-IP-Address-unconfigured(4)
                          Switch IP or CPU IP address unconfigured
                  fail-InBandManagement-IP-Address-unconfigured(5)
                          InBandManagement IP address unconfigured."
                ::= { returnCode 60}


chassisOverTempAlarmReasonCode OBJECT-TYPE 
                SYNTAX INTEGER  { 
                        set(1), 
                        clear(2) 
                       } 
                MAX-ACCESS read-only 
                STATUS current 
                DESCRIPTION "Indicator of presence of chassis 
                over temperature alarm." 
                ::= { returnCode 61 }

-- System Control Group sysControl

saveConfiguration OBJECT-TYPE
                SYNTAX INTEGER {
                                equipment(1),
                                connections(2),
                                routing(3),
                                all(4)
                               }
                MAX-ACCESS read-write
                STATUS current
                DESCRIPTION "save configuration "
                ::= { sysControl 1 }

upgradeSoftware OBJECT-TYPE
                SYNTAX INTEGER {
                                upgrade(1),
                                fallBack(2),
                                forceUpgrade(3),
                                forceFallBack(4),
                                synchronize(5),-- backup sw ver sync
                                abort(6),-- abort any ver control progress
                                forceSynchronize(7),--similar to forceUpgrade/forceFallBack
                                forceAbort(8) -- abort for forceUpgrade/forceFallBack
                                }
                MAX-ACCESS read-write
                STATUS current
                DESCRIPTION "software load management"
                ::= { sysControl 2 }

purgePvcConnections OBJECT-TYPE
                SYNTAX IntfIndex
                MAX-ACCESS read-write
                STATUS current
                DESCRIPTION "purge PVC connections on indicated interface"
                ::= { sysControl 3 }

purgeRoutingTable OBJECT-TYPE
                SYNTAX INTEGER {
                                    iispCbr(1),
                                iispVbr(2)
                               }
                MAX-ACCESS read-write
                STATUS current
                DESCRIPTION "purge indicated routing table"
                ::= { sysControl 4 }

resetPortStatistics OBJECT-TYPE
                SYNTAX Integer32
                MAX-ACCESS read-write
                STATUS current
                DESCRIPTION "Reset the statistics counters for the given
                             port Id (SSPP)"
                ::= { sysControl 5 }

resetInterfaceStatistics OBJECT-TYPE
                SYNTAX IntfIndex
                MAX-ACCESS read-write
                STATUS current
                DESCRIPTION "Reset the interface counters for the given
                             port Id (SSPPCCC)"
                ::= { sysControl 6 }

resetAllStatistics OBJECT-TYPE
                SYNTAX Integer32
                MAX-ACCESS read-write
                STATUS current
                DESCRIPTION "Reset all port and interface statistics
                             counters, accpets any integer value"
                ::= { sysControl 7 }

upgradeIpAddress OBJECT-TYPE
                SYNTAX IpAddress
                MAX-ACCESS read-write
                STATUS current
                DESCRIPTION "IP Address for upgrade ftp server."
                ::= { sysControl 8 }
 
upgradeAccountName OBJECT-TYPE
                SYNTAX DisplayString (SIZE(20))
                MAX-ACCESS read-write
                STATUS current
                DESCRIPTION "ftp account name for access to upgrade ftp server."                ::= { sysControl 9 }
 
upgradeAccountPassword OBJECT-TYPE
                SYNTAX DisplayString (SIZE(20))
                MAX-ACCESS read-write
                STATUS current
                DESCRIPTION "ftp account password for access to upgrade ftp
                             server."
                ::= { sysControl 10 }
 
upgradeCdromFile OBJECT-TYPE
                SYNTAX DisplayString (SIZE(79))
                MAX-ACCESS read-write
                STATUS current
                DESCRIPTION "cdrom file path on upgrade ftp server to upgrade
                             image library."
                ::= { sysControl 11 }

upgradeLicenseKey OBJECT-TYPE
                SYNTAX DisplayString (SIZE(30))
                MAX-ACCESS read-write
                STATUS current
                DESCRIPTION "software license key."
                ::= { sysControl 12 }
 
upgradeSwCopyStatus OBJECT-TYPE
                SYNTAX INTEGER {
                                noActivity(1),
                                working(2),
                                doneSuccessfully(3),
                                doneWithError(4),
                                aborted(5)
                               } 
                MAX-ACCESS read-only
                STATUS current
                DESCRIPTION "Current status of the ftp software upgrade 
                             download.
                             Status of the software upgrade.  noActivity is
                             the initial start state from boot-up.  working
                             is set while ftp'ing the upgrade.  The final state
                             is one of doneSuccessfully, doneWithError, or
                             aborted, all self-explanatory.  It will stay in
                             this state until re-boot or starting an upgrade.
                             If the state is doneWithError then
                             upgradeSwErrorStatus will be set to reflect the
                             type of error."
                ::= { sysControl 13 }

upgradeSwErrorStatus OBJECT-TYPE
                SYNTAX INTEGER {
                                none(1),
                                userAbort(2),
                                invalidIpAddress(3),
                                invalidAccountName(4),
                                invalidAccountPassword(5),
                                invalidCdromFile(6),
                                libraryCRCFail(7),
                                unableToOpenLibraryFile(8),
                                unableToLoadLibraryModule(9),
                                unableToFindTaskSymbolName(10),
                                failureInSpawningTask(11),
                                failureInCreatingMsgQ(12),
                                failureInCopyingDataFiles(13),
                                failureToRemoveNextTree(14),
                                unableToMakeNextTree(15),
                                unableToOpenFile(16),
                                unableToMakeFtpConnection(17),
                                unableToWriteFile(18),
                                unableToCompleteFtp(19),
                                fileCRCFail(20),
                                unableToWritePackageList(21),
                                taskSuspendOrDead(22),
                                unableToUpdateBackup(23),
                                cpuAbort(24),
                                failureToTakeSemaphore(25),
                                failureToRemoveFallBackTree(26),
                                unableToMakeFallBackTree(27)
                               }
                MAX-ACCESS read-only
                STATUS current
                DESCRIPTION "The result of the finish of the ftp software
                             upgrade download.
                             Set to a value 3-22 if upgradeSwCopyStatus is
                             doneWithError.  Set to none if upgradeSwCopyStatus
                             is doneSuccessfully.  Set to userAbort if
                             upgradeSwCopyStatus is aborted."
                DEFVAL { none }
                ::= { sysControl 14 }

systemSwCopy    OBJECT-TYPE
                SYNTAX INTEGER {
                                start(1),
                                abort(2)
                               }
                MAX-ACCESS read-write
                STATUS current
                DESCRIPTION "start copy system files according to the profile.
                             When upgradeSwCopyStatus is working, the start
                             request will be ignored.  Abort will have effect
                             only when upgradeSwCopystatus is working."
                ::= { sysControl 15 }


fwReleaseTable OBJECT-TYPE
                SYNTAX SEQUENCE OF FwReleaseEntry
                MAX-ACCESS not-accessible
                STATUS current
                DESCRIPTION "Table of firmware inventory data"
                ::= { sysControl 16 }

fwReleaseEntry OBJECT-TYPE
                SYNTAX FwReleaseEntry
                MAX-ACCESS not-accessible
                STATUS current
                DESCRIPTION "Row definition for firmware inventory"
                INDEX { fwReleaseSlot }
                ::= { fwReleaseTable 1 }

FwReleaseEntry ::= SEQUENCE {
                fwReleaseSlot                INTEGER,
                fwReleaseRunning        OCTET STRING,
                fwReleaseEpromVersion        OCTET STRING,
                fwReleaseCurrentVersion        OCTET STRING,
                fwReleaseNextVersion        OCTET STRING,
                fwReleaseUpdate                INTEGER,
                fwReleaseUpgrade        INTEGER
                }

fwReleaseSlot        OBJECT-TYPE
                SYNTAX INTEGER (1..16)
                MAX-ACCESS not-accessible
                STATUS current
                DESCRIPTION "Physical slot location.  Valid range is a number
                             between 1 and 16."
                ::= { fwReleaseEntry 1 }

fwReleaseRunning OBJECT-TYPE
                SYNTAX OCTET STRING (SIZE(15))
                MAX-ACCESS read-only
                STATUS current
                DESCRIPTION "the firmware release currently running in a
                             physical slot (e.g., 01.03.C01)."
                ::= { fwReleaseEntry 2 }

fwReleaseEpromVersion OBJECT-TYPE
                SYNTAX OCTET STRING (SIZE(9))
                MAX-ACCESS read-only
                STATUS current
                DESCRIPTION "the version of the firmware located on the I/O
                             card (e.g., 01.03.C01)."
                ::= { fwReleaseEntry 3 }

fwReleaseCurrentVersion OBJECT-TYPE
                SYNTAX OCTET STRING (SIZE(9))
                MAX-ACCESS read-only
                STATUS current
                DESCRIPTION "the version of the firmware located in 
                             /scsi/current/io on the CPU disk drive 
                             (e.g., 01.03.C01)."
                ::= { fwReleaseEntry 4 }

fwReleaseNextVersion OBJECT-TYPE
                SYNTAX OCTET STRING (SIZE(9))
                MAX-ACCESS read-only
                STATUS current
                DESCRIPTION "the version of the firmware located in
                             /scsi/next/io on the CPU disk drive 
                             (e.g., 01.03.C01)."
                ::= { fwReleaseEntry 5 }

fwReleaseUpdate OBJECT-TYPE
                SYNTAX INTEGER {
                                activate(1)
                               }
                MAX-ACCESS read-write
                STATUS current
                DESCRIPTION "Update the fwReleaseCurrentVersion and the
                             fwReleaseNextVersion variables by remapping
                             the firmware files from the CPU disk drive."
                ::= { fwReleaseEntry 6 }

fwReleaseUpgrade OBJECT-TYPE
                SYNTAX INTEGER {
                                eprom(1),
                                current(2),
                                next(3)
                               }
                MAX-ACCESS read-write
                STATUS current
                DESCRIPTION "Update the fwReleaseCurrentVersion and the
                             fwReleaseNextVersion variables by remapping
                             the firmware files from the CPU disk drive."
                DEFVAL { eprom }
                ::= { fwReleaseEntry 7 }


resetBridgeDomainStatistics OBJECT-TYPE
                SYNTAX Integer32
                MAX-ACCESS read-write
                STATUS current
                DESCRIPTION "Resets bridge domain statistics."
                ::= { sysControl 17 }

remoteRebootCommand OBJECT-TYPE
                SYNTAX INTEGER {
                                ioCard1Reboot(1),
                                ioCard2Reboot(2),
                                ioCard3Reboot(3),
                                ioCard4Reboot(4),
                                ioCard5Reboot(5),
                                ioCard6Reboot(6),
                                ioCard7Reboot(7),
                                ioCard8Reboot(8),
                                ioCard9Reboot(9),
                                ioCard10Reboot(10),
                                ioCard11Reboot(11),
                                ioCard12Reboot(12),
                                ioCard13Reboot(13),
                                ioCard14Reboot(14),
                                ioCard15Reboot(15),
                                ioCard16Reboot(16),
                                allIOCardReboot(100),
                                chassisReboot(101),
                                backupCpuReboot(102),
                                primaryCpuReboot(103),
                                primaryCpuSwitchover(200)
                               } 
                MAX-ACCESS read-write
                STATUS current
                DESCRIPTION "type of reboot."
                ::= { sysControl 18 }

resetFrLmiStatistics OBJECT-TYPE
                SYNTAX Integer32
                MAX-ACCESS read-write
                STATUS current
                DESCRIPTION "Reset the frame relay LMI statistics counters for 
                             the given port Id (SSPPCCC)"
                ::= { sysControl 19 }

removeConfigurationFiles OBJECT-TYPE
                SYNTAX INTEGER {
                                all(1)
                               } 
                MAX-ACCESS read-write
                STATUS current
                DESCRIPTION "Removes the user configuration/connection files
                             from the hard disk on the cpu."
                DEFVAL { all }
                ::= { sysControl 20 }

systemFilesDirtyBitStatus OBJECT-TYPE
                SYNTAX INTEGER (0..4096) 
                MAX-ACCESS read-only
                STATUS current
                DESCRIPTION "Bit mask for system files:
                             0:  all are clean
                             1:  console.def
                             2:  ecd.def
                             4:  ssid.def
                             8:  cnctn.db
                            16:  iisp.cbr
                            32:  iisp.vbr
                            64:  spvc.db
               128:  vipr.cfg
               256:  fwc.def
               512:  vi.db
              1024:  iproute.db
              2048:  atmvuni.db"
                ::= { sysControl 21 }

resetAtmIlmiStatistics OBJECT-TYPE
                SYNTAX Integer32
                MAX-ACCESS read-write
                STATUS current
                DESCRIPTION "Reset the ATM ILMI statistics counters for 
                             the given channel Id (SSPPCCC)"
                ::= { sysControl 22 }

resetImaGrpChannelStatistics OBJECT-TYPE
                SYNTAX IntfIndex
                MAX-ACCESS read-write
                STATUS current
                DESCRIPTION "Reset the IMA Group Statistics counters for the 
                             given port Id (SSPPCCC)"
                ::= { sysControl 23 }

oc3APSResetStats OBJECT-TYPE
                SYNTAX Integer32
                MAX-ACCESS read-write
                STATUS current
                DESCRIPTION "Reset the oc3aps Group Statistics counters for 
                             the given port Id (SSPP)"
                ::= { sysControl 24 }

resetsonetSectionStatistics OBJECT-TYPE
                 SYNTAX Integer32
                 MAX-ACCESS read-write
                 STATUS current
                 DESCRIPTION "Reset the sonetSectionCurrent Statistics 
                                 counters for the given port Id (SSPP)"
                 ::= { sysControl 25 }
  
resetsonetLineStatistics OBJECT-TYPE
                 SYNTAX Integer32
                 MAX-ACCESS read-write
                 STATUS current
                 DESCRIPTION "Reset the sonetLineCurrent Statistics 
                                 counters for the given port Id (SSPP)"
                 ::= { sysControl 26 }

resetsonetVTPathStatistics OBJECT-TYPE
                 SYNTAX Integer32
                 MAX-ACCESS read-write
                 STATUS current
                 DESCRIPTION "Reset the sonetVTPathCurrent Statistics 
                                 counters for the given port Id (SSPP)"
                 ::= { sysControl 27 }

viprVpnReset     OBJECT-TYPE
                 SYNTAX Integer32
                 MAX-ACCESS read-write
                 STATUS current
                 DESCRIPTION "Reset the VPN statistics for VPN specified by (SSVV)"
                 ::= { sysControl 28 }


svcRetBackupStatus     OBJECT-TYPE
                SYNTAX INTEGER {                 
                                no-sync (1),
                                sync-in-progress (2),
                                fully-sync(3)
                               }
                 MAX-ACCESS read-only
                 STATUS current
                 DESCRIPTION "Indicates backup status wrt SVC retention"
                 ::= { sysControl 29 }

resetsonetPathStatistics OBJECT-TYPE
                 SYNTAX Integer32
                 MAX-ACCESS read-write
                 STATUS current
                 DESCRIPTION "Reset the sonetPathCurrent Statistics
                        counters for the given port Id (SSPP)"
                ::= { sysControl 30 }

ambientTemperature OBJECT-TYPE
                 SYNTAX Integer32
                 MAX-ACCESS read-only
                 STATUS current
                 DESCRIPTION "Ambient temperature in degree Celcius where the  
                             system is kept"
                ::= { sysControl 31 }

remoteDbServerGroup OBJECT IDENTIFIER  ::=  {sysControl 32}

remoteDbServerIpAddress OBJECT-TYPE
                SYNTAX IpAddress
                MAX-ACCESS read-write
                STATUS current
                DESCRIPTION "IP Address for remote database server."
                ::= { remoteDbServerGroup 1 }

remoteDbServerLogin OBJECT-TYPE
                SYNTAX DisplayString (SIZE(20))
                MAX-ACCESS read-write
                STATUS current
                DESCRIPTION "ftp account name for remote database
                             server."
                ::= { remoteDbServerGroup 2 }

remoteDbServerPassword OBJECT-TYPE
                SYNTAX DisplayString (SIZE(20))
                MAX-ACCESS read-write
                STATUS current
                DESCRIPTION "ftp account password for remote database
                             server."
                ::= { remoteDbServerGroup 3 }

remoteDbServerDirectory OBJECT-TYPE
                SYNTAX DisplayString (SIZE(79))
                MAX-ACCESS read-write
                STATUS current
                DESCRIPTION "directory on remote database server where
                             to save/restore database files from."
                ::= { remoteDbServerGroup 4 }

remoteDbCommand OBJECT-TYPE
                SYNTAX INTEGER {
                                noOperation(1),
                                remoteSave(2),
                                remoteLoad(3)
                               }
                MAX-ACCESS read-write
                STATUS current
                DESCRIPTION "remote database operation."
                ::= { remoteDbServerGroup 5 }

remoteDbOperationStatus OBJECT-TYPE
                SYNTAX INTEGER {
                                noActivity(1),
                                working(2),
                                doneSuccessfully(3),
                                doneWithError(4),
                                aborted(5)
                               }
                MAX-ACCESS read-only
                STATUS current
                DESCRIPTION "Current status of remote database command."
                ::= { remoteDbServerGroup 6 }

remoteDbOperationErrorStatus OBJECT-TYPE
                SYNTAX INTEGER {
                                none(0),
                                unableToMakeFtpConnection(1),
                                invalidDirectory(2),
                                unableToOpenDatabaseFile(3),
                                unableToCompleteFtp(4),
                                databaseSanityFail(5),
                                unableToUpdateBackup(6)
                               }
                MAX-ACCESS read-only
                STATUS current
                DESCRIPTION "The result at the finish of remote database
                             operation."
                DEFVAL { none }
                ::= { remoteDbServerGroup 7 }


stratumSyncSource OBJECT-TYPE
                SYNTAX INTEGER {
                                lineTiming(1),
                                compositeClock(2),
                                freerun(3),
                                t1BITS(4),
                                e1ETSI(5)
                               }
                MAX-ACCESS read-write
                STATUS current
                DESCRIPTION "Clock source for the stratum card - 
                                lineTiming: must have slot and port
                                specified in stratumPrimaryLineId.
                                compositeClock: local clock must
                                be available. "
                DEFVAL { lineTiming }
                ::= { stratumConfig 1 }

stratumPrimaryLineId OBJECT-TYPE
                SYNTAX Integer32
                MAX-ACCESS read-write
                STATUS current
                DESCRIPTION "Format SSPP (slot and port #'s) to be used
                                     when lineTiming is specified in 
                                stratumSyncSource."
                ::= { stratumConfig 2 }

stratumSecondaryLineId OBJECT-TYPE
                SYNTAX Integer32
                MAX-ACCESS read-write
                STATUS current
                DESCRIPTION "Format SSPP (slot and port #'s) to be used if
                             the primary line has failed. Zeros imply that
                             the stratum should switch to holdover mode 
                             instead."
                ::= { stratumConfig 3 }

stratumLevel         OBJECT-TYPE
                SYNTAX INTEGER {
                                stratum3(1),
                                stratum4(2)
                               }
                MAX-ACCESS read-write
                STATUS current
                DESCRIPTION "Enable or disable the switching over to stratum
                             4 when stratum 3 is not possible."
                DEFVAL { stratum3 }
                ::= { stratumConfig 4 }

stratumLineCommand OBJECT-TYPE
                SYNTAX INTEGER {
                                gotoPrimaryLine(1),
                                gotoSecondaryLine(2)
                               }
                MAX-ACCESS read-write
                STATUS current
                DESCRIPTION "Forces the stratum card to use one of the two
                             specified lines as its clock source when the 
                             stratumSyncSource is lineTiming."
                ::= { stratumConfig 5 }

stratumLineTimingStatus OBJECT-TYPE
                SYNTAX INTEGER {
                                primaryLine(1),
                                secondaryLine(2),
                                none(3)
                               }
                MAX-ACCESS read-only
                STATUS current
                DESCRIPTION "Represents the source of the current clock."
                ::= { stratumConfig 6 }

stratumMode        OBJECT-TYPE
                SYNTAX INTEGER {
                                synchronized3(1),
                                synchronized4(2),
                                holdover(3),
                                freerun(4),
                                cardRemoved(5)
                                }
                MAX-ACCESS read-only
                STATUS current
                DESCRIPTION "Current status of the primary stratum card.
                synchronized3(1) stratum is synchronized with accuracy
                                 4.6 x 10e-6
                synchronized4(2) stratum is synchronized with accuracy
                                 3.2 x 10e-5
                holdover(3)      an operating condition of a clock that has
                                 lost its controlling input and is using
                                 stored data acquired while in normal
                                 operation, to control its output
                freerun(4)       an operating condition of the clock whose
                                 output signals are internally controlled
                cardRemoved(5)   stratum removed
                "
                ::= { stratumConfig 7 }

stratumBackupMode OBJECT-TYPE
                SYNTAX INTEGER {
                                synchronized3(1),
                                synchronized4(2),
                                holdover(3),
                                freerun(4),
                                cardRemoved(5)
                                }
                MAX-ACCESS read-only
                STATUS current
                DESCRIPTION "Current status of the backup stratum card. "
                ::= { stratumConfig 8 }


stratumRefFailAction OBJECT-TYPE
                SYNTAX INTEGER {
                                holdover(1),
                                freerun(2)
                               }
                MAX-ACCESS read-write
                STATUS current
                DESCRIPTION "Defines whether the stratum should switch to
                             freerun or holdover on reference clock failure."
                DEFVAL { holdover }
                ::= { stratumConfig 9 }

stratumPortStatus OBJECT-TYPE
                SYNTAX INTEGER {
                                unconfigured(1),
                                noalarm(2),
                                portAIS(3),
                                portLOF(4),
                                portLOS(5),
                                portFOS(6)
                                }
                MAX-ACCESS read-only
                STATUS current
                DESCRIPTION "Current status of the primary stratum card.
                             portFOS indicates port frequency offset. "
                ::= { stratumConfig 10 }

stratumBkupPortStatus OBJECT-TYPE
                SYNTAX INTEGER {
                                unconfigured(1),
                                noalarm(2),
                                portAIS(3),
                                portLOF(4),
                                portLOS(5),
                                portFOS(6)
                                }
                MAX-ACCESS read-only
                STATUS current
                DESCRIPTION "Current status of the backup stratum card.
                             portFOS indicates port frequency offset. "
                ::= { stratumConfig 11 }

activeStratum OBJECT-TYPE
                SYNTAX INTEGER {
                                stratumA(1),
                                stratumB(2)
                                }
                MAX-ACCESS read-only
                STATUS current
                DESCRIPTION "Current status of the backup stratum card."
                ::= { stratumConfig 12 }



-- Cell Test specific objects



cellTestIfB OBJECT-TYPE
                SYNTAX IntfIndex
                MAX-ACCESS read-write
                STATUS current
                DESCRIPTION "Interface index used for testing cell transfer.
                             Number value is interpreted as an interface of the 
                             form, SSPPCCC, where SS is the card slot, PP is 
                             the port number, and CCC is the channel number."
                ::= { cellTest 1 }

cellTestVpiB OBJECT-TYPE
                SYNTAX INTEGER (0..4095)
                MAX-ACCESS read-write
                STATUS current
                DESCRIPTION "VPI value for testing cell transfer to an I/O card.
                             Valid range is a number between 0 and 4095.  If
                             the I/O card interface is not ATM, then this will 
                             always be zero."
                ::= { cellTest 2 }

cellTestVcidB OBJECT-TYPE
                SYNTAX INTEGER (0..65535)
                MAX-ACCESS read-write
                STATUS current
                DESCRIPTION "Virtual Check Id for testing cell transfer to an
                             I/O card.  Valid range is a number between 0 and
                             65535.  If the I/O card interface is frame relay,
                             this field acts as DLCI and the valid range is a
                             number between 0 and 1023.  If the I/O card 
                             interface is circuit emulation, then this will
                             always be 0."
              ::= { cellTest 3 }

cellTestServiceType OBJECT-TYPE
               SYNTAX INTEGER  {
                                ubr(1),
                                vbr-nrt2(2),
                                vbr-nrt1(3),
                                vbr-rt2(4),
                                vbr-rt1(5),
                                vbr-express(6),
                                cbr4(7),
                                cbr3(8),
                                cbr2(9),
                                cbr1(10)
                               }
                MAX-ACCESS read-write
                STATUS current
                DESCRIPTION "Service types for testing cell transfer"
                DEFVAL { ubr }
                ::= { cellTest 4 }

cellTestConnType OBJECT-TYPE
                SYNTAX INTEGER {
                                simplexTx(1),
                                simplexRx(2),
                                duplex(3)
                               }
                MAX-ACCESS read-write
                STATUS current
                DESCRIPTION "Connection types for testing cell transfer"
                DEFVAL { simplexTx }
                ::= { cellTest 5 }

cellTestProtocol OBJECT-TYPE
                SYNTAX INTEGER {
                                atm(1),
                                frame-relay (2),




                                hdlc(4)
                               }
                MAX-ACCESS read-only
                STATUS current
                DESCRIPTION "Protocol (interface type) on the I/O"
                DEFVAL { atm }
                ::= { cellTest 6 }

cellTestPayLoadTx OBJECT-TYPE
                SYNTAX OCTET STRING (SIZE(88))
                MAX-ACCESS read-write
                STATUS current
                DESCRIPTION "PayLoad to be transmitted on I/O interface"
                ::= { cellTest 7 }

cellTestPayLoadRx OBJECT-TYPE
                SYNTAX OCTET STRING (SIZE(88))
                MAX-ACCESS read-only
                STATUS current
                DESCRIPTION "Last PayLoad received  on I/O interface"
                ::= { cellTest 8 }

cellTestAction OBJECT-TYPE
               SYNTAX INTEGER
                       {
                         send(1),
                         send-10(2),
                         setupconn(3),
                         stop (4),
                          clearTxStats(5),
                         clearRxStats(6)
                       }
                MAX-ACCESS read-write
                STATUS current
                DESCRIPTION "PayLoad received  on I/O interface"
                DEFVAL { stop }
                ::= { cellTest 9 }

cellTestRxPduCount OBJECT-TYPE
                SYNTAX Integer32
                MAX-ACCESS read-only
                STATUS current
                DESCRIPTION "Valid cells received (Input Billing Count)"
                ::= { cellTest 10 }

cellTestTxPduCount OBJECT-TYPE
                SYNTAX Integer32
                MAX-ACCESS read-only
                STATUS current
                DESCRIPTION "Valid cells transmitted (Output Billing Count)"
                ::= { cellTest 11 }

cellTestMismatchPduCount OBJECT-TYPE
                SYNTAX Integer32
                MAX-ACCESS read-only
                STATUS current
                DESCRIPTION "Number of times Rx payload mismatched with Tx
                             payload."
                ::= { cellTest 12 }

cellTestStatus        OBJECT-TYPE
                SYNTAX INTEGER
                        {
                         running(1),
                         not-running(2)
                        }
                MAX-ACCESS read-only
                STATUS current
                DESCRIPTION "Indicates whether a cellTest test is in progress
                             or not."
                DEFVAL { not-running }
                ::= { cellTest 13 }


cellTestVUNIB OBJECT-TYPE
                SYNTAX INTEGER (0..255)
                MAX-ACCESS read-write
                STATUS current
                DESCRIPTION "VUNI id for testing cell transfer to an I/O card.
                     This field is valid only for ATM interface."
                ::= { cellTest 14 }


-- System Information specific objects

sysInfoTxOneCellTotal OBJECT-TYPE
                SYNTAX Integer32
                MAX-ACCESS read-only
                STATUS current
                DESCRIPTION "Total amount of cells within the transmit one
                             cell pool."
                ::= { sysInfo 1 }

sysInfoTxOneCellUsed OBJECT-TYPE
                SYNTAX Integer32
                MAX-ACCESS read-only
                STATUS current
                DESCRIPTION "Amount of cells currently being used within
                             the transmit one cell pool."
                ::= { sysInfo 2 }

sysInfoTxOneCellHigh OBJECT-TYPE
                SYNTAX Integer32
                MAX-ACCESS read-only
                STATUS current
                DESCRIPTION "High-water mark of cells used within the
                             transmit one cell pool."
                ::= { sysInfo 3 }

sysInfoRxOneCellTotal OBJECT-TYPE
                SYNTAX Integer32
                MAX-ACCESS read-only
                STATUS current
                DESCRIPTION "Total amount of cells within the receive one
                             cell pool."
                ::= { sysInfo 4 }

sysInfoRxOneCellUsed OBJECT-TYPE
                SYNTAX Integer32
                MAX-ACCESS read-only
                STATUS current
                DESCRIPTION "Amount of cells currently being used within
                             the receive one cell pool."
                ::= { sysInfo 5 }

sysInfoRxOneCellHigh OBJECT-TYPE
                SYNTAX Integer32
                MAX-ACCESS read-only
                STATUS current
                DESCRIPTION "High-water mark of cells used within the
                             receive one cell pool."
                ::= { sysInfo 6 }

sysInfoRxMultiCellTotal OBJECT-TYPE
                SYNTAX Integer32
                MAX-ACCESS read-only
                STATUS current
                DESCRIPTION "Total amount of multi-cells within the receive
                             multi-cell pool."
                ::= { sysInfo 7 }

sysInfoRxMultiCellUsed OBJECT-TYPE
                SYNTAX Integer32
                MAX-ACCESS read-only
                STATUS current
                DESCRIPTION "Amount of multi-cells currently being used
                             within the receive multi-cell pool."
                ::= { sysInfo 8 }

sysInfoRxMultiCellHigh OBJECT-TYPE
                SYNTAX Integer32
                MAX-ACCESS read-only
                STATUS current
                DESCRIPTION "High-water mark of multi-cells used within the
                             receive multi-cell pool."
                ::= { sysInfo 9 }

sysInfoMsgPoolTotal OBJECT-TYPE
                SYNTAX Integer32
                MAX-ACCESS read-only
                STATUS current
                DESCRIPTION "Total amount of messages within the message pool."
                ::= { sysInfo 10 }

sysInfoMsgPoolUsed OBJECT-TYPE
                SYNTAX Integer32
                MAX-ACCESS read-only
                STATUS current
                DESCRIPTION "Amount of messages currently being used within
                             the message pool."
                ::= { sysInfo 11 }

sysInfoMsgPoolHigh OBJECT-TYPE
                SYNTAX Integer32
                MAX-ACCESS read-only
                STATUS current
                DESCRIPTION "High-water mark of messages used within the
                             message pool."
                ::= { sysInfo 12 }

sysInfoDiscFreeKBytes OBJECT-TYPE
                SYNTAX Integer32
                MAX-ACCESS read-only
                STATUS current
                DESCRIPTION "Amount of disc free space available in KB's."
                ::= { sysInfo 13 }

sysInfoCpuUtilization1 OBJECT-TYPE
                SYNTAX INTEGER (0..99)
                MAX-ACCESS read-only
                STATUS current
                DESCRIPTION "xx.yy% - cpuUtilization1 is the xx part of it."
                ::= { sysInfo 14 }

sysInfoCpuUtilization2 OBJECT-TYPE
                SYNTAX INTEGER (0..99)
                MAX-ACCESS read-only
                STATUS current
                DESCRIPTION "xx.yy% - cpuUtilization2 is the yy part of it."
                ::= { sysInfo 15 }

sysInfoSysUptime OBJECT-TYPE
                SYNTAX Integer32
                MAX-ACCESS read-only
                STATUS current
                DESCRIPTION "Amount of time cpu has been up in seconds."
                ::= { sysInfo 16 }

sysInfoBadCellRx OBJECT-TYPE
                SYNTAX Integer32
                MAX-ACCESS read-only
                STATUS current
                DESCRIPTION "The number of bad cells (BIP16) received so far."
                ::= { sysInfo 17 }

sysInfoMisaligned OBJECT-TYPE
                SYNTAX Integer32
                MAX-ACCESS read-only
                STATUS current
                DESCRIPTION "The number of misaligned cells received so far."
                ::= { sysInfo 18 }

sysInfoClockAErr OBJECT-TYPE
                SYNTAX INTEGER (0..1)
                MAX-ACCESS read-only
                STATUS current
                DESCRIPTION "Value is 1, TRUE, if the clock on backplane A 
                             is errored, otherwise, the value is 0, FALSE."
                ::= { sysInfo 19 }

sysInfoClockBErr OBJECT-TYPE
                SYNTAX INTEGER (0..1)
                MAX-ACCESS read-only
                STATUS current
                DESCRIPTION "Value is 1, TRUE, if the clock on backplane B 
                             is errored, otherwise, the value is 0, FALSE."
                ::= { sysInfo 20 }

sysInfoBIPAErr        OBJECT-TYPE
                SYNTAX INTEGER (0..1)
                MAX-ACCESS read-only
                STATUS current
                DESCRIPTION "Value is 1, TRUE, if the cell circuit on backplane 
                             A is errored, otherwise, the value is 0, FALSE."
                ::= { sysInfo 21 }

sysInfoBIPBErr        OBJECT-TYPE
                SYNTAX INTEGER (0..1)
                MAX-ACCESS read-only
                STATUS current
                DESCRIPTION "Value is 1, TRUE, if the cell circuit on backplane 
                             B is errored, otherwise, the value is 0, FALSE."
                ::= { sysInfo 22 }

sysInfoDiscTotalKBytes OBJECT-TYPE
                SYNTAX Integer32
                MAX-ACCESS read-only
                STATUS current
                DESCRIPTION "Amount of disc space available in KB's."
                ::= { sysInfo 23 }

sysInfoRAMFreeKBytes OBJECT-TYPE
                SYNTAX Integer32
                MAX-ACCESS read-only
                STATUS current
                DESCRIPTION "Amount of RAM memory available for use in KB's."
                ::= { sysInfo 24 }

sysInfoRAMTotalKBytes OBJECT-TYPE
                SYNTAX Integer32
                MAX-ACCESS read-only
                STATUS current
                DESCRIPTION "Amount of RAM memory available on cpu card in 
                             KB's."
                ::= { sysInfo 25 }

msgPoolViewTable OBJECT-TYPE
                 SYNTAX SEQUENCE OF MsgPoolViewEntry
                 MAX-ACCESS not-accessible
                 STATUS current
                 DESCRIPTION "Table of Msg Pools In the System,
                              Used only for diagnostic purposes"
                 ::= { sysInfo 26 }


primaryCpuHwType OBJECT-TYPE
                  SYNTAX INTEGER {
                                notKnown(1), 
                                version1(2),
                                version2(3)
                               }
                  MAX-ACCESS read-only
                STATUS current
                DESCRIPTION "Indicates the hardware version type of the 
                                primary CPU.
                             version1: 150MHz Saturn13 board supporting 
                                        8MB-64MB Memory.
                             version2: 200MHz Saturn15 board supporting 
                                        64MB-256MB Memory."
                DEFVAL { notKnown }
                ::= { sysInfo 27 }

secondaryCpuHwType OBJECT-TYPE
                  SYNTAX INTEGER {
                                notKnown(1),
                                version1(2),
                                version2(3)
                                }
                  MAX-ACCESS read-only
                STATUS current
                DESCRIPTION "Indicates the hardware version type of the 
                                secondary CPU.
                             version1: 150MHz Saturn13 board supporting 
                                8MB-64MB Memory.
                             version2: 200MHz Saturn15 board supporting 
                                64MB-256MB Memory."
                DEFVAL { notKnown }
                ::= { sysInfo 28 }

msgPoolViewEntry OBJECT-TYPE
                 SYNTAX MsgPoolViewEntry
                 MAX-ACCESS not-accessible
                 STATUS current
                 DESCRIPTION "Row definition of Msg Pool Table"
                 INDEX { msgPoolViewIndex }
                 ::= { msgPoolViewTable 1 }

MsgPoolViewEntry ::= SEQUENCE {
                         msgPoolViewIndex                Integer32,
                        msgPoolViewTskId                Integer32,
                        msgPoolViewTskName                DisplayString,
                        msgPoolViewMsgCmd                Integer32
                 }

msgPoolViewIndex OBJECT-TYPE
                 SYNTAX Integer32
                 MAX-ACCESS not-accessible
                 STATUS current
                 DESCRIPTION "It is the index of the MsgPool array for which
                              the information is requested. Information about
                              Msgs Which are not there in the free pool is
                              returned.A msg is said to be out of the free
                              pool by comparing the signature.
                              The limit being the max number of msgs allowed
                              on the system"
                 ::= { msgPoolViewEntry 1 }

msgPoolViewTskId OBJECT-TYPE
                 SYNTAX Integer32
                 MAX-ACCESS read-only
                 STATUS current
                 DESCRIPTION "Task Id of the Sender of the Particular Msg,
                              This will give the integer value, has to be
                              converted to hex for comparison"
                 ::= { msgPoolViewEntry 2}

msgPoolViewTskName OBJECT-TYPE
                   SYNTAX DisplayString (SIZE(20))
                   MAX-ACCESS read-only
                   STATUS current
                   DESCRIPTION "Task Name of the Sender of the Particular Msg"
                 ::= { msgPoolViewEntry 3}

msgPoolViewMsgCmd OBJECT-TYPE
                  SYNTAX Integer32
                  MAX-ACCESS read-only
                  STATUS current
                  DESCRIPTION "msgCmd being sent by the sending Task"
                 ::= { msgPoolViewEntry 4}


sysInfoDiskCheck OBJECT-TYPE
                  SYNTAX INTEGER {
                                  ok    (1),
                                  error (2)
                                 }
                          
                  MAX-ACCESS read-only
                  STATUS current
                  DESCRIPTION "Indicates the checking status of 
                               the disk in CPU card. "
                  ::= { sysInfo 29 }

switchAlarmStatus        OBJECT-TYPE
                    SYNTAX INTEGER {
                                notAvailable(1),
                                none(2),
                                minor(3),
                                major(4),
                                critical(5)
                                }
                    MAX-ACCESS read-only
                    STATUS current
                    DESCRIPTION "Current status of the alarm on the switch.
                    notAvailable - The alarm status could not be retreived.
                    none - No alarm is present.
                    minor, major, critical - An alarm of the enumerated type
                                             is present"
                    ::= { sysInfo 30 }


-- Ethernet cache configuration group

arp1Table        OBJECT-TYPE
                SYNTAX SEQUENCE OF Arp1Entry
                MAX-ACCESS not-accessible
                STATUS current
                DESCRIPTION "Table of ARP cache data."
                ::= { ethernetConfig 1 }

arp1Entry        OBJECT-TYPE
                SYNTAX Arp1Entry
                MAX-ACCESS not-accessible
                STATUS current
                DESCRIPTION "Row definition for ARP cache."
                INDEX { arp1CardSlot, arp1BridgeGroupNum, arp1IpAddress }
                ::= { arp1Table 1 }

Arp1Entry        ::= SEQUENCE {
                              arp1CardSlot                INTEGER,
                              arp1BridgeGroupNum        INTEGER,
                              arp1IpAddress                IpAddress,
                              arp1PhysicalAddr                OCTET STRING,
                              arp1EntryAge                Integer32
                             }

arp1CardSlot        OBJECT-TYPE
                SYNTAX INTEGER (1..16)
                MAX-ACCESS not-accessible
                STATUS current
                DESCRIPTION "Slot ethernet card is in."
                ::= { arp1Entry 1 }

arp1BridgeGroupNum OBJECT-TYPE
                SYNTAX INTEGER (1..999)
                MAX-ACCESS not-accessible
                STATUS current
                DESCRIPTION "Bridge Group the entry belongs to."
                ::= { arp1Entry 2 }

arp1IpAddress        OBJECT-TYPE
                SYNTAX IpAddress
                MAX-ACCESS not-accessible
                STATUS current
                DESCRIPTION "Entry IP address."
                ::= { arp1Entry 3 }

arp1PhysicalAddr OBJECT-TYPE
                SYNTAX OCTET STRING (SIZE(6))
                MAX-ACCESS read-only
                STATUS current
                DESCRIPTION "Entry physical address."
                ::= { arp1Entry 4 }

arp1EntryAge        OBJECT-TYPE
                SYNTAX Integer32
                MAX-ACCESS read-only
                STATUS current
                DESCRIPTION "Age of cache entry."
                DEFVAL { 0 }
                ::= { arp1Entry 5 }


arp2Table        OBJECT-TYPE
                SYNTAX SEQUENCE OF Arp2Entry
                MAX-ACCESS not-accessible
                STATUS current
                DESCRIPTION "Table of ARP cache data."
                ::= { ethernetConfig 2 }

arp2Entry        OBJECT-TYPE
                SYNTAX Arp2Entry
                MAX-ACCESS not-accessible
                STATUS current
                DESCRIPTION "Row definition for ARP cache."
                INDEX { arp2CardSlot, arp2BridgeGroupNum, arp2PhysicalAddr }
                ::= { arp2Table 1 }

Arp2Entry        ::= SEQUENCE {
                              arp2CardSlot                INTEGER,
                              arp2BridgeGroupNum        INTEGER,
                              arp2PhysicalAddr                OCTET STRING,
                              arp2IpAddress                IpAddress,
                              arp2EntryAge                Integer32
                             }

arp2CardSlot        OBJECT-TYPE
                SYNTAX INTEGER (1..16)
                MAX-ACCESS not-accessible
                STATUS current
                DESCRIPTION "Slot ethernet card is in."
                ::= { arp2Entry 1 }

arp2BridgeGroupNum OBJECT-TYPE
                SYNTAX INTEGER (1..999)
                MAX-ACCESS not-accessible
                STATUS current
                DESCRIPTION "Bridge Group the entry belongs to."
                ::= { arp2Entry 2 }

arp2PhysicalAddr OBJECT-TYPE
                SYNTAX OCTET STRING (SIZE(6))
                MAX-ACCESS not-accessible
                STATUS current
                DESCRIPTION "Entry physical address."
                ::= { arp2Entry 3 }

arp2IpAddress        OBJECT-TYPE
                SYNTAX IpAddress
                MAX-ACCESS read-only
                STATUS current
                DESCRIPTION "Entry IP address."
                ::= { arp2Entry 4 }

arp2EntryAge        OBJECT-TYPE
                SYNTAX Integer32
                MAX-ACCESS read-only
                STATUS current
                DESCRIPTION "Age of cache entry."
                DEFVAL { 0 }
                ::= { arp2Entry 5 }


bridgeCacheTable OBJECT-TYPE
                SYNTAX SEQUENCE OF BridgeCacheEntry
                MAX-ACCESS not-accessible
                STATUS current
                DESCRIPTION "Table of bridge cache data."
                ::= { ethernetConfig 3 }

bridgeCacheEntry OBJECT-TYPE
                SYNTAX BridgeCacheEntry
                MAX-ACCESS not-accessible
                STATUS current
                DESCRIPTION "Row definition for bridge cache."
                INDEX { bridgeCacheCardSlot, bridgeCacheBridgeGroupNum,
                        bridgeCachePhysicalAddr }
                ::= { bridgeCacheTable 1 }

BridgeCacheEntry ::= SEQUENCE {
                              bridgeCacheCardSlot        INTEGER,
                              bridgeCacheBridgeGroupNum        INTEGER,
                              bridgeCachePhysicalAddr        OCTET STRING,
                              bridgeCacheType                INTEGER,
                              bridgeCacheSourcePort        INTEGER,
                              bridgeCacheEntryAge        Integer32
                             }

bridgeCacheCardSlot OBJECT-TYPE
                SYNTAX INTEGER (1..16)
                MAX-ACCESS not-accessible
                STATUS current
                DESCRIPTION "Slot ethernet card is in."
                ::= { bridgeCacheEntry 1 }

bridgeCacheBridgeGroupNum OBJECT-TYPE
                SYNTAX INTEGER (1..999)
                MAX-ACCESS not-accessible
                STATUS current
                DESCRIPTION "Bridge Group the entry belongs to."
                ::= { bridgeCacheEntry 2 }

bridgeCachePhysicalAddr OBJECT-TYPE
                SYNTAX OCTET STRING (SIZE(6))
                MAX-ACCESS not-accessible
                STATUS current
                DESCRIPTION "Entry physical address."
                ::= { bridgeCacheEntry 3 }

bridgeCacheType        OBJECT-TYPE
                SYNTAX INTEGER {
                                learned(1),
                                permanent(2),
                                policy(3)
                               }
                MAX-ACCESS read-only
                STATUS current
                DESCRIPTION "Type of Entry."
                DEFVAL { learned }
                ::= { bridgeCacheEntry 4 }

bridgeCacheSourcePort OBJECT-TYPE
                SYNTAX INTEGER (1..75)
                MAX-ACCESS read-only
                STATUS current
                DESCRIPTION "Port entry was obtained from."
                ::= { bridgeCacheEntry 5 }

bridgeCacheEntryAge OBJECT-TYPE
                SYNTAX Integer32
                MAX-ACCESS read-only
                STATUS current
                DESCRIPTION "Age of cache entry."
                ::= { bridgeCacheEntry 6 }


-- Alarm card configuration group

alarmStatusInputBitmap OBJECT-TYPE
                SYNTAX OCTET STRING (SIZE(2))
                MAX-ACCESS read-only
                STATUS current
                DESCRIPTION "Remote status from external device.
                             bit = 0  closed,
                             bit = 1  open,
                
                             LSB 15 bits represent 15 external inputs.
                             MSB bit 15 is always 0."
                ::= { alarmConfig 1 }

alarmStatusOutputBitmap OBJECT-TYPE
                SYNTAX OCTET STRING (SIZE(1))
                MAX-ACCESS read-write
                STATUS current
                DESCRIPTION "Control output for alarm card.
                             bit = 0  deactivated,
                             bit = 1  activated,
                
                             LSB 4 bits represent 4 external outputs.
                             Bit 0 through bit 3 is output 1 through 4
                             Control output 4 will be activated upon
                             power failure."
                DEFVAL { 0 }
                ::= { alarmConfig 2 }

alarmSeverityLevelBitmap OBJECT-TYPE
                SYNTAX OCTET STRING (SIZE(1))
                MAX-ACCESS read-write
                STATUS current
                DESCRIPTION "Alarm severity level.
                             bit = 0  noAlarm,
                             bit = 1  Alarm present,
                
                             LSB 3 bits represent severity levels.
                             bit 0 = Minor Alarm,
                             bit 1 = Major Alarm,
                             bit 2 = Critical Alarm."
                DEFVAL { 0 }
                ::= { alarmConfig 3 }

alarmAcoStatusBitmap OBJECT-TYPE
                SYNTAX OCTET STRING (SIZE(1))
                MAX-ACCESS read-only
                STATUS current
                DESCRIPTION "Audio alarm status.
                             bit = 0  No alarm cutoff,
                             bit = 1  Alarm cutoff,
                
                             LSB 3 bits represent audio alarms.
                             bit 0 = Local alarm cutoff,
                             bit 1 = remote alarm cutoff,
                             bit 2 = composite alarm cutoff status."
                ::= { alarmConfig 4 }


-- system test configuration group

oamTest                OBJECT IDENTIFIER ::= { sysTest 1 }

oamTestIfB        OBJECT-TYPE
                SYNTAX IntfIndex
                MAX-ACCESS read-write
                STATUS current
                DESCRIPTION "Interface index used for starting loopback test.
                             Number value is interpreted as an interface of the 
                             form, SSPPCCC, where SS is the card slot, PP is 
                             the port number, and CCC is the channel number."
                ::= { oamTest 1 }

oamTestVpiB         OBJECT-TYPE
                SYNTAX INTEGER (0..4095)
                MAX-ACCESS read-write
                STATUS current
                DESCRIPTION "VPI value under testing for oam loopback test.
                             Valid range is a number between 0 and 4095."
                ::= { oamTest 2 }

oamTestVciB         OBJECT-TYPE
                SYNTAX INTEGER (0..65535)
                MAX-ACCESS read-write
                STATUS current
                DESCRIPTION "VCI value under testing for oam loopback test.
                             Valid range is a number between 0 and 65535."
                ::= { oamTest 3 }

oamTestStatus        OBJECT-TYPE
                SYNTAX INTEGER  {
                                not-running(1),
                                running(2),
                                successful(3),
                                failure(4),
                                timedout(5),
                                waiting-for-response(6)
                                }
                MAX-ACCESS read-only
                STATUS current
                DESCRIPTION "Inidcates the current status of oam test."
                DEFVAL { not-runnin }
                ::= { oamTest 4 }

oamTestAction        OBJECT-TYPE
                SYNTAX INTEGER {
                                sendLoopback(1),
                                sendContinuously(2),
                                stopTest(3),
                                resetTxCount(4),
                                resetRxCount(5),
                                resetMismatchCount(6)
                               }
                MAX-ACCESS read-write
                STATUS current
                DESCRIPTION "Test action to be performed."
                DEFVAL { sendLoopback }
                ::= { oamTest 5 }

oamTestTxCount        OBJECT-TYPE
                SYNTAX Integer32
                MAX-ACCESS read-only
                STATUS current
                DESCRIPTION "Valid cells transmitted."
                ::= { oamTest 6 }

oamTestRxCount        OBJECT-TYPE
                SYNTAX Integer32
                MAX-ACCESS read-only
                STATUS current
                DESCRIPTION "Valid cells received."
                ::= { oamTest 7 }

oamTestMismatchCount OBJECT-TYPE
                SYNTAX Integer32
                MAX-ACCESS read-only
                STATUS current
                DESCRIPTION "Number of times Rx correlation tag is mismatched
                             with the Tx correlation tag."
                ::= { oamTest 8 }

oamTestLocationID OBJECT-TYPE
                SYNTAX OCTET STRING (SIZE(16))
                MAX-ACCESS read-write
                STATUS current
                DESCRIPTION "Location ID of the ATM Node where the loopback is 
                             to occur."
                DEFVAL { 'FFFFFFFFFFFFFFFFFFFFFFFFFFFFFFFF'H }
                ::= { oamTest 9 }

oamTestLoopbackType OBJECT-TYPE
                SYNTAX INTEGER {
                                end-to-end(1),
                                segment-endpoint(2),
                                next-connection-point(3),
                                specific-location(4)
                                }
                MAX-ACCESS read-write
                STATUS current
                DESCRIPTION "OAM Loopback type. Determines whether to 
                        send ete or segment loopback cell, and the value
                        of location Id field in the cell. Only for
                        specific-location value, user specified locationId 
                        field value taken into account."
                DEFVAL { end-to-end }
                ::= { oamTest 10 }

-- sysTest 2 

oamActDeactTable OBJECT-TYPE
                SYNTAX SEQUENCE OF OamActDeactEntry
                  MAX-ACCESS not-accessible
                  STATUS current
                  DESCRIPTION "Table of oam activate and deactivate functions"
                  ::= { sysTest 2 }

oamActDeactEntry OBJECT-TYPE
                  SYNTAX OamActDeactEntry
                MAX-ACCESS not-accessible 
                STATUS current
                DESCRIPTION "Row definition of oam activate and deactivate"
                INDEX { oamActDeactIfB, oamActDeactVpiB, oamActDeactVciB}
                ::= { oamActDeactTable 1 }

OamActDeactEntry ::= SEQUENCE {
                  oamActDeactIfB   IntfIndex,
                  oamActDeactVpiB  INTEGER,
                  oamActDeactVciB  INTEGER,
                  oamActDeactFuncType  INTEGER,
                 oamActDeactDirFlow  INTEGER,
                  oamActDeactFlowType     INTEGER,
                  oamActDeactBlkSizeAB  INTEGER,
                  oamActDeactBlkSizeBA  INTEGER,
                  oamActDeactStsSrcPointEteCC  INTEGER,
                  oamActDeactStsSnkPointEteCC  INTEGER,
                  oamActDeactRsltPrevReq INTEGER,
                  oamActDeactRowStatus  RowStatus,
                oamActDeactStsSrcPointEtePM  INTEGER,
                oamActDeactStsSnkPointEtePM  INTEGER,
                oamActDeactStsSrcPointEtePMBR  INTEGER,
                oamActDeactStsSnkPointEtePMBR  INTEGER,
                oamActDeactBRBlockError  INTEGER,
                oamActDeactBRLostInsertedCell   INTEGER,
                oamActDeactBRMisInsertedCell INTEGER,
                oamActDeactStsSrcPointSegPM          INTEGER,
                    oamActDeactStsSnkPointSegPM          INTEGER,
                  oamActDeactStsSrcPointSegPMBR          INTEGER,
                    oamActDeactStsSnkPointSegPMBR          INTEGER,
                  oamActDeactStsSrcPointSegCC          INTEGER,
                    oamActDeactStsSnkPointSegCC          INTEGER
                }


oamActDeactIfB OBJECT-TYPE
                  SYNTAX IntfIndex
                  MAX-ACCESS not-accessible
                  STATUS current
                DESCRIPTION "Interface index for an  OAM CC connection.  
                        Number value is interpreted as an interface of the 
                        form, SSPPCCC, where SS is the card slot, PP 
                        is the port number, and CCC is the channel number."
                  ::= { oamActDeactEntry 1 }

oamActDeactVpiB OBJECT-TYPE
                  SYNTAX INTEGER (0..4095)
                  MAX-ACCESS not-accessible
                  STATUS current
                  DESCRIPTION "VPI value for an  oam CC connection.  
                            Valid range is a number between 0 and 4095."
                  ::= { oamActDeactEntry 2 }

oamActDeactVciB OBJECT-TYPE
                  SYNTAX INTEGER (0..65535)
                MAX-ACCESS not-accessible
                STATUS current
                DESCRIPTION "VCI value for oam CC connection.  
                        Valid range is a number between 0 and 65535."
                  ::= { oamActDeactEntry 3 }

oamActDeactFuncType OBJECT-TYPE
                  SYNTAX INTEGER  {
                                    fpm-and-br(1),
                                    fpm-only(2),
                                continuity-check(3),
                                pmbr-and-cc(4),
                                pm-and-cc(5)
                                }
                MAX-ACCESS read-write
                STATUS current
                DESCRIPTION "OAM Function type represents the OAM flow for
                        activation or deactivattion for this connection.
                        the possible function types activated in one connection 
                        are :
                        fpm-and-br : forward performance monitoring/backward 
                                     reporting
                        fpm-only : forward performance monitoring
                        continuity-check : continuity check
                        pmbr-and-cc : forward performance monitoring/backward 
                                      reporting and continuity check
                        pm-and-cc : forward performance monitoring and 
                                    continuity check"
                DEFVAL { continuity-check }
                ::= { oamActDeactEntry 4 }

oamActDeactDirFlow OBJECT-TYPE
                  SYNTAX INTEGER  {
                                    towards-far-end(1),
                                    towards-near-end(2),
                                    both-way(3)
                                    }
                  MAX-ACCESS read-write
                  STATUS current
                  DESCRIPTION "The direction in which cells will be 
                                transmitted."
                  DEFVAL { towards-near-end }
                  ::= { oamActDeactEntry 5 }

oamActDeactFlowType OBJECT-TYPE
                  SYNTAX INTEGER  {
                                end-to-end(1),
                                segment(2)
                                }
                  MAX-ACCESS read-write
                  STATUS current
                DESCRIPTION "Flow Type."
                DEFVAL { end-to-end }
                  ::= { oamActDeactEntry 6 }

oamActDeactBlkSizeAB OBJECT-TYPE
                  SYNTAX INTEGER  {
                                size128(1),
                                size256(2),
                                size512(3),
                                size1024(4),
                                size4096(5),
                                size8192(6),
                                size16384(7),
                                size32768(8),
                                size2048(9)
                                }
                  MAX-ACCESS read-write
                  STATUS current
                  DESCRIPTION "Block Size A-B represents the size of 
                        the block of user cells taken into consideration 
                        for performance monitoring in A-B direction."
                  DEFVAL { size1024 }
                  ::= { oamActDeactEntry 7 }

oamActDeactBlkSizeBA OBJECT-TYPE
                SYNTAX INTEGER  {
                                size128(1),
                                size256(2),
                                size512(3),
                                size1024(4),
                                size4096(5),
                                size8192(6),
                                size16384(7),
                                size32768(8),
                                size2048(9)
                                }
                MAX-ACCESS read-write
                STATUS current
                DESCRIPTION "Block Size A-B is the size of the block of 
                        user cells taken into consideration for 
                        performance monitoring in B-A direction."
                DEFVAL { size1024 }
                ::= { oamActDeactEntry 8 }

oamActDeactStsSrcPointEteCC OBJECT-TYPE
                SYNTAX INTEGER  {
                                activated(1),
                                deactivated(2),
                                waitActConfirm(3),
                                waitDeactConfirm(4)
                                }
                MAX-ACCESS read-only 
                STATUS current
                DESCRIPTION "Source point showed in the status portion 
                        displays the current status of Activation or 
                        Deactivation request for the source point  "
                DEFVAL { deactivated }
                ::= { oamActDeactEntry 9 }

oamActDeactStsSnkPointEteCC OBJECT-TYPE
                SYNTAX INTEGER  {
                                activated(1),
                                deactivated(2),
                                waitActConfirm(3),
                                waitDeactConfirm(4)
                                }
                MAX-ACCESS read-only
                STATUS current
                DESCRIPTION "Sink point showed in the status portion 
                        displays the current status of Activation 
                        or Deactivation request for the sink point"
                DEFVAL { deactivated }
                ::= { oamActDeactEntry 10 }

oamActDeactRsltPrevReq OBJECT-TYPE
                SYNTAX INTEGER  {
                                denied(1),
                                timedout(2),
                                locResrcUnavl(3),
                                oamUnsupported(4),
                                reqCancelled(5),
                                funcNotImplemented(6),
                                none(7),
                                successful(8)
                                }
                MAX-ACCESS read-only
                STATUS current
                DESCRIPTION "Cause of Failure shows the reasons of failure 
                        of the last activation request on this connection 
                        form the local user."
                DEFVAL { none }
                ::= { oamActDeactEntry 11 }

oamActDeactRowStatus OBJECT-TYPE
                  SYNTAX RowStatus
                  MAX-ACCESS read-write
                  STATUS current
                  DESCRIPTION "row status"
                  ::= { oamActDeactEntry 12 }

oamActDeactStsSrcPointEtePM OBJECT-TYPE
                SYNTAX INTEGER  {
                                activated(1),
                                deactivated(2),
                                waitActConfirm(3),
                                waitDeactConfirm(4)
                                }
                MAX-ACCESS read-only 
                STATUS current
                DESCRIPTION "Source point showed in the status portion 
   displays the current status of Activation or 
   Deactivation request for the source point  "
                DEFVAL { deactivated }
                ::= { oamActDeactEntry 13}

oamActDeactStsSnkPointEtePM OBJECT-TYPE
                SYNTAX INTEGER  {
                                activated(1),
                                deactivated(2),
                                waitActConfirm(3),
                                  waitDeactConfirm(4)
                                }
                MAX-ACCESS read-only
                STATUS current
                DESCRIPTION "Sink point showed in the status portion 
                           displays the current status of Activation 
                           or Deactivation request for the sink point"
                DEFVAL { deactivated }
                ::= { oamActDeactEntry 14 }

oamActDeactStsSrcPointEtePMBR OBJECT-TYPE
                SYNTAX INTEGER  {
                                activated(1),
                                deactivated(2),
                                waitActConfirm(3),
                                waitDeactConfirm(4)
                                }
                MAX-ACCESS read-only 
                STATUS current
                DESCRIPTION "Source point showed in the status portion 
                           displays the current status of Activation or 
                        Deactivation request for the source point  "
                DEFVAL { deactivated }
                ::= { oamActDeactEntry 15}

oamActDeactStsSnkPointEtePMBR OBJECT-TYPE
                SYNTAX INTEGER  {
                                activated(1),
                                deactivated(2),
                                waitActConfirm(3),
                                  waitDeactConfirm(4)
                                }
                MAX-ACCESS read-only
                STATUS current
                DESCRIPTION "Sink point showed in the status portion 
                           displays the current status of Activation 
                           or Deactivation request for the sink point"
                DEFVAL { deactivated }
                ::= { oamActDeactEntry 16 }

oamActDeactBRBlockError  OBJECT-TYPE
                  SYNTAX INTEGER (0..32768)
                MAX-ACCESS read-only
                STATUS current
                DESCRIPTION "Backware reporting Block error for PM connection.
                        Valid range is a number between 0 and 32768."
                ::= { oamActDeactEntry 17 }

oamActDeactBRLostInsertedCell  OBJECT-TYPE
                SYNTAX INTEGER (0..32768)
                MAX-ACCESS read-only
                STATUS current
                DESCRIPTION "Backware reporting lost inserted cell  for 
                        PM connection.  Valid range is a number between 
                        0 and 32768."
                ::= { oamActDeactEntry 18}

oamActDeactBRMisInsertedCell  OBJECT-TYPE
                SYNTAX INTEGER (0..32768)
                MAX-ACCESS read-only
                STATUS current
                DESCRIPTION "Backware reporting misinserted cell  for 
                PM connection.  Valid range is a number between 0 
                and 32768."
                ::= { oamActDeactEntry 19}

oamActDeactStsSrcPointSegPM OBJECT-TYPE
                SYNTAX INTEGER  {
                                activated(1),
                                deactivated(2),
                                waitActConfirm(3),
                                  waitDeactConfirm(4)
                                }
                MAX-ACCESS read-only 
                STATUS current
                DESCRIPTION "Source point showed in the status portion 
                                displays the current status of Activation or 
                                Deactivation request for the source point  "
                DEFVAL { deactivated }
                ::= { oamActDeactEntry 20}

oamActDeactStsSnkPointSegPM OBJECT-TYPE
                SYNTAX INTEGER  {
                                activated(1),
                                deactivated(2),
                                waitActConfirm(3),
                                  waitDeactConfirm(4)
                                }
                MAX-ACCESS read-only
                STATUS current
                DESCRIPTION "Sink point showed in the status portion 
                                displays the current status of Activation 
                                or Deactivation request for the sink point"
                DEFVAL { deactivated }
                ::= { oamActDeactEntry 21}

oamActDeactStsSrcPointSegPMBR OBJECT-TYPE
                SYNTAX INTEGER  {
                                activated(1),
                                deactivated(2),
                                waitActConfirm(3),
                                  waitDeactConfirm(4)
                                }
                MAX-ACCESS read-only 
                STATUS current
                DESCRIPTION "Source point showed in the status portion 
                                displays the current status of Activation or 
                                Deactivation request for the source point  "
                DEFVAL { deactivated }
                ::= { oamActDeactEntry 22}

oamActDeactStsSnkPointSegPMBR OBJECT-TYPE
                SYNTAX INTEGER  {
                                activated(1),
                                deactivated(2),
                                waitActConfirm(3),
                                  waitDeactConfirm(4)
                                }
                MAX-ACCESS read-only
                STATUS current
                DESCRIPTION "Sink point showed in the status portion 
                                displays the current status of Activation 
                                or Deactivation request for the sink point"
                DEFVAL { deactivated }
                ::= { oamActDeactEntry 23 }

oamActDeactStsSrcPointSegCC OBJECT-TYPE
                SYNTAX INTEGER  {
                                activated(1),
                                deactivated(2),
                                waitActConfirm(3),
                                    waitDeactConfirm(4)
                                }
                MAX-ACCESS read-only 
                STATUS current
                DESCRIPTION "Source point showed in the status portion 
                                displays the current status of Activation or 
                                Deactivation request for the source point  "
                DEFVAL { deactivated }
                ::= { oamActDeactEntry 24 }

oamActDeactStsSnkPointSegCC OBJECT-TYPE
                SYNTAX INTEGER  {
                                activated(1),
                                deactivated(2),
                                waitActConfirm(3),
                                    waitDeactConfirm(4)
                                }
                MAX-ACCESS read-only
                STATUS current
                DESCRIPTION "Sink point showed in the status portion 
                                displays the current status of Activation 
                                or Deactivation request for the sink point"
                DEFVAL { deactivated }
                ::= { oamActDeactEntry 25 }



-- sysTest 3

oamLoopbackTable OBJECT-TYPE
                SYNTAX SEQUENCE OF OamLoopbackEntry
                MAX-ACCESS not-accessible
                STATUS current
                DESCRIPTION "Table of oam loopback functions"
                ::= { sysTest 3 }

oamLoopbackEntry OBJECT-TYPE
                SYNTAX OamLoopbackEntry
                MAX-ACCESS not-accessible
                STATUS current
                DESCRIPTION "Row definition of oam loop back"
                INDEX { oamLpbkIfB, oamLpbkVpiB, oamLpbkVciB}
                ::= { oamLoopbackTable 1 }

OamLoopbackEntry ::= SEQUENCE {
                oamLpbkIfB   IntfIndex,
                oamLpbkVpiB  INTEGER,
                oamLpbkVciB  INTEGER,
                oamLoopbackType   INTEGER,
                oamLpbkLocationID OCTET STRING,
                oamLpbkAction     INTEGER,
                oamLpbkStatus     INTEGER,
                oamLpbkTxCount    Integer32,
                oamLpbkRxCount    Integer32,
                oamLpbkMismatchCount   Integer32,
                oamLpbkTimeout INTEGER
                }

oamLpbkIfB      OBJECT-TYPE
                SYNTAX IntfIndex
                MAX-ACCESS not-accessible
                STATUS current
                DESCRIPTION "Interface index used for starting loopback
                        test.  Number value is interpreted as an interface 
                        of the form, SSPPCCC, where SS is the card slot, PP 
                        is the port number, and CCC is the channel number."
                ::= { oamLoopbackEntry 1 }

oamLpbkVpiB     OBJECT-TYPE
                SYNTAX INTEGER (0..4095)
                MAX-ACCESS not-accessible
                STATUS current
                DESCRIPTION "VPI value under testing for oam loopback test.
                             Valid range is a number between 0 and 4095."
                ::= { oamLoopbackEntry 2 }

oamLpbkVciB     OBJECT-TYPE
                SYNTAX INTEGER (0..65535)
                MAX-ACCESS not-accessible
                STATUS current
                DESCRIPTION "VCI value under testing for oam loopback test.
                             Valid range is a number between 0 and 65535."
                ::= {oamLoopbackEntry  3 }

oamLoopbackType OBJECT-TYPE
                SYNTAX INTEGER {
                                end-to-end(1),
                                segment-endpoint(2),
                                next-connection-point(3),
                                specific-location(4)
                                }
                MAX-ACCESS read-write
                STATUS current
                DESCRIPTION "OAM Loopback type. Determines whether to
                        send ete or segment loopback cell, and the value
                        of location Id field in the cell. Only for
                        specific-location value, user specified locationId
                        field value taken into account."
                DEFVAL { end-to-end }
                ::= { oamLoopbackEntry 4 }

oamLpbkLocationID OBJECT-TYPE
                SYNTAX OCTET STRING (SIZE(16))
                MAX-ACCESS read-write
                STATUS current
                DESCRIPTION "Location ID of the ATM Node where the 
loopback is
                             to occur."
                DEFVAL { 'FFFFFFFFFFFFFFFFFFFFFFFFFFFFFFFF'H }
                ::= { oamLoopbackEntry  5 }

oamLpbkAction   OBJECT-TYPE
                SYNTAX INTEGER {
                                sendLoopbackOnce(1),
                                sendLoopbackContinuously(2),
                                stopTest(3),
                                resetStats(4)
                               }
                MAX-ACCESS read-write
                STATUS current
                DESCRIPTION "Test action to be performed.
                             endLoopbackContinuously is not used. "
                DEFVAL { sendLoopbackOnce }
                ::= { oamLoopbackEntry  6 }

oamLpbkStatus   OBJECT-TYPE
                SYNTAX INTEGER  {
                                inactive(1),
                                waiting-for-response(2),
                                successful(3),
                                timedout(4)
                                }
                MAX-ACCESS read-only
                STATUS current
                DESCRIPTION "Inidcates the current status of oam test."
                DEFVAL { inactive}
                ::= { oamLoopbackEntry  7}



oamLpbkTxCount  OBJECT-TYPE
                SYNTAX Integer32
                MAX-ACCESS read-only
                STATUS current
                DESCRIPTION "Valid cells transmitted."
                ::= { oamLoopbackEntry  8 }

oamLpbkRxCount  OBJECT-TYPE
                SYNTAX Integer32
                MAX-ACCESS read-only
                STATUS current
                DESCRIPTION "Valid cells received."
                ::= { oamLoopbackEntry  9 }

oamLpbkMismatchCount OBJECT-TYPE
                SYNTAX Integer32
                MAX-ACCESS read-only
                STATUS current
                DESCRIPTION "Number of times Rx correlation tag is 
                        mismatched with the Tx correlation tag."
                ::= { oamLoopbackEntry  10 }

oamLpbkTimeout  OBJECT-TYPE
                SYNTAX Integer32
                MAX-ACCESS read-only
                STATUS current
                DESCRIPTION "number of time out "
                ::= { oamLoopbackEntry  11 }


-- Vipr Router Configuration Group
 
viprRouterConfigTable  OBJECT-TYPE
                SYNTAX SEQUENCE OF ViprRouterConfigEntry
                MAX-ACCESS not-accessible
                STATUS current
                DESCRIPTION "Table of Vipr Router Instance Information"
                ::= { viprConfig 1 }
 
viprRouterConfigEntry  OBJECT-TYPE
                SYNTAX ViprRouterConfigEntry
                MAX-ACCESS not-accessible
                STATUS current
                DESCRIPTION " definition for VIPR Route instance attributes"
                INDEX { viprSlot, viprRouterId }
                ::= { viprRouterConfigTable 1 }
 
ViprRouterConfigEntry  ::= SEQUENCE {
                viprSlot                        Integer32,
                viprRouterId                    INTEGER,
                viprRouterName                  DisplayString,
                viprRouterNoOfInterfaces        INTEGER,
                viprRouterNoOfRoutes            INTEGER,
                viprRouterAdminStatus           INTEGER,
                viprRouterOperStatus            INTEGER,
                viprRouterInitTmr               Integer32,
                viprRouterDisabWarnTmr          Integer32,
                viprRouterShutDwnWarnTmr        Integer32,
                viprRouterDisableWarning        INTEGER,
                viprRouterDisableReason         INTEGER,
                viprRouterRowStatus             RowStatus
                }
 
viprSlot        OBJECT-TYPE
                SYNTAX Integer32
                MAX-ACCESS not-accessible
                STATUS current
                DESCRIPTION "The slot number of the Virtual Router card (SS)"
                ::= { viprRouterConfigEntry 1 }
 
viprRouterId    OBJECT-TYPE
                SYNTAX INTEGER(1..6)
                MAX-ACCESS not-accessible
                STATUS current
                DESCRIPTION "A unique Id for the Router Instance in a router card"
                ::= { viprRouterConfigEntry 2 }
 
viprRouterName  OBJECT-TYPE
                SYNTAX DisplayString (SIZE(32))
                MAX-ACCESS read-write
                STATUS current
                DESCRIPTION "The ASCII name of the Router Instance"
                ::= { viprRouterConfigEntry 3 }
 
viprRouterNoOfInterfaces OBJECT-TYPE
                SYNTAX INTEGER (1..99)
                MAX-ACCESS read-only
                STATUS current
                DESCRIPTION "This variable describes the no of interfaces
                             defined in the Router Instance"
                DEFVAL { 1 }
                ::= { viprRouterConfigEntry 4 }
 
viprRouterNoOfRoutes OBJECT-TYPE
                SYNTAX INTEGER (1..1024)
                MAX-ACCESS read-only
                STATUS current
                DESCRIPTION "This variable describes the no of static routes
                             defined in the Router Instance"
                DEFVAL { 1 }
                ::= { viprRouterConfigEntry 5 }
 
viprRouterAdminStatus       OBJECT-TYPE
                SYNTAX INTEGER  {
                       outOfService(1),
                       inService(2)
                       }
                MAX-ACCESS read-write
                STATUS current
                DESCRIPTION "This variable represents the various X.731 states
                             the Router state machine can take Administartively"
                DEFVAL { outOfService }
                ::= { viprRouterConfigEntry 6 }
 
viprRouterOperStatus       OBJECT-TYPE
                SYNTAX INTEGER  {
                       outOfService(1),
                       inService(2),
                       unlocked-Init(3),
                       unlocked-Disable(4),
                       locked-Shutting(5)
                       }
                MAX-ACCESS read-only
                STATUS current
                DESCRIPTION "This variable represents the various X.731 states
                             the Router state machine can take operationally"
                DEFVAL { outOfService }
                ::= { viprRouterConfigEntry 7 }
 
viprRouterInitTmr OBJECT-TYPE
                SYNTAX Integer32
                MAX-ACCESS read-write
                STATUS current
                DESCRIPTION "This variable describes the waiting period in
                             the locked-Init state before moving onto
                             locked-Diable state."
                DEFVAL { 192 }
                ::= { viprRouterConfigEntry 8 }
 
viprRouterDisabWarnTmr OBJECT-TYPE
                SYNTAX Integer32
                MAX-ACCESS read-write
                STATUS current
                DESCRIPTION "This variable describes the periodicity in which
                             the error messages are to be flashed when the
                             system is in unlocked-Disable state."
                DEFVAL { 36000 }
                ::= { viprRouterConfigEntry 9 }
 
viprRouterShutDwnWarnTmr OBJECT-TYPE
                SYNTAX Integer32
                MAX-ACCESS read-write
                STATUS current
                DESCRIPTION "This variable describes the periodicity in which
                             the error messages are to be flashed when the
                             system is in locked-Shutting state."
                DEFVAL { 36000 }
                ::= { viprRouterConfigEntry 10 }
 
 
viprRouterDisableWarning OBJECT-TYPE
                SYNTAX INTEGER {
                       enabled(1),
                       disabled(2)
                       }
                MAX-ACCESS read-write
                STATUS current
                DESCRIPTION "This variable when disabled will mask all the
                             warning messages."
                DEFVAL { enabled }
                ::= { viprRouterConfigEntry 11 }
 
viprRouterDisableReason OBJECT-TYPE
                SYNTAX INTEGER {
                       none(1),
                       manual(2),
                       automatic(3)
                       }
                MAX-ACCESS read-only
                STATUS current
                DESCRIPTION "This variable describes the reason why the Router
                             in the unlocked-Disabled state."
                DEFVAL { none }
                ::= { viprRouterConfigEntry 12 }

viprRouterRowStatus      OBJECT-TYPE
                SYNTAX RowStatus
                MAX-ACCESS read-write
                STATUS current
                DESCRIPTION "row status"
                ::= { viprRouterConfigEntry 13 }

-- Vipr Interface Configuration Group
 
viprIntfConfigTable  OBJECT-TYPE
                SYNTAX SEQUENCE OF ViprIntfConfigEntry
                MAX-ACCESS not-accessible
                STATUS current
                DESCRIPTION "Table of Vipr Interface Config Information"
                ::= { viprConfig 2 }
 
viprIntfConfigEntry  OBJECT-TYPE
                SYNTAX ViprIntfConfigEntry
                MAX-ACCESS not-accessible
                STATUS current
                DESCRIPTION " definition for VIPR interface attributes"
                INDEX { viprSlot, viprRouterId, viprIntfId }
                ::= { viprIntfConfigTable 1 }
 
ViprIntfConfigEntry  ::= SEQUENCE {
                viprIntfId                      Integer32,
                viprIntfIPAddress               IpAddress,
                viprIntfIPNetMask               IpAddress,
                viprIntfAdminStatus             INTEGER,
                viprIntfOperStatus              INTEGER,
                viprIntfInitTmr                 Integer32,
                viprIntfDisabWarnTmr            Integer32,
                viprIntfShutDwnWarnTmr          Integer32,
                viprIntfDisableWarning          INTEGER,
                viprIntfDisableReason           INTEGER,
                viprIntfRipVersion              INTEGER,
                viprIntfRipMode                 INTEGER,
                viprIntfRowStatus               RowStatus,
                viprIntfRipLineType             INTEGER,
                viprIntfAuthPasswd              DisplayString
                }
 
 
viprIntfId      OBJECT-TYPE
                SYNTAX Integer32(1..16)
                MAX-ACCESS not-accessible
                STATUS current
                DESCRIPTION "A unique Id for the Interface in a router instance"
                ::= { viprIntfConfigEntry 1 }
 
viprIntfIPAddress   OBJECT-TYPE
                SYNTAX IpAddress
                MAX-ACCESS read-write
                STATUS current
                DESCRIPTION "The IP address of the entrprise network to which the
                             interface is attached to"
                ::= { viprIntfConfigEntry 2 }
 
viprIntfIPNetMask   OBJECT-TYPE
                SYNTAX IpAddress
                MAX-ACCESS read-write
                STATUS current
                DESCRIPTION "The IP Subnet Mask of the entrprise network to which 
                             the interface is attached to"
                ::= { viprIntfConfigEntry 3 }
 
 
viprIntfAdminStatus       OBJECT-TYPE
                SYNTAX INTEGER  {
                       outOfService(1),
                       inService(2)
                       }
 
                MAX-ACCESS read-write
                STATUS current
                DESCRIPTION "This variable represents the various X.731 states
                             the Interfce statemachine can take Administratively"
                DEFVAL { outOfService }
                ::= { viprIntfConfigEntry 4 }


viprIntfOperStatus       OBJECT-TYPE
                SYNTAX INTEGER  {
                       outOfService(1),
                       inService(2),
                       unlocked-Init(3),
                       unlocked-Disable(4),
                       locked-Shutting(5)
                       }
 
                MAX-ACCESS read-only
                STATUS current
                DESCRIPTION "This variable represents the various X.731 states
                             the Interfce statemachine can take operationally"
                DEFVAL { outOfService }
                ::= { viprIntfConfigEntry 5 }
 
viprIntfInitTmr OBJECT-TYPE
                SYNTAX Integer32
                MAX-ACCESS read-write
                STATUS current
                DESCRIPTION "This variable describes the waiting period in
                             the locked-Init state before moving onto
                             locked-Diable state."
                DEFVAL { 192 }
                ::= { viprIntfConfigEntry 6 }
 
viprIntfDisabWarnTmr OBJECT-TYPE
                SYNTAX Integer32
                MAX-ACCESS read-write
                STATUS current
                DESCRIPTION "This variable describes the periodicity in which
                             the error messages are to be flashed when the
                             system is in unlocked-Disable state."
                DEFVAL { 18000 }
                ::= { viprIntfConfigEntry 7 }
 
viprIntfShutDwnWarnTmr OBJECT-TYPE
                SYNTAX Integer32
                MAX-ACCESS read-write
                STATUS current
                DESCRIPTION "This variable describes the periodicity in which
                             the error messages are to be flashed when the
                             system is in locked-Shutting state."
                DEFVAL { 18000 }
                ::= { viprIntfConfigEntry 8 }
 
 
viprIntfDisableWarning OBJECT-TYPE
                SYNTAX INTEGER {
                       enabled(1),
                       disabled(2)
                       }
                MAX-ACCESS read-write
                STATUS current
                DESCRIPTION "This variable when disabled will mask all the
                             Disable warning messages."
                DEFVAL { enabled }
                ::= { viprIntfConfigEntry 9 }
 
viprIntfDisableReason OBJECT-TYPE
                SYNTAX INTEGER {
                       none(1),
                       intfDisabled(2),
                       routDisabled(3)
                       }
                MAX-ACCESS read-only
                STATUS current
                DESCRIPTION "This variable describes the reason why the Interface
                             in the unlocked-Disabled state."
                DEFVAL { none }
                ::= { viprIntfConfigEntry 10 }
 
viprIntfRipVersion  OBJECT-TYPE
                SYNTAX INTEGER {
                       version-1(1),
                       version-2(2)
                       }
                MAX-ACCESS read-write
                STATUS current
                DESCRIPTION "This specifies the version of RIP that interface supports."
                DEFVAL { version-1 }
                ::= { viprIntfConfigEntry 11 }
 
viprIntfRipMode  OBJECT-TYPE
                SYNTAX INTEGER {
                       disabled(1),
                       active(2),
                       passive(3)
                       }
                MAX-ACCESS read-write
                STATUS current
                DESCRIPTION "This specifies the mode in which RIP protocol runs."
                DEFVAL { disabled }
                ::= { viprIntfConfigEntry 12 }
 

viprIntfRowStatus      OBJECT-TYPE
                SYNTAX RowStatus
                MAX-ACCESS read-write
                STATUS current
                DESCRIPTION "row status"
                ::= { viprIntfConfigEntry 13 }
 
viprIntfRipLineType OBJECT-TYPE
                SYNTAX INTEGER {
                        broadcast(1),
                        multicast(2)
                        }
                MAX-ACCESS read-write
                STATUS current
                DESCRIPTION "This specifies the line type when the RIP version is 2.
                             When the RIP version is 1, the RIP line type will be 
                             set to broadcast(1)."
                DEFVAL { multicast }
                ::= { viprIntfConfigEntry 14 } 

viprIntfAuthPasswd  OBJECT-TYPE
                SYNTAX DisplayString (SIZE(16))
                MAX-ACCESS read-write
                STATUS current
                DESCRIPTION "The authentication password for RIP version 2"
                ::= { viprIntfConfigEntry 15 } 

-- Vipr Sub Channel Configuration Group
 
 
viprSubChnlConfigTable  OBJECT-TYPE
                SYNTAX SEQUENCE OF ViprSubChnlConfigEntry
                MAX-ACCESS not-accessible
                STATUS current
                DESCRIPTION "Table of Vipr Sub Channel Config Information"
                ::= { viprConfig 3 }
 
viprSubChnlConfigEntry  OBJECT-TYPE
                SYNTAX ViprSubChnlConfigEntry
                MAX-ACCESS not-accessible
                STATUS current
                DESCRIPTION " definition for VIPR sub channel attributes"
                INDEX { viprSlot, viprRouterId, viprIntfId, viprSubChnlId }
                ::= { viprSubChnlConfigTable 1 }
 
ViprSubChnlConfigEntry  ::= SEQUENCE {
                viprSubChnlId                      Integer32,
                viprSubChnlIntfIndex               IntfIndex,
                viprSubChnlTrafficType             INTEGER,
                viprSubChnlLlcEncapType            INTEGER,
                viprSubChnlMacEncapType            INTEGER,
                viprSubChnlTosFeature              INTEGER,
                viprSubChnlTosValue                INTEGER,
                viprSubChnlTosMask                 INTEGER,
                viprSubChnlVpiDlci                 INTEGER,
                viprSubChnlVci                     INTEGER,
                viprSubChnlSarType                 INTEGER,
                viprSubChnlServiceType             INTEGER,
                viprSubChnlFwdErrCorrection        INTEGER,
                viprSubChnlInterworkingType        INTEGER,
                viprSubChnlFrameSize               Integer32,
                viprSubChnlComBurstSize            Integer32,
                viprSubChnlExcessBurstSize         Integer32,
                viprSubChnlCommitedInfoRate        Integer32,
                viprSubChnlTimeInterval            INTEGER,
                viprSubChnlAtmPeakCellRate         Integer32,
                viprSubChnlAtmSustainedCellRate    Integer32,
                viprSubChnlAtmMaxBurstSize         Integer32,
                viprSubChnlFrPeakCellRate          Integer32,
                viprSubChnlFrSustainedCellRate     Integer32,
                viprSubChnlFrMaxBurstSize          Integer32,
                viprSubChnlFlowType                INTEGER,
                viprSubChnlAdminStatus             INTEGER,
                viprSubChnlOperStatus              INTEGER,
                viprSubChnlInitTmr                 Integer32,
                viprSubChnlDisabWarnTmr            Integer32,
                viprSubChnlShutDwnWarnTmr          Integer32,
                viprSubChnlDisableWarning          INTEGER,
                viprSubChnlDisableReason           INTEGER,
                viprSubChnlRowStatus               RowStatus,
                viprSubChnlImIpAddr                IpAddress,
                viprSubChnlImMask                  IpAddress,
                viprSubChnlViB                     INTEGER

                ,viprSubChnlVUNIB                  INTEGER

                ,viprSubChnlTrafficShaping         INTEGER,
                viprSubChnlAtmOamStatus            INTEGER
                }
 
 
viprSubChnlId   OBJECT-TYPE
                SYNTAX Integer32(1..3)
                MAX-ACCESS not-accessible
                STATUS current
                DESCRIPTION "A unique Id for the sub channel in the interface"
                ::= { viprSubChnlConfigEntry 1 }
 
 
viprSubChnlIntfIndex   OBJECT-TYPE
                SYNTAX IntfIndex
                MAX-ACCESS read-write
                STATUS current
                DESCRIPTION "The Slot Port Channel to which the IP Packet to be
                             forwarded when the TOS specified in the incoming
                             IP packet is matched to the TosValue, TosMask pair"
                ::= { viprSubChnlConfigEntry 2 }
 
viprSubChnlTrafficType   OBJECT-TYPE
                SYNTAX INTEGER{
                       atm(1),
                       fR(2),
                       bridge(3),
                       routing(4),
                       inband(5)
                       }
                MAX-ACCESS read-write
                STATUS current
                DESCRIPTION "The type of interface configured on the SSPPCCC,
                             viprSubChnlIntfIndex"
                DEFVAL { atm }
                ::= { viprSubChnlConfigEntry 3 }
 
viprSubChnlLlcEncapType    OBJECT-TYPE
                SYNTAX INTEGER{
                       vc(1),
                       llcSnap(2)
                       }
                MAX-ACCESS read-write
                STATUS current
                DESCRIPTION "The encapsulation technique used in making IP packet
                             to ATM cell"
                DEFVAL { none }
                ::= { viprSubChnlConfigEntry 4 }
 
viprSubChnlMacEncapType    OBJECT-TYPE
                SYNTAX INTEGER{
                       macHdr(1),
                       noMacHdr(2)
                       }
                MAX-ACCESS read-write
                STATUS current
                DESCRIPTION "The encapsulation technique used in making IP packet
                             to ATM cell"
                DEFVAL { none }
                ::= { viprSubChnlConfigEntry 5 }
 
viprSubChnlTosFeature    OBJECT-TYPE
                SYNTAX INTEGER{
                       disabled(1),
                       enabled(2)
                       }
                MAX-ACCESS read-only
                STATUS current
                DESCRIPTION "Allow the user to set the TOS values or not"
                DEFVAL { 1 }
                ::= { viprSubChnlConfigEntry 6 }
 

viprSubChnlTosValue   OBJECT-TYPE
                SYNTAX INTEGER(0..255)
                MAX-ACCESS read-only
                STATUS current
                DESCRIPTION "The type of service specified in IP packet masked
                             with viprSubChnlTosMask has to be equal to this
                             value in order to have the IP packets getting
                             forwarded in this sub channel"
                DEFVAL { 255 }
                ::= { viprSubChnlConfigEntry 7 }
 
viprSubChnlTosMask   OBJECT-TYPE
                SYNTAX INTEGER(0..255)
                MAX-ACCESS read-only
                STATUS current
                DESCRIPTION "The Type of Service mask"
                DEFVAL { 255 }
                ::= { viprSubChnlConfigEntry 8 }
 
viprSubChnlVpiDlci   OBJECT-TYPE
                SYNTAX INTEGER (0..255)
                MAX-ACCESS read-write
                STATUS current
                DESCRIPTION "The VPI/DLCI value of the connection"
                ::= { viprSubChnlConfigEntry 9 }
 
viprSubChnlVci   OBJECT-TYPE
                SYNTAX INTEGER (0..4096)
                MAX-ACCESS read-write
                STATUS current
                DESCRIPTION "The VCI value of the connection"
                ::= { viprSubChnlConfigEntry 10 }
 
viprSubChnlSarType   OBJECT-TYPE
                SYNTAX INTEGER {
                       aal5(1)
                }
                MAX-ACCESS read-only
                STATUS current
                DESCRIPTION "The SAR Type supported for the connection"
                DEFVAL { aal5 }
                ::= { viprSubChnlConfigEntry 11 }
 
viprSubChnlServiceType   OBJECT-TYPE
                SYNTAX INTEGER {
                       gold(1),
                       silver(2),
                       bronze(3)
                }
                MAX-ACCESS read-write
                STATUS current
                DESCRIPTION "The Service types that are supported"
                DEFVAL { gold }
                ::= { viprSubChnlConfigEntry 12 }
 
viprSubChnlFwdErrCorrection   OBJECT-TYPE
                SYNTAX INTEGER {
                       none(1),
                       eighthRate(2),
                       quarterRate(3),
                       halfRate(4),
                       autoHiQ(5),
                       auto(6),
                       autoLoQ(7)
                }
                MAX-ACCESS read-write
                STATUS current
                DESCRIPTION "The Forward error correction to be used"
                DEFVAL { none }
                ::= { viprSubChnlConfigEntry 13 }
 
viprSubChnlInterworkingType   OBJECT-TYPE
                SYNTAX INTEGER {
                       frf8(1)
                       }
                MAX-ACCESS read-write
                STATUS current
                DESCRIPTION "The Encapsulation type used for Frame relay subchannels"
                DEFVAL { frf8 }
                ::= { viprSubChnlConfigEntry 14 }
 
viprSubChnlFrameSize   OBJECT-TYPE
                SYNTAX Integer32
                MAX-ACCESS read-write
                STATUS current
                DESCRIPTION "The value of this object is the size in octets of
                             the largest frame relay information field for this
                             PVC in the ingress direction (out of the frame
                             relay UNI)."
                DEFVAL { 19200 }
                ::= { viprSubChnlConfigEntry 15 }
 
viprSubChnlComBurstSize   OBJECT-TYPE
                SYNTAX Integer32
                MAX-ACCESS read-write
                STATUS current
                DESCRIPTION "The value of this object is equal to the
                             committed burst size (Bc) parameter (measured in
                             bits) for this PVC in the ingress
                             direction (into the frame relay UNI)."
                DEFVAL { 0 }
                ::= { viprSubChnlConfigEntry 16 }
 
viprSubChnlExcessBurstSize   OBJECT-TYPE
                SYNTAX Integer32
                MAX-ACCESS read-write
                STATUS current
                DESCRIPTION "The value of this object is equal to the excess
                             burst size (Be) parameter (measured in bits) for
                             this PVC in the ingress direction (into
                             the frame relay UNI)."
                DEFVAL { 45000000 }
                ::= { viprSubChnlConfigEntry 17 }
 
viprSubChnlCommitedInfoRate   OBJECT-TYPE
                SYNTAX Integer32
                MAX-ACCESS read-write
                STATUS current
                DESCRIPTION "The value of this object is equal to the
                             committed information rate (CIR) parameter
                             (measured in bits per second) for this PVC
                             in the ingress direction (into the frame
                             relay UNI)."
                DEFVAL { 0 }
                ::= { viprSubChnlConfigEntry 18 }
 
viprSubChnlTimeInterval   OBJECT-TYPE
                SYNTAX INTEGER(64..4000)
                MAX-ACCESS read-only
                STATUS current
                DESCRIPTION "The time interval over which CIR and the burst
                             sizes (Bc and Be) are measured in the A2B
                             direction.  The unit is milliseconds."
                DEFVAL { 1000 }
                ::= { viprSubChnlConfigEntry 19 }
 
viprSubChnlAtmPeakCellRate   OBJECT-TYPE
                SYNTAX Integer32
                MAX-ACCESS read-write
                STATUS current
                DESCRIPTION "Peak cell rate, in cells per second,
                             this will reflect the frame relay parameters in
                             atm terms."
                DEFVAL { 1 }
                ::= { viprSubChnlConfigEntry 20 }
 
viprSubChnlAtmSustainedCellRate   OBJECT-TYPE
                SYNTAX Integer32
                MAX-ACCESS read-write
                STATUS current
                DESCRIPTION "Sustained cell rate, in cells per second,
                                  this will reflect the frame relay parameters in
                                    atm terms."
                DEFVAL { 1 }
                ::= { viprSubChnlConfigEntry 21 }
 
viprSubChnlAtmMaxBurstSize   OBJECT-TYPE
                SYNTAX Integer32
                MAX-ACCESS read-write
                STATUS current
                DESCRIPTION "Maximum burst size, in cells, 
                                  this will reflect the frame relay parameters in
                                    atm terms."
                DEFVAL { 1 }
                ::= { viprSubChnlConfigEntry 22 }
 
viprSubChnlFrPeakCellRate   OBJECT-TYPE
                SYNTAX Integer32
                MAX-ACCESS read-only
                STATUS current
                DESCRIPTION "Peak cell rate, in cells per second,
                             this will reflect the frame relay parameters in
                             atm terms."
                DEFVAL { 1 }
                ::= { viprSubChnlConfigEntry 23 }
 
viprSubChnlFrSustainedCellRate   OBJECT-TYPE
                SYNTAX Integer32
                MAX-ACCESS read-only
                STATUS current
                DESCRIPTION "Sustained cell rate, in cells per second,
                                  this will reflect the frame relay parameters in
                                    atm terms."
                DEFVAL { 1 }
                ::= { viprSubChnlConfigEntry 24 }
 
viprSubChnlFrMaxBurstSize   OBJECT-TYPE
                SYNTAX Integer32
                MAX-ACCESS read-only
                STATUS current
                DESCRIPTION "Maximum burst size, in cells, 
                                  this will reflect the frame relay parameters in
                                    atm terms."
                DEFVAL { 1 }
                ::= { viprSubChnlConfigEntry 25 }
 
viprSubChnlFlowType   OBJECT-TYPE
                SYNTAX INTEGER {
                       duplex(1)
                }
                MAX-ACCESS read-write
                STATUS current
                DESCRIPTION "The type of flow"
                DEFVAL { duplex }
                ::= { viprSubChnlConfigEntry 26 }
 
viprSubChnlAdminStatus       OBJECT-TYPE
                SYNTAX INTEGER  {
                       outOfService(1),
                       inService(2)
                       }
                MAX-ACCESS read-write
                STATUS current
                DESCRIPTION "This variable represents the various X.731 states
                             the Sub Channel state machine can take Administartively"
                DEFVAL { outOfService }
                ::= { viprSubChnlConfigEntry 27 }
 
viprSubChnlOperStatus       OBJECT-TYPE
                SYNTAX INTEGER  {
                       outOfService(1),
                       inService(2),
                       unlocked-Init(3),
                       unlocked-Disable(4),
                       locked-Shutting(5)
                       }
                MAX-ACCESS read-only
                STATUS current
                DESCRIPTION "This variable represents the various X.731 states
                             the Sub Channel state machine can take Operationally"
                DEFVAL { outOfService }
                ::= { viprSubChnlConfigEntry 28 }
 
viprSubChnlInitTmr OBJECT-TYPE
                SYNTAX Integer32
                MAX-ACCESS read-write
                STATUS current
                DESCRIPTION "This variable describes the waiting period in
                             the locked-Init state before moving onto
                             locked-Diable state."
                DEFVAL { 192 }
                ::= { viprSubChnlConfigEntry 29 }
 
viprSubChnlDisabWarnTmr OBJECT-TYPE
                SYNTAX Integer32
                MAX-ACCESS read-write
                STATUS current
                DESCRIPTION "This variable describes the periodicity in which
                             the error messages are to be flashed when the
                             system is in unlocked-Disable state."
                DEFVAL { 18000 }
                ::= { viprSubChnlConfigEntry 30 }
 
viprSubChnlShutDwnWarnTmr OBJECT-TYPE
                SYNTAX Integer32
                MAX-ACCESS read-write
                STATUS current
                DESCRIPTION "This variable describes the periodicity in which
                             the error messages are to be flashed when the
                             system is in locked-Shutting state."
                DEFVAL { 18000 }
                ::= { viprSubChnlConfigEntry 31 }
 
 
viprSubChnlDisableWarning OBJECT-TYPE
                SYNTAX INTEGER {
                       enabled(1),
                       disabled(2)
                       }
                MAX-ACCESS read-write
                STATUS current
                DESCRIPTION "This variable when disabled will mask all the
                             Disable warning messages."
                DEFVAL { enabled }
                ::= { viprSubChnlConfigEntry 32 }
 
viprSubChnlDisableReason OBJECT-TYPE
                SYNTAX INTEGER {
                       none(1),
                       intfDisabled(2),
                       routDisabled(3)
                       }
                MAX-ACCESS read-only
                STATUS current
                DESCRIPTION "This variable describes the reason why the SubChnl
                             in the unlocked-Disabled state."
                DEFVAL { none }
                ::= { viprSubChnlConfigEntry 33 }
 
viprSubChnlRowStatus      OBJECT-TYPE
                SYNTAX RowStatus
                MAX-ACCESS read-write
                STATUS current
                DESCRIPTION "row status"
                ::= { viprSubChnlConfigEntry 34 }

viprSubChnlImIpAddr     OBJECT-TYPE
                SYNTAX IpAddress
                MAX-ACCESS read-write
                STATUS current
                DESCRIPTION "inband management IpAddr"
                ::= { viprSubChnlConfigEntry 35 }

viprSubChnlImMask      OBJECT-TYPE
                SYNTAX IpAddress
                MAX-ACCESS read-write
                STATUS current
                DESCRIPTION "inband management Mask"
                ::= { viprSubChnlConfigEntry 36 }

viprSubChnlViB   OBJECT-TYPE
                SYNTAX INTEGER (0..4096)
                MAX-ACCESS read-write
                STATUS current
                DESCRIPTION "The viB value of the connection"
                ::= { viprSubChnlConfigEntry 37 }


viprSubChnlVUNIB   OBJECT-TYPE
                SYNTAX INTEGER (0..255)
                MAX-ACCESS read-write
                STATUS current
                DESCRIPTION "The VUNIB value of the connection"
                ::= { viprSubChnlConfigEntry 38 }

 
viprSubChnlTrafficShaping       OBJECT-TYPE
                SYNTAX INTEGER {
                                disabled(1),
                                enabled(2)
                               }
                MAX-ACCESS read-write
                STATUS current
                DESCRIPTION "Traffic Shaping Support in the A2B direction 
                             for outgoing ATM connections."
                DEFVAL { disabled }
                ::= { viprSubChnlConfigEntry 39 }

viprSubChnlAtmOamStatus OBJECT-TYPE
                SYNTAX INTEGER {
                                unsupp(1),
                                end-Pt(2),
                                end-Seg-Pt(3)
                               }
                MAX-ACCESS read-write
                STATUS current
                DESCRIPTION "Indicates the OAM monitoring status.
                             The 3 possible states are:
                             Unsupp:  No monitoring enabled.
                             End-Pt:  A side is only an end point, therefore
                                it will respond to AIS/RDI.
                             End-Seg-Pt: Connection endPoint that is also
                             a segment endPoint."
                DEFVAL { unsupp }
                ::= { viprSubChnlConfigEntry 40 }



-- Vipr Route Table
 
 
viprRouteConfigTable  OBJECT-TYPE
                SYNTAX SEQUENCE OF ViprRouteConfigEntry
                MAX-ACCESS not-accessible
                STATUS current
                DESCRIPTION "Table of Vipr static route Config Information"
                ::= { viprConfig 4 }
 
viprRouteConfigEntry  OBJECT-TYPE
                SYNTAX ViprRouteConfigEntry
                MAX-ACCESS not-accessible
                STATUS current
                DESCRIPTION "Definition for Vipr static route attributes"
                INDEX { viprSlot, viprRouterId, viprRouteId }
                ::= { viprRouteConfigTable 1 }
 
ViprRouteConfigEntry  ::= SEQUENCE {
                viprRouteId                      Integer32,
                viprRouteIPAddress               IpAddress,
                viprRouteIPNetMask               IpAddress,
                viprRouteDestAddress             IpAddress,
                viprRouteGatewayAddress          IpAddress,
                viprRouteServiceType             INTEGER,
                viprRouteMetric                  Integer32,
                viprRouteAdminStatus             INTEGER,
                viprRouteOperStatus              INTEGER,
                viprRouteInitTmr                 Integer32,
                viprRouteDisabWarnTmr            Integer32,
                viprRouteShutDwnWarnTmr          Integer32,
                viprRouteDisableWarning          INTEGER,
                viprRouteDisableReason           INTEGER,
                viprRouteRowStatus               RowStatus,
                viprRouteDestMask                IpAddress
                }
 
 
 
viprRouteId     OBJECT-TYPE
                SYNTAX Integer32(1..1024)
                MAX-ACCESS not-accessible
                STATUS current
                DESCRIPTION "The unique Id to the routing table entry"
                ::= { viprRouteConfigEntry 1 }
 
viprRouteIPAddress   OBJECT-TYPE
                SYNTAX IpAddress
                MAX-ACCESS read-write
                STATUS current
                DESCRIPTION "The IP address of the host/network in the route
                             entry"
                ::= { viprRouteConfigEntry 2 }
 
viprRouteIPNetMask   OBJECT-TYPE
                SYNTAX IpAddress
                MAX-ACCESS read-write
                STATUS current
                DESCRIPTION "The IP Subnet Mask for the route entry to identify
                             whether the route entry is a host or network"
                ::= { viprRouteConfigEntry 3 }
 
viprRouteDestAddress   OBJECT-TYPE
                SYNTAX IpAddress
                MAX-ACCESS read-write
                STATUS current
                DESCRIPTION "The IP address of the host/network in the route
                             entry"
                ::= { viprRouteConfigEntry 4 }

viprRouteGatewayAddress   OBJECT-TYPE
                SYNTAX IpAddress
                MAX-ACCESS read-write
                STATUS current
                DESCRIPTION "The IP address of the Gateway"
                ::= { viprRouteConfigEntry 5 }
 
viprRouteServiceType OBJECT-TYPE
                SYNTAX INTEGER {
                       gold(1),
                       silver(2),
                       bronze(3)
                }
                MAX-ACCESS read-write
                STATUS current
                DESCRIPTION "The Service types that are supported"
                DEFVAL { gold }
                ::= { viprRouteConfigEntry 6 }
 
viprRouteMetric OBJECT-TYPE
                SYNTAX Integer32
                MAX-ACCESS read-write
                STATUS current
                DESCRIPTION "A scalar value for user-supplied static 
                             route metric values. "
                ::= { viprRouteConfigEntry 7 }
 
 
viprRouteAdminStatus       OBJECT-TYPE
                SYNTAX INTEGER  {
                       outOfService(1),
                       inService(2)
                       }
                MAX-ACCESS read-write
                STATUS current
                DESCRIPTION "This variable represents the various X.731 states
                             the Route state machine can take Administratively"
                DEFVAL { outOfService }
                ::= { viprRouteConfigEntry 8 }

viprRouteOperStatus       OBJECT-TYPE
                SYNTAX INTEGER  {
                       outOfService(1),
                       inService(2),
                       unlocked-Init(3),
                       unlocked-Disable(4),
                       locked-Shutting(5)
                       }
                MAX-ACCESS read-only
                STATUS current
                DESCRIPTION "This variable represents the various X.731 states
                             the Route state machine can take Operationally"
                DEFVAL { outOfService }
                ::= { viprRouteConfigEntry 9 }
 
viprRouteInitTmr OBJECT-TYPE
                SYNTAX Integer32
                MAX-ACCESS read-write
                STATUS current
                DESCRIPTION "This variable describes the waiting period in
                             the locked-Init state before moving onto
                             locked-Diable state."
                DEFVAL { 192 }
                ::= { viprRouteConfigEntry 10 }
 
viprRouteDisabWarnTmr OBJECT-TYPE
                SYNTAX Integer32
                MAX-ACCESS read-write
                STATUS current
                DESCRIPTION "This variable describes the periodicity in which
                             the error messages are to be flashed when the
                             system is in unlocked-Disable state."
                DEFVAL { 18000 }
                ::= { viprRouteConfigEntry 11 }
 
viprRouteShutDwnWarnTmr OBJECT-TYPE
                SYNTAX Integer32
                MAX-ACCESS read-write
                STATUS current
                DESCRIPTION "This variable describes the periodicity in which
                             the error messages are to be flashed when the
                             system is in locked-Shutting state."
                DEFVAL { 18000 }
                ::= { viprRouteConfigEntry 12 }
 
 
viprRouteDisableWarning OBJECT-TYPE
                SYNTAX INTEGER {
                       enabled(1),
                       disabled(2)
                       }
                MAX-ACCESS read-write
                STATUS current
                DESCRIPTION "This variable when disabled will mask all the
                             Disable warning messages."
                DEFVAL { enabled }
                ::= { viprRouteConfigEntry 13 }
 
viprRouteDisableReason OBJECT-TYPE
                SYNTAX INTEGER {
                       none(1),
                       intfDisabled(2),
                       routDisabled(3)
                       }
                MAX-ACCESS read-only
                STATUS current
                DESCRIPTION "This variable describes the reason why the
                             Route in the unlocked-Disabled state."
                DEFVAL { none }
                ::= { viprRouteConfigEntry 14 }
 
viprRouteRowStatus      OBJECT-TYPE
                SYNTAX RowStatus
                MAX-ACCESS read-write
                STATUS current
                DESCRIPTION "row status"
                ::= { viprRouteConfigEntry 15 }
 
 
viprRouteDestMask    OBJECT-TYPE
                SYNTAX IpAddress
                MAX-ACCESS read-write
                STATUS current
                DESCRIPTION "The IP Mask of the host/network in the route
                             entry"
                ::= { viprRouteConfigEntry 16 }
 


-- Vipr Routing Table
 


viprRoutingConfigTable  OBJECT-TYPE
                SYNTAX SEQUENCE OF ViprRoutingConfigEntry
                MAX-ACCESS not-accessible
                STATUS current
                DESCRIPTION "Table of Vipr routes Config Information"
                ::= { viprConfig 5 }
 
viprRoutingConfigEntry  OBJECT-TYPE
                SYNTAX ViprRoutingConfigEntry
                MAX-ACCESS not-accessible
                STATUS current
                DESCRIPTION "Definition for Vipr route attributes"
                INDEX { viprSlot, viprRouterId, viprRoutingCommand, viprRoutingIndex }
                ::= { viprRoutingConfigTable 1 }
 
ViprRoutingConfigEntry  ::= SEQUENCE {
                viprRoutingCommand                 INTEGER,
                viprRoutingIPAddress               IpAddress,
                viprRoutingIPNetMask               IpAddress,
                viprRoutingDestAddress             IpAddress,
                viprRoutingGatewayAddress          IpAddress,
                viprRoutingServiceType             INTEGER,
                viprRoutingType                    INTEGER,
                viprRoutingMetric                  Integer32,
                viprRoutingDestMask                IpAddress,
                viprRoutingAge                     Integer32,
                viprRoutingIndex                   Integer32
                }
 
viprRoutingCommand   OBJECT-TYPE
                SYNTAX INTEGER {
                       start(1),
                       more(2),
                       abort(3),
                       retrieve(4)
                }
                MAX-ACCESS not-accessible
                STATUS current
                DESCRIPTION "The Routing table request command
                             Set to start to initiate the caching of first 15 entries
                             Set to more to initiate the caching of next 15 entries
                             Set to abort to reset the counter in I/O card
                             Set to retrieve in order to get the entries"
                ::= { viprRoutingConfigEntry 1 }
 
viprRoutingIPAddress   OBJECT-TYPE
                SYNTAX IpAddress
                MAX-ACCESS read-only
                STATUS current
                DESCRIPTION "The IP address of the host/network in the route
                             entry"
                ::= { viprRoutingConfigEntry 2 }
 
viprRoutingIPNetMask   OBJECT-TYPE
                SYNTAX IpAddress
                MAX-ACCESS read-only
                STATUS current
                DESCRIPTION "The IP Subnet Mask for the route entry to identify
                             whether the route entry is a host or network"
                ::= { viprRoutingConfigEntry 3 }
 
viprRoutingDestAddress   OBJECT-TYPE
                SYNTAX IpAddress
                MAX-ACCESS read-only
                STATUS current
                DESCRIPTION "The IP address of the host/network in the route
                             entry"
                ::= { viprRoutingConfigEntry 4 }
 
viprRoutingGatewayAddress   OBJECT-TYPE
                SYNTAX IpAddress
                MAX-ACCESS read-only
                STATUS current
                DESCRIPTION "The IP address of the Gateway"
                ::= { viprRoutingConfigEntry 5 }
 
viprRoutingServiceType OBJECT-TYPE
                SYNTAX INTEGER {
                       gold(1),
                       silver(2),
                       bronze(3)
                }
                MAX-ACCESS read-only
                STATUS current
                DESCRIPTION "The Service types that are supported"
                DEFVAL { gold }
                ::= { viprRoutingConfigEntry 6 }
 
viprRoutingType    OBJECT-TYPE
                SYNTAX INTEGER  {
                       stat(1),
                       rip(2),
                       ospf(3),
                       intf(4)
                       }
                MAX-ACCESS read-only
                STATUS current
                DESCRIPTION "Route types supported by the RS Card."
                DEFVAL { intf }
                ::= { viprRoutingConfigEntry 7 }

viprRoutingMetric OBJECT-TYPE
                SYNTAX Integer32
                MAX-ACCESS read-only
                STATUS current
                DESCRIPTION "The Path cost"
                ::= { viprRoutingConfigEntry 8 }
 
viprRoutingDestMask   OBJECT-TYPE
                SYNTAX IpAddress
                MAX-ACCESS read-only
                STATUS current
                DESCRIPTION "The IP address Mask of the host/network in the route
                             entry"
                ::= { viprRoutingConfigEntry 9 }

viprRoutingAge OBJECT-TYPE
                SYNTAX Integer32
                MAX-ACCESS read-only
                STATUS current
                DESCRIPTION "Age of the routing entry"
                ::= { viprRoutingConfigEntry 10 }
 
viprRoutingIndex  OBJECT-TYPE
                SYNTAX Integer32
                MAX-ACCESS not-accessible
                STATUS current
                DESCRIPTION "Index to the routing entry"
                ::= { viprRoutingConfigEntry 11 }

-- Vipr ARP Table
 


 
viprArpConfigTable  OBJECT-TYPE
                SYNTAX SEQUENCE OF ViprArpConfigEntry
                MAX-ACCESS not-accessible
                STATUS current
                DESCRIPTION "Table of Vipr Arp Table Information"
                ::= { viprConfig 6 }
 
viprArpConfigEntry  OBJECT-TYPE
                SYNTAX ViprArpConfigEntry
                MAX-ACCESS not-accessible
                STATUS current
                DESCRIPTION "Definition for Vipr Arp Table attributes"
                INDEX { viprSlot, viprRouterId, viprArpCommand , viprArpIndex}
                ::= { viprArpConfigTable 1 }
 
ViprArpConfigEntry  ::= SEQUENCE {
                viprArpCommand                 INTEGER,
                viprArpIPAddress               IpAddress,
                viprArpHwAddress               OCTET STRING,
                viprArpEntryAge                Integer32,
                viprArpInterfaceIPAddress      IpAddress,
                viprArpInterfaceIPMask         IpAddress,
                viprArpInterfaceServiceType    INTEGER,
                viprArpIndex                   Integer32
                }
 
viprArpCommand   OBJECT-TYPE
                SYNTAX INTEGER {
                       start(1),
                       more(2),
                       abort(3),
                       retrieve(4)
                }
                MAX-ACCESS not-accessible
                STATUS current
                DESCRIPTION "The ARP table request command
                             Set to start to initiate the caching of first 15 entries
                             Set to more to initiate the caching of next 15 entries
                             Set to abort to reset the counter in I/O card
                             Set to retrieve in order to get the entries"
                ::= { viprArpConfigEntry 1 }
 
viprArpIPAddress   OBJECT-TYPE
                SYNTAX IpAddress
                MAX-ACCESS read-only
                STATUS current
                DESCRIPTION "The IP address of the host/network"
                ::= { viprArpConfigEntry 2 }
 
viprArpHwAddress   OBJECT-TYPE
                SYNTAX OCTET STRING (SIZE(6))
                MAX-ACCESS read-only
                STATUS current
                DESCRIPTION "The hardware address of the host/network"
                ::= { viprArpConfigEntry 3 }

viprArpEntryAge   OBJECT-TYPE
                SYNTAX Integer32
                MAX-ACCESS read-only
                STATUS current
                DESCRIPTION "Age of cache entry."
                ::= { viprArpConfigEntry 4 }

viprArpInterfaceIPAddress   OBJECT-TYPE
                SYNTAX IpAddress
                MAX-ACCESS read-only
                STATUS current
                DESCRIPTION "The Interface IP address through which it is learned"
                ::= { viprArpConfigEntry 5 }

viprArpInterfaceIPMask   OBJECT-TYPE
                SYNTAX IpAddress
                MAX-ACCESS read-only
                STATUS current
                DESCRIPTION "The Interface IP address Mask"
                ::= { viprArpConfigEntry 6 }

viprArpInterfaceServiceType   OBJECT-TYPE
                SYNTAX INTEGER {
                       gold(1),
                       silver(2),
                       bronze(3)
                }
                MAX-ACCESS read-only
                STATUS current
                DESCRIPTION "The Service type of the interface through which the
                             ARP table is learned"
                DEFVAL { gold }
                ::= { viprArpConfigEntry 7 }

viprArpIndex   OBJECT-TYPE
                SYNTAX Integer32 
                MAX-ACCESS not-accessible
                STATUS current
                DESCRIPTION "The Index to the Arp table"
                ::= { viprArpConfigEntry 8 }


-- Vipr PING Table
 
 
viprPingConfigTable  OBJECT-TYPE
                SYNTAX SEQUENCE OF ViprPingConfigEntry
                MAX-ACCESS not-accessible
                STATUS current
                DESCRIPTION "Table of Vipr Ping Table Information"
                ::= { viprConfig 7 }
 
viprPingConfigEntry  OBJECT-TYPE
                SYNTAX ViprPingConfigEntry
                MAX-ACCESS not-accessible
                STATUS current
                DESCRIPTION "Definition for Vipr Ping Table attributes"
                INDEX { viprSlot, viprRouterId, ipAddr }
                ::= { viprPingConfigTable 1 }
 
ViprPingConfigEntry  ::= SEQUENCE {
                ipAddr                    IpAddress,
                pingStatus                INTEGER
                }
 
 
ipAddr   OBJECT-TYPE
                SYNTAX IpAddress
                MAX-ACCESS not-accessible
                STATUS current
                DESCRIPTION "The IP address of the host/network to be echoed"
                ::= { viprPingConfigEntry 1 }

pingStatus   OBJECT-TYPE
                SYNTAX INTEGER {
                       alive(1),
                       not-Alive(2)
                }
                MAX-ACCESS read-only
                STATUS current
                DESCRIPTION "The response value - Alive/Not Alive"
                ::= { viprPingConfigEntry 2 }

-- Vipr Router RIP Update Interval per Slot

viprRipConfigTable      OBJECT-TYPE
                SYNTAX SEQUENCE OF ViprRipConfigEntry
                MAX-ACCESS not-accessible
                STATUS current
                DESCRIPTION "Table of Vipr Rip Update Interval for each card"
                ::= { viprConfig 8 }

viprRipConfigEntry      OBJECT-TYPE
                SYNTAX ViprRipConfigEntry
                MAX-ACCESS not-accessible
                STATUS current
                DESCRIPTION "Definition of Rip Update attributes"
                INDEX { viprSlot }
                ::= { viprRipConfigTable 1 }

ViprRipConfigEntry  ::= SEQUENCE {
                viprRipUpdateInt        INTEGER
                }

viprRipUpdateInt        OBJECT-TYPE
                SYNTAX INTEGER  {
                        lowUpdateInt(8),
                        mediumUpdateInt(16),
                        normalUpdateInt(30)
                        }
                MAX-ACCESS read-write
                STATUS current
                DESCRIPTION "This variable represents the Rip Update Interval
                             used by the RIP protocol to transmit packets.
                             The unit is in seconds. The default is 30 seconds
                             and user can change it to 8 or 16 seconds for a
                             route server card. The value will apply to all
                             VPN's in a route server card. But different
                             route server cards in different slots can have
                             separate values for Rip Update Interval"
                DEFVAL { normalUpdateInt }
                ::= { viprRipConfigEntry 1 }

--  VPN level statistics will be on the port level statistics. 

viprVpnStatsTable OBJECT-TYPE
                SYNTAX SEQUENCE OF ViprVpnStatsEntry
                MAX-ACCESS not-accessible
                STATUS current
                DESCRIPTION "Statistics collected per vpn based"
                ::= { equipStatistics 9 }

viprVpnStatsEntry OBJECT-TYPE
                SYNTAX ViprVpnStatsEntry
                MAX-ACCESS not-accessible
                STATUS current
                DESCRIPTION "Statistics collected per vpn based"
                INDEX { viprSlot, viprRouterId }
                ::= { viprVpnStatsTable 1 }

ViprVpnStatsEntry ::= SEQUENCE {
               viprVpnStatsTimer                     Integer32,
               viprVpnStatsIcmpOutEchoRPs            Integer32,
               viprVpnStatsIcmpOutDestURs            Integer32,
               viprVpnStatsIcmpOutSrcQ               Integer32,
               viprVpnStatsIcmpOutRedirects          Integer32,
               viprVpnStatsIcmpOutEchoRQs            Integer32,
               viprVpnStatsIcmpOutTimeXs             Integer32,
               viprVpnStatsIcmpOutParamps            Integer32,
               viprVpnStatsIcmpOutTimeRQs            Integer32,
               viprVpnStatsIcmpOutTimeRPs            Integer32,
               viprVpnStatsIcmpOutInfoRQs            Integer32,
               viprVpnStatsIcmpOutInfoRPs            Integer32,
               viprVpnStatsIcmpOutMaskRQs            Integer32,
               viprVpnStatsIcmpOutMaskRPs            Integer32,
               viprVpnStatsIcmpOutErrors             Integer32,
               viprVpnStatsIcmpInErrors              Integer32,
               viprVpnStatsIcmpInEchoRQs             Integer32,
               viprVpnStatsIcmpInAddrMasks           Integer32,
               viprVpnStatsIcmpInAddrMaskReps        Integer32,
               viprVpnStatsIcmpInEchoReps            Integer32,
               viprVpnStatsIcmpInDestUnreachs        Integer32,
               viprVpnStatsIcmpInSrcQuenchs          Integer32,
               viprVpnStatsIcmpInTimeExcds           Integer32,
               viprVpnStatsIcmpInParamProbs          Integer32,
               viprVpnStatsIcmpInTimeStamps          Integer32,
               viprVpnStatsIcmpInTimeStampsReps      Integer32
               }

viprVpnStatsTimer OBJECT-TYPE
                SYNTAX Integer32
                MAX-ACCESS read-only
                STATUS current
                DESCRIPTION " A timeout value in which the RS Module 
                             must reply to statistics requests."
                ::= { viprVpnStatsEntry 1 }

viprVpnStatsIcmpOutEchoRPs OBJECT-TYPE
                SYNTAX Integer32
                MAX-ACCESS read-only
                STATUS current
                DESCRIPTION "Echo Reply"
                ::= { viprVpnStatsEntry 2 }

viprVpnStatsIcmpOutDestURs OBJECT-TYPE
                SYNTAX Integer32
                MAX-ACCESS read-only
                STATUS current
                DESCRIPTION "Destination unreachable"
                ::= { viprVpnStatsEntry 3}

viprVpnStatsIcmpOutSrcQ OBJECT-TYPE
                SYNTAX Integer32
                MAX-ACCESS read-only
                STATUS current
                DESCRIPTION "Source Quenches"
                ::= { viprVpnStatsEntry 4 }

viprVpnStatsIcmpOutRedirects OBJECT-TYPE
                SYNTAX Integer32
                MAX-ACCESS read-only
                STATUS current
                DESCRIPTION "Redirect message type"
                ::= { viprVpnStatsEntry 5}

viprVpnStatsIcmpOutEchoRQs OBJECT-TYPE
                SYNTAX Integer32
                MAX-ACCESS read-only
                STATUS current
                DESCRIPTION "Echo Requests"
                ::= { viprVpnStatsEntry 6 }

viprVpnStatsIcmpOutTimeXs OBJECT-TYPE
                SYNTAX Integer32
                MAX-ACCESS read-only
                STATUS current
                DESCRIPTION "Time exceeded"
                ::= { viprVpnStatsEntry 7}

viprVpnStatsIcmpOutParamps OBJECT-TYPE
                SYNTAX Integer32
                MAX-ACCESS read-only
                STATUS current
                DESCRIPTION "Parameter problem"
                ::= { viprVpnStatsEntry 8 }

viprVpnStatsIcmpOutTimeRQs OBJECT-TYPE
                SYNTAX Integer32
                MAX-ACCESS read-only
                STATUS current
                DESCRIPTION "Timestamp requests"
                ::= { viprVpnStatsEntry 9 }

viprVpnStatsIcmpOutTimeRPs OBJECT-TYPE
                SYNTAX Integer32
                MAX-ACCESS read-only
                STATUS current
                DESCRIPTION "Timestamp replies"
                ::= { viprVpnStatsEntry 10 }

viprVpnStatsIcmpOutInfoRQs OBJECT-TYPE
                SYNTAX Integer32
                MAX-ACCESS read-only
                STATUS current
                DESCRIPTION "Information Request"
                ::= { viprVpnStatsEntry 11 }

viprVpnStatsIcmpOutInfoRPs OBJECT-TYPE
                SYNTAX Integer32
                MAX-ACCESS read-only
                STATUS current
                DESCRIPTION "Echo Reply"
                ::= { viprVpnStatsEntry 12 }

viprVpnStatsIcmpOutMaskRQs OBJECT-TYPE
                SYNTAX Integer32
                MAX-ACCESS read-only
                STATUS current
                DESCRIPTION "Mask Request"
                ::= { viprVpnStatsEntry 13 }

viprVpnStatsIcmpOutMaskRPs OBJECT-TYPE
                SYNTAX Integer32
                MAX-ACCESS read-only
                STATUS current
                DESCRIPTION "Mask Reply"
                ::= { viprVpnStatsEntry 14}

viprVpnStatsIcmpOutErrors OBJECT-TYPE
                SYNTAX Integer32
                MAX-ACCESS read-only
                STATUS current
                DESCRIPTION "unrecognized ICMP type"
                ::= { viprVpnStatsEntry 15 }

viprVpnStatsIcmpInErrors OBJECT-TYPE
                SYNTAX Integer32
                MAX-ACCESS read-only
                STATUS current
                DESCRIPTION "error in received icmp message"
                ::= { viprVpnStatsEntry 16 }

viprVpnStatsIcmpInEchoRQs OBJECT-TYPE
                SYNTAX Integer32
                MAX-ACCESS read-only
                STATUS current
                DESCRIPTION "received echo request"
                ::= { viprVpnStatsEntry 17 }

viprVpnStatsIcmpInAddrMasks OBJECT-TYPE
                SYNTAX Integer32
                MAX-ACCESS read-only
                STATUS current
                DESCRIPTION "received mask request"
                ::= { viprVpnStatsEntry 18 }

viprVpnStatsIcmpInAddrMaskReps OBJECT-TYPE
                SYNTAX Integer32
                MAX-ACCESS read-only
                STATUS current
                DESCRIPTION "received mask reply"
                ::= { viprVpnStatsEntry 19 }

viprVpnStatsIcmpInEchoReps OBJECT-TYPE
                SYNTAX Integer32
                MAX-ACCESS read-only
                STATUS current
                DESCRIPTION "received echo replies"
                ::= { viprVpnStatsEntry 20 }

viprVpnStatsIcmpInDestUnreachs OBJECT-TYPE
                SYNTAX Integer32
                MAX-ACCESS read-only
                STATUS current
                DESCRIPTION "received destination unreacheable message"
                ::= { viprVpnStatsEntry 21 }

viprVpnStatsIcmpInSrcQuenchs OBJECT-TYPE
                SYNTAX Integer32
                MAX-ACCESS read-only
                STATUS current
                DESCRIPTION "received source quench"
                ::= { viprVpnStatsEntry 22 }

viprVpnStatsIcmpInTimeExcds OBJECT-TYPE
                SYNTAX Integer32
                MAX-ACCESS read-only
                STATUS current
                DESCRIPTION "received time exceeded message"
                ::= { viprVpnStatsEntry 23 }

viprVpnStatsIcmpInParamProbs OBJECT-TYPE
                SYNTAX Integer32
                MAX-ACCESS read-only
                STATUS current
                DESCRIPTION "received parameter problem message"
                ::= { viprVpnStatsEntry 24 }

viprVpnStatsIcmpInTimeStamps OBJECT-TYPE
                SYNTAX Integer32
                MAX-ACCESS read-only
                STATUS current
                DESCRIPTION "received time stamp request"
                ::= { viprVpnStatsEntry 25 }

viprVpnStatsIcmpInTimeStampsReps OBJECT-TYPE
                SYNTAX Integer32
                MAX-ACCESS read-only
                STATUS current
                DESCRIPTION "received time stamp replies"
                ::= { viprVpnStatsEntry 26 }


--  Interface level statistics that will be based on per CID.

viprStatsTable OBJECT-TYPE
                SYNTAX SEQUENCE OF ViprStatsEntry
                MAX-ACCESS not-accessible
                STATUS current
                DESCRIPTION " The table which holds viprStatsEntry data."
                ::= { intfStatistics 10 }
                        
viprStatsEntry OBJECT-TYPE
                SYNTAX ViprStatsEntry
                MAX-ACCESS not-accessible
                STATUS current
                DESCRIPTION " A table entry for VPN related statistics 
                              information."
                INDEX { viprSlot, viprRouterId,  viprIntfId, viprSubChnlId, 
                        viprSubChnlIntfIndex, viprSubChnlVpiDlci, 
                        viprSubChnlVci, viprSubChnlTrafficType }
                ::= { viprStatsTable 1 }

ViprStatsEntry ::= SEQUENCE {
                viprStatsReset                  INTEGER,
                viprStatsPacketsRxHi            Integer32,
                viprStatsPacketsRxLo            Integer32,
                viprStatsPacketsTxHi            Integer32,
                viprStatsPacketsTxLo            Integer32,
                viprStatsMismatchCrcHi          Integer32,
                viprStatsMismatchCrcLo          Integer32,
                viprStatsInsufficientPcktsHi    Integer32,
                viprStatsInsufficientPcktsLo    Integer32,
                viprStatsExceedAal5CellsHi      Integer32,
                viprStatsExceedAal5CellsLo      Integer32,
                viprStatsPrototypeErrorsHi      Integer32,
                viprStatsPrototypeErrorsLo      Integer32,
                viprStatsArpProtoRxHi           Integer32,
                viprStatsArpProtoRxLo           Integer32,
                viprStatsIPInHdrErrorsHi        Integer32,
                viprStatsIPInHdrErrorsLo        Integer32,
                viprStatsIPInAddrErrorsHi       Integer32,
                viprStatsIPInAddrErrorsLo       Integer32
                 }

viprStatsReset OBJECT-TYPE
                SYNTAX INTEGER {
                       reset(1)
                }
                MAX-ACCESS read-write
                STATUS current
                DESCRIPTION " A SNMP set action to reset VPN related 
                              statistics info."
                ::= { viprStatsEntry 1 }

viprStatsPacketsRxHi OBJECT-TYPE
                SYNTAX Integer32
                MAX-ACCESS read-only
                STATUS current
                DESCRIPTION "Good packets received from the backplane"
                ::= { viprStatsEntry 2 }

viprStatsPacketsRxLo OBJECT-TYPE
                SYNTAX Integer32
                MAX-ACCESS read-only
                STATUS current
                DESCRIPTION "Good packets received from the backplane"
                ::= { viprStatsEntry 3 }

viprStatsPacketsTxHi OBJECT-TYPE
                SYNTAX Integer32
                MAX-ACCESS read-only
                STATUS current
                DESCRIPTION "packets transmitted to the backplane"
                ::= { viprStatsEntry 4 }

viprStatsPacketsTxLo OBJECT-TYPE
                SYNTAX Integer32
                MAX-ACCESS read-only
                STATUS current
                DESCRIPTION "packets transmitted to the backplane"
                ::= { viprStatsEntry 5 }

viprStatsMismatchCrcHi OBJECT-TYPE
                SYNTAX Integer32
                MAX-ACCESS read-only
                STATUS current
                DESCRIPTION "packets received has been dropped due to a mismached CRC"
                ::= { viprStatsEntry 6 }

viprStatsMismatchCrcLo OBJECT-TYPE
                SYNTAX Integer32
                MAX-ACCESS read-only
                STATUS current
                DESCRIPTION "packets received has been dropped due to a mismached CRC"
                ::= { viprStatsEntry 7 }

viprStatsInsufficientPcktsHi OBJECT-TYPE
                SYNTAX Integer32
                MAX-ACCESS read-only
                STATUS current
                DESCRIPTION "packet received length is greater than the number of cells received"
                ::= { viprStatsEntry 8 }

viprStatsInsufficientPcktsLo OBJECT-TYPE
                SYNTAX Integer32
                MAX-ACCESS read-only
                STATUS current
                DESCRIPTION "packet received length is greater than the number of cells received"
                ::= { viprStatsEntry 9 }

viprStatsExceedAal5CellsHi OBJECT-TYPE
                SYNTAX Integer32
                MAX-ACCESS read-only
                STATUS current
                DESCRIPTION "number of cells received is greater than the actual length of the aal5"
                ::= { viprStatsEntry 10 }

viprStatsExceedAal5CellsLo OBJECT-TYPE
                SYNTAX Integer32
                MAX-ACCESS read-only
                STATUS current
                DESCRIPTION "number of cells received is greater than the actual length of the aal5"
                ::= { viprStatsEntry 11 }

viprStatsPrototypeErrorsHi OBJECT-TYPE
                SYNTAX Integer32
                MAX-ACCESS read-only
                STATUS current
                DESCRIPTION "unrecognized encapsulation type"
                ::= { viprStatsEntry 12 }

viprStatsPrototypeErrorsLo OBJECT-TYPE
                SYNTAX Integer32
                MAX-ACCESS read-only
                STATUS current
                DESCRIPTION "unrecognized encapsulation type"
                ::= { viprStatsEntry 13 }

viprStatsArpProtoRxHi OBJECT-TYPE
                SYNTAX Integer32
                MAX-ACCESS read-only
                STATUS current
                DESCRIPTION "ARP received"
                ::= { viprStatsEntry 14 }

viprStatsArpProtoRxLo OBJECT-TYPE
                SYNTAX Integer32
                MAX-ACCESS read-only
                STATUS current
                DESCRIPTION "ARP received"
                ::= { viprStatsEntry 15 }

viprStatsIPInHdrErrorsHi OBJECT-TYPE
                SYNTAX Integer32
                MAX-ACCESS read-only
                STATUS current
                DESCRIPTION "IP packeted received has a bad header"
                ::= { viprStatsEntry 16 }

viprStatsIPInHdrErrorsLo OBJECT-TYPE
                SYNTAX Integer32
                MAX-ACCESS read-only
                STATUS current
                DESCRIPTION "IP packeted received has a bad header"
                ::= { viprStatsEntry 17 }

viprStatsIPInAddrErrorsHi OBJECT-TYPE
                SYNTAX Integer32
                MAX-ACCESS read-only
                STATUS current
                DESCRIPTION "IP packeted received has a bad IP Address"
                ::= { viprStatsEntry 18 }

viprStatsIPInAddrErrorsLo OBJECT-TYPE
                SYNTAX Integer32
                MAX-ACCESS read-only
                STATUS current
                DESCRIPTION "IP packeted received has a bad IP Address"
                ::= { viprStatsEntry 19 }



--  SubChannel level statistics that will be based on per CID.

viprSubChnlStatsTable OBJECT-TYPE
                SYNTAX SEQUENCE OF ViprSubChnlStatsEntry
                MAX-ACCESS not-accessible
                STATUS current
                DESCRIPTION " The table which holds 
                              viprSubChnlStatsEntry data."
                ::= { connectionStatistics 17 }
                        
viprSubChnlStatsEntry OBJECT-TYPE
                SYNTAX ViprSubChnlStatsEntry
                MAX-ACCESS not-accessible
                STATUS current
                DESCRIPTION " A table entry that contains IP interface 
                              sub channel statistics."
                INDEX { viprSlot, viprRouterId,  viprIntfId, viprSubChnlId, 
                        viprSubChnlIntfIndex, viprSubChnlVpiDlci, 
                        viprSubChnlVci, viprSubChnlTrafficType }
                ::= { viprSubChnlStatsTable 1 }

ViprSubChnlStatsEntry ::= SEQUENCE {
                viprSubChnlStatsInCellCountHiA          Integer32,
                viprSubChnlStatsInCellCountLoA          Integer32,
                     viprSubChnlStatsOutCellCountHiA         Integer32,
                     viprSubChnlStatsOutCellCountLoA         Integer32,
                viprSubChnlStatsInCellCountHiB          Integer32,
                viprSubChnlStatsInCellCountLoB          Integer32,
                     viprSubChnlStatsOutCellCountHiB         Integer32,
                     viprSubChnlStatsOutCellCountLoB         Integer32,
                viprSubChnlStatsTimer                        Integer32,
                viprSubChnlStatsInOdometerCellCountHiA  Integer32,
                viprSubChnlStatsInOdometerCellCountLoA  Integer32,
                     viprSubChnlStatsOutOdometerCellCountHiA Integer32,
                     viprSubChnlStatsOutOdometerCellCountLoA Integer32,
                viprSubChnlStatsInOdometerCellCountHiB  Integer32,
                viprSubChnlStatsInOdometerCellCountLoB  Integer32,
                     viprSubChnlStatsOutOdometerCellCountHiB Integer32,
                     viprSubChnlStatsOutOdometerCellCountLoB Integer32,
                viprSubChnlStatsOdometerTimer                Integer32,
                viprSubChnlStatsOdometerReset                 INTEGER,
                viprSubChnlStatsCellsDroppedB                 Integer32,
                viprSubChnlStatsCellsTaggedB                 Integer32
                }

viprSubChnlStatsInCellCountHiA OBJECT-TYPE
                SYNTAX Integer32
                MAX-ACCESS read-only
                STATUS current
                DESCRIPTION "cells received on rt interface from another conn"
                ::= { viprSubChnlStatsEntry 1 }

viprSubChnlStatsInCellCountLoA OBJECT-TYPE
                SYNTAX Integer32
                MAX-ACCESS read-only
                STATUS current
                DESCRIPTION "cells received on rt interface from another conn"
                ::= { viprSubChnlStatsEntry 2 }

viprSubChnlStatsOutCellCountHiA OBJECT-TYPE
                SYNTAX Integer32
                MAX-ACCESS read-only
                STATUS current
                DESCRIPTION "cells sent out of a rt interface to another dest"
                ::= { viprSubChnlStatsEntry 3 }

viprSubChnlStatsOutCellCountLoA OBJECT-TYPE
                SYNTAX Integer32
                MAX-ACCESS read-only
                STATUS current
                DESCRIPTION "cells sent out of a rt interface to another dest"
                ::= { viprSubChnlStatsEntry 4 }

viprSubChnlStatsInCellCountHiB OBJECT-TYPE
                SYNTAX Integer32
                MAX-ACCESS read-only
                STATUS current
                DESCRIPTION "cells received on atm/fr/bridge 
                             physical interface "
                ::= { viprSubChnlStatsEntry 5 }

viprSubChnlStatsInCellCountLoB OBJECT-TYPE
                SYNTAX Integer32
                MAX-ACCESS read-only
                STATUS current
                DESCRIPTION "cells received on atm/fr/bridge 
                             physical interface "
                ::= { viprSubChnlStatsEntry 6 }

viprSubChnlStatsOutCellCountHiB OBJECT-TYPE
                SYNTAX Integer32
                MAX-ACCESS read-only
                STATUS current
                DESCRIPTION "cell transmitted out of a 
                             physical atm/fr/bridge interface"
                ::= { viprSubChnlStatsEntry 7 }

viprSubChnlStatsOutCellCountLoB OBJECT-TYPE
                SYNTAX Integer32
                MAX-ACCESS read-only
                STATUS current
                DESCRIPTION "cell transmitted out of a 
                             physical atm/fr/bridge interface"
                ::= { viprSubChnlStatsEntry 8 }

viprSubChnlStatsTimer OBJECT-TYPE
                SYNTAX Integer32
                MAX-ACCESS read-only
                STATUS current
                DESCRIPTION "Number of seconds stats have been collecting"
                ::= { viprSubChnlStatsEntry 9 }

viprSubChnlStatsInOdometerCellCountHiA OBJECT-TYPE
                SYNTAX Integer32
                MAX-ACCESS read-only
                STATUS current
                DESCRIPTION "odometer cells received on 
                             rt interface from another conn"
                ::= { viprSubChnlStatsEntry 10 }

viprSubChnlStatsInOdometerCellCountLoA OBJECT-TYPE
                SYNTAX Integer32
                MAX-ACCESS read-only
                STATUS current
                DESCRIPTION "odometer cells received on 
                             rt interface from another conn"
                ::= { viprSubChnlStatsEntry 11 }

viprSubChnlStatsOutOdometerCellCountHiA OBJECT-TYPE
                SYNTAX Integer32
                MAX-ACCESS read-only
                STATUS current
                DESCRIPTION "odometer cells sent out of a 
                             rt interface to another dest"
                ::= { viprSubChnlStatsEntry 12 }

viprSubChnlStatsOutOdometerCellCountLoA OBJECT-TYPE
                SYNTAX Integer32
                MAX-ACCESS read-only
                STATUS current
                DESCRIPTION "odometer cells sent out of a 
                             rt interface to another dest"
                ::= { viprSubChnlStatsEntry 13 }

viprSubChnlStatsInOdometerCellCountHiB OBJECT-TYPE
                SYNTAX Integer32
                MAX-ACCESS read-only
                STATUS current
                DESCRIPTION "odometer cells received on atm/fr/bridge 
                             physical interface "
                ::= { viprSubChnlStatsEntry 14 }

viprSubChnlStatsInOdometerCellCountLoB OBJECT-TYPE
                SYNTAX Integer32
                MAX-ACCESS read-only
                STATUS current
                DESCRIPTION "odometer cells received on atm/fr/bridge 
                             physical interface "
                ::= { viprSubChnlStatsEntry 15 }

viprSubChnlStatsOutOdometerCellCountHiB OBJECT-TYPE
                SYNTAX Integer32
                MAX-ACCESS read-only
                STATUS current
                DESCRIPTION "odometer cells transmitted out of a 
                             physical atm/fr/bridge interface"
                ::= { viprSubChnlStatsEntry 16 }

viprSubChnlStatsOutOdometerCellCountLoB OBJECT-TYPE
                SYNTAX Integer32
                MAX-ACCESS read-only
                STATUS current
                DESCRIPTION "odometer cells transmitted out of a 
                             physical atm/fr/bridge interface"
                ::= { viprSubChnlStatsEntry 17 }

viprSubChnlStatsOdometerTimer OBJECT-TYPE
                SYNTAX Integer32
                MAX-ACCESS read-only
                STATUS current
                DESCRIPTION "Odometer Number of seconds 
                             stats have been collecting"
                ::= { viprSubChnlStatsEntry 18 }

viprSubChnlStatsOdometerReset  OBJECT-TYPE
                SYNTAX INTEGER {
                    reset(1)
                }
                MAX-ACCESS read-write
                STATUS current
                DESCRIPTION "to reset the subchannel statistics"
                ::= { viprSubChnlStatsEntry 19 }

viprSubChnlStatsCellsDroppedB OBJECT-TYPE
                SYNTAX Integer32
                MAX-ACCESS read-only
                STATUS current
                DESCRIPTION "Cells Dropped on the Incoming side of B"
                ::= { viprSubChnlStatsEntry 20 }

viprSubChnlStatsCellsTaggedB OBJECT-TYPE
                SYNTAX Integer32
                MAX-ACCESS read-only
                STATUS current
                DESCRIPTION "Cells Tagged on the Incoming side of B"
                ::= { viprSubChnlStatsEntry 21 }
 
virtualIntfStatsTable OBJECT-TYPE
        SYNTAX SEQUENCE OF VirtualIntfStatsEntry
        MAX-ACCESS not-accessible
        STATUS current
        DESCRIPTION "Table of Virtual Interfaces Configurations"
        ::= { intfStatistics 11 }

virtualIntfStatsEntry OBJECT-TYPE
        SYNTAX VirtualIntfStatsEntry
        MAX-ACCESS not-accessible
        STATUS current
        DESCRIPTION "Index is the Interface and the Virutal Interface"
        INDEX { virtualIntfStatsIf, virtualIntfStatsVi }
        ::= { virtualIntfStatsTable 1 }

VirtualIntfStatsEntry ::= SEQUENCE {
          virtualIntfStatsIf   IntfIndex,
        virtualIntfStatsVi   INTEGER,
        virtualIntfStatsEgrCellCount  Integer32,
        virtualIntfStatsTimer   Integer32,
        virtualIntfStatsReset   INTEGER
        }

virtualIntfStatsIf OBJECT-TYPE
          SYNTAX IntfIndex
        MAX-ACCESS not-accessible
        STATUS current
        DESCRIPTION "Interface index for side A of an ATM-to-ATM PVC VCC
                connection.  Number value is interpreted as an
                interface of the form, SSPPCCC, where SS is the 
                card slot, PP is the port number, and CCC is the 
                channel number."
        ::= { virtualIntfStatsEntry 1 }

virtualIntfStatsVi OBJECT-TYPE
          SYNTAX INTEGER (0..1024)
        MAX-ACCESS not-accessible
        STATUS current
        DESCRIPTION "VI value. Def Val is 1 because 0 cannot be 
                configured"
        ::= { virtualIntfStatsEntry 2 }

virtualIntfStatsEgrCellCount OBJECT-TYPE
          SYNTAX Integer32
        MAX-ACCESS read-only
        STATUS current
        DESCRIPTION " Egress Cell Count on VI "
        ::= { virtualIntfStatsEntry 3 }

virtualIntfStatsTimer OBJECT-TYPE
          SYNTAX Integer32 (1..899)
          MAX-ACCESS read-only
        STATUS current
        DESCRIPTION "Time, in seconds, since last reset."
        ::= { virtualIntfStatsEntry 4 }

virtualIntfStatsReset OBJECT-TYPE
          SYNTAX INTEGER {
                        reset(1)
                        }
          MAX-ACCESS read-write
          STATUS current
          DESCRIPTION "stats reset field."
        ::= { virtualIntfStatsEntry 5 }


-- FW download group, two tables

cardFwVerTable OBJECT-TYPE
                   SYNTAX SEQUENCE OF CardFwVerEntry
                   MAX-ACCESS not-accessible
                   STATUS current
                   DESCRIPTION "Table of card firware version status"
                   ::= {  fwDriverSup 1 }
 
cardFwVerEntry OBJECT-TYPE
                   SYNTAX CardFwVerEntry
                   MAX-ACCESS not-accessible
                   STATUS current
                  DESCRIPTION "Row definition for card firmware version status"
                   INDEX { cardFwVerSlot }
                   ::= { cardFwVerTable 1 }
 
CardFwVerEntry ::= SEQUENCE {
                   cardFwVerSlot            INTEGER,
                   cardFwVerType            Integer32,
                   cardFwVerCurrent            OCTET STRING,
                   cardFwVerCurrentIsDefault            Integer32,
                   cardFwVerNext            OCTET STRING,
                   cardFwVerNextIsDefault            INTEGER,
                   cardFwDnldStatus            INTEGER,
                   cardFwRetries            Integer32
   }

cardFwVerSlot  OBJECT-TYPE
                   SYNTAX INTEGER (1..24)
                MAX-ACCESS not-accessible
                   STATUS current
                   DESCRIPTION "card slot number"
                   ::= { cardFwVerEntry 1 }

cardFwVerType  OBJECT-TYPE
                   SYNTAX Integer32
                   MAX-ACCESS read-write
                   STATUS current
                   DESCRIPTION "Card type"
                   ::= { cardFwVerEntry 2 }

cardFwVerCurrent  OBJECT-TYPE
                   SYNTAX OCTET STRING (SIZE(13))
                   MAX-ACCESS read-only
                   STATUS current
                   DESCRIPTION "Card firmware version currently loaded on 
                                firmware"
                   ::= { cardFwVerEntry 3 }

cardFwVerCurrentIsDefault  OBJECT-TYPE
                   SYNTAX Integer32
                   MAX-ACCESS read-only
                   STATUS current
                   DESCRIPTION "curent driver is default"
                   ::= { cardFwVerEntry 4 }

cardFwVerNext  OBJECT-TYPE
                   SYNTAX OCTET STRING (SIZE(13))
                   MAX-ACCESS read-write
                   STATUS current
                   DESCRIPTION "Card firmware version that user wants to 
                             upgrade to.  The values are limited those 
                             supported by the release."
                   ::= { cardFwVerEntry 5 }

cardFwVerNextIsDefault  OBJECT-TYPE
                   SYNTAX INTEGER (0..1)
                   MAX-ACCESS read-write
                   STATUS current
                   DESCRIPTION "next driver is default"
                   ::= { cardFwVerEntry 6 }

cardFwDnldStatus  OBJECT-TYPE
                   SYNTAX INTEGER  {
                              failed(1),
                              retry(2),
                              progress(3),
                              done(4),
            wrongCardType(5),
            wrongCardSType(6),
            drvUnavailable(7),
            drvInvHdrChksum(8),
            drvInvRecChksum(9),
            reqRepTimeout(10),
            cmplRepTimeout(11),
            mapCorrupted(12),
            mapUnavailable(13),
            mapInvChksum(14),
            mapNameImprop(15),
            cfgCorrupted(16),
            cfgUnavailable(17),
            cfgInvChksum(18),
            removeCardBeforeFinish(19),
            ioUnsupported(20)
      		}
   		MAX-ACCESS read-only
   		STATUS current
   		DESCRIPTION "firmware download procedure status"
   		DEFVAL { done }
   		::= { cardFwVerEntry 7 }

cardFwRetries  OBJECT-TYPE
                   SYNTAX Integer32
                   MAX-ACCESS read-only
                   STATUS current
                   DESCRIPTION "Number of times firmware download 
                             procedure failed consequently."
                   ::= { cardFwVerEntry 8 }

fwDriverTable OBJECT-TYPE
                   SYNTAX SEQUENCE OF FwDriverEntry
                   MAX-ACCESS not-accessible
                   STATUS current
                   DESCRIPTION "Table of available firmware drivers"
                   ::= {  fwDriverSup 2 }
 
fwDriverEntry OBJECT-TYPE
                SYNTAX FwDriverEntry
                   MAX-ACCESS not-accessible
                   STATUS current
                   DESCRIPTION "Row definition for available firmware drivers"
                   INDEX { fwSlotId, fwDriverType, fwIsDefault, fwDriverName }
                   ::= { fwDriverTable 1 }
 
FwDriverEntry ::= SEQUENCE {
                fwSlotId                Integer32,
                fwDriverType            Integer32,
                            fwIsDefault                    Integer32,
                fwDriverName            OCTET STRING,
                fwDriverFrn             Integer32,
                fwDriverSize            Integer32,
                fwDriverChecksum        Integer32
                }
 
fwSlotId OBJECT-TYPE
                SYNTAX Integer32
                MAX-ACCESS not-accessible
                STATUS current
                DESCRIPTION "driver slot id"
                ::= { fwDriverEntry 1 }

fwDriverType OBJECT-TYPE
                SYNTAX Integer32
                MAX-ACCESS not-accessible
                STATUS current
                DESCRIPTION "firmware driver type - definition 
                             consistent with cardType."
                ::= { fwDriverEntry 2 }

fwIsDefault OBJECT-TYPE
                SYNTAX Integer32
                MAX-ACCESS not-accessible
                STATUS current
                DESCRIPTION "firmware driver wether default or not"
                ::= { fwDriverEntry 3 }

fwDriverName OBJECT-TYPE
                SYNTAX OCTET STRING (SIZE(13))
                MAX-ACCESS not-accessible
                STATUS current
                DESCRIPTION "firmware driver file name"
                ::= { fwDriverEntry 4 }
 
fwDriverFrn  OBJECT-TYPE
                SYNTAX Integer32
                MAX-ACCESS read-only
                STATUS current
                DESCRIPTION "Firmware Release Number of firmware driver"
                ::= { fwDriverEntry 5 }

fwDriverSize  OBJECT-TYPE
                SYNTAX Integer32
                MAX-ACCESS read-only
                STATUS current
                DESCRIPTION "file size of firmware driver"
                ::= { fwDriverEntry 6 }

fwDriverChecksum  OBJECT-TYPE
                SYNTAX Integer32
                MAX-ACCESS read-only
                STATUS current
                DESCRIPTION "checksum of firmware driver file"
                ::= { fwDriverEntry 7 }
--
-- Tone Annce Control group
--
-- Fields for initiating the compression action.
tasCmprsAnnceId OBJECT-TYPE
                SYNTAX INTEGER (1..100)
                MAX-ACCESS read-write
                STATUS current
                DESCRIPTION "Announcement ID for this announcement file
                            to be compressed."
                ::= { toneAnnceControl 31 }

tasCmprsAnnceReplaceId OBJECT-TYPE
                SYNTAX INTEGER (1..100)
                MAX-ACCESS read-write
                STATUS current
                DESCRIPTION "Announcement ID of the announcement file
                             to be replaced from the announcement
                             table by this file."
                ::= { toneAnnceControl 32 }

tasCmprsAnnceFilename OBJECT-TYPE
                SYNTAX DisplayString (SIZE(79))
                MAX-ACCESS read-write
                STATUS current
                DESCRIPTION "File name for this announcement which is 
                        to be compressed."
                ::= { toneAnnceControl 33 }

tasCmprsAnnceDescription OBJECT-TYPE
                SYNTAX DisplayString (SIZE(255))
                MAX-ACCESS read-write
                STATUS current
                DESCRIPTION "Description for this announcement which is to
                             to be compressed."
                ::= { toneAnnceControl 34 }

tasCmprsAnnceCmprsType OBJECT-TYPE
               SYNTAX INTEGER {
                                uncompressed(1),
                                compress8k(2),
                                compress16k(3),
                                compress32k(4)
                               }
                MAX-ACCESS read-write
                STATUS current
                DESCRIPTION "The type of compression used for
                             storing this announcement."
                ::= { toneAnnceControl 35 }

tasCmprsAnnceType OBJECT-TYPE
                SYNTAX INTEGER {
                                voice(1),
                                toneVoice(2),
                                userTones(3),
                                music(4),
                                musicVoice(5),
                                toneMusic(6)
                               }
                MAX-ACCESS read-write
                STATUS current
                DESCRIPTION "The type of this announcement."
                ::= { toneAnnceControl 36 }

tasCmprsAnnceIntfIndex OBJECT-TYPE
                SYNTAX IntfIndex
                MAX-ACCESS read-write
                STATUS current
                DESCRIPTION "Interface index in SSPPCCC format of TASM
                        card on which this announcement is to be 
                        compressed."
                ::= { toneAnnceControl 37 }


tasCmprsAction  OBJECT-TYPE
                SYNTAX INTEGER  {
                                 compress(1),
                                 delete(2),
                                 store(3) 
                                }
                MAX-ACCESS read-write
                STATUS current
                DESCRIPTION "Action to be performed on this announcement."
                ::= { toneAnnceControl 38 }

--  Fields for initiating  the playing of the specified 
--  announcement on the specified interface.

tasTstAnnceId OBJECT-TYPE
                SYNTAX INTEGER (1..100)
                MAX-ACCESS read-write
                STATUS current
                DESCRIPTION "Announcement ID to be played for testing."
                ::= { toneAnnceControl 39 }

tasTstAnnceIntfIndex OBJECT-TYPE
                SYNTAX IntfIndex
                MAX-ACCESS read-write
                STATUS current
                DESCRIPTION "Interface index in SSPPCCC format of 
                        CE card on which this announcement
                        is to be played for testing."
                ::= { toneAnnceControl 40 }

tasTstAnnceLawType OBJECT-TYPE
                SYNTAX INTEGER {
                                a-Law(1),
                                u-Law(2)
                                }
                MAX-ACCESS read-write
                STATUS current
                DESCRIPTION "The type of CE card towards which
                        this announcement is to be played.
                        A-Law is for E1 and U-Law is for DS1"
                ::= { toneAnnceControl 41 }

tasTstAnnceAction  OBJECT-TYPE
                SYNTAX INTEGER  {
                                 playStart(1),
                                 playStop(2),
                                 playAbort(3)
                                }
                MAX-ACCESS read-write
                STATUS current
                DESCRIPTION "Action to be performed on this announcement
                             for testing."
                ::= { toneAnnceControl 42 }

-- Fields for initiating the specified line tests on the specified interface.
--
tasTstLineId OBJECT-TYPE
                SYNTAX Integer32
                MAX-ACCESS read-write
                STATUS current
                DESCRIPTION "Test ID to be started for line testing."
                ::= { toneAnnceControl 43 }

tasTstLineIntfIndex OBJECT-TYPE
                SYNTAX IntfIndex
                MAX-ACCESS read-write
                STATUS current
                DESCRIPTION "Interface index in SSPPCCC format of 
                        CE card on which this test is to be initiated."
                ::= { toneAnnceControl 44 }

tasTstLineAction  OBJECT-TYPE
                SYNTAX INTEGER {
                                tstStart(1),
                                tstStop(2),
                                tstAbort(3)
                               }
                MAX-ACCESS read-write
                STATUS current
                DESCRIPTION "Test action to be performed."
                ::= { toneAnnceControl 45 }

tasMemIntfIndex       OBJECT-TYPE
                SYNTAX IntfIndex
                MAX-ACCESS read-write
                STATUS current
                DESCRIPTION "Interface index in SSPPCCC format of TASM card on which
                             the memory  is to be initialised."
                ::= { toneAnnceControl 46 }

tasMemAction  OBJECT-TYPE
                SYNTAX INTEGER {
                                re-initialize(1)
                               }
                MAX-ACCESS read-write
                STATUS current
                DESCRIPTION "Test action to be performed."
                ::= { toneAnnceControl 47 } 

-- OAM segment flows

toneAnnceIpAddress OBJECT-TYPE
                SYNTAX IpAddress
                MAX-ACCESS read-write
                STATUS current
                DESCRIPTION "IP Address for announcement ftp server."
                ::= { toneAnnceControl 48 }
 
toneAnnceAccountName OBJECT-TYPE
                SYNTAX DisplayString (SIZE(20))
                MAX-ACCESS read-write
                STATUS current
                DESCRIPTION "ftp account name for access to announcement 
                        ftp server."
                ::= { toneAnnceControl 49 }
 
toneAnnceAccountPassword OBJECT-TYPE
                SYNTAX DisplayString (SIZE(20))
                MAX-ACCESS read-write
                STATUS current
                DESCRIPTION "ftp account password for access to announcement ftp
                             server."
                ::= { toneAnnceControl 50 }
 
toneAnnceSourceFile OBJECT-TYPE
                SYNTAX DisplayString (SIZE(79))
                MAX-ACCESS read-write
                STATUS current
                DESCRIPTION "announcement file with complete path on the ftp 
                        server "
                ::= { toneAnnceControl 51 }

toneAnnceDestinationFile OBJECT-TYPE
                SYNTAX DisplayString (SIZE(12))
                MAX-ACCESS read-write
                STATUS current
                DESCRIPTION "The announcementSourceFile will be renamed with
                        MS DOS file format and placed in the /scsi/announce 
                        directory on the disk."
                ::= { toneAnnceControl 52 }
 
toneAnnceFtpStatus OBJECT-TYPE
                SYNTAX INTEGER {
                                noActivity(1),
                                working(2),
                                doneSuccessfully(3),
                                doneWithError(4),
                                aborted(5)
                               } 
                MAX-ACCESS read-only
                STATUS current
                DESCRIPTION "Current status of the ftp announcement download.
                             Status of the software announcement.  noActivity 
                             is the initial start state from boot-up.  working
                             is set while ftp'ing the announcement.  
                             The final state is one of doneSuccessfully, 
                             doneWithError, or aborted, all self-explanatory.  
                             It will stay in this state until re-boot or 
                             starting an announcement.  If the state is 
                             doneWithError then announcementSwErrorStatus will 
                             be set to reflect the type of error."
                ::= { toneAnnceControl 53 }

toneAnnceFtpErrorStatus OBJECT-TYPE
                SYNTAX INTEGER {
                                none(1),
                                userAbort(2),
                                invalidIpAddress(3),
                                invalidAccountName(4),
                                invalidAccountPassword(5),
                                invalidSourceFile(6),
                                invalidDstFileNameFormat(7),
                                dstFileNameAlreadyExist(8),
                                tooManyAnnouncementNow(9),
                                diskSpaceUsageExceed(10),
                                unableToOpenFile(11),
                                unableToMakeFtpConnection(12),
                                unableToWriteFile(13),
                                unableToCompleteFtp(14),
                                unableToSpawnTask(15),
                                unableToOpenScsiAnncDir(16),
                                statFails(17)
                               } 
                MAX-ACCESS read-only
                STATUS current
                DESCRIPTION "The result of the finish of the ftp software
                             announcement download.
                             Set to a value 3-21 if announcementSwCopyStatus is
                             doneWithError.  Set to none if 
                             announcementFtpCopyStatus
                             is doneSuccessfully.  Set to userAbort if
                             announcementSwCopyStatus is aborted."
                DEFVAL { none }
                ::= { toneAnnceControl 54 }

toneAnnceFtpAction    OBJECT-TYPE
                SYNTAX INTEGER {
                                start(1),
                                abort(2)
                               } 
                MAX-ACCESS read-write
                STATUS current
                DESCRIPTION "start ftp announcement files.  When 
                        announcementFtpCopyStatus is working, the start
                        request will be ignored.  Abort will have effect
                        only when announcementFtpCopystatus is working."
                ::= { toneAnnceControl 55 }



-- ATM Trunking IWF Group
 
atmTrunkingIWFBaseGroup   OBJECT IDENTIFIER ::= { atmTrunkingMIBObjects 1 }
 
atmTrunkingIWFIdentifier OBJECT-TYPE
        SYNTAX Integer32
        MAX-ACCESS read-write
        STATUS current
        DESCRIPTION "IWF ID for the local endpoint"
        DEFVAL { 0 }
        ::= { atmTrunkingIWFBaseGroup 1 }
 
atmTrunkingIWFLocalAddress OBJECT-TYPE
        SYNTAX OCTET STRING (SIZE(20))
        MAX-ACCESS read-write
        STATUS current
        DESCRIPTION "IWF ATM address for the local endpoint"
        ::= { atmTrunkingIWFBaseGroup 2 }
 
atmTrunkingIWFMaxRemoteIWF OBJECT-TYPE
        SYNTAX Integer32
        MAX-ACCESS read-write
        STATUS current
        DESCRIPTION "Maximum remote IWF that can connect to this endpoint"
        DEFVAL { 100 }
        ::= { atmTrunkingIWFBaseGroup 3 }
 
atmTrunkingIWFAdminStatus OBJECT-TYPE
        SYNTAX INTEGER { up(1), down(2), delete(3) }
        MAX-ACCESS read-write
        STATUS current
        DESCRIPTION "Indicates whether the Local IWF is active or not"
        ::= { atmTrunkingIWFBaseGroup 4 }
 
 
 
atmTrunkingRemoteIWFTable OBJECT-TYPE
        SYNTAX SEQUENCE OF AtmTrunkingRemoteIWFEntry
        MAX-ACCESS not-accessible
        STATUS current
        DESCRIPTION "Remote IWF table"
        ::= { atmTrunkingMIBObjects 2 }
 
atmTrunkingRemoteIWFEntry OBJECT-TYPE
        SYNTAX AtmTrunkingRemoteIWFEntry
        MAX-ACCESS not-accessible
        STATUS current
        DESCRIPTION "Entry in atmTrunkingRemoteIWFTable"
        INDEX { atmTrunkingRemoteIWFIdentifier }
        ::= { atmTrunkingRemoteIWFTable 1 }
 
AtmTrunkingRemoteIWFEntry ::=
        SEQUENCE {
                atmTrunkingRemoteIWFIdentifier Integer32,
                atmTrunkingRemoteIWFAddress OCTET STRING,
                atmTrunkingRemoteIWFTrnkMode INTEGER,
                atmTrunkingRemoteIWFAdminStatus INTEGER,
                atmTrunkingRemoteIWFRowStatus RowStatus
                }
 
atmTrunkingRemoteIWFIdentifier OBJECT-TYPE
        SYNTAX Integer32
        MAX-ACCESS not-accessible
        STATUS current
        DESCRIPTION "IWF ID for the remote IWF"
        ::= { atmTrunkingRemoteIWFEntry 1 }
 
atmTrunkingRemoteIWFAddress OBJECT-TYPE
        SYNTAX OCTET STRING (SIZE(20))
        MAX-ACCESS read-create
        STATUS current
        DESCRIPTION "IWF ATM address for the remote IWF"
        ::= { atmTrunkingRemoteIWFEntry 2 }

atmTrunkingRemoteIWFTrnkMode OBJECT-TYPE
        SYNTAX INTEGER { switched(1), non-switched(2) }
        MAX-ACCESS read-create
        STATUS current
        DESCRIPTION "Maximum remote IWF that can connect to this endpoint"
        DEFVAL { switched }
        ::= { atmTrunkingRemoteIWFEntry 3 }
 
atmTrunkingRemoteIWFAdminStatus OBJECT-TYPE
        SYNTAX INTEGER { up(1), down(2) }
        MAX-ACCESS read-create
        STATUS current
        DESCRIPTION "Indicates whether the Local IWF is active or not"
        ::= { atmTrunkingRemoteIWFEntry 4 }
 
atmTrunkingRemoteIWFRowStatus OBJECT-TYPE
        SYNTAX RowStatus
        MAX-ACCESS read-create
        STATUS current
        DESCRIPTION "Maximum remote IWF that can connect to this endpoint"
        ::= { atmTrunkingRemoteIWFEntry 5 }
 
 
 
atmTrunkingSigVccTable OBJECT-TYPE
        SYNTAX SEQUENCE OF AtmTrunkingSigVccEntry
        MAX-ACCESS not-accessible
        STATUS current
        DESCRIPTION "Table of iwf signaling vcc configuration entities"
        ::= { atmTrunkingMIBObjects 3 }
 
atmTrunkingSigVccEntry OBJECT-TYPE
        SYNTAX AtmTrunkingSigVccEntry
        MAX-ACCESS not-accessible
        STATUS current
        DESCRIPTION "Entry in atmTrunkingSigVccTable"
        INDEX { atmTrunkingSigVccRmtIWFIdentifier,
                atmTrunkingSigVccIdentifier }
        ::= { atmTrunkingSigVccTable 1 }
 
 
AtmTrunkingSigVccEntry ::=
        SEQUENCE {
                atmTrunkingSigVccRmtIWFIdentifier Integer32,
                atmTrunkingSigVccIdentifier    INTEGER,
                atmTrunkingSigVccOutgoingIfIndex IntfIndex,
                atmTrunkingSigVccOutgoingVpi   INTEGER,
                atmTrunkingSigVccOutgoingVci   INTEGER,
                atmTrunkingSigVccOwner         INTEGER,
                atmTrunkingSigVccInactiveTimer Integer32,
                atmTrunkingSigVccType          INTEGER,
                atmTrunkingSigVccSignaling     INTEGER,
                atmTrunkingSigVccFwPcr01       Integer32,
                atmTrunkingSigVccBwPcr01       Integer32,
                atmTrunkingSigVccFwScr01       Integer32,
                atmTrunkingSigVccBwScr01       Integer32,
                atmTrunkingSigVccFwMbs01       Integer32,
                atmTrunkingSigVccBwMbs01       Integer32,
                atmTrunkingSigVccMaxAal2Vcc    Integer32,
                atmTrunkingSigVccActiveAal2Vcc Integer32,
                atmTrunkingSigVccOperStatus    Integer32,
                atmTrunkingSigVccRowStatus     RowStatus,
                atmTrunkingSigVccViB           INTEGER,
                atmTrunkingSigVccVUNIB         INTEGER,
                atmTrunkingSigVccRetryTimer    Integer32,
                atmTrunkingSigVccRetryLimit    Integer32,
                atmTrunkingSigVccRestart       INTEGER,
                atmTrunkingSigVccPriority      INTEGER,
                atmTrunkingSigVccRetryCounter  Integer32
                }
 
atmTrunkingSigVccRmtIWFIdentifier OBJECT-TYPE
        SYNTAX Integer32
        MAX-ACCESS not-accessible
        STATUS current
        DESCRIPTION "IWF ID for the remote IWF"
        ::= { atmTrunkingSigVccEntry 1 }

atmTrunkingSigVccIdentifier OBJECT-TYPE
        SYNTAX INTEGER (0..16383)
        MAX-ACCESS not-accessible
        STATUS current
        DESCRIPTION "Vcc ID assigned by the owner of this signaling Vcc"
        ::= { atmTrunkingSigVccEntry 2 }

atmTrunkingSigVccOutgoingIfIndex OBJECT-TYPE
        SYNTAX IntfIndex
        MAX-ACCESS read-create
        STATUS current
        DESCRIPTION "Intf index of the outgoing interface,readonly for SVC/SPVC"
        ::= { atmTrunkingSigVccEntry 3 }
 
atmTrunkingSigVccOutgoingVpi OBJECT-TYPE
        SYNTAX INTEGER (0..4095)
        MAX-ACCESS read-create
        STATUS current
        DESCRIPTION "VPI used at the outgoing interface, readonly for SVC/SPVC"
        ::= { atmTrunkingSigVccEntry 4 }
 
atmTrunkingSigVccOutgoingVci OBJECT-TYPE
        SYNTAX INTEGER (0..65535)
        MAX-ACCESS read-create
        STATUS current
        DESCRIPTION "VCI used at the outgoing interface, readonly for SVC/SPVC"
        ::= { atmTrunkingSigVccEntry 5 }
 
atmTrunkingSigVccOwner OBJECT-TYPE
        SYNTAX INTEGER { local(1), remote(2) }
        MAX-ACCESS read-create
        STATUS current
        DESCRIPTION "Indicates who is the owner of the Sig VCC"
        ::= { atmTrunkingSigVccEntry 6 }
 
atmTrunkingSigVccInactiveTimer OBJECT-TYPE
        SYNTAX Integer32
        MAX-ACCESS read-create
        STATUS current
        DESCRIPTION "Inactive time period on which to clear the call"
        DEFVAL { 3600 }
        ::= { atmTrunkingSigVccEntry 7 }
 
atmTrunkingSigVccType OBJECT-TYPE
        SYNTAX INTEGER { pvc(1), spvc(2), svc(3) }
        MAX-ACCESS read-create
        STATUS current
        DESCRIPTION "Indicates if the SigVcc should be setup as PVC/SPVC/SVC"
        DEFVAL { svc }
        ::= { atmTrunkingSigVccEntry 8 }
 
atmTrunkingSigVccSignaling OBJECT-TYPE
        SYNTAX INTEGER { pss1(1), dss1(2), dpnss(3), other(4) }
        MAX-ACCESS read-create
        STATUS current
        DESCRIPTION "Indicates the signalling protocol used between the IWFs"
        DEFVAL { other }
        ::= { atmTrunkingSigVccEntry 9 }
 
atmTrunkingSigVccFwPcr01 OBJECT-TYPE
        SYNTAX Integer32
        MAX-ACCESS read-create
        STATUS current
        DESCRIPTION "Forward PCR for the call"
        DEFVAL { 1 }
        ::= { atmTrunkingSigVccEntry 10 }
 
atmTrunkingSigVccBwPcr01 OBJECT-TYPE
        SYNTAX Integer32
        MAX-ACCESS read-create
        STATUS current
        DESCRIPTION "Backward PCR for the call"
        DEFVAL { 1 }
        ::= { atmTrunkingSigVccEntry 11 }
 
atmTrunkingSigVccFwScr01 OBJECT-TYPE
        SYNTAX Integer32
        MAX-ACCESS read-create
        STATUS current
        DESCRIPTION "Forward SCR for the call"
        DEFVAL { 1 }
        ::= { atmTrunkingSigVccEntry 12 }

atmTrunkingSigVccBwScr01 OBJECT-TYPE
        SYNTAX Integer32
        MAX-ACCESS read-create
        STATUS current
        DESCRIPTION "Backward SCR for the call"
        DEFVAL { 1 }
        ::= { atmTrunkingSigVccEntry 13 }
 
atmTrunkingSigVccFwMbs01 OBJECT-TYPE
        SYNTAX Integer32
        MAX-ACCESS read-create
        STATUS current
        DESCRIPTION "Forward MBS for the call"
        DEFVAL { 1 }
        ::= { atmTrunkingSigVccEntry 14 }
 
atmTrunkingSigVccBwMbs01 OBJECT-TYPE
        SYNTAX Integer32
        MAX-ACCESS read-create
        STATUS current
        DESCRIPTION "Backward MBS for the call"
        DEFVAL { 1 }
        ::= { atmTrunkingSigVccEntry 15 }
 
atmTrunkingSigVccMaxAal2Vcc OBJECT-TYPE
        SYNTAX Integer32
        MAX-ACCESS read-create
        STATUS current
        DESCRIPTION "Maximum number of bearer VCCs controlled by this SigVcc"
        DEFVAL { 255 }
        ::= { atmTrunkingSigVccEntry 16 }
 
atmTrunkingSigVccActiveAal2Vcc OBJECT-TYPE
        SYNTAX Integer32
        MAX-ACCESS read-only
        STATUS current
        DESCRIPTION "Number of active bearer VCCs controlled by this SigVcc"
        ::= { atmTrunkingSigVccEntry 17 }
 
atmTrunkingSigVccOperStatus OBJECT-TYPE
        SYNTAX INTEGER { idle(1),
                         outOfService(2),
                         init(3),
                         connecting(4),
                         active(5),
                         release(6) }
        MAX-ACCESS read-only
        STATUS current
        DESCRIPTION "Indicates whether the Local IWF is active or not"
        ::= { atmTrunkingSigVccEntry 18 }
 
atmTrunkingSigVccRowStatus OBJECT-TYPE
        SYNTAX RowStatus
        MAX-ACCESS read-create
        STATUS current
        DESCRIPTION "Row status"
        ::= { atmTrunkingSigVccEntry 19 }
 
atmTrunkingSigVccViB  OBJECT-TYPE
                SYNTAX INTEGER (0..1024)
                MAX-ACCESS read-create
                STATUS current
                DESCRIPTION "VI to associate the Egress part of A2B connection"
                DEFVAL { 0 }
                ::= { atmTrunkingSigVccEntry 20 }
 
atmTrunkingSigVccVUNIB  OBJECT-TYPE
                SYNTAX INTEGER (0..255)
                MAX-ACCESS read-create
                STATUS current
                DESCRIPTION "VUNI associated the Egress part of A2B connection"
                DEFVAL { 0 }
                ::= { atmTrunkingSigVccEntry 21 }


atmTrunkingSigVccRetryTimer OBJECT-TYPE
        SYNTAX Integer32
        MAX-ACCESS read-create
        STATUS current
        DESCRIPTION " the time(seconds) to wait before attempting to establish
                      the ATM Trunking Signalling VCC SPVC after previous failed
                      call attempt. 0 indicates retries will be attempted immedi
                      ately"
        DEFVAL { 30 }
        ::= { atmTrunkingSigVccEntry 22}

atmTrunkingSigVccRetryLimit OBJECT-TYPE
        SYNTAX Integer32
        MAX-ACCESS read-create
        STATUS current
        DESCRIPTION "ATM Trunking Signalling VCC SPVC Retry Limit. 
                     0 indicates unlimited "
        DEFVAL { 0 }
        ::= { atmTrunkingSigVccEntry 23}

atmTrunkingSigVccRestart OBJECT-TYPE
        SYNTAX INTEGER  {
                restart(1),
                noop(2)
                }
        MAX-ACCESS read-write
        STATUS current
        DESCRIPTION "The active ATM Trunking SPVC is released, if necessary, 
                 and a new setup procedure is begun if restart,
                 otherwise, noop."
        ::= { atmTrunkingSigVccEntry 24 }

atmTrunkingSigVccPriority OBJECT-TYPE
        SYNTAX INTEGER  {
                priority-1(1),
                priority-2(2),
                priority-3(3),
                priority-4(4)
                }
        MAX-ACCESS read-write
        STATUS current
        DESCRIPTION "Priority of TrunkingSigVcc - priority-1 being highest priority ."
        DEFVAL { priority-1 }
        ::= { atmTrunkingSigVccEntry 25 }


atmTrunkingSigVccRetryCounter OBJECT-TYPE
        SYNTAX Integer32
        MAX-ACCESS read-only
        STATUS current
        DESCRIPTION "Indicates how many attempts to establish the
                 connection have failed.  It is reset whenever a
                 connection is successfully established or the SigVcc SPVC
                 is restarted."
        ::= { atmTrunkingSigVccEntry 26 }

 
atmTrunkingBrVccConfigTable  OBJECT-TYPE
                SYNTAX SEQUENCE OF AtmTrunkingBrVccConfigEntry
                MAX-ACCESS not-accessible
                STATUS     current
                DESCRIPTION "Table of iwf aal2 bearer vcci configuration
                             entities"
                ::= { atmTrunkingMIBObjects 4 }
 
atmTrunkingBrVccConfigEntry  OBJECT-TYPE
                SYNTAX AtmTrunkingBrVccConfigEntry
                MAX-ACCESS not-accessible
                STATUS current
                DESCRIPTION   "Row definition for iwf aal2 vcci configuration"
                INDEX { atmTrunkingBrVccRmtIWFId,
                        atmTrunkingBrVccId
                      }
                ::= { atmTrunkingBrVccConfigTable 1 }

AtmTrunkingBrVccConfigEntry  ::= SEQUENCE {
                atmTrunkingBrVccRmtIWFId                     Integer32,
                atmTrunkingBrVccSigVccId                     INTEGER,
                atmTrunkingBrVccId                           INTEGER,
                atmTrunkingBrVccIf                           IntfIndex,
                atmTrunkingBrVccVpi                          INTEGER,
                atmTrunkingBrVccVci                          INTEGER,
                atmTrunkingBrVccViB                          INTEGER,
                atmTrunkingBrVccVUNIB                        INTEGER,
                atmTrunkingBrVccServiceType                  INTEGER,
                atmTrunkingBrVccSarType                      INTEGER,
                atmTrunkingBrVccOwner                        INTEGER,
                atmTrunkingBrVccOperStatus                   INTEGER,
                atmTrunkingBrVccFwAtmPcr01                   Integer32,
                atmTrunkingBrVccBwAtmPcr01                   Integer32,
                atmTrunkingBrVccFwAtmScr01                   Integer32,
                atmTrunkingBrVccBwAtmScr01                   Integer32,
                atmTrunkingBrVccFwAtmMbs01                   Integer32,
                atmTrunkingBrVccBwAtmMbs01                   Integer32,
                atmTrunkingBrVccConnType                     INTEGER,
                atmTrunkingBrVccActiveChanCnt                Integer32,
                atmTrunkingBrVccMaxAal2ChanId                Integer32,
                atmTrunkingBrVccCircuitModeDataSupp          INTEGER,
                atmTrunkingBrVccFrameModeSupp                INTEGER,
                atmTrunkingBrVccFaxModSupp                   INTEGER,
                atmTrunkingBrVccCASPktXportSupp              INTEGER,
                atmTrunkingBrVccDTMFPktXportSupp             INTEGER,
                atmTrunkingBrVccMFR1PktXportSupp             INTEGER,
                atmTrunkingBrVccMFR2PktXportSupp             INTEGER,
                atmTrunkingBrVccPCMEncoding                  INTEGER,
                atmTrunkingBrVccMaxFrameLength               INTEGER,
                atmTrunkingBrVccIdleChannSuprSupp            INTEGER,
                atmTrunkingBrVccSilenceDetSupp               INTEGER,
                atmTrunkingBrVccCompressionSpec              INTEGER,
                atmTrunkingBrVccAudioProfileSource           INTEGER,
                atmTrunkingBrVccAudioProfileId               INTEGER,
                atmTrunkingBrVccAvailBw                      INTEGER,
                atmTrunkingBrVccRowStatus                    RowStatus,
                atmTrunkingBrVccGr303Supp                    INTEGER,
                atmTrunkingBrVccOamStatus                    INTEGER,
                atmTrunkingBrVccInactiveTimer                Integer32,
                atmTrunkingBrVccRetryTimer                   Integer32,
                atmTrunkingBrVccRetryLimit                   Integer32,
                atmTrunkingBrVccRestart                      INTEGER,
                atmTrunkingBrVccCuTimer                      INTEGER,
                atmTrunkingBrVccPriority                     INTEGER,
                atmTrunkingBrVccRetryCounter                 Integer32
                }
 
atmTrunkingBrVccRmtIWFId OBJECT-TYPE
        SYNTAX Integer32
        MAX-ACCESS not-accessible
        STATUS current
        DESCRIPTION "IWF ID for the remote IWF"
        ::= { atmTrunkingBrVccConfigEntry 1 }

atmTrunkingBrVccSigVccId OBJECT-TYPE
        SYNTAX INTEGER (0..16383)
        MAX-ACCESS read-only
        STATUS current
        DESCRIPTION "Signalling Vcc associated with this Br Vcc"
        ::= { atmTrunkingBrVccConfigEntry 2 }

atmTrunkingBrVccId      OBJECT-TYPE
                SYNTAX INTEGER (1..4096)
                MAX-ACCESS not-accessible
                STATUS current
                DESCRIPTION "Id of the AAL2 Bear Vcc"
                ::= { atmTrunkingBrVccConfigEntry 3 }
 
atmTrunkingBrVccIf  OBJECT-TYPE
                SYNTAX IntfIndex
                MAX-ACCESS read-create
                STATUS current
                DESCRIPTION "Intf index of the outgoing interface,
                             readonly for SVC/SPVC"
                ::= { atmTrunkingBrVccConfigEntry 4 }
 
atmTrunkingBrVccVpi  OBJECT-TYPE
                SYNTAX INTEGER (0..4095)
                MAX-ACCESS read-create
                STATUS current
                DESCRIPTION "VPI value of this VCC connection.
                             Valid range is a number between 0 and 4095."
                ::= { atmTrunkingBrVccConfigEntry 5 }
atmTrunkingBrVccVci  OBJECT-TYPE
                SYNTAX INTEGER (0..65535)
                MAX-ACCESS read-create
                STATUS current
                DESCRIPTION "VCI value of this VCC connection.
                             Valid range is a number between 0 and 65535."
                ::= { atmTrunkingBrVccConfigEntry 6 }
 
atmTrunkingBrVccViB  OBJECT-TYPE
                SYNTAX INTEGER (0..1024)
                MAX-ACCESS read-create
                STATUS current
                DESCRIPTION "VI to associate the Egress part of A2B connection"
                DEFVAL { 0 }
                ::= { atmTrunkingBrVccConfigEntry 7 }
 
atmTrunkingBrVccVUNIB  OBJECT-TYPE
                SYNTAX INTEGER (0..255)
                MAX-ACCESS read-create
                STATUS current
                DESCRIPTION "VUNI associated the Egress part of A2B connection"
                DEFVAL { 0 }
                ::= { atmTrunkingBrVccConfigEntry 8 }
 
atmTrunkingBrVccServiceType  OBJECT-TYPE
                SYNTAX INTEGER {
                               cbr-1(1),
                               cbr-2(2),
                               cbr-3(3),
                               cbr-4(4),
                               ubr(5),
                               vbr-nrt2(6),
                               vbr-nrt1(7),
                               vbr-rt2(8),
                               vbr-rt1(9),
                               vbr-express(10)
                               }
                MAX-ACCESS read-create
                STATUS current
                DESCRIPTION "service type"
                DEFVAL { cbr-1 }
                ::= { atmTrunkingBrVccConfigEntry 9 }
 
atmTrunkingBrVccSarType  OBJECT-TYPE
                SYNTAX INTEGER {
                               aal1(1),
                               aal2(2)
                               }
                MAX-ACCESS read-create
                STATUS current
                DESCRIPTION "sar type"
                DEFVAL { aal2 }
                ::= { atmTrunkingBrVccConfigEntry 10 }
 
atmTrunkingBrVccOwner  OBJECT-TYPE
                SYNTAX INTEGER {
                               local (1),
                               remote (2)
                               }
                MAX-ACCESS read-create
                STATUS current
                DESCRIPTION "The owner of this Vcc"
                ::= { atmTrunkingBrVccConfigEntry 11 }
 
atmTrunkingBrVccOperStatus  OBJECT-TYPE
                SYNTAX INTEGER {
                               idle (1),
                               outOfService(2),
                               init (3),
                               active (4),
                               release(5)
                               }
                MAX-ACCESS read-only
                STATUS current
                DESCRIPTION "The Operational Status of this Bearer Vcc"
                ::= { atmTrunkingBrVccConfigEntry 12 }
atmTrunkingBrVccFwAtmPcr01  OBJECT-TYPE
                SYNTAX Integer32
                MAX-ACCESS read-create
                STATUS current
                DESCRIPTION "Forward pcr (0+1)"
                DEFVAL { 172 }
                ::= { atmTrunkingBrVccConfigEntry 13 }
 
atmTrunkingBrVccBwAtmPcr01  OBJECT-TYPE
                SYNTAX Integer32
                MAX-ACCESS read-create
                STATUS current
                DESCRIPTION "Backward pcr (0+1)"
                DEFVAL { 172 }
                ::= { atmTrunkingBrVccConfigEntry 14 }
 
atmTrunkingBrVccFwAtmScr01  OBJECT-TYPE
                SYNTAX Integer32
                MAX-ACCESS read-create
                STATUS current
                DESCRIPTION "Forward scr (0+1)"
                DEFVAL { 172 }
                ::= { atmTrunkingBrVccConfigEntry 15 }
 
atmTrunkingBrVccBwAtmScr01  OBJECT-TYPE
                SYNTAX Integer32
                MAX-ACCESS read-create
                STATUS current
                DESCRIPTION "Backward scr (0+1)"
                DEFVAL { 172 }
                ::= { atmTrunkingBrVccConfigEntry 16 }
 
atmTrunkingBrVccFwAtmMbs01  OBJECT-TYPE
                SYNTAX Integer32
                MAX-ACCESS read-create
                STATUS current
                DESCRIPTION "Forward Mbs (0+1)"
                DEFVAL { 1 }
                ::= { atmTrunkingBrVccConfigEntry 17 }
 
atmTrunkingBrVccBwAtmMbs01  OBJECT-TYPE
                SYNTAX Integer32
                MAX-ACCESS read-create
                STATUS current
                DESCRIPTION "Backward Mbs (0+1)"
                DEFVAL { 1 }
                ::= { atmTrunkingBrVccConfigEntry 18 }
 
atmTrunkingBrVccConnType  OBJECT-TYPE
                SYNTAX INTEGER  {
                                svc  (1),
                                spvc (2),
                                pvc  (3)
                                }
                MAX-ACCESS read-create
                STATUS current
                DESCRIPTION "connection type"
                DEFVAL { svc }
                ::= { atmTrunkingBrVccConfigEntry 19 }
 
atmTrunkingBrVccActiveChanCnt  OBJECT-TYPE
                SYNTAX Integer32
                MAX-ACCESS read-only
                STATUS current
                DESCRIPTION "Number of currently active channels in this Vcc"
                DEFVAL { 0 }
                ::= { atmTrunkingBrVccConfigEntry 20 }
atmTrunkingBrVccMaxAal2ChanId  OBJECT-TYPE
                SYNTAX INTEGER (9..255)
                MAX-ACCESS read-create
                STATUS current
                DESCRIPTION "Max Id of channels supported within this br vcc"
                DEFVAL { 255 }
                ::= { atmTrunkingBrVccConfigEntry 21 }
 
atmTrunkingBrVccCircuitModeDataSupp OBJECT-TYPE
                SYNTAX INTEGER {
                               disable (1),
                               enable (2)
                               }
                MAX-ACCESS read-create
                STATUS current
                DESCRIPTION "Circuit mode data"
                DEFVAL { enable }
                ::= { atmTrunkingBrVccConfigEntry 22 }
 
atmTrunkingBrVccFrameModeSupp OBJECT-TYPE
                SYNTAX INTEGER {
                               disable (1),
                               enable (2)
                               }
                MAX-ACCESS read-create
                STATUS current
                DESCRIPTION "Frame mode data"
                DEFVAL { disable }
                ::= { atmTrunkingBrVccConfigEntry 23 }
 
atmTrunkingBrVccFaxModSupp OBJECT-TYPE
                SYNTAX INTEGER {
                               disable (1),
                               enable (2)
                               }
                MAX-ACCESS read-create
                STATUS current
                DESCRIPTION "FAX Demodulation"
                DEFVAL { enable }
                ::= { atmTrunkingBrVccConfigEntry 24 }
 
atmTrunkingBrVccCASPktXportSupp OBJECT-TYPE
                SYNTAX INTEGER {
                               disable (1),
                               enable (2)
                               }
                MAX-ACCESS read-create
                STATUS current
                DESCRIPTION "Channel Associated Signaling"
                DEFVAL { disable }
                ::= { atmTrunkingBrVccConfigEntry 25 }
 
atmTrunkingBrVccDTMFPktXportSupp OBJECT-TYPE
                SYNTAX INTEGER {
                               disable (1),
                               enable (2)
                               }
                MAX-ACCESS read-create
                STATUS current
                DESCRIPTION "DTMF Dialed Digits"
                DEFVAL { enable }
                ::= { atmTrunkingBrVccConfigEntry 26 }
atmTrunkingBrVccMFR1PktXportSupp OBJECT-TYPE
                SYNTAX INTEGER {
                               disable (1),
                               enable (2)
                               }
                MAX-ACCESS read-create
                STATUS current
                DESCRIPTION "MF-R1 Dialed Digits"
                DEFVAL { disable }
                ::= { atmTrunkingBrVccConfigEntry 27 }
 
atmTrunkingBrVccMFR2PktXportSupp OBJECT-TYPE
                SYNTAX INTEGER {
                               disable (1),
                               enable (2)
                               }
                MAX-ACCESS read-create
                STATUS current
                DESCRIPTION "MF-R2 Dialed Digits"
                DEFVAL { disable }
                ::= { atmTrunkingBrVccConfigEntry 28 }
 
atmTrunkingBrVccPCMEncoding OBJECT-TYPE
                SYNTAX INTEGER {
                               none (1),
                               a-law (2),
                               u-law (3)
                               }
                MAX-ACCESS read-create
                STATUS current
                DESCRIPTION "DTMF Dialed Digits"
                DEFVAL { a-law }
                ::= { atmTrunkingBrVccConfigEntry 29 }
 
atmTrunkingBrVccMaxFrameLength OBJECT-TYPE
                SYNTAX INTEGER (1..65535)
                MAX-ACCESS read-create
                STATUS current
                DESCRIPTION "Maximum length of frame mode data"
                DEFVAL { 4095 }
                ::= { atmTrunkingBrVccConfigEntry 30 }
 
atmTrunkingBrVccIdleChannSuprSupp OBJECT-TYPE
                SYNTAX INTEGER {
                               disable (1),
                               enable (2)
                               }
                MAX-ACCESS read-create
                STATUS current
                DESCRIPTION "Idle Channel Supression"
                DEFVAL { enable }
                ::= { atmTrunkingBrVccConfigEntry 31 }
 
atmTrunkingBrVccSilenceDetSupp OBJECT-TYPE
                SYNTAX INTEGER {
                               disable (1),
                               enable (2)
                               }
                MAX-ACCESS read-create
                STATUS current
                DESCRIPTION "Silence Detection"
                DEFVAL { enable }
                ::= { atmTrunkingBrVccConfigEntry 32 }
 
atmTrunkingBrVccCompressionSpec OBJECT-TYPE
                SYNTAX INTEGER {
                               none (1),
                               g726-16K (2),
                               g726-24K (3),
                               g726-32K (4),
                               g726-40K (5),
                               g729a-8K (6)
                               }
                MAX-ACCESS read-create
                STATUS current
                DESCRIPTION "Compression Type"
                DEFVAL { none }
                ::= { atmTrunkingBrVccConfigEntry 33 }

atmTrunkingBrVccAudioProfileSource OBJECT-TYPE
                SYNTAX INTEGER {
                               itu-t (1),
                               other (2)
                               }
                MAX-ACCESS read-create
                STATUS current
                DESCRIPTION "Profile Source"
                DEFVAL { itu-t }
                ::= { atmTrunkingBrVccConfigEntry 34 }

atmTrunkingBrVccAudioProfileId OBJECT-TYPE
                SYNTAX INTEGER (1..255)
                MAX-ACCESS read-create
                STATUS current
                DESCRIPTION "Profile ID"
                ::= { atmTrunkingBrVccConfigEntry 35 }
 
atmTrunkingBrVccAvailBw  OBJECT-TYPE
                SYNTAX Integer32
                MAX-ACCESS read-only
                STATUS current
                DESCRIPTION "Available Bandwidth left in this Vcc"
                DEFVAL { 0 }
                ::= { atmTrunkingBrVccConfigEntry 36 }
 
atmTrunkingBrVccRowStatus OBJECT-TYPE
                SYNTAX RowStatus
                MAX-ACCESS read-create
                STATUS current
                DESCRIPTION "Row status"
                ::= { atmTrunkingBrVccConfigEntry 37 }
 
atmTrunkingBrVccGr303Supp OBJECT-TYPE
                SYNTAX INTEGER {
                               disable (1),
                               enable (2)
                               }
                MAX-ACCESS read-create
                STATUS current
                DESCRIPTION "GR303 Support"
                DEFVAL { disable }
                ::= { atmTrunkingBrVccConfigEntry 38 }
 
atmTrunkingBrVccOamStatus OBJECT-TYPE
                SYNTAX INTEGER {
                                unsupp(1),
                                end-Pt(2)
                               }
                MAX-ACCESS read-write
                STATUS current  
                DESCRIPTION "Indicates the OAM monitoring status of side A.
                             The 2 possible states are:
                             Unsupp:  No monitoring enabled.
                             End-Pt:  Atm side is only an end point, therefore
                                it will respond to AIS/RDI."
                DEFVAL { unsupp }
                ::= { atmTrunkingBrVccConfigEntry 39 } 


atmTrunkingBrVccInactiveTimer OBJECT-TYPE
        SYNTAX Integer32
        MAX-ACCESS read-create
        STATUS current
        DESCRIPTION " The time(in seconds) to wait before releasing the
                      ATM Trunking Bearer VCC SVC after all narrow band
                      calls are dropped"
        DEFVAL { 3600 }
        ::= { atmTrunkingBrVccConfigEntry 40 }

atmTrunkingBrVccRetryTimer OBJECT-TYPE
        SYNTAX Integer32
        MAX-ACCESS read-create
        STATUS current
        DESCRIPTION " the time(seconds) to wait before attempting to establish
                      the ATM Trunking Bearer VCC SPVC after previous failed
                      call attempt. 0 indicates retries will be attempted 
                      immediately"
        DEFVAL { 30 }
        ::= { atmTrunkingBrVccConfigEntry 41 }

atmTrunkingBrVccRetryLimit OBJECT-TYPE
        SYNTAX Integer32
        MAX-ACCESS read-create
        STATUS current
        DESCRIPTION "ATM Trunking Bearer VCC SPVC Retry Limit. 0 indicates 
                     unlimited "
        DEFVAL { 0 }
        ::= { atmTrunkingBrVccConfigEntry 42 }

atmTrunkingBrVccRestart OBJECT-TYPE
        SYNTAX INTEGER  {
                restart(1),
                noop(2)
                }
        MAX-ACCESS read-write
        STATUS current
        DESCRIPTION "The active ATM Trunking BrVcc SPVC is released, 
                 if necessary, and a
                 new setup procedure is begun if 'restart',
                 otherwise, noop."
        ::= { atmTrunkingBrVccConfigEntry 43 }

atmTrunkingBrVccCuTimer   OBJECT-TYPE
                SYNTAX INTEGER (0..8)
                MAX-ACCESS read-write
                STATUS current
                DESCRIPTION "CuTimer represents combined use timer, is 
                             set to zero such that every ATM cell
                             transmitted contains one, and only one, 
                             AAL2 packet, and the first octet of the AAL2
                             packet header follows immediately after the Start 
                             Field in the ATM cell payload. If the
                             AAL2 packet payload is less than 44 octets, 
                             the remainder of the ATM cell payload
                             following the end of the AAL2 packet shall be 
                             filled with zeros as padding.
                             Each  increment of CuTimer means 5ms more to wait.
                             And cuTimer default value 4 means to wait 20ms
                             before the ATM cell is sent out. "
                DEFVAL { 4 }
                ::= { atmTrunkingBrVccConfigEntry 44 }

atmTrunkingBrVccPriority OBJECT-TYPE
        SYNTAX INTEGER  {
                priority-1(1),
                priority-2(2),
                priority-3(3),
                priority-4(4)
                }
        MAX-ACCESS read-write
        STATUS current
        DESCRIPTION "Priority of TrunkingBrVcc - priority-1 being highest priority ."
        DEFVAL { priority-1 }
        ::= { atmTrunkingBrVccConfigEntry 45 }


atmTrunkingBrVccRetryCounter OBJECT-TYPE
        SYNTAX Integer32
        MAX-ACCESS read-only
        STATUS current
        DESCRIPTION "Indicates how many attempts to establish the
                 connection have failed.  It is reset whenever a
                 connection is successfully established or the BrVcc SPVC
                 is restarted."
        ::= { atmTrunkingBrVccConfigEntry 46 }


atmTrunkingDataChannelConfigTable  OBJECT-TYPE
                SYNTAX SEQUENCE OF AtmTrunkingDataChannelConfigEntry
                MAX-ACCESS not-accessible
                STATUS current
                DESCRIPTION "Table of iwf aal2 data channel configuration
                             entities"
                ::= { atmTrunkingMIBObjects 5 }
 
atmTrunkingDataChannelConfigEntry  OBJECT-TYPE
                SYNTAX        AtmTrunkingDataChannelConfigEntry
                MAX-ACCESS    not-accessible
                STATUS        current
                DESCRIPTION   "Row definition for iwf aal2 data channel
                               configuration"
                INDEX { atmTrunkingDataChannelRmtIWFId,
                        atmTrunkingDataChannelBrVccId,
                        atmTrunkingDataChannelId
                      }
                ::= { atmTrunkingDataChannelConfigTable 1}
 
AtmTrunkingDataChannelConfigEntry  ::= SEQUENCE {
                atmTrunkingDataChannelRmtIWFId                    Integer32,
                atmTrunkingDataChannelSigVccId                    INTEGER,
                atmTrunkingDataChannelBrVccId                    INTEGER,
                atmTrunkingDataChannelId                    INTEGER,
                atmTrunkingDataChanOperStatus               INTEGER,
                atmTrunkingDataChanOwner                    INTEGER,
                atmTrunkingDataChanNBIntf                   IntfIndex
                }
 
atmTrunkingDataChannelRmtIWFId OBJECT-TYPE
                SYNTAX Integer32
                MAX-ACCESS not-accessible
                STATUS current
                DESCRIPTION "IWF ID for the remote IWF"
                ::= { atmTrunkingDataChannelConfigEntry 1 }
 
atmTrunkingDataChannelSigVccId OBJECT-TYPE
                SYNTAX INTEGER (0..16383)
                MAX-ACCESS read-only
                STATUS current
                DESCRIPTION "Vcc ID assigned by the owner of this signaling Vcc"
                ::= { atmTrunkingDataChannelConfigEntry 2 }

atmTrunkingDataChannelBrVccId      OBJECT-TYPE
                SYNTAX INTEGER (1..4096)
                MAX-ACCESS not-accessible
                STATUS current
                DESCRIPTION "Id of the AAL2 Bear Vcc"
                ::= { atmTrunkingDataChannelConfigEntry 3 }

atmTrunkingDataChannelId  OBJECT-TYPE
                SYNTAX INTEGER (8..255)
                MAX-ACCESS not-accessible
                STATUS current
                DESCRIPTION "The AAL2 Channel Id of this channel"

                ::= { atmTrunkingDataChannelConfigEntry 4 }

atmTrunkingDataChanOperStatus  OBJECT-TYPE
                SYNTAX INTEGER {
                               idle (1),
                               active (2)
                               }
                MAX-ACCESS read-only
                STATUS current
                DESCRIPTION "Operational Status of this channel"
                ::= { atmTrunkingDataChannelConfigEntry 5 }
 
atmTrunkingDataChanOwner  OBJECT-TYPE
                SYNTAX INTEGER {
                               local (1),
                               remote (2)
                               }
                MAX-ACCESS read-only
                STATUS current
                DESCRIPTION "The owner of this channel"
                ::= { atmTrunkingDataChannelConfigEntry 6 }
 
atmTrunkingDataChanNBIntf  OBJECT-TYPE
                SYNTAX IntfIndex
                MAX-ACCESS read-only
                STATUS current
                DESCRIPTION "The index of narrowband interface this channel
                             is mapped to"
                ::= { atmTrunkingDataChannelConfigEntry 7 }

-- End of ATM Trunking IWF Group

--
-- Beginning of H.248 MIB
--
-- H.248 Permanent Termination ID Table
h248TermIdTable OBJECT-TYPE 
                SYNTAX SEQUENCE OF H248TermIdEntry 
                MAX-ACCESS not-accessible
                STATUS current
                DESCRIPTION "Table of H.248 Terminations"
                ::= {  h248Config 1 }

h248TermIdEntry OBJECT-TYPE 
                SYNTAX H248TermIdEntry
                MAX-ACCESS not-accessible
                STATUS current
                DESCRIPTION "Row definition for H.248 
                    Termination ID table"
                INDEX { h248TermSlotId, 
                        h248TermPhyPortId,
                        h248TermLogPortId,
                        h248TermChanId ,
                        h248TermVpi,
                        h248TermVci
                        }
                ::= { h248TermIdTable 1 }

H248TermIdEntry ::= SEQUENCE {
                        h248TermSlotId                 INTEGER,
                        h248TermPhyPortId          INTEGER,
                        h248TermLogPortId        INTEGER,
                        h248TermChanId                INTEGER,
                        h248TermVpi                INTEGER,
                        h248TermVci                INTEGER,
                        h248TermId                OCTET STRING,
                        h248TermAal2Cid                INTEGER,
                        h248TermActivation      INTEGER,
                        h248TermRowStatus        RowStatus
                        }

h248TermSlotId OBJECT-TYPE
                SYNTAX INTEGER ( 1..99 )
                MAX-ACCESS not-accessible
                STATUS current
                DESCRIPTION "Slot # for termination"
                ::= { h248TermIdEntry 1 }

h248TermPhyPortId OBJECT-TYPE
                SYNTAX INTEGER ( 0..999 )
                MAX-ACCESS not-accessible
                STATUS current
                DESCRIPTION "Physical Port # for termination"
                ::= { h248TermIdEntry 2 }

h248TermLogPortId OBJECT-TYPE
                SYNTAX INTEGER ( 0..999 )
                MAX-ACCESS not-accessible
                STATUS current
                DESCRIPTION "Logical Port # for termination"
                ::= { h248TermIdEntry 3 }

h248TermChanId OBJECT-TYPE
                SYNTAX INTEGER ( 0..999 )
                MAX-ACCESS not-accessible
                STATUS current
                DESCRIPTION "Chan # for termination"
                ::= { h248TermIdEntry 4 }

h248TermVpi OBJECT-TYPE
                SYNTAX INTEGER ( 0..4096 )
                MAX-ACCESS not-accessible
                STATUS current
                DESCRIPTION "VPI # for termination. Value 0 is
                        reserved to indicate N/A, e.g., TDM
                        termination. Thus, VPI = h248TermVpi - 1,
                        for h248TermVpi > 0."
                ::= { h248TermIdEntry 5 }

h248TermVci OBJECT-TYPE
                SYNTAX INTEGER ( 0..65536 )
                MAX-ACCESS not-accessible
                STATUS current
                DESCRIPTION "VCI # for termination. Value 0 is
                        reserved to indicate N/A, e.g., TDM
                        termination. Thus, VCI = h248TermVci - 1,
                        for h248TermVci > 0."
                ::= { h248TermIdEntry 6 }

h248TermId OBJECT-TYPE
                SYNTAX OCTET STRING (SIZE(32))
                MAX-ACCESS read-write
                STATUS current
                DESCRIPTION "Termination ID is provisioned
                        by user and used for identifying termination
                        between MGC and MG"
                ::= { h248TermIdEntry 7 }

h248TermAal2Cid OBJECT-TYPE
                SYNTAX INTEGER (0..255)
                MAX-ACCESS read-write
                STATUS current
                DESCRIPTION "AAL2 CID"
                ::= { h248TermIdEntry 8 }

h248TermActivation OBJECT-TYPE
                SYNTAX INTEGER {
                        disable(1),
                        enable(2)
                        }
                MAX-ACCESS read-write
                STATUS current
                DESCRIPTION "Activation for termination ID"
                ::= { h248TermIdEntry 9 }

h248TermRowStatus OBJECT-TYPE
                SYNTAX RowStatus
                MAX-ACCESS read-write
                STATUS current
                DESCRIPTION "h248TermIdEntry row status"
                ::= { h248TermIdEntry 10 }

--
-- H.248 Root Package At h248SysControl Group
--
h248MaxNumberOfContexts OBJECT-TYPE 
                SYNTAX Integer32 
                MAX-ACCESS read-write
                STATUS current
                DESCRIPTION "The value of the property gives the 
                        maximum number of contexts that can exist at
                        anytime.  The NULL context is not included 
                        in this number."
                DEFVAL { 1000 }
                ::= {  h248SysControl 1 }

h248MaxTerminationsPerContext OBJECT-TYPE 
                SYNTAX Integer32
                MAX-ACCESS read-write
                STATUS current
                DESCRIPTION "The max number of terminations allowed
                        in a context."
                     DEFVAL { 2 }
                ::= { h248SysControl 2 }

h248NormalMGExecutionTime OBJECT-TYPE 
                SYNTAX Integer32
                MAX-ACCESS read-write
                STATUS current
                DESCRIPTION "Settable by the MGC to indicate the 
                        interval within which the MGC expects
                        a response to any transaction from the MG
                        (exclusive of the network delay). Value
                        represents milliseconds."
                DEFVAL { 1000 }
                ::= { h248SysControl 3 }

h248NormalMGCExecutionTime OBJECT-TYPE 
                SYNTAX Integer32
                MAX-ACCESS read-write
                STATUS current
                DESCRIPTION "Settable by the MGC to indicate the
                        interval within which the MG expects
                        a response to any transaction from the MG
                        (exclusive of the network delay). Value
                        represents milliseconds."
                     DEFVAL { 1000 }
                ::= { h248SysControl 4 }

h248MGProvisionalResponseTimerValue OBJECT-TYPE 
                SYNTAX Integer32
                MAX-ACCESS read-write
                STATUS current
                DESCRIPTION "Indicates the time within which the MGC should expect
                        a Pending Response from the MG if a Transaction can not be
                        completed. Initially set to h248NormalMGExecutionTime,
			plus network delay, but maybe lowered. Value represents
			milliseconds."
                     DEFVAL { 1000 }
                ::= { h248SysControl 5 }

h248MGCProvisionalResponseTimerValue OBJECT-TYPE 
                SYNTAX Integer32
                MAX-ACCESS read-write
                STATUS current
                DESCRIPTION "Indicates the time within which the MG should expect
                        a Pending Response from the MGC if a Transaction can not be
                        completed. Initially set to h248NormalMGCExecutionTime,
			plus network delay, but maybe lowered. Value represents
			milliseconds."
                     DEFVAL { 1000 }
                ::= { h248SysControl 6 }

h248MGCIpAddress1 OBJECT-TYPE 
                SYNTAX IpAddress
                MAX-ACCESS read-write
                STATUS current
                DESCRIPTION "The IP address of the 1st MGC."
                ::= { h248SysControl 7 }

h248MGCIpAddress2 OBJECT-TYPE 
                SYNTAX IpAddress
                MAX-ACCESS read-write
                STATUS current
                DESCRIPTION "The IP address of the 2nd MGC."
                ::= { h248SysControl 8 }



-- Protection Group protectionGroup

protectionGroupTable OBJECT-TYPE
                SYNTAX SEQUENCE OF ProtectionGroupEntry
                MAX-ACCESS not-accessible
                STATUS current
                DESCRIPTION "Table of interface protection group
                           attributes"
                 ::= { protectionGroup 1 }

protectionGroupEntry OBJECT-TYPE
                 SYNTAX ProtectionGroupEntry
                 MAX-ACCESS not-accessible
                 STATUS current
                 DESCRIPTION "Defines one interface protection group"
                 INDEX { pgtGroupId }
                 ::= { protectionGroupTable 1 }

ProtectionGroupEntry ::= SEQUENCE {
                 pgtGroupId         Integer32,
                 pgtSwitchoverMethod      INTEGER,
                       pgtSwitchbackMethod      INTEGER,
                 pgtStandbySelection      INTEGER,
                pgtRowStatus             RowStatus
                        }

pgtGroupId    OBJECT-TYPE
                SYNTAX Integer32
                MAX-ACCESS not-accessible
                STATUS current
                DESCRIPTION "a user selected logical number representing
                            a protection  group uniquely within a PSAX"
                ::= { protectionGroupEntry 1 }

pgtSwitchoverMethod OBJECT-TYPE
                SYNTAX INTEGER  {
                           auto(1),
                           manual(2)
                              }
                MAX-ACCESS read-write
                STATUS current
                DESCRIPTION " switchover method to switch traffic from
                failed primary interface to available standby interface. In
                auto method, PSAX automatically switches the traffic
                without user   intervention. In manual method, a failed
                primary does not switch   traffic and gives control to user
                to do so."
                DEFVAL { auto }
                ::= { protectionGroupEntry 2 }

pgtSwitchbackMethod OBJECT-TYPE
                    SYNTAX INTEGER  {
                           auto(1),
                           manual(2)
                                 }
                MAX-ACCESS read-write
                STATUS current
                DESCRIPTION " switchback method to switch traffic
                from a standby to its corresponding recovered primary
                interface. In auto method, PSAX automatically
                switches the traffic without user intervention. In
                manual method, standby does not switch traffic and
                gives control to user to do so."
                DEFVAL { auto }
                ::= { protectionGroupEntry 3 }

pgtStandbySelection OBJECT-TYPE
                SYNTAX INTEGER  {
                          sequential(1),
                          latest-used(2),
                          oldest-used(3),
                          random(4),
                          explicit(5)
                      }
                 MAX-ACCESS read-write
                 STATUS current
                 DESCRIPTION "Standby selection method determines the
                 order of selection of    standby when primary interface
                 fails. The options are:
                 sequential -- internally select next higher available
                 standby to the last one,
                 latest_used -- used last one freed,
                 oldest_used -- used to longest idle one,  
                                  random \255 randomly select one,
                 explicit -- selected by user."
                   DEFVAL { sequential }
                   ::= { protectionGroupEntry 4 }

pgtRowStatus    OBJECT-TYPE
                SYNTAX RowStatus
                MAX-ACCESS read-write
                STATUS current
                DESCRIPTION "row status"
                ::= { protectionGroupEntry  5 }

interfaceProtectionTable OBJECT-TYPE
                 SYNTAX SEQUENCE OF InterfaceProtectionEntry
                 MAX-ACCESS not-accessible
                 STATUS current
                 DESCRIPTION "Table of interface protection  attributes"
                 ::= { protectionGroup 2 }

interfaceProtectionEntry OBJECT-TYPE
                SYNTAX InterfaceProtectionEntry
                MAX-ACCESS not-accessible
                STATUS current
                       DESCRIPTION "Defines attributes for interface protection"
                      INDEX  { iptGroupId ,iptLogicalIntfId }
                ::= { interfaceProtectionTable 1 }

InterfaceProtectionEntry ::= SEQUENCE {
                iptGroupId                Integer32,
                iptLogicalIntfId        Integer32,
                iptPhysicalIntfId        Integer32,
                iptOperState                INTEGER,
                iptIntfType                INTEGER,
                iptOperatingIntf        Integer32,
                iptProtCommand                INTEGER,
                iptSelectedStandby          Integer32,
                iptRowStatus                RowStatus          
                  }

iptGroupId       OBJECT-TYPE
                 SYNTAX Integer32
                 MAX-ACCESS not-accessible
                 STATUS current
                 DESCRIPTION "a user selected logical number representing
                              a protection group uniquely within a PSAX."
                 ::= { interfaceProtectionEntry 1 }

iptLogicalIntfId        OBJECT-TYPE
                        SYNTAX  Integer32
                        MAX-ACCESS not-accessible
                        STATUS current
                        DESCRIPTION " Logical interface number assigned by user"
                        ::= { interfaceProtectionEntry 2 }

iptPhysicalIntfId        OBJECT-TYPE
                 SYNTAX  Integer32
                 MAX-ACCESS read-write
                 STATUS current
                 DESCRIPTION "physical interface in SSPPCCC format"
                 DEFVAL { 0 }
                 ::= { interfaceProtectionEntry 3 }

iptIntfType        OBJECT-TYPE
                 SYNTAX INTEGER  {
                          primary(1),
                          secondary(2)
                                    }
                 MAX-ACCESS read-write
                 STATUS current
                 DESCRIPTION "interface primary or secondary."
                 DEFVAL { primary }
                 ::= { interfaceProtectionEntry 4 }

iptOperState        OBJECT-TYPE
                SYNTAX INTEGER  {
                          inactive(1),
                          active(2)
                            }
                 MAX-ACCESS read-only
                 STATUS current
                 DESCRIPTION "indicates operational state of the interface."
                 DEFVAL { inactive }
                 ::= { interfaceProtectionEntry 5 }

iptOperatingIntf        OBJECT-TYPE
                SYNTAX Integer32
                MAX-ACCESS read-only
                STATUS current
                DESCRIPTION "protection operational state of the interface.
                Indicates which logical interface is carrying traffic originally
                configured  for this interface."
                ::= { interfaceProtectionEntry 6 }

iptProtCommand        OBJECT-TYPE
                 SYNTAX INTEGER  {
                        none(1),
                        switchover(2),
                         switchback(3)
                      }
                 MAX-ACCESS read-write
                 STATUS current
                 DESCRIPTION "protection operational state of the interface.
                 Indicates    which logical interface is carrying traffic
                 originally configured  for this interface."
                 DEFVAL{ none }
                 ::= { interfaceProtectionEntry 7 }

iptSelectedStandby        OBJECT-TYPE
                 SYNTAX Integer32
                 MAX-ACCESS read-write
                 STATUS current
                 DESCRIPTION "Standby interface logical number on which to
                 switch traffic. Used only in case of manual switchover
                 with explicit standby  selection."
                 DEFVAL { 0 }
                  ::= { interfaceProtectionEntry 8 }


iptRowStatus    OBJECT-TYPE
                SYNTAX RowStatus
                MAX-ACCESS read-write
                STATUS current
                DESCRIPTION "row status"
                ::= { interfaceProtectionEntry  9 }


-- End of protection Group 




-- Traps Group sysTraps 

-- systemEvents

systemColdStartNotify NOTIFICATION-TYPE
        STATUS        current
        DESCRIPTION "Info : System has successfully completed initialization
                     from a complete power down stage and is ready for 
                     operation."
        ::= { systemEvents 1 }

systemWarmStartNotify NOTIFICATION-TYPE
        STATUS current
        DESCRIPTION "Info : System has successfully completed initialization 
                     from a user or other system level interrupt or restart and 
                     is ready for operation."
        ::= { systemEvents 2 }

ecdBootFailureNotify NOTIFICATION-TYPE
        STATUS current
        DESCRIPTION "Critical : System failed in the Boot (startup) procedures.
                     Please call Support immediately to resolve the problem."
        ::= { systemEvents 3 }

referenceClockFailNotify NOTIFICATION-TYPE
        STATUS current
        DESCRIPTION "Critical : The reference clock used for the operation of 
                     the bus-based backplane has failed.  Please call Support 
                     immediately to resolve the problem."
        ::= { systemEvents 4 }

referenceClockClearedNotify NOTIFICATION-TYPE
        STATUS current
        DESCRIPTION "Info : The error in the backplane reference clock has 
                     been corrected."
        ::= { systemEvents 5 }

compositeClockFailNotify NOTIFICATION-TYPE
        STATUS current
        DESCRIPTION "Critical : The composite clock has failed.  Please call 
                     Support immediately to resolve the problem."
        ::= { systemEvents 6 }

compositeClockClearedNotify NOTIFICATION-TYPE
        STATUS current
        DESCRIPTION "Info : The error in the composite clock has been 
                     corrected."
        ::= { systemEvents 7 }

stratumModeChangeNotify NOTIFICATION-TYPE
             OBJECTS { stratumMode }
             STATUS current
        DESCRIPTION "Info : The current operational status of the Stratum card
                     has changed."
        ::= { systemEvents 8 }

powerSupplyStatusNotify NOTIFICATION-TYPE
             OBJECTS { powerSupplyReasonCode }
             STATUS current
        DESCRIPTION "Minor : Indicates the status of the power supply."
        ::= { systemEvents 9 }

softwareDownloadStatusNotify NOTIFICATION-TYPE
        OBJECTS { upgradeSwCopyStatus, upgradeSwErrorStatus }
        STATUS current
        DESCRIPTION  "Info : Indicates the completion status of the ftp 
                      download of a software upgrade."
        ::= { systemEvents 10 }


--        Notifications added for NEC
muxReadyConfirmReceivedNotify NOTIFICATION-TYPE
        STATUS current
        DESCRIPTION "Info : Indicates that the MUX (AC 120) has received a
                     MUX_READY_CONF message in response to the MUX_READY_IND
                     message when the AC 120 is configured as the TCP client
                     for the AC 120 to Signalling Gateway connection."
        ::= { systemEvents 11 }
 
muxReadyConfirmNotReceivedNotify NOTIFICATION-TYPE
        STATUS current
        DESCRIPTION "Major : If AC 120 is configured as TCP client, this trap
                     is sent if the MUX_READY_CONF message is not received
                     after sending the MUX_READY_IND message three times.
                     This indicates unexpected behavior on the AC 120 to
                     Signalling Gateway link."
        ::= { systemEvents 12 }
 
oneWayMessageWhileInTwoWayStateNotify NOTIFICATION-TYPE
        STATUS current
        DESCRIPTION "Major : This trap indicates that a one way message is
                     received from the Signalling Gateway (SG) when the AC 120
                     is in the two way state of the keep-alive protocol on the
                     TCP link between the AC 120 and the SG."
        ::= { systemEvents 13 }
 
inactivityTimerExpiredNotify NOTIFICATION-TYPE
        STATUS current
        DESCRIPTION "Major : Sent by the AC 120 when the inactivity timer of
                     the keep-alive protocoal expires, i.e. when the AC 120
                     does not see a message from the Signalling Gateway on the
                     TCP link during the time period specified by the
                     inactivity timer value setting."
        ::= { systemEvents 14 }
 
keepAliveTimerExpiredInLlDownStateNotify NOTIFICATION-TYPE
        STATUS current
        DESCRIPTION "Major : Sent by the AC 120 when the keep-alive timer
                     expires in the LLDOWN state of the keep-alive protocol,
                     i.e. when the AC 120 does not see a keep-alive message
                     from the Signalling Gateway on the TCP link during the
                     time period specified by the keep-alive timer setting."
        ::= { systemEvents 15 }
 
keepAliveTimerExpiredInOneWayStateNotify NOTIFICATION-TYPE
        STATUS current
        DESCRIPTION "Major : Sent by the AC 120 when the keep-alive timer
                     expires in the ONE-WAY state of the keep-alive protocol,
                     i.e. when the AC 120 does not see a keep-alive message
                     from the Signalling Gateway on the TCP link during the
                     time period specified by the keep-alive timer setting."
        ::= { systemEvents 16 }


completeClockFailedNotify NOTIFICATION-TYPE
        STATUS current
        DESCRIPTION "Critical : The stratum cards have either been removed or 
                     have failed leading to no clock being provided."
        ::= { systemEvents 17 }

completeClockRecoveredNotify NOTIFICATION-TYPE
        STATUS current
        DESCRIPTION "Info : A stratum card is now available to provide a clock
                     source."
        ::= { systemEvents 18 }

backplaneCircuitryFailedNotify NOTIFICATION-TYPE
        STATUS current
        DESCRIPTION "Critical : There is no activity on the cell bus.  Please
                     call Support immediately to resolve the problem."
        ::= { systemEvents 19 }

backplaneCircuitryRecoveredNotify NOTIFICATION-TYPE
        STATUS current
        DESCRIPTION "Info : The cpu card is able to detect activity on the
                     cell bus."
        ::= { systemEvents 20 }

remoteRebootNotify NOTIFICATION-TYPE
        OBJECTS { remoteRebootReasonCode }
        STATUS current
        DESCRIPTION  "Info : Indicates the result of the requested reboot 
                      action."
        ::= { systemEvents 21 }

saveConfigurationNotify NOTIFICATION-TYPE
        OBJECTS { saveConfigurationReasonCode }
        STATUS current
        DESCRIPTION  "Info : Indicates the result of the requested save
                      configuration."
        ::= { systemEvents 22 }

versionConfigurationNotify NOTIFICATION-TYPE
        OBJECTS { versionConfigurationReasonCode }
        STATUS current
        DESCRIPTION  "Info : Indicates the completion status of the upgrade or 
                      downgrade."
        ::= { systemEvents 23 }

fileTransferStatusNotify NOTIFICATION-TYPE
        OBJECTS { percentComplete }
        STATUS current
        DESCRIPTION  "Info : Indicates the percent complete of the current 
                      upgrade, downgrade, or ftp download in progress."
        ::= { systemEvents 24 }

ipOrMaskInvalidNotify NOTIFICATION-TYPE
             OBJECTS { ipTypeReasonCode }
             STATUS current
        DESCRIPTION "Response : The indicated ip address is invalid."
        ::= { systemEvents 25 }

alarmCardInputChangeNotify NOTIFICATION-TYPE
        OBJECTS { alarmCardReasonCode, deviceId }
        STATUS current
        DESCRIPTION  "Info : Indicates that the deviceId with 
                      alarmCardReasonCode has changed its status."
        ::= { systemEvents 26 }

removeConfigFilesNotify NOTIFICATION-TYPE
        OBJECTS { removeConfigFiles }
        STATUS current
        DESCRIPTION  "Info : Indicates the status of the removal of the 
                      configuration files."
        ::= { systemEvents 27 }

alarmCardOutputChangeNotify NOTIFICATION-TYPE
        OBJECTS { alarmCardReasonCode, deviceId }
        STATUS current
        DESCRIPTION  "Info : Indicates that the deviceId with 
                      alarmCardReasonCode has changed its status."
        ::= { systemEvents 28 }

alarmCardAcoChangeNotify NOTIFICATION-TYPE
        OBJECTS { alarmCardReasonCode }
        STATUS current
        DESCRIPTION  "Info : Indicates the action taken by the indicated type 
                      of the audible alarm."
        ::= { systemEvents 29 }

snmpCommunityStringsChangedToPublicNotify NOTIFICATION-TYPE
        STATUS current
        DESCRIPTION "Critical : An error has been detected in the agt.pty file 
                     and the community strings have been changed to be public."
        ::= { systemEvents 30 }


pnniNodeCfgNotify NOTIFICATION-TYPE
        OBJECTS { swtchNodeIndx, pnniCode }
        STATUS current
        DESCRIPTION  "Info : Indicates that a PNNI Node has been created." 
        ::= { systemEvents 31 }

pnniNodeCfgFailNotify NOTIFICATION-TYPE
        OBJECTS { swtchNodeIndx, pnniCode }
        STATUS current
        DESCRIPTION  "Info : Indicates that a PNNI Node Creation has failed." 
        ::= { systemEvents 32 }

pnniNodeModFailNotify NOTIFICATION-TYPE
        OBJECTS { swtchNodeIndx, pnniCode }
        STATUS current
        DESCRIPTION  "Info : Indicates that a PNNI Node Modification has 
                      failed." 
        ::= { systemEvents 33 }

pnniNodeDelFailNotify NOTIFICATION-TYPE
        OBJECTS { swtchNodeIndx, pnniCode }
        STATUS current
        DESCRIPTION  "Info : Indicates that a PNNI Node Deletion has failed." 
        ::= { systemEvents 34 }

pnniNodeOOSFailNotify NOTIFICATION-TYPE
        OBJECTS { swtchNodeIndx, pnniCode }
        STATUS current
        DESCRIPTION  "Info : Indicates that the action of taking a PNNI Node 
                      Out of Service has failed." 
        ::= { systemEvents 35 }

pnniNodeISFailNotify NOTIFICATION-TYPE
        OBJECTS { swtchNodeIndx, pnniCode }
        STATUS current
        DESCRIPTION  "Info : Indicates that the action of bringing a PNNI Node 
                      into service has failed." 
        ::= { systemEvents 36 }

pnniRtAddrCfgNotify NOTIFICATION-TYPE
        OBJECTS { swtchNodeIndx, interfaceIndex, pnniCode }
        STATUS current
        DESCRIPTION  "Info : Indicates that a new PNNI Route Address 
                      has been Created." 
        ::= { systemEvents 37 }

pnniRtAddrCfgFailNotify NOTIFICATION-TYPE
        OBJECTS { swtchNodeIndx, interfaceIndex, pnniCode }
        STATUS current
        DESCRIPTION  "Info : Indicates that a PNNI Route Address Configuration
                      has failed." 
        ::= { systemEvents 38 }

pnniRtAddrModFailNotify NOTIFICATION-TYPE
        OBJECTS { swtchNodeIndx, interfaceIndex, pnniCode }
        STATUS current
        DESCRIPTION  "Info : Indicates that a PNNI Route Address Modification
                      has failed." 
        ::= { systemEvents 39 }

pnniRtAddrDelFailNotify NOTIFICATION-TYPE
        OBJECTS { swtchNodeIndx, interfaceIndex, pnniCode }
        STATUS current
        DESCRIPTION  "Info : Indicates that a PNNI Route Address Deletion
                      has failed." 
        ::= { systemEvents 40 }

pnniRtAddrAddByIlmiNotify NOTIFICATION-TYPE
        OBJECTS { swtchNodeIndx, interfaceIndex, pnniCode }
        STATUS current
        DESCRIPTION  "Info : Indicates that an end system Address has been
                      dynamically added to PNNI by ILMI."
        ::= { systemEvents 41 }

pnniRtAddrDelByIlmiNotify NOTIFICATION-TYPE
        OBJECTS { swtchNodeIndx, interfaceIndex, pnniCode }
        STATUS current
        DESCRIPTION  "Info : Indicates that an end system Address has been
                      dynamically deleted from PNNI by ILMI."
        ::= { systemEvents 42 }


callContrlResAllocFailNotify NOTIFICATION-TYPE
        STATUS current
        DESCRIPTION  "Info: Indicates that the configuration of call 
                      control resource allocation fails." 
        ::= { systemEvents 43 }

differentSystemSoftwareNotify NOTIFICATION-TYPE
             OBJECTS { primarySoftwareVersion, backupSoftwareVersion }
        STATUS current
        DESCRIPTION  "Critical: Indicates that the primary and backup cpu's
                      are running different versions of software.  This could
                      cause system problems since the database files will not
                      be transferred between cpu's so a change of cpu will
                      result."
        ::= { systemEvents 44 }


inputPortClockFailNotify NOTIFICATION-TYPE
        STATUS current
        DESCRIPTION "Critical : The input port clock has failed.  
                        Please call Support immediately to 
                        resolve the problem."
        ::= { systemEvents 45 }

inputPortClockClearedNotify NOTIFICATION-TYPE
        STATUS current
        DESCRIPTION "Info : The error in the input port clock has been
                     corrected."
        ::= { systemEvents 46 }

oldStratumCardNotify NOTIFICATION-TYPE
        STATUS current
        DESCRIPTION "Critical : This trap indicates that the primary 
                        stratum card does not support this mode of 
                        operation being applied in the stratum 
                        configuration. Card must be upgraded. A default
                        configuration is being applied to stratum "
        ::= { systemEvents 47 }

stratumCardMismatchNotify NOTIFICATION-TYPE
        STATUS current
        DESCRIPTION "Critical : Indicates that the secondary stratum
                     card does not support this mode of operation being
                     applied to the primary stratum. Card must be
                     upgraded."
        ::= { systemEvents 48 }

tasCmprsAnnceNotify NOTIFICATION-TYPE
        OBJECTS { tasCmprsAnnceReasonCode , tasTrapAnnceId }
        STATUS current
        DESCRIPTION  "Info : Indicates the result of the requested compress
                      announcement operation."
        ::= { systemEvents 49 }

tasTstLineNotify NOTIFICATION-TYPE
        OBJECTS { tasTstLineReasonCode , tasTrapTstId }
        STATUS current
        DESCRIPTION  "Info : Indicates the result of the requested line test
                      initiation operation."
        ::= { systemEvents 50 }

tasMemNotify NOTIFICATION-TYPE
        OBJECTS { tasMemReasonCode }
        STATUS current
        DESCRIPTION  "Info : Indicates the result of the requested TASM memory
                      initiation operation."
        ::= { systemEvents 51 }

ambientTemperatureChangeNotify NOTIFICATION-TYPE
        OBJECTS { ambientTemperature }
        STATUS current
        DESCRIPTION  "Info : Indicates the ambient temperature has changed by
                      5 degrees centigrade since the last trap message."
        ::= { systemEvents 52 }

systemInsuffMemNotify NOTIFICATION-TYPE
        STATUS  current
        DESCRIPTION "Info : no enough memory for one or more features
                     to be turned on."
        ::= { systemEvents 53 }

toneAnnceFtpStatusNotify NOTIFICATION-TYPE
        OBJECTS { toneAnnceFtpStatus, toneAnnceFtpErrorStatus }
        STATUS current
        DESCRIPTION  "Info : Indicates the completion status of the ftp
                download of a tone annoucement file."
        ::= { systemEvents 54 } 

tasmControlBlockResAllocFailNotify NOTIFICATION-TYPE
        OBJECTS { tasmControlBlockAllocFailReasonCode }
        STATUS current
        DESCRIPTION  "Info: Indicates that the configuration of tasm
                      control block resource allocation fails.
                      Data send with the trap: 
                      tasmControlBlockAllocFailReasonCode Possible values are:
                      res-alloc-success(1),
                      res-alloc-Fail-announce-control-blocks-mem-unavail(2),
                      res-alloc-Fail-digit-control-blocks-mem-unavail(3),
                      res-alloc-Fail-line-test-control-blocks-mem-unavail(4)"
        ::= { systemEvents 55}

tasmCacheMemAllocFailNotify NOTIFICATION-TYPE
        OBJECTS { tasmCacheMemAllocFailReasonCode }
        STATUS current
        DESCRIPTION  "Info: Indicates that the configuration of tasm
                      memory cache for announcement caching allocation fails.
                      Data send with the trap:tasmCacheMemAllocFailReasonCode 
                      Possible values are:
                      res-alloc-success(1),
                      res-alloc-Fail-announce-cache-mem-unavail(2)"
        ::= { systemEvents 56}

remoteDbOperationStatusNotify NOTIFICATION-TYPE
        OBJECTS { remoteDbOperationStatus, remoteDbOperationErrorStatus }
        STATUS current
        DESCRIPTION  "Info : Indicates the completion status of remote
                      database operation."
        ::= { systemEvents 57 }


sapphireInterfaceAddressAssignFailNotify NOTIFICATION-TYPE
        OBJECTS { sapphireIntfAddressFailReasonCode }
        STATUS current
        DESCRIPTION  "Info: Indicates that the assignment of the Sapphire 
                      interface address on which TCP connect requests
                      are sent to SoftSwitch when PSAX is configured as
                      Client has failed.
                      Data send with the trap: sapphireIntfAddressFailReasonCode
                      Possible values are:
                      address-ok(1),        Address assignment succeeded 
                      fail-Ilegal-IP-address(2),  
                          Illegal IP address assigned address not matching
                      fail-not-match-InBandManagement-Switch-CPU-IP-Address(3)
                          In-Band Management IP or Switch IP or CPU IP address
                      fail-Switch-or-CPU-IP-Address-unconfigured(4)
                          Switch IP or CPU IP address unconfigured
                      fail-InBandManagement-IP-Address-unconfigured(5)
                          InBandManagement IP address unconfigured. "
        ::= { systemEvents 58}

switchAlarmStatusChangeNotify NOTIFICATION-TYPE
        OBJECTS { switchAlarmStatus }
        STATUS current
        DESCRIPTION "Critical : Trap to notify a change in the status of the
        alarm on the switch."
        ::= { systemEvents 59 }

chassisOverTempAlarmNotify NOTIFICATION-TYPE 
        OBJECTS { chassisOverTempAlarmReasonCode } 
        STATUS current 
        DESCRIPTION "Critical : Trap sent when the temperature of the
                     chassis goes above or below a preset temperature 
                     threshold." 
        ::= { systemEvents 60 }

-- moduleEvents

cardInsertionNotify  NOTIFICATION-TYPE
             OBJECTS { cardSlot, cardType, cardProtectionStatus, cardOperStatus}
             STATUS  current
        DESCRIPTION "Info : The indicated slot has had a card inserted into it."
             ::= { moduleEvents 1 }

cardRemovedOrFailedNotify  NOTIFICATION-TYPE
             OBJECTS { cardSlot }
             STATUS  current
             DESCRIPTION "Major : The indicated slot has changed state."
             ::= { moduleEvents 2 }

lineStatusChangedNotify    NOTIFICATION-TYPE
             OBJECTS { portId, lineStatus }
             STATUS  current
             DESCRIPTION "Major : The indicated port has had a change in the line
                     status."
             ::= { moduleEvents 3 }

firmwareDownloadSucceededNotify NOTIFICATION-TYPE
             OBJECTS { fwReleaseSlot }
             STATUS  current
             DESCRIPTION "Info : The indicated slot has successfully completed a 
                     firmware download." 
             ::= { moduleEvents 4 }

firmwareDownloadFailedNotify NOTIFICATION-TYPE
             OBJECTS { fwReleaseSlot, firmwareDownloadReasonCode }
             STATUS  current
             DESCRIPTION "Minor : The indicated slot had the indicated failure
                     during a firmware download."
             ::= { moduleEvents 5 }

moduleRebootNotify NOTIFICATION-TYPE
             OBJECTS { cardSlot, cardType }
             STATUS  current
             DESCRIPTION "Major : This trap indicates that a cardType in cardSlot 
                     becomes busy and the CPU reboots it.  This is different 
                     from when an I/O card is actually removed."
             ::= { moduleEvents 6 }

oc3APSStateChangeNotify NOTIFICATION-TYPE
        OBJECTS { 
                  oc3APSPairPortIndex, oc3APSReasonCode, 
                  oc3APSK1K2Rx, oc3APSK1K2Tx,oc3APSSelectorState, 
                  oc3APSWorkingLineSignalStatus,
                  oc3APSProtectionLineSignalStatus
                }
        STATUS current
        DESCRIPTION "Notification of a change in the APS state machine."
        ::= { moduleEvents 7 }

oc3APSSwitchoverNotify NOTIFICATION-TYPE
        OBJECTS { 
                  oc3APSPairPortIndex, oc3APSReasonCode, 
                  oc3APSK1K2Rx, oc3APSK1K2Tx,oc3APSSelectorState,
                  oc3APSWorkingLineSignalStatus,
                  oc3APSProtectionLineSignalStatus
                }
        STATUS current
        DESCRIPTION "Notification of a switchover in an APS pair."
        ::= { moduleEvents 8 }

portModifyFailNotify NOTIFICATION-TYPE
        OBJECTS {portId, portFailureReasonCode}
        STATUS current
        DESCRIPTION "Info : Notification that an attempt to modify an 
                     port parameters has failed."
        ::= { moduleEvents 9 }

stratumActivitySwitchOverNotify NOTIFICATION-TYPE
        OBJECTS { activeStratum }
        STATUS  current
        DESCRIPTION "Info : The secondary stratum card has become the 
                        primary primary card."
        ::= { moduleEvents 10 }


imaGroupStatusChangeNotify NOTIFICATION-TYPE
    OBJECTS {
              interfaceIndex,imaGrpChannelNeState, imaGrpChannelFeState,
              imaGrpChannelFailureStatus, imaGrpChannelSymmetry
             }
    STATUS current
    DESCRIPTION "The indicated SSPPCCC has a change in the states of the IMA
    Group Channel"
    ::= { moduleEvents 11 }

-- interfaceEvents

interfaceCreatedNotify NOTIFICATION-TYPE
        OBJECTS {interfaceIndex, interfaceType}
        STATUS current
        DESCRIPTION "Info : Notification that an interface has been created."
        ::= { interfaceEvents 1}

interfaceDeletedNotify NOTIFICATION-TYPE
        OBJECTS {interfaceIndex}
        STATUS current
        DESCRIPTION "Info : Notification that an interface has been deleted."
        ::= { interfaceEvents 2 }

interfaceModifiedNotify NOTIFICATION-TYPE
        OBJECTS {interfaceIndex, interfaceType}
        STATUS current
        DESCRIPTION "Info : Notification that an interface has been modified."
        ::= { interfaceEvents 3 }

interfaceModifyFailNotify NOTIFICATION-TYPE
        OBJECTS {interfaceIndex, interfaceType, interfaceFailureReasonCode}
        STATUS current
        DESCRIPTION "Info : Notification that an attempt to modify an 
                     interface has failed."
        ::= { interfaceEvents 4 }

interfaceOutOfServiceNotify        NOTIFICATION-TYPE
        OBJECTS {interfaceIndex, interfaceType}
        STATUS current
        DESCRIPTION "Major : Notification that an interface is now out of 
                     service."
        ::= { interfaceEvents 5 }

interfaceInServiceNotify NOTIFICATION-TYPE
        OBJECTS {interfaceIndex, interfaceType}
        STATUS current
        DESCRIPTION "Info : Notification that an interface is now in service."
        ::= { interfaceEvents 6 }

bridgeDomainFullNotify NOTIFICATION-TYPE
        OBJECTS { bridgeDomainNumber }
        STATUS current
        DESCRIPTION "Info : The 15 ports available for the bridge domain are
                     being used, leaving no space for an additional port." 
        ::= { interfaceEvents 7 }

bridgeDomainExceededForSlotNotify NOTIFICATION-TYPE
        OBJECTS { cardSlot }
        STATUS current
        DESCRIPTION "Info : The bridge domain number has been exceeded for
                     the slot."
        ::= { interfaceEvents 8 }

bridgeDomainNumberInUseNotify NOTIFICATION-TYPE
        OBJECTS { bridgeDomainNumber }
        STATUS current
        DESCRIPTION "Info : Notification that a bridge domain number is 
                     currently in use."
        ::= { interfaceEvents 9 }

bridgeDomainInServiceNotify NOTIFICATION-TYPE
        OBJECTS { bridgeDomainNumber }
        STATUS current
        DESCRIPTION "Info : Notification that a bridge domain is now in 
                     service."
        ::= { interfaceEvents 10 }

bridgeDomainNumberInvalidNotify NOTIFICATION-TYPE
        OBJECTS { interfaceIndex }
        STATUS current
        DESCRIPTION "Info : Indicates that this interface contains an invalid 
                     bridge domain number.  In order to create a domain, 
                     associate a port with a domain, or bring an interface in 
                     service, a valid domain number must be provided."
        ::= { interfaceEvents 11 }

signalingModifyFailNotify NOTIFICATION-TYPE
        OBJECTS { interfaceIndex, interfaceType, interfaceFailureReasonCode }
        STATUS current
        DESCRIPTION "Info : This trap indicates that signaling has already been
                     configured for this port and to change, you must bring
                     all interfaces out of service -- including the channel
                     specified in interfaceIndex."
        ::= { interfaceEvents 12 }

lmiIntfStatusNotify NOTIFICATION-TYPE
        OBJECTS { interfaceIndex, frLmiOperStatus }
        STATUS current
        DESCRIPTION "Info : This trap indicates the status of an interface 
                     from the LMI perspective."
        ::= { interfaceEvents 13 }


isdnLapdDownNotify NOTIFICATION-TYPE
        OBJECTS { interfaceIndex, isdnIntfDChanId }
        STATUS current
        DESCRIPTION "Info : This trap indicates that LAPD on the ISDN interface
                     has gone down."
        ::= { interfaceEvents 14 }

isdnLapdUpNotify NOTIFICATION-TYPE
        OBJECTS { interfaceIndex, isdnIntfDChanId }
        STATUS current
        DESCRIPTION "Info : This trap indicates that LAPD is functional on the 
                     specified ISDN interface."
        ::= { interfaceEvents 15 }


bridgeDomainTimingRelationshipNotify NOTIFICATION-TYPE
        OBJECTS { bridgeDomainNumber, timingReasonCode }
        STATUS current
        DESCRIPTION "Info : Trap sent when one of the following relationships
                     is violated:
                     (1) 2 * (BridgeForwardDelay - 1.0 sec) >= BridgeMaxAge 
                     (2) BridgeMaxAge >= 2 * (BridgeHelloTime + 1.0 sec)."
        ::= { interfaceEvents 16 }

ts16UsageModifyFailNotify NOTIFICATION-TYPE
        OBJECTS { interfaceIndex, interfaceFailureReasonCode }
        STATUS current
        DESCRIPTION "Info : Indicates that either TS16 has been in use for data 
                     while trying to change e1 TS16 from CCS to CAS, or
                     signaling is on for at least one of the channels while 
                     trying to change e1 TS16 from CAS to CCS."
        ::= { interfaceEvents 17 }

ceServiceTypeModifyFailNotify NOTIFICATION-TYPE
        OBJECTS { portId, interfaceFailureReasonCode }
        STATUS current
        DESCRIPTION "Info : Indicates that configuring unstructured CE failed.
                     Possible reasons are: (1) the port has been channelized;
                     (2) the port has CAS turned on."
        ::= { interfaceEvents 18 }

channelizationModifyFailNotify NOTIFICATION-TYPE
        OBJECTS { portId, interfaceFailureReasonCode }
        STATUS current
        DESCRIPTION "Info : Indicates that channelizing/unchannelizing failed.
                     Possible reasons are: (1) the port has been configured for
                     unstructured CE; (2) the port has CAS turned on."
        ::= { interfaceEvents 19 }


cirEmSpvcConfiguredNotify NOTIFICATION-TYPE
	OBJECTS { interfaceIndex }
	STATUS current
	DESCRIPTION "Info : Notification that an endpoint has  been configured 
		     as CES SPVC endpoint.
             Return value - interfaceIndex"
	::= { interfaceEvents 20 }

cirEmSpvcConfigFailNotify NOTIFICATION-TYPE
	OBJECTS { interfaceIndex, spvcConfigFailureCode }
	STATUS current
	DESCRIPTION "Info : Notification that an attempt to configure an 
		     endpoint as CE SPVC endpoint has failed.
             Return values - interfaceIndex
                          - spvcConfigFailureCode: An identified reason for
                            failure while configuring/modifying SPVC
                            parameters."
	::= { interfaceEvents 21 }

cirEmSpvcDeletedNotify NOTIFICATION-TYPE
	OBJECTS { interfaceIndex }
	STATUS current
	DESCRIPTION "Info : Notification that CE SPVC configuration has been 
		     deleted.
             Return value - interfaceIndex"
	::= { interfaceEvents 22}

cirEmSpvcModifiedNotify NOTIFICATION-TYPE
	OBJECTS { interfaceIndex }
	STATUS current
	DESCRIPTION "Info : Notification that a SPVC endpoint has been 
		     modified - this trap has been obsoleted 07/01/2001."
	::= { interfaceEvents 23 }

cirEmSpvcModifyFailNotify NOTIFICATION-TYPE
	OBJECTS { interfaceIndex, spvcConfigFailureCode }
	STATUS current
	DESCRIPTION "Info : Notification that an attempt to modify a CE SPVC 
		     endpoint has failed - this trap has been obsoleted 07/01/2001."
	::= { interfaceEvents 24 }

vbrSpvcConfiguredNotify NOTIFICATION-TYPE
	OBJECTS { interfaceIndex }
	STATUS current
	DESCRIPTION "Info : Notification that an endpoint has been configured 
		    as TE SPVC endpoint.
            Return value - interfaceIndex"
	::= { interfaceEvents 25}

vbrSpvcConfigFailNotify NOTIFICATION-TYPE
	OBJECTS { interfaceIndex, spvcConfigFailureCode }
	STATUS current
	DESCRIPTION "Info : Notification that an attempt to configure an 
		     endpoint as TE SPVC endpoint has failed.
             Return values - interfaceIndex
                           - spvcConfigFailureCode: An identified reason for 
                             failure while configuring/modifying SPVC
                             parameters."
	::= { interfaceEvents 26 }

vbrSpvcDeletedNotify NOTIFICATION-TYPE
	OBJECTS { interfaceIndex }
	STATUS current
	DESCRIPTION "Info : Notification that TE SPVC configuration has been 
		     deleted.
             Return value - interfaceIndex"
	::= { interfaceEvents 27 }

vbrSpvcModifiedNotify NOTIFICATION-TYPE
	OBJECTS { interfaceIndex }
	STATUS current
	DESCRIPTION "Info : Notification that a SPVC endpoint has been 
		     modified - this trap has been obsoleted 07/01/2001."
	::= { interfaceEvents 28 }

vbrSpvcModifyFailNotify NOTIFICATION-TYPE
	OBJECTS { interfaceIndex, spvcConfigFailureCode }
	STATUS current
	DESCRIPTION "Info : Notification that an attempt to modify a TE SPVC  
		     endpoint has failed - this trap has been obsoleted 07/01/2001."
	::= { interfaceEvents 29 }

atmSpvcConfiguredNotify NOTIFICATION-TYPE
	OBJECTS { atmSpvcVccIfA, atmSpvcVccVpiA, atmSpvcVccVciA }
	STATUS current
	DESCRIPTION "Info : Notification that an endpoint has  been configured 
		     as ATM SPVC endpoint.
             Return value - interfaceIndex
                          - A-side vpi/vci value"
	::= { interfaceEvents 30 }

atmSpvcConfigFailNotify NOTIFICATION-TYPE
	OBJECTS { atmSpvcVccIfA, atmSpvcVccVpiA, atmSpvcVccVciA, 
		  spvcConfigFailureCode }
	STATUS current
	DESCRIPTION "Info : Notification that an attempt to configure an 
		     endpoint as ATM SPVC endpoint has failed.
             Return value - interfaceIndex
                          - A-side vpi/vci value
                          - spvcConfigFailureCode: An identified reason for
                            failure while configuring/modifying SPVC
                            parameters."
	::= { interfaceEvents 31 }

atmSpvcDeletedNotify NOTIFICATION-TYPE
	OBJECTS { atmSpvcVccIfA, atmSpvcVccVpiA, atmSpvcVccVciA }
	STATUS current
	DESCRIPTION "Info : Notification that ATM SPVC configuration has been 
		     deleted.
             Return value - interfaceIndex
                          - A-side vpi/vci value"
	::= { interfaceEvents 32 }

atmSpvcModifiedNotify NOTIFICATION-TYPE
	OBJECTS { atmSpvcVccIfA, atmSpvcVccVpiA, atmSpvcVccVciA }
	STATUS current
	DESCRIPTION "Info : Notification that a SPVC endpoint has been 
		     modified - this trap has been obsoleted 07/01/2001."
	::= { interfaceEvents 33 }

atmSpvcModifyFailNotify NOTIFICATION-TYPE
	OBJECTS { atmSpvcVccIfA, atmSpvcVccVpiA, atmSpvcVccVciA, 
		  spvcConfigFailureCode }
	STATUS current
	DESCRIPTION "Info : Notification that an attempt to modify a TE SPVC 
		     endpoint has failed - this trap has been obsoleted 07/01/2001."
	::= { interfaceEvents 34 }


cRC4ModifyFailNotify NOTIFICATION-TYPE
        OBJECTS { portId, interfaceFailureReasonCode }
        STATUS current
        DESCRIPTION "Info: Notification that modification of the CRC4 field of
        an E1 port failed."
        ::= { interfaceEvents 35 }

imaGrpChannelFailNotify NOTIFICATION-TYPE
        OBJECTS { imaGrpChannelId, imaGrpChannelStatus }
        STATUS current
        DESCRIPTION
          "Info : The imaGrpChannelFailNotify trap indicates a failure in the
           IMA group. The imaGrpChannelStatus field indicates the reason
           for the failure."
        ::= { interfaceEvents 36 }

atmImaIntfFailNotify NOTIFICATION-TYPE
        OBJECTS { atmImaIntfIndex, atmImaIntfStatus }
        STATUS current
        DESCRIPTION
          "Info : The atmImaIntfFailNotify trap indicates a failure in the
           physical IMA interface. The atmImaIntfStatus field indicates
           the reason for the failure."
        ::= { interfaceEvents 37 }

imaGrpChannelClearedNotify NOTIFICATION-TYPE
        OBJECTS { imaGrpChannelId, imaGrpChannelStatus }
        STATUS current
        DESCRIPTION
          "Info : The imaGrpChannelClearedNotify trap indicates a failure has 
           been cleared in an IMA group. The imaGrpChannelStatus field indicates
           the failure that has been cleared."
        ::= { interfaceEvents 38 }

atmImaIntfClearedNotify NOTIFICATION-TYPE
        OBJECTS { atmImaIntfIndex, atmImaIntfStatus }
        STATUS current
        DESCRIPTION
          "Info : The atmImaIntfClearedNotify trap indicates a failure has been
           cleared in an IMA interface. The atmImaIntfStatus field indicates
           the failure that has been cleared."
        ::= { interfaceEvents 39 }


pnniProtLnkUpAndAdv NOTIFICATION-TYPE
        OBJECTS { interfaceIndex, pnniCode }
        STATUS current
        DESCRIPTION
          "Info : Indicates that the Protocol Status of the PNNI Link is 
           Up and Advertising."
        ::= { interfaceEvents 40 }

pnniProtLinkUpAndNotAdv NOTIFICATION-TYPE
        OBJECTS { interfaceIndex, pnniCode }
        STATUS current
        DESCRIPTION
          "Info : Indicates that the Protocol Status of the PNNI Link is 
           Up but not Advertising."
        ::= { interfaceEvents 41 }

pnniProtLnkStatDown NOTIFICATION-TYPE
        OBJECTS { interfaceIndex, pnniCode }
        STATUS current
        DESCRIPTION
          "Info : Indicates that the Protocol Status of the PNNI Link is 
           Down."
        ::= { interfaceEvents 42 }

pnniIntfCfgFailNotify NOTIFICATION-TYPE
        OBJECTS { interfaceIndex, pnniCode }
        STATUS current
        DESCRIPTION
          "Info : Indicates that a PNNI Interface has failed to be 
           Created."
        ::= { interfaceEvents 43 }



-- VIPR Task Traps.

-- Ray Change.
viprPingTrap NOTIFICATION-TYPE
        OBJECTS { viprSlot, viprRouterId, ipAddrNumber, pingStatusReasonCode }
        STATUS current
        DESCRIPTION
                "Info : The Vipr Task is notifying Network Management of the
                disposition of a previous Ping Request."
        ::= { interfaceEvents 44 }

-- Ray Change.
viprArpTrap NOTIFICATION-TYPE
        OBJECTS { viprSlot, viprRouterId, arpStatus }
        STATUS current
        DESCRIPTION
                "Info : The Vipr Task is notifying Network Management of the
                disposition of a previous Arp Table Request."
        ::= { interfaceEvents 45 }

-- Ray Change.
viprRoutingTrap NOTIFICATION-TYPE
        OBJECTS { viprSlot, viprRouterId, routingStatus }
        STATUS current
        DESCRIPTION
                "Info : The Vipr Task is notifying Network Management of the
                disposition of a previous Routing Table Request."
        ::= { interfaceEvents 46 }


viprVpnTrap NOTIFICATION-TYPE
        OBJECTS { viprSlot, viprRouterId, vpnTrapStatus }
        STATUS current
        DESCRIPTION
          "Info : Indicates success/fail of VPN level operations."
        ::= { interfaceEvents 47 }

viprIpIntfTrap NOTIFICATION-TYPE
        OBJECTS { viprSlot, viprRouterId, viprIntfId, ipIntfStatus }
        STATUS current
        DESCRIPTION
          "Info : Indicates success/fail of IP Network Interface level
           operations."
        ::= { interfaceEvents 48 }

viprSubChanTrap NOTIFICATION-TYPE
        OBJECTS { viprSlot, viprRouterId, viprIntfId, viprSubChnlId, subChanStatus }
        STATUS current
        DESCRIPTION
          "Info : Indicates success/fail of Sub Channel level operations."
        ::= { interfaceEvents 49 }

viprRtSrvTrap NOTIFICATION-TYPE
        OBJECTS { cardSlot, routeSrvStatus }
        STATUS current
        DESCRIPTION
          "Info : Indicates success/fail of Vipr (Route Server) operations."
        ::= { interfaceEvents 50 }


atmSvcIntfLayer2Up NOTIFICATION-TYPE
        OBJECTS { interfaceIndex, interfaceType }
        STATUS current
        DESCRIPTION "Info : Indicates that an ATM Svc Interface 
                        Assured Data Link is Up."
        ::= { interfaceEvents 51 }

atmSvcIntfLayer2Down NOTIFICATION-TYPE
        OBJECTS { interfaceIndex, interfaceType }
        STATUS current
        DESCRIPTION "Info : Indicates that an ATM Svc Interface
                        Assured Data Link is Down."
        ::= { interfaceEvents 52 }

apsConfigurationModifyFailNotify NOTIFICATION-TYPE
         OBJECTS { oc3PortId, apsFailureReasonCode }
         STATUS current
         DESCRIPTION "Info: Notification that an attempt to modify
                         an APS configuration has failed"
         ::={ interfaceEvents 53 }

viprStatRtTrap NOTIFICATION-TYPE
        OBJECTS { viprSlot, viprRouterId, viprRouteId, statRtStatus }
        STATUS current
        DESCRIPTION
          "Info : Indicates success/fail of Static Route operations."
        ::= { interfaceEvents 54 }

interfaceCreateFailNotify NOTIFICATION-TYPE
        OBJECTS {interfaceIndex, interfaceType, interfaceFailureReasonCode}
        STATUS current
        DESCRIPTION "Info : Notification that an attempt to create an 
                     interface has failed. interfaceFailureReasonCode gives details."
        ::= { interfaceEvents 55 }

virtualIntfCreatedNotify NOTIFICATION-TYPE
         OBJECTS { virtualIntfConfigIf, virtualIntfConfigVi }
        STATUS current
        DESCRIPTION "Response to creation of VI"
        ::= { interfaceEvents 56 }

virtualIntfModifiedNotify NOTIFICATION-TYPE
         OBJECTS { virtualIntfConfigIf, virtualIntfConfigVi }
        STATUS current
        DESCRIPTION "Response to modification of VI"
        ::= { interfaceEvents 57 }

virtualIntfDeleteNotify NOTIFICATION-TYPE
         OBJECTS { virtualIntfConfigIf, virtualIntfConfigVi }
        STATUS current
        DESCRIPTION "Response to deletion of VI"
        ::= { interfaceEvents 58 }

virtualIntfModifyFailNotify NOTIFICATION-TYPE
         OBJECTS { virtualIntfConfigIf, virtualIntfConfigVi, 
                pvcFailureReasonCode}
        STATUS current
        DESCRIPTION "Response to Modify Fail of VI, Overload 
                        pvcFailureReasonCode"
        ::= { interfaceEvents 59 }



frAtmSpvcConfiguredNotify NOTIFICATION-TYPE
    OBJECTS { spvcAddrIfA, frAtmSpvcVccDlciA }
    STATUS current
    DESCRIPTION "Info : Notification that an endpoint has  been configured
             as FR SPVC endpoint.
             Return values - interfaceIndex
                           - dlci value"
    ::= { interfaceEvents 60 }

frAtmSpvcConfigFailNotify NOTIFICATION-TYPE
    OBJECTS { spvcAddrIfA, frAtmSpvcVccDlciA, spvcConfigFailureCode }
    STATUS current
    DESCRIPTION "Info : Notification that an attempt to configure an
             endpoint as FR SPVC endpoint has failed.
             Return values - interfaceIndex
                           - dlci value
                           - spvcConfigFailureCode: An identified reason for
                            failure while configuring/modifying SPVC
                            parameters."
    ::= { interfaceEvents 61 }

frAtmSpvcDeletedNotify NOTIFICATION-TYPE
    OBJECTS { spvcAddrIfA, frAtmSpvcVccDlciA }
    STATUS current
    DESCRIPTION "Info : Notification that FR SPVC configuration has been
             deleted.
             Return values - interfaceIndex
                           - dlci value"
    ::= { interfaceEvents 62}

frAtmSpvcModifiedNotify NOTIFICATION-TYPE
    OBJECTS { spvcAddrIfA, frAtmSpvcVccDlciA }
    STATUS current
    DESCRIPTION "Info : Notification that a SPVC endpoint has been
             modified - this trap has been obsoleted 07/01/2001.
             Return values - interfaceIndex
                           - dlci value"
    ::= { interfaceEvents 63 }

frAtmSpvcModifyFailNotify NOTIFICATION-TYPE
    OBJECTS { spvcAddrIfA, frAtmSpvcVccDlciA, spvcConfigFailureCode }
    STATUS current
    DESCRIPTION "Info : Notification that an attempt to modify a FR SPVC
             endpoint has failed - this trap has been obsoleted 07/01/2001."
    ::= { interfaceEvents 64 }

-- Changes for 1  integration - new trap declaration.
-- Frame Relay Spvc's don't need the new change. 

atmAtmSpvcConfiguredNotify NOTIFICATION-TYPE
        OBJECTS { spvcAddrIfA, atmAtmSpvcVccVpiA, atmAtmSpvcVccVciA, 
          atmAtmSpvcVccRemoteAtmPortAddr  }
	STATUS current
	DESCRIPTION "Info : Notification that an endpoint has  been configured 
		     as ATM SPVC endpoint.
             Return values - interfaceIndex
                           - A-side vpi/vci values
                           - remote NSAP address"
	::= { interfaceEvents 65 }

atmAtmSpvcConfigFailNotify NOTIFICATION-TYPE
        OBJECTS { spvcAddrIfA, atmAtmSpvcVccVpiA, atmAtmSpvcVccVciA, 
          atmAtmSpvcVccRemoteAtmPortAddr,
		  spvcConfigFailureCode }
	STATUS current
	DESCRIPTION "Info : Notification that an attempt to configure an 
		     endpoint as ATM SPVC endpoint has failed.
             Return values - interfaceIndex
                           - A-side vpi/vci values
                           - remote NSAP address 
                           - spvcConfigFailureCode: An identified reason for
                             failure while configuring/modifying SPVC
                             parameters"
	::= { interfaceEvents 66 }

atmAtmSpvcDeletedNotify NOTIFICATION-TYPE
        OBJECTS { spvcAddrIfA, atmAtmSpvcVccVpiA,
          atmAtmSpvcVccVciA,atmAtmSpvcVccRemoteAtmPortAddr  }
	STATUS current
	DESCRIPTION "Info : Notification that ATM SPVC configuration has been 
		     deleted.
             Return values - interfaceIndex
                           - A-side vpi/vci values
                           - remote NSAP address"
	::= { interfaceEvents 67 }

atmAtmSpvcModifiedNotify NOTIFICATION-TYPE
        OBJECTS { spvcAddrIfA, atmAtmSpvcVccVpiA, atmAtmSpvcVccVciA, 
          atmAtmSpvcVccRemoteAtmPortAddr }
	STATUS current
	DESCRIPTION "Info : Notification that a SPVC endpoint has been 
		     modified - this trap has been obsoleted 07/01/2001."
	::= { interfaceEvents 68 }

atmAtmSpvcModifyFailNotify NOTIFICATION-TYPE
        OBJECTS { spvcAddrIfA, atmAtmSpvcVccVpiA, atmAtmSpvcVccVciA,
          atmAtmSpvcVccRemoteAtmPortAddr, spvcConfigFailureCode }
	STATUS current
	DESCRIPTION "Info : Notification that an attempt to modify a TE SPVC 
		     endpoint has failed - this trap has been obsoleted 07/01/2001."
	::= { interfaceEvents 69 }


cirAtmSpvcConfiguredNotify NOTIFICATION-TYPE
	OBJECTS { spvcAddrIfA, cirAtmSpvcVccRemoteCePortAddr}
	STATUS current
	DESCRIPTION "Info : Notification that an endpoint has  been configured 
		     as CE SPVC endpoint.
             Return values - interfaceIndex
                           - remote NSAP address"
	::= { interfaceEvents 70 }

cirAtmSpvcConfigFailNotify NOTIFICATION-TYPE
	OBJECTS { spvcAddrIfA, cirAtmSpvcVccRemoteCePortAddr, spvcConfigFailureCode }
	STATUS current
	DESCRIPTION "Info : Notification that an attempt to configure an 
		     endpoint as CE SPVC endpoint has failed.
             Return values - interfaceIndex
                           - remote NSAP address
                           - spvcConfigFailureCode: An identified reason for
                             failure while configuring/modifying SPVC
                             parameters"
	::= { interfaceEvents 71 }

cirAtmSpvcDeletedNotify NOTIFICATION-TYPE
	OBJECTS { spvcAddrIfA, cirAtmSpvcVccRemoteCePortAddr }
	STATUS current
	DESCRIPTION "Info : Notification that CE SPVC configuration has been 
		     deleted.
             Return values - interfaceIndex
                           - remote NSAP address"
	::= { interfaceEvents 72}

cirAtmSpvcModifiedNotify NOTIFICATION-TYPE
	OBJECTS { spvcAddrIfA, cirAtmSpvcVccRemoteCePortAddr }
	STATUS current
	DESCRIPTION "Info : Notification that a SPVC endpoint has been 
		     modified - this trap has been obsoleted 07/01/2001."
	::= { interfaceEvents 73 }

cirAtmSpvcModifyFailNotify NOTIFICATION-TYPE
	OBJECTS { spvcAddrIfA,cirAtmSpvcVccRemoteCePortAddr, spvcConfigFailureCode }
	STATUS current
	DESCRIPTION "Info : Notification that an attempt to modify a CE SPVC 
		     endpoint has failed - this trap has been obsoleted 07/01/2001."
	::= { interfaceEvents 74 }

vbrAtmSpvcConfiguredNotify NOTIFICATION-TYPE
	OBJECTS { spvcAddrIfA, vbrAtmSpvcRemoteVbrPortAddr }
	STATUS current
	DESCRIPTION "Info : Notification that an endpoint has been configured 
		    as TE SPVC endpoint.
            Return values - interfaceIndex
                          - remote NSAP address"
	::= { interfaceEvents 75}

vbrAtmSpvcConfigFailNotify NOTIFICATION-TYPE
	OBJECTS { spvcAddrIfA, vbrAtmSpvcRemoteVbrPortAddr, spvcConfigFailureCode }
	STATUS current
	DESCRIPTION "Info : Notification that an attempt to configure an 
		     endpoint as TE SPVC endpoint has failed.
             Return values - interfaceIndex
                           - remote NSAP address
                           - spvcConfigFailureCode: An identified reason for
                             failure while configuring/modifying SPVC
                             parameters"
	::= { interfaceEvents 76 }

vbrAtmSpvcDeletedNotify NOTIFICATION-TYPE
	OBJECTS { spvcAddrIfA, vbrAtmSpvcRemoteVbrPortAddr }
	STATUS current
	DESCRIPTION "Info : Notification that TE SPVC configuration has been 
		     deleted.
             Return values - interfaceIndex
                           - remote NSAP address"
	::= { interfaceEvents 77 }

vbrAtmSpvcModifiedNotify NOTIFICATION-TYPE
	OBJECTS { spvcAddrIfA, vbrAtmSpvcRemoteVbrPortAddr }
	STATUS current
	DESCRIPTION "Info : Notification that a SPVC endpoint has been 
		     modified - this trap has been obsoleted 07/01/2001."
	::= { interfaceEvents 78 }

vbrAtmSpvcModifyFailNotify NOTIFICATION-TYPE
	OBJECTS { spvcAddrIfA, vbrAtmSpvcRemoteVbrPortAddr, spvcConfigFailureCode }
	STATUS current
	DESCRIPTION "Info : Notification that an attempt to modify a TE SPVC  
		     endpoint has failed - this trap has been obsoleted 07/01/2001."
	::= { interfaceEvents 79 }




virtualUNIIntfCreatedNotify NOTIFICATION-TYPE
         OBJECTS { virtualUNIIfIndex, virtualUNIVUNIId} 
        STATUS current
        DESCRIPTION "Response to creation of Virtual UNI"
        ::= { interfaceEvents 80 }

virtualUNIIntfCreateFailNotify NOTIFICATION-TYPE
        OBJECTS {virtualUNIIfIndex, virtualUNIVUNIId, interfaceFailureReasonCode}
        STATUS current
        DESCRIPTION "Info : Notification that an attempt to create an 
                     interface has failed. interfaceFailureReasonCode gives details."
        ::= { interfaceEvents 81 }

virtualUNIIntfModifiedNotify NOTIFICATION-TYPE
         OBJECTS { virtualUNIIfIndex, virtualUNIVUNIId }
        STATUS current
        DESCRIPTION "Notification of a failure to modify a Virtual
        UNI interface."
        ::= { interfaceEvents 82 }

virtualUNIIntfDeleteNotify NOTIFICATION-TYPE
         OBJECTS { virtualUNIIfIndex, virtualUNIVUNIId }
        STATUS current
        DESCRIPTION "Response to deletion of Virtual UNI"
        ::= { interfaceEvents 83 }

virtualUNIIntfModifyFailNotify NOTIFICATION-TYPE
         OBJECTS { virtualUNIIfIndex, virtualUNIVUNIId, 
                interfaceFailureReasonCode}
        STATUS current
        DESCRIPTION "Response to Modify Fail of Virtual UNI, Overload 
                        interfaceFailureReasonCode"
        ::= { interfaceEvents 84 }

virtualUNIIntfOutOfServiceNotify NOTIFICATION-TYPE
        OBJECTS { virtualUNIIfIndex, virtualUNIVUNIId }
        STATUS current
        DESCRIPTION "Notification of virtualUNI Out Of Service"
        ::= { interfaceEvents 85 }

virtualUNIIntfInServiceNotify NOTIFICATION-TYPE
        OBJECTS { virtualUNIIfIndex, virtualUNIVUNIId }
        STATUS current
        DESCRIPTION "Notification of virtualUNI in Service"
        ::= { interfaceEvents 86 }



gr303IgCreatedNotify NOTIFICATION-TYPE
         OBJECTS { gr303IgId }
        STATUS current
        DESCRIPTION "Response to creation of GR303IG"
        ::= { interfaceEvents 87 }

gr303IgCreateFailNotify NOTIFICATION-TYPE
        OBJECTS {gr303IgId, interfaceFailureReasonCode}
        STATUS current
        DESCRIPTION "Info : Notification that an attempt to create a
                     gr303 interface group has failed.
                     interfaceFailureReasonCode gives details."
        ::= { interfaceEvents 88 }

gr303IgModifiedNotify NOTIFICATION-TYPE
         OBJECTS { gr303IgId }
        STATUS current
        DESCRIPTION "Response to modification of GR303IG"
        ::= { interfaceEvents 89 }

gr303IgDeleteNotify NOTIFICATION-TYPE
         OBJECTS { gr303IgId }
        STATUS current
        DESCRIPTION "Response to deletion of GR303IG"
        ::= { interfaceEvents 90 }

gr303IgModifyFailNotify NOTIFICATION-TYPE
         OBJECTS { gr303IgId, interfaceFailureReasonCode}
        STATUS current
        DESCRIPTION "Response to Modify Fail of GR303IG, Overload 
                        interfaceFailureReasonCode"
        ::= { interfaceEvents 91 }

gr303IgOutOfServiceNotify NOTIFICATION-TYPE
        OBJECTS { gr303IgId }
        STATUS current
        DESCRIPTION "Notification of GR303IG Out Of Service"
        ::= { interfaceEvents 92 }

gr303IgInServiceNotify NOTIFICATION-TYPE
        OBJECTS { gr303IgId }
        STATUS current
        DESCRIPTION "Notification of GR303IG in Service"
        ::= { interfaceEvents 93 }

gr303IgIntfAddedNotify NOTIFICATION-TYPE
         OBJECTS { gr303IntfIgId, gr303IgIntfId} 
        STATUS current
        DESCRIPTION "Response to addition of DS1 interface into GR303IG"
        ::= { interfaceEvents 94 }

gr303IgIntfAddFailNotify NOTIFICATION-TYPE
        OBJECTS {gr303IntfIgId, gr303IgIntfId, interfaceFailureReasonCode}
        STATUS current
        DESCRIPTION "Info : Notification that an attempt to add an 
                     interface has failed. interfaceFailureReasonCode gives details."
        ::= { interfaceEvents 95 }

gr303IgIntfDeleteNotify NOTIFICATION-TYPE
         OBJECTS { gr303IntfIgId, gr303IgIntfId }
        STATUS current
        DESCRIPTION "Response to deletion of DS1 interface from GR303IG"
        ::= { interfaceEvents 96 }

gr303TMCChanDownNotify NOTIFICATION-TYPE
        OBJECTS { interfaceIndex, gr303TMCChannelId }
        STATUS current
        DESCRIPTION "Info : This trap indicates that TMC (LAPD) on the GR303 interface
                     has gone down."
        ::= { interfaceEvents 97 }

gr303EOCChanDownNotify NOTIFICATION-TYPE
        OBJECTS { interfaceIndex, gr303EOCChannelId }
        STATUS current
        DESCRIPTION "Info : This trap indicates that EOC (LAPD) on the GR303 interface
                     has gone down."
        ::= { interfaceEvents 98 }

gr303TMCChanUpNotify NOTIFICATION-TYPE
        OBJECTS { interfaceIndex, gr303TMCChannelId }
        STATUS current
        DESCRIPTION "Info : This trap indicates that TMC(LAPD) is functional on the 
                     specified GR303 interface."
        ::= { interfaceEvents 99 }

gr303EOCChanUpNotify NOTIFICATION-TYPE
        OBJECTS { interfaceIndex, gr303EOCChannelId }
        STATUS current
        DESCRIPTION "Info : This trap indicates that EOC(LAPD) is functional on the 
                     specified GR303 interface."
        ::= { interfaceEvents 100 }

gr303PPSStateChangeNotify NOTIFICATION-TYPE
        OBJECTS { 
                  gr303IgId, gr303PPSReasonCode, gr303PPSSource, 
                  gr303IgPrimaryTMCStatus,
          gr303IgPrimaryEOCStatus,
          gr303IgBackupTMCStatus,
          gr303IgBackupEOCStatus
		}
	STATUS current
	DESCRIPTION "This indicates a change in the states of primary
    and secondary TMC/EOC (lapd)"
	::= { interfaceEvents 101 }

gr303PPSSwitchoverNotify NOTIFICATION-TYPE
        OBJECTS { 
                  gr303IgId, gr303PPSReasonCode,  gr303PPSSource,
                  gr303IgPrimaryTMCStatus,
          gr303IgPrimaryEOCStatus,
          gr303IgBackupTMCStatus,
          gr303IgBackupEOCStatus
		}
	STATUS current
	DESCRIPTION "This notification is the result of PPS switching command
    which will indicate the reason code, initiator and states"
	::= { interfaceEvents 102 }

gr303PPSCommandFailNotify NOTIFICATION-TYPE
        OBJECTS { 
                  gr303IgId, gr303PPSReasonCode,  gr303PPSSource,
                  gr303IgPrimaryTMCStatus,
          gr303IgPrimaryEOCStatus,
          gr303IgBackupTMCStatus,
          gr303IgBackupEOCStatus
		}
	STATUS current
	DESCRIPTION "This is the notification of failure of PPS switching command"
	::= { interfaceEvents 103 }

interfaceBandwidthChangeNotify NOTIFICATION-TYPE
        OBJECTS {interfaceIndex, interfaceFailureReasonCode}
        STATUS current
        DESCRIPTION "Info : Notification that a interface has undergone
                     reduction in bandwidth. Critical depending on 
                     Failure Reason Code."
        ::= { interfaceEvents 104 }



--
-- Notiification of SPVP actions
--

atmAtmSpvpConfiguredNotify NOTIFICATION-TYPE
        OBJECTS { spvcAddrIfA, atmAtmSpvcVpcVpiA,atmAtmSpvcVpcRemoteAtmPortAddr
 }
        STATUS current
        DESCRIPTION "Info : Notification that an ATM SPVP has been configured
                     at the ATM SPVC endpoint.
                     Return values - interfaceIndex
                                   - A-side vpi value
                                   - remote NSAP Address"
        ::= { interfaceEvents 105 }

atmAtmSpvpConfigFailNotify NOTIFICATION-TYPE
        OBJECTS { spvcAddrIfA, atmAtmSpvcVpcVpiA,atmAtmSpvcVpcRemoteAtmPortAddr,
                  spvcConfigFailureCode }
        STATUS current
        DESCRIPTION "Info : Notification that an attempt to configure an ATM SPVP
                     at the ATM SPVC endpoint has failed.
                     Return values - interfaceIndex
                                   - A-side vpi value
                                   - remote NSAP Address
                                   - spvcConfigFailureCode: An identified reason for
                                     failure while configuring/modifying SPVC
                                     parameters."
        ::= { interfaceEvents 106 }

atmAtmSpvpDeletedNotify NOTIFICATION-TYPE
        OBJECTS { spvcAddrIfA, atmAtmSpvcVpcVpiA, atmAtmSpvcVpcRemoteAtmPortAddr
 }
        STATUS current
        DESCRIPTION "Info : Notification that an ATM SPVP configuration has been
                     deleted.
                     Return values - interfaceIndex
                                   - A-side vpi value
                                   - remote NSAP Address"
        ::= { interfaceEvents 107 }

atmAtmSpvpModifiedNotify NOTIFICATION-TYPE
        OBJECTS { spvcAddrIfA, atmAtmSpvcVpcVpiA,atmAtmSpvcVpcRemoteAtmPortAddr
}
        STATUS current
        DESCRIPTION "Info : Notification that an ATM SPVP configuration has been
                     modified - this trap has been obsoleted 07/01/2001."
        ::= { interfaceEvents 108 }

atmAtmSpvpModifyFailNotify NOTIFICATION-TYPE
        OBJECTS { spvcAddrIfA, atmAtmSpvcVpcVpiA,atmAtmSpvcVpcRemoteAtmPortAddr,

                  spvcConfigFailureCode }
        STATUS current
        DESCRIPTION "Info : Notification that an attempt to modify a ATM SPVP
                     configuration has failed - this trap has been obsoleted
                     07/01/2001."
        ::= { interfaceEvents 109 }


atmTrunkingLocalIWFConfiguredNotify NOTIFICATION-TYPE
        OBJECTS { atmTrunkingIWFIdentifier }
        STATUS current
        DESCRIPTION "Info: Local IWF Configured
                     return value: atmTrunkingIWFIdentifier"
        ::= { interfaceEvents 110 }

atmTrunkingLocalIWFConfigFailNotify NOTIFICATION-TYPE
        OBJECTS { atmTrunkingIWFIdentifier, atmTrunkingConfigFailureCode }
        STATUS current
        DESCRIPTION "Info: Local IWF Configured
                     return value: atmTrunkingIWFIdentifier
                                   atmTrunkingConfigFailureCode"
        ::= { interfaceEvents 111 }

atmTrunkingLocalIWFModifiedNotify  NOTIFICATION-TYPE
        OBJECTS { atmTrunkingIWFIdentifier }
        STATUS current
        DESCRIPTION "Info: configuration of Local IWF modified
                     return value: atmTrunkingIWFIdentifier"
        ::= { interfaceEvents 112 }

atmTrunkingLocalIWFModifyFailNotify NOTIFICATION-TYPE
        OBJECTS { atmTrunkingIWFIdentifier, atmTrunkingConfigFailureCode }
        STATUS current
        DESCRIPTION "Info: Modification of Local IWF has failed
                           return value: atmTrunkingIWFIdentifier
                                   atmTrunkingConfigFailureCode"
        ::= { interfaceEvents 113 }

atmTrunkingLocalIWFDeletedNotify NOTIFICATION-TYPE
        OBJECTS { atmTrunkingIWFIdentifier }
        STATUS current
        DESCRIPTION "Info: configuration of Local IWF deleted
                     return value: atmTrunkingIWFIdentifier"
        ::= { interfaceEvents 114 }

atmTrunkingLocalIWFDeleteFailNotify NOTIFICATION-TYPE
        OBJECTS { atmTrunkingIWFIdentifier, atmTrunkingConfigFailureCode }
        STATUS current
        DESCRIPTION "Info: configuration of Local IWF can not be deleted
                     return value: atmTrunkingIWFIdentifier
                                   atmTrunkingConfigFailureCode"
        ::= { interfaceEvents 115 }

atmTrunkingRemoteIWFConfiguredNotify NOTIFICATION-TYPE
        OBJECTS { atmTrunkingRemoteIWFIdentifier }
        STATUS current
        DESCRIPTION "Info : Notification that an ATM TRUNKING Remote IWF has
                     been configured with return values
                     - atmTrunkingRmtIWFIdentifier"
        ::= { interfaceEvents 116 }

atmTrunkingRemoteIWFConfigFailNotify  NOTIFICATION-TYPE
        OBJECTS { atmTrunkingRemoteIWFIdentifier, atmTrunkingConfigFailureCode }
        STATUS current
        DESCRIPTION "Info : Notification that an ATM TRUNKING Remote IWF configuration
                     has failed with return value :
                     - atmTrunkingRmtIWFIdentifier
                     - atmTrunkingConfigFailureCode "
        ::= { interfaceEvents 117 }


atmTrunkingRemoteIWFDeletedNotify NOTIFICATION-TYPE
        OBJECTS { atmTrunkingRemoteIWFIdentifier }
        STATUS current
        DESCRIPTION "Info : Notification that an ATM TRUNKING Remote IWF has
                     been deleted with return values
                     - atmTrunkingRmtIWFIdentifier"
        ::= { interfaceEvents 118 }

atmTrunkingRemoteIWFModifiedNotify NOTIFICATION-TYPE
        OBJECTS { atmTrunkingRemoteIWFIdentifier }
        STATUS current
        DESCRIPTION "Info : Notification that an ATM TRUNKING Remote IWF has
                     been modified with return values
                     - atmTrunkingRmtIWFIdentifier"
        ::= { interfaceEvents 119 }


atmTrunkingRemoteIWFModifyFailNotify NOTIFICATION-TYPE
        OBJECTS { atmTrunkingRemoteIWFIdentifier,atmTrunkingConfigFailureCode }
        STATUS current
        DESCRIPTION "Info : Notification that an ATM TRUNKING Remote IWF has
                     been configured with return values
                     - atmTrunkingRmtIWFIdentifier"
        ::= { interfaceEvents 120 }

atmTrunkingSigVccConfiguredNotify NOTIFICATION-TYPE
        OBJECTS { atmTrunkingSigVccRmtIWFIdentifier, atmTrunkingSigVccIdentifier }
        STATUS current
        DESCRIPTION "Info : Notification that an ATM TRUNKING Signalling VCC has
                     been configured between Local IWF and with return values
                     - atmTrunkingSigVccRmtIWFIdentifier
                     - atmTrunkingSigVccIdentifier "
        ::= { interfaceEvents 121 }

atmTrunkingSigVccConfigFailNotify NOTIFICATION-TYPE
        OBJECTS { atmTrunkingSigVccRmtIWFIdentifier, 
                  atmTrunkingSigVccIdentifier,
                  atmTrunkingConfigFailureCode }
        STATUS current
        DESCRIPTION "Info : Notification that an ATM TRUNKING Signalling VCC configuration
                     has failed with return value:
                     - atmTrunkingSigVccRmtIWFIdentifier
                     - atmTrunkingSigVccIdentifier
                     - atmTrunkingConfigFailureCode "
        ::= { interfaceEvents 122 }

atmTrunkingSigVccDeletedNotify NOTIFICATION-TYPE
        OBJECTS { atmTrunkingSigVccRmtIWFIdentifier, atmTrunkingSigVccIdentifier }
        STATUS current
        DESCRIPTION "Info : Notification that an ATM TRUNKING Signalling VCC has
                     been deleted with return values
                     - atmTrunkingSigVccRmtIWFIdentifier
                     - atmTrunkingSigVccIdentifier "
        ::= { interfaceEvents 123 }

atmTrunkingBrVccConfiguredNotify NOTIFICATION-TYPE
        OBJECTS { atmTrunkingBrVccRmtIWFId, atmTrunkingBrVccId }
        STATUS current
        DESCRIPTION "Info : Notification that an ATM TRUNKING Bearer VCC has
                     been configured between Local IWF and with return values
                     - atmTrunkingBrVccRmtIWFIdentifier
                     - atmTrunkingBrVccIdentifier "
        ::= { interfaceEvents 124 }

atmTrunkingBrVccConfigFailNotify NOTIFICATION-TYPE
        OBJECTS { atmTrunkingBrVccRmtIWFId, atmTrunkingBrVccId,
                  atmTrunkingConfigFailureCode }
        STATUS current
        DESCRIPTION "Info : Notification that an ATM TRUNKING Bearer VCC configuration
                     has failed with return value:
                     - atmTrunkingBrVccRmtIWFIdentifier
                     - atmTrunkingBrVccIdentifier
                     - atmTrunkingConfigFailureCode "
        ::= { interfaceEvents 125 }

atmTrunkingBrVccDeletedNotify NOTIFICATION-TYPE
        OBJECTS { atmTrunkingBrVccRmtIWFId, atmTrunkingBrVccId }
        STATUS current
        DESCRIPTION "Info : Notification that an ATM TRUNKING Bearer VCC has
                     been deleted with return values
                     - atmTrunkingBrVccRmtIWFIdentifier
                     - atmTrunkingBrVccIdentifier "
        ::= { interfaceEvents 126  }


-- connectionEvents

-- Request Fail Notify

atmPvcVccReqFailNotify  NOTIFICATION-TYPE
     OBJECTS {  atmPvcVccIfA, atmPvcVccVpiA, atmPvcVccVciA,
                atmPvcVccIfB, atmPvcVccVpiB, atmPvcVccVciB,
                 pvcFailureReasonCode} 
     STATUS  current
     DESCRIPTION "Response : The PVC VCC connection request between two atm 
                  interfaces failed."
        ::= { connectionEvents 1 }

atmPvcVpcReqFailNotify  NOTIFICATION-TYPE
     OBJECTS {  atmPvcVpcIfA,  atmPvcVpcVpiA, 
                atmPvcVpcIfB, atmPvcVpcVpiB,
                 pvcFailureReasonCode} 
     STATUS  current
     DESCRIPTION "Response : The PVC VPC connection request between two atm 
                  interfaces failed."
        ::= { connectionEvents 2 }

ipAtmAppPvcVccReqFailNotify  NOTIFICATION-TYPE
     OBJECTS { ipAtmAppPvcVccDestAddrA, ipAtmAppPvcVccSubnetMaskA, 
               ipAtmAppPvcVccIfB, ipAtmAppPvcVccVpiB,
               ipAtmAppPvcVccVciB, pvcFailureReasonCode }
     STATUS current
     DESCRIPTION "Response : The PVC VCC connection request between in-band 
                  management and an atm interface has failed."
        ::= { connectionEvents 3 }

cirEmAtmPvcVccReqFailNotify  NOTIFICATION-TYPE
     OBJECTS { cirEmAtmPvcVccIfA, cirEmAtmPvcVccIfB, 
               cirEmAtmPvcVccVpiB, cirEmAtmPvcVccVciB,
               pvcFailureReasonCode }
     STATUS current
     DESCRIPTION "Response : The PVC VCC connection request between a circuit 
                  emulation interface and an atm interface has failed."
        ::= { connectionEvents 4 }

vbrAtmPvcVccReqFailNotify NOTIFICATION-TYPE
     OBJECTS { vbrAtmPvcVccIfA,  vbrAtmPvcVccIfB,
               vbrAtmPvcVccVpiB, vbrAtmPvcVccVciB, 
               pvcFailureReasonCode }
     STATUS current
     DESCRIPTION "Response : The PVC VCC connection request between a 
                  variable-bit rate interface and an atm interface has failed."
        ::= { connectionEvents 5 }

frAtmPvcVccReqFailNotify  NOTIFICATION-TYPE
     OBJECTS { frAtmPvcVccIfA, frAtmPvcVccDlciA, frAtmPvcVccIfB,
               frAtmPvcVccVpiB, frAtmPvcVccVciB, pvcFailureReasonCode } 
     STATUS current
     DESCRIPTION "Response : The PVC VCC connection request between a 
                  frame-relay interface and an atm interface has failed."
        ::= {connectionEvents 6 }

frFrPvcReqFailNotify NOTIFICATION-TYPE
     OBJECTS { frFrPvcIfA, frFrPvcDlciA,
               frFrPvcIfB, frFrPvcDlciB, pvcFailureReasonCode }
     STATUS current
     DESCRIPTION "Response : The PVC connection request between two frame-relay
                  interfaces has failed."
        ::= { connectionEvents 7 }

cirEmCirEmPvcReqFailNotify  NOTIFICATION-TYPE
     OBJECTS { cirEmCirEmPvcIfA, cirEmCirEmPvcIfB,
               pvcFailureReasonCode
             }
     STATUS current
     DESCRIPTION "Response : The PVC connection request between two circuit 
                  emulation interfaces has failed."
        ::= { connectionEvents 8 }

vbrVbrPvcReqFailNotify NOTIFICATION-TYPE
     OBJECTS { vbrVbrPvcIfA,  vbrVbrPvcIfB,
               pvcFailureReasonCode }
     STATUS current
     DESCRIPTION "Response : The PVC connection request between two variable-bit
                  rate interfaces has failed."
        ::= { connectionEvents 9 }


-- Setup Notify

atmPvcVccSetupNotify NOTIFICATION-TYPE
        OBJECTS { atmPvcVccIfA, atmPvcVccVpiA, atmPvcVccVciA,
                  atmPvcVccIfB, atmPvcVccVpiB, atmPvcVccVciB }
        STATUS current
        DESCRIPTION "Response : The PVC VCC connection between two atm 
                     interfaces has been created."
        ::= { connectionEvents 10 }

atmPvcVpcSetupNotify NOTIFICATION-TYPE
        OBJECTS { atmPvcVpcIfA, atmPvcVpcVpiA,
                  atmPvcVpcIfB, atmPvcVpcVpiB }
        STATUS current
        DESCRIPTION "Response : The PVC VPC connection between two atm
                     interfaces has been created."
        ::= { connectionEvents 11 }

ipAtmAppPvcVccSetupNotify  NOTIFICATION-TYPE
     OBJECTS { ipAtmAppPvcVccDestAddrA, ipAtmAppPvcVccSubnetMaskA, 
               ipAtmAppPvcVccIfB, ipAtmAppPvcVccVpiB,
               ipAtmAppPvcVccVciB }
     STATUS current
     DESCRIPTION "Response : The PVC VCC connection between in-band management
                  and an atm interface has been created."
        ::= { connectionEvents 12 }

cirEmAtmPvcVccSetupNotify  NOTIFICATION-TYPE
     OBJECTS { cirEmAtmPvcVccIfA, cirEmAtmPvcVccIfB, 
               cirEmAtmPvcVccVpiB, cirEmAtmPvcVccVciB }
     STATUS current
     DESCRIPTION "Response : The PVC VCC connection between a circuit emulation
                  interface and an atm interface has been created."
        ::= { connectionEvents 13 }

vbrAtmPvcVccSetupNotify NOTIFICATION-TYPE
     OBJECTS { vbrAtmPvcVccIfA, vbrAtmPvcVccIfB,
               vbrAtmPvcVccVpiB, vbrAtmPvcVccVciB }
     STATUS current
     DESCRIPTION "Response : The PVC VCC connection between a variable-bit rate
                  interface and an atm interface has been created."
        ::= { connectionEvents 14 }

frAtmPvcVccSetupNotify  NOTIFICATION-TYPE
     OBJECTS { frAtmPvcVccIfA, frAtmPvcVccDlciA, frAtmPvcVccIfB,
               frAtmPvcVccVpiB, frAtmPvcVccVciB }
     STATUS current
     DESCRIPTION "Response : The PVC VCC connection between a frame-relay
                  interface and an atm interface has been created."
        ::= { connectionEvents 15 }

frFrPvcSetupNotify NOTIFICATION-TYPE
     OBJECTS { frFrPvcIfA, frFrPvcDlciA,
               frFrPvcIfB, frFrPvcDlciB }
     STATUS current
     DESCRIPTION "Response : The PVC connection between two frame-relay
                  interfaces has been created."
        ::= { connectionEvents 16 }

cirEmCirEmPvcSetupNotify  NOTIFICATION-TYPE
     OBJECTS { cirEmCirEmPvcIfA, cirEmCirEmPvcIfB
             }
     STATUS current
     DESCRIPTION "Response : The PVC connection between two circuit-emulation
                  interfaces has been created."
        ::= { connectionEvents 17 }

vbrVbrPvcSetupNotify NOTIFICATION-TYPE
     OBJECTS { vbrVbrPvcIfA, vbrVbrPvcIfB
               }
     STATUS current
     DESCRIPTION "Response : The PVC connection between two variable-bit rate
                  interfaces has been created."
        ::= { connectionEvents 18 }


-- Tear Down Notify

atmPvcVccTearDownNotify NOTIFICATION-TYPE
        OBJECTS { atmPvcVccIfA, atmPvcVccVpiA, atmPvcVccVciA,
                  atmPvcVccIfB, atmPvcVccVpiB, atmPvcVccVciB }
        STATUS current
        DESCRIPTION "Response : The PVC VCC connection between two atm 
                     interfaces has been deleted."
        ::= { connectionEvents 19 }

atmPvcVpcTearDownNotify NOTIFICATION-TYPE
        OBJECTS { atmPvcVpcIfA, atmPvcVpcVpiA,
                  atmPvcVpcIfB, atmPvcVpcVpiB }
        STATUS current
        DESCRIPTION "Response : The PVC VPC connection between two atm
                     interfaces has been deleted."
        ::= { connectionEvents 20 }

ipAtmAppPvcVccTearDownNotify  NOTIFICATION-TYPE
     OBJECTS { ipAtmAppPvcVccDestAddrA, ipAtmAppPvcVccSubnetMaskA, 
               ipAtmAppPvcVccIfB, ipAtmAppPvcVccVpiB,
               ipAtmAppPvcVccVciB }
     STATUS current
     DESCRIPTION "Response : The PVC VCC connection between in-band management
                  and an atm interface has been deleted."
        ::= { connectionEvents 21 }

cirEmAtmPvcVccTearDownNotify  NOTIFICATION-TYPE
     OBJECTS { cirEmAtmPvcVccIfA, cirEmAtmPvcVccIfB,
               cirEmAtmPvcVccVpiB, cirEmAtmPvcVccVciB }
     STATUS current
     DESCRIPTION "Response : The PVC VCC connection between a circuit-emulation
                  interface and an atm interface has been deleted."
        ::= { connectionEvents 22 }

vbrAtmPvcVccTearDownNotify NOTIFICATION-TYPE
     OBJECTS { vbrAtmPvcVccIfA, vbrAtmPvcVccIfB,
               vbrAtmPvcVccVpiB, vbrAtmPvcVccVciB }
     STATUS current
     DESCRIPTION "Response : The PVC VCC connection between a variable-bit rate
                  interface and an atm interface has been deleted."
        ::= { connectionEvents 23 }

frAtmPvcVccTearDownNotify  NOTIFICATION-TYPE
     OBJECTS { frAtmPvcVccIfA, frAtmPvcVccDlciA, frAtmPvcVccIfB,
               frAtmPvcVccVpiB, frAtmPvcVccVciB }
     STATUS current
     DESCRIPTION "Response : The PVC VCC connection between a frame-relay 
                  interface and an atm interface has been deleted."
        ::= { connectionEvents 24 }

frFrPvcTearDownNotify NOTIFICATION-TYPE
     OBJECTS { frFrPvcIfA, frFrPvcDlciA,
               frFrPvcIfB, frFrPvcDlciB }
     STATUS current
     DESCRIPTION "Response : The PVC connection between two frame-relay
                  interfaces has been deleted."
        ::= { connectionEvents 25 }

cirEmCirEmPvcTearDownNotify  NOTIFICATION-TYPE
     OBJECTS { cirEmCirEmPvcIfA, cirEmCirEmPvcIfB
             }
     STATUS current
     DESCRIPTION "Response : The PVC connection between two circuit-emulation
                  interfaces has been deleted."
        ::= { connectionEvents 26 }

vbrVbrPvcTearDownNotify NOTIFICATION-TYPE
     OBJECTS { vbrVbrPvcIfA, vbrVbrPvcIfB
               }
     STATUS current
     DESCRIPTION "Response : The PVC connection between two variable-bit rate
                  interfaces has been deleted."
        ::= { connectionEvents 27 }

bridgeBridgePvcReqFailNotify NOTIFICATION-TYPE
     OBJECTS { bridgeBridgePvcIfA,  bridgeBridgePvcIfB,
               pvcFailureReasonCode }
     STATUS current
     DESCRIPTION "Response : The PVC connection request between two bridge 
                  interfaces has failed."
        ::= { connectionEvents 28 }

bridgeBridgePvcSetupNotify NOTIFICATION-TYPE
     OBJECTS { bridgeBridgePvcIfA, bridgeBridgePvcIfB
               }
     STATUS current
     DESCRIPTION "Response : The PVC connection between two bridge interfaces
                  has been created."
        ::= { connectionEvents 29 }

bridgeBridgePvcTearDownNotify NOTIFICATION-TYPE
     OBJECTS { bridgeBridgePvcIfA, bridgeBridgePvcIfB
               }
     STATUS current
     DESCRIPTION "Response : The PVC connection between two bridge interfaces
                  has been deleted."
        ::= { connectionEvents 30 }

bridgeAtmPvcVccReqFailNotify NOTIFICATION-TYPE
     OBJECTS { bridgeAtmPvcVccIfA,  bridgeAtmPvcVccIfB,
               bridgeAtmPvcVccVpiB, bridgeAtmPvcVccVciB, 
               pvcFailureReasonCode }
     STATUS current
     DESCRIPTION "Response : The PVC VCC connection request between a bridge
                  interface and an atm interface has failed."
        ::= { connectionEvents 31 }

bridgeAtmPvcVccSetupNotify NOTIFICATION-TYPE
     OBJECTS { bridgeAtmPvcVccIfA, bridgeAtmPvcVccIfB,
               bridgeAtmPvcVccVpiB, bridgeAtmPvcVccVciB }
     STATUS current
     DESCRIPTION "Response : The PVC VCC connection between a bridge interface
                  and an atm interface has been created."
        ::= { connectionEvents 32 }

bridgeAtmPvcVccTearDownNotify NOTIFICATION-TYPE
     OBJECTS { bridgeAtmPvcVccIfA, bridgeAtmPvcVccIfB,
               bridgeAtmPvcVccVpiB, bridgeAtmPvcVccVciB }
     STATUS current
     DESCRIPTION "Response : The PVC VCC connection between a bridge interface
                  and an atm interface has been deleted."
        ::= { connectionEvents 33 }

cellTestReqFailNotify  NOTIFICATION-TYPE
     OBJECTS { cellTestIfB, cellTestVpiB,
               cellTestVcidB, pvcFailureReasonCode }
     STATUS current
     DESCRIPTION "Response : The PVC connection request has failed."
        ::= { connectionEvents 34 }

lmiDlciStatusNotify NOTIFICATION-TYPE
     OBJECTS { interfaceIndex, dlciNumber, lmiDlciOperStatus }
     STATUS current
     DESCRIPTION "Response : Indicates the end-to-end status of the PVC of
                  which this DLCI is a segment of."
        ::= { connectionEvents 35 }


cirEmAtmBkPvcVccReqFailNotify  NOTIFICATION-TYPE
     OBJECTS { cirEmAtmPvcVccIfA, cirEmAtmPvcVccIfB, 
               cirEmAtmPvcVccVpiB, cirEmAtmPvcVccVciB,
               pvcFailureReasonCode }
     STATUS current
     DESCRIPTION "Response : The DHPVC VCC backup connection request between a 
                  circuit emulation interface and an atm interface has failed."
        ::= { connectionEvents 36 }

cirEmAtmBkPvcVccSetupNotify  NOTIFICATION-TYPE
     OBJECTS { cirEmAtmPvcVccIfA, cirEmAtmPvcVccIfB, 
               cirEmAtmPvcVccVpiB, cirEmAtmPvcVccVciB }
     STATUS current
     DESCRIPTION "Response : The DHPVC VCC backup connection between a circuit 
                  emulation interface and an atm interface has been created."
        ::= { connectionEvents 37 }

cirEmAtmBkPvcVccTearDownNotify  NOTIFICATION-TYPE
     OBJECTS { cirEmAtmPvcVccIfA, cirEmAtmPvcVccIfB,
               cirEmAtmPvcVccVpiB, cirEmAtmPvcVccVciB }
     STATUS current
     DESCRIPTION "Response : The DHPVC VCC backup connection between a 
                  circuit-emulation interface and an atm interface has been 
                  deleted."
        ::= { connectionEvents 38}

vbrAtmBkPvcVccReqFailNotify NOTIFICATION-TYPE
     OBJECTS { vbrAtmPvcVccIfA,  vbrAtmPvcVccIfB,
               vbrAtmPvcVccVpiB, vbrAtmPvcVccVciB, 
               pvcFailureReasonCode }
     STATUS current
     DESCRIPTION "Response : The DHPVC VCC backup connection request between a 
                  variable-bit rate interface and an atm interface has failed."
        ::= { connectionEvents 39 }

vbrAtmBkPvcVccSetupNotify NOTIFICATION-TYPE
     OBJECTS { vbrAtmPvcVccIfA, vbrAtmPvcVccIfB,
               vbrAtmPvcVccVpiB, vbrAtmPvcVccVciB }
     STATUS current
     DESCRIPTION "Response : The DHPVC VCC backup connection between a 
                  variable-bit rate interface and an atm interface has been 
                  created."
        ::= { connectionEvents 40 }

vbrAtmBkPvcVccTearDownNotify NOTIFICATION-TYPE
     OBJECTS { vbrAtmPvcVccIfA, vbrAtmPvcVccIfB,
               vbrAtmPvcVccVpiB, vbrAtmPvcVccVciB }
     STATUS current
     DESCRIPTION "Response : The DHPVC VCC backup connection between a 
                  variable-bit rate interface and an atm interface has been 
                  deleted."
        ::= { connectionEvents 41 }

atmBkPvcVccReqFailNotify NOTIFICATION-TYPE
     OBJECTS { atmPvcVccIfA,  atmPvcVccVpiA, atmPvcVccVciA, atmPvcVccIfB,
               atmPvcVccVpiB, atmPvcVccVciB, pvcFailureReasonCode }
     STATUS current
     DESCRIPTION "Response : The DHPVC VCC backup connection request between an 
                  atm interface and an atm interface has failed."
        ::= { connectionEvents 42 }

atmBkPvcVccSetupNotify NOTIFICATION-TYPE
     OBJECTS { atmPvcVccIfA,  atmPvcVccVpiA, atmPvcVccVciA, atmPvcVccIfB,
               atmPvcVccVpiB, atmPvcVccVciB }
     STATUS current
     DESCRIPTION "Response : The DHPVC VCC backup connection between an atm
                  interface and an atm interface has been created."
        ::= { connectionEvents 43 }

atmBkPvcVccTearDownNotify NOTIFICATION-TYPE
     OBJECTS { atmPvcVccIfA,  atmPvcVccVpiA, atmPvcVccVciA, atmPvcVccIfB,
               atmPvcVccVpiB, atmPvcVccVciB }
     STATUS current
     DESCRIPTION "Response : The DHPVC VCC backup connection between an atm 
                  interface and an atm interface has been deleted."
        ::= { connectionEvents 44 }

frAtmBkPvcVccReqFailNotify NOTIFICATION-TYPE
     OBJECTS { frAtmPvcVccIfA,  frAtmPvcVccDlciA, frAtmPvcVccIfB,
               frAtmPvcVccVpiB, frAtmPvcVccVciB, pvcFailureReasonCode }
     STATUS current
     DESCRIPTION "Response : The DHPVC VCC backup connection request between a 
                  frame relay interface and an atm interface has failed."
        ::= { connectionEvents 45 }

frAtmBkPvcVccSetupNotify NOTIFICATION-TYPE
     OBJECTS { frAtmPvcVccIfA,  frAtmPvcVccDlciA, frAtmPvcVccIfB,
               frAtmPvcVccVpiB, frAtmPvcVccVciB }
     STATUS current
     DESCRIPTION "Response : The DHPVC VCC backup connection between a 
                  frame relay interface and an atm interface has been created."
        ::= { connectionEvents 46 }

frAtmBkPvcVccTearDownNotify NOTIFICATION-TYPE
     OBJECTS { frAtmPvcVccIfA,  frAtmPvcVccDlciA, frAtmPvcVccIfB,
               frAtmPvcVccVpiB, frAtmPvcVccVciB }
     STATUS current
     DESCRIPTION "Response : The DHPVC VCC backup connection between a 
                  frame relay interface and an atm interface has been deleted."
        ::= { connectionEvents 47 }

atmBkPvcVpcReqFailNotify NOTIFICATION-TYPE
     OBJECTS { atmPvcVpcIfA,  atmPvcVpcVpiA, atmPvcVpcIfB, atmPvcVpcVpiB, 
               pvcFailureReasonCode }
     STATUS current
     DESCRIPTION "Response : The DHPVC VPC backup connection request between an 
                  atm interface and an atm interface has failed."
        ::= { connectionEvents 48 }

atmBkPvcVpcSetupNotify NOTIFICATION-TYPE
     OBJECTS { atmPvcVpcIfA,  atmPvcVpcVpiA, atmPvcVpcIfB, atmPvcVpcVpiB }
     STATUS current
     DESCRIPTION "Response : The DHPVC VPC backup connection between an atm
                  interface and an atm interface has been created."
        ::= { connectionEvents 49 }

atmBkPvcVpcTearDownNotify NOTIFICATION-TYPE
     OBJECTS { atmPvcVpcIfA,  atmPvcVpcVpiA, atmPvcVpcIfB, atmPvcVpcVpiB }
     STATUS current
     DESCRIPTION "Response : The DHPVC VPC backup connection between an atm 
                  interface and an atm interface has been deleted."
        ::= { connectionEvents 50 }

bridgeAtmBkPvcVccReqFailNotify NOTIFICATION-TYPE
     OBJECTS { bridgeAtmPvcVccIfA,  bridgeAtmPvcVccIfB, bridgeAtmPvcVccVpiB, 
               bridgeAtmPvcVccVciB, pvcFailureReasonCode }
     STATUS current
     DESCRIPTION "Response : The DHPVC VCC backup connection request between a 
                  bridge interface and an atm interface has failed."
        ::= { connectionEvents 51 }

bridgeAtmBkPvcVccSetupNotify NOTIFICATION-TYPE
     OBJECTS { bridgeAtmPvcVccIfA,  bridgeAtmPvcVccIfB, bridgeAtmPvcVccVpiB, 
               bridgeAtmPvcVccVciB }
     STATUS current
     DESCRIPTION "Response : The DHPVC VCC backup connection between a bridge
                  interface and an atm interface has been created."
        ::= { connectionEvents 52 }

bridgeAtmBkPvcVccTearDownNotify NOTIFICATION-TYPE
     OBJECTS { bridgeAtmPvcVccIfA,  bridgeAtmPvcVccIfB, bridgeAtmPvcVccVpiB, 
               bridgeAtmPvcVccVciB }
     STATUS current
     DESCRIPTION "Response : The DHPVC VCC backup connection between a bridge
                  interface and an atm interface has been deleted."
        ::= { connectionEvents 53 }

ipAtmBkAppPvcVccReqFailNotify NOTIFICATION-TYPE
     OBJECTS { ipAtmAppPvcVccDestAddrA,  ipAtmAppPvcVccSubnetMaskA,
               ipAtmAppPvcVccIfB, ipAtmAppPvcVccVpiB, ipAtmAppPvcVccVciB,
               pvcFailureReasonCode }
     STATUS current
     DESCRIPTION "Response : The DHPVC VCC backup connection request between an 
                  in-band management interface and an atm interface has failed."
        ::= { connectionEvents 54 }

ipAtmBkAppPvcVccSetupNotify NOTIFICATION-TYPE
     OBJECTS { ipAtmAppPvcVccDestAddrA,  ipAtmAppPvcVccSubnetMaskA,
               ipAtmAppPvcVccIfB, ipAtmAppPvcVccVpiB, ipAtmAppPvcVccVciB }
     STATUS current
     DESCRIPTION "Response : The DHPVC VCC backup connection between an in-band 
                  management interface and an atm interface has been created."
        ::= { connectionEvents 55 }

ipAtmBkAppPvcVccTearDownNotify NOTIFICATION-TYPE
     OBJECTS { ipAtmAppPvcVccDestAddrA,  ipAtmAppPvcVccSubnetMaskA,
               ipAtmAppPvcVccIfB, ipAtmAppPvcVccVpiB, ipAtmAppPvcVccVciB }
     STATUS current
     DESCRIPTION "Response : The DHPVC VCC backup connection between an in-band 
                  management interface and an atm interface has been deleted."
        ::= { connectionEvents 56 }



cirEmAtmSpvcVccSetUpNotify  NOTIFICATION-TYPE
     OBJECTS { cirEmAtmSpvcVccIfA, cirEmAtmSpvcVccIfB, cirEmAtmSpvcVccVpiB, 
               cirEmAtmSpvcVccVciB }
     STATUS current
     DESCRIPTION "Response : Notification that a SPVC connection between CE and
		  ATM endpoints has been made successfully.
          Return values - A-side interfaceIndex
                          B-side interfaceIndex
                          B-side vpi/vci"
	::= { connectionEvents 57 }

vbrAtmSpvcVccSetUpNotify  NOTIFICATION-TYPE
     OBJECTS { vbrAtmSpvcVccIfA, vbrAtmSpvcVccIfB, vbrAtmSpvcVccVpiB, 
               vbrAtmSpvcVccVciB }
     STATUS current
     DESCRIPTION "Response :  Notification that a SPVC connection between TE 
		  and ATM endpoints has been made successfully.
          Return values - A-side interfaceIndex
                          B-side interfaceIndex
                          B-side vpi/vci"
	::= { connectionEvents 58 }

atmSpvcVccSetUpNotify  NOTIFICATION-TYPE
     OBJECTS { atmSpvcVccIfA, atmSpvcVccVpiA, atmSpvcVccVciA,
               atmSpvcVccIfB, atmSpvcVccVpiB, atmSpvcVccVciB }
     STATUS current
     DESCRIPTION "Response : Notification that a SPVC connection between ATM 
		  and ATM endpoints has been made successfully.
          Return values - A-side interfaceIndex
                          A-side vpi/vci
                          B-side interfaceIndex
                          B-side vpi/vci"
	::= { connectionEvents 59 }

cirEmAtmSpvcVccTearDownNotify  NOTIFICATION-TYPE
     OBJECTS { cirEmAtmSpvcVccIfA, cirEmAtmSpvcVccIfB, cirEmAtmSpvcVccVpiB, 
               cirEmAtmSpvcVccVciB }
     STATUS current
     DESCRIPTION "Response : Notification that a SPVC connection between CE and
		  ATM endpoints has been deleted.
          Return values - A-side interfaceIndex
                          B-side interfaceIndex
                          B-side vpi/vci"
	::= { connectionEvents 60 }

vbrAtmSpvcVccTearDownNotify  NOTIFICATION-TYPE
     OBJECTS { vbrAtmSpvcVccIfA, vbrAtmSpvcVccIfB, vbrAtmSpvcVccVpiB, 
               vbrAtmSpvcVccVciB }
     STATUS current
     DESCRIPTION "Response : Notification that a SPVC connection between TE and
		  ATM endpoints has been deleted.
          Return values - A-side interfaceIndex
                          B-side interfaceIndex
                          B-side vpi/vci"
	::= { connectionEvents 61 }

atmSpvcVccTearDownNotify  NOTIFICATION-TYPE
     OBJECTS { atmSpvcVccIfA, atmSpvcVccVpiA, atmSpvcVccVciA,
               atmSpvcVccIfB, atmSpvcVccVpiB, atmSpvcVccVciB }
     STATUS current
     DESCRIPTION "Response : Notification that a SPVC connection between ATM 
		  and ATM endpoints has been deleted.
          Return values - A-side interfaceIndex
                          A-side vpi/vci
                          B-side interfaceIndex
                          B-side vpi/vci"
	::= { connectionEvents 62 }


oamTestReqFailNotify NOTIFICATION-TYPE
     OBJECTS { oamTestIfB, oamTestVpiB, oamTestVciB, oamTestFailureReasonCode }
     STATUS current
     DESCRIPTION "Response : OAM loopback test request has failed."
        ::= { connectionEvents 63 }

oamActDeactResultNotify NOTIFICATION-TYPE
     OBJECTS { oamActDeactIfB, oamActDeactVpiB,
                oamActDeactVciB, oamActDeactResultCode }
     STATUS current
     DESCRIPTION "Response : the final status of oam
        Activation-Deactivation request."
     ::= { connectionEvents 64 }


frAtmSpvcVccSetUpNotify  NOTIFICATION-TYPE
     OBJECTS { spvcAddrIfA, frAtmSpvcVccDlciA, frAtmSpvcVccIfB,
             frAtmSpvcVccVpiB, frAtmSpvcVccVciB }
     STATUS current
     DESCRIPTION "Response : Notification that a SPVC connection between FR and
          ATM endpoints has been made successfully.
          Return values - A-side interfaceIndex
                          A-side dlci
                          B-side interfaceIndex
                          B-side vpi/vci"
    ::= { connectionEvents 65 }

frAtmSpvcVccTearDownNotify  NOTIFICATION-TYPE
     OBJECTS { spvcAddrIfA, frAtmSpvcVccDlciA, frAtmSpvcVccIfB,
             frAtmSpvcVccVpiB, frAtmSpvcVccVciB }
     STATUS current
     DESCRIPTION "Response : Notification that a SPVC connection between FR and
          ATM endpoints has been deleted.
          Return values - A-side interfaceIndex
                          A-side dlci
                          B-side interfaceIndex
                          B-side vpi/vci"
    ::= { connectionEvents 66 }

-- Changes for 1  integration - new trap declaration.
-- Frame Relay Spvc's don't need the new change. 

atmAtmSpvcVccSetUpNotify  NOTIFICATION-TYPE
     OBJECTS { spvcAddrIfA, atmAtmSpvcVccVpiA,
     atmAtmSpvcVccVciA,atmAtmSpvcVccRemoteAtmPortAddr,
               atmAtmSpvcVccIfB, atmAtmSpvcVccVpiB, atmAtmSpvcVccVciB }
     STATUS current
     DESCRIPTION "Response : Notification that a SPVC connection between ATM 
		  and ATM endpoints has been made successfully.
          Return values - A-side interfaceIndex
                          A-side vpi/vci
                          Remote NSAP address
                          B-side interfaceIndex
                          B-side vpi/vci"
	::= { connectionEvents 67 }

atmAtmSpvcVccTearDownNotify  NOTIFICATION-TYPE
     OBJECTS { spvcAddrIfA, atmAtmSpvcVccVpiA, atmAtmSpvcVccVciA,
               atmAtmSpvcVccRemoteAtmPortAddr,
               atmAtmSpvcVccIfB, atmAtmSpvcVccVpiB, atmAtmSpvcVccVciB }
     STATUS current
     DESCRIPTION "Response : Notification that a SPVC connection between ATM 
		  and ATM endpoints has been deleted.
          Return values - A-side interfaceIndex
                          A-side vpi/vci
                          Remote NSAP address
                          B-side interfaceIndex
                          B-side vpi/vci"
	::= { connectionEvents 68 }

cirAtmSpvcVccSetUpNotify  NOTIFICATION-TYPE
     OBJECTS { spvcAddrIfA, cirAtmSpvcVccRemoteCePortAddr,
               cirAtmSpvcVccIfB, cirAtmSpvcVccVpiB, 
               cirAtmSpvcVccVciB }
     STATUS current
     DESCRIPTION "Response : Notification that a SPVC connection between CE and
		  ATM endpoints has been made successfully.
          Return values - A-side interfaceIndex
                          Remote NSAP address
                          B-side interfaceIndex
                          B-side vpi/vci"
	::= { connectionEvents 69 }

cirAtmSpvcVccTearDownNotify  NOTIFICATION-TYPE
     OBJECTS { spvcAddrIfA, cirAtmSpvcVccRemoteCePortAddr,
               cirAtmSpvcVccIfB, cirAtmSpvcVccVpiB, 
               cirAtmSpvcVccVciB }
     STATUS current
     DESCRIPTION "Response : Notification that a SPVC connection between CE and
		  ATM endpoints has been deleted.
          Return values - A-side interfaceIndex
                          Remote NSAP address
                          B-side interfaceIndex
                          B-side vpi/vci"
	::= { connectionEvents 70 }

vbrAtmSpvcSetUpNotify  NOTIFICATION-TYPE
     OBJECTS { spvcAddrIfA, vbrAtmSpvcRemoteVbrPortAddr,
                vbrAtmSpvcIfB, vbrAtmSpvcVpiB, 
               vbrAtmSpvcVciB }
     STATUS current
     DESCRIPTION "Response :  Notification that a SPVC connection between TE 
		  and ATM endpoints has been made successfully.
          Return values - A-side interfaceIndex
                          Remote NSAP address
                          B-side interfaceIndex
                          B-side vpi/vci"
	::= { connectionEvents 71 }

vbrAtmSpvcTearDownNotify  NOTIFICATION-TYPE
     OBJECTS { spvcAddrIfA, vbrAtmSpvcRemoteVbrPortAddr,
               vbrAtmSpvcIfB, vbrAtmSpvcVpiB, 
               vbrAtmSpvcVciB }
     STATUS current
     DESCRIPTION "Response : Notification that a SPVC connection between TE and
		  ATM endpoints has been deleted.
          Return values - A-side interfaceIndex
                          Remote NSAP address
                          B-side interfaceIndex
                          B-side vpi/vci"
	::= { connectionEvents 72 }




aal2TrunkConfigSetupNotify  NOTIFICATION-TYPE
     OBJECTS { aal2TrunkConfigIf, aal2TrunkConfigVpi,
               aal2TrunkConfigVci }
     STATUS current
     DESCRIPTION "Response : The PVC VCC connection for aal2 trunk"
        ::= { connectionEvents 73 }

aal2TrunkConfigTearDownNotify  NOTIFICATION-TYPE
     OBJECTS { aal2TrunkConfigIf, aal2TrunkConfigVpi,
               aal2TrunkConfigVci }
     STATUS current
     DESCRIPTION "Response : The PVC VCC AAL2 Trunk has been deleted"
        ::= { connectionEvents 74 }

aal2TrunkConfigReqFailNotify  NOTIFICATION-TYPE
     OBJECTS { aal2TrunkConfigIf, aal2TrunkConfigVpi,
               aal2TrunkConfigVci, pvcFailureReasonCode }
     STATUS current
     DESCRIPTION "Response : The PVC VCC aal2 trunk could not be setup"
        ::= { connectionEvents 75 }

gr303Aal2PvcConfigReqFailNotify  NOTIFICATION-TYPE
     OBJECTS { gr303Aal2PvcVccGr303IgId,
                             gr303Aal2PvcVccGr303CallRef,
                             gr303Aal2PvcVccIfB,
                             gr303Aal2PvcVccVpiB,
                             gr303Aal2PvcVccVciB,
                             gr303Aal2PvcVccAal2Cid
               }
     STATUS current
     DESCRIPTION "Response : The GR303 PVC VCC on aal2 trunk could not be setup"
        ::= { connectionEvents 76 }

gr303Aal2PvcSetUpNotify  NOTIFICATION-TYPE
     OBJECTS { gr303Aal2PvcVccGr303IgId,
                             gr303Aal2PvcVccGr303CallRef,
                             gr303Aal2PvcVccIfB,
                             gr303Aal2PvcVccVpiB,
                             gr303Aal2PvcVccVciB,
                             gr303Aal2PvcVccAal2Cid
               }
     STATUS current
     DESCRIPTION "Response : Notification that a monitor connection between Gr303 call ref and
                  ATM AAL2 CID has been made successfully."
        ::= { connectionEvents 77 }

gr303Aal2PvcTearDownNotify  NOTIFICATION-TYPE
     OBJECTS { gr303Aal2PvcVccGr303IgId,
                             gr303Aal2PvcVccGr303CallRef,
                             gr303Aal2PvcVccIfB,
                             gr303Aal2PvcVccVpiB,
                             gr303Aal2PvcVccVciB,
                             gr303Aal2PvcVccAal2Cid
               }
     STATUS current
     DESCRIPTION "Response : Notification that a monitor connection between Gr303 call ref and
                  ATM AAL2 CID has been deleted"
        ::= { connectionEvents 78 }

dhpvcChangeNotify  NOTIFICATION-TYPE
     OBJECTS {
                interfaceIndex,
                atmVpi,
                atmVci,
                pvcFailureReasonCode
             }
     STATUS current
     DESCRIPTION "This will indicate the changes in a dual home pvc. 
                  This will have 2 indications. One is when there is a switchover
                  which indicate the last state and the new one (eg Prim To Bkup)
                  Secondly there will also be an indication when there is a
                  state change which will indicate the new state only 
                  (eg Primary is Active and in No Fail Condition and Backup
                   is Passive and in Fail Condition). In case of state change
                  the traffic path is not changed but it indicates  the
                  state of the passive path. "
        ::= { connectionEvents 79 }

--
-- Notification of SPVP connections
--
atmAtmSpvcVpcSetUpNotify  NOTIFICATION-TYPE
     OBJECTS { spvcAddrIfA, atmAtmSpvcVpcVpiA,atmAtmSpvcVpcRemoteAtmPortAddr,
               atmAtmSpvcVpcIfB, atmAtmSpvcVccVpiB}
     STATUS current
     DESCRIPTION "Response : Notification that a SPVP connection between ATM
                  and ATM endpoints has been made successfully."
        ::= { connectionEvents 80}

atmAtmSpvcVpcTearDownNotify  NOTIFICATION-TYPE
     OBJECTS { spvcAddrIfA, atmAtmSpvcVccVpiA,atmAtmSpvcVpcRemoteAtmPortAddr,
               atmAtmSpvcVpcIfB, atmAtmSpvcVpcVpiB}
     STATUS current
     DESCRIPTION "Response : Notification that a SPVP connection between ATM
                  and ATM endpoints has been deleted."
        ::= { connectionEvents 81 }

iptResultNotify NOTIFICATION-TYPE
     OBJECTS { iptGroupId, iptLogicalIntfId, iptResultCode }
     STATUS current
     DESCRIPTION "Response : the final status of interface protection 
         request."
     ::= { connectionEvents 82}

pgtResultNotify NOTIFICATION-TYPE
     OBJECTS { pgtGroupId,  pgtResultCode }
     STATUS current
     DESCRIPTION "Response : the final status of interface protection group
         request."
     ::= { connectionEvents 83}

atmTrunkingSigVccSetUpNotify  NOTIFICATION-TYPE
     OBJECTS { atmTrunkingSigVccRmtIWFIdentifier, atmTrunkingSigVccIdentifier }
     STATUS current
     DESCRIPTION "Response : Notification that a ATM Trunking Signalling VCC
                  has been setup successfully.
          Return values - atmTrunkingSigVccRmtIWFIdentifier
                          atmTrunkingSigVccIdentifier"
        ::= { connectionEvents 84 }

atmTrunkingSigVccTearDownNotify NOTIFICATION-TYPE
     OBJECTS { atmTrunkingSigVccRmtIWFIdentifier, atmTrunkingSigVccIdentifier }
     STATUS current
     DESCRIPTION "Response : Notification that a ATM Trunking Signalling VCC
                  has been torn down successfully.
          Return values - atmTrunkingSigVccRmtIWFIdentifier
                          atmTrunkingSigVccIdentifier"
        ::= { connectionEvents 85 }

atmTrunkingBrVccSetUpNotify  NOTIFICATION-TYPE
     OBJECTS { atmTrunkingBrVccRmtIWFId, atmTrunkingBrVccId }
     STATUS current
     DESCRIPTION "Response : Notification that a ATM Trunking Bearer VCC
                  has been setup successfully.
          Return values - atmTrunkingBrVccRmtIWFIdentifier
                          atmTrunkingBrVccIdentifier"
        ::= { connectionEvents 86 }

atmTrunkingBrVccTearDownNotify NOTIFICATION-TYPE
     OBJECTS { atmTrunkingBrVccRmtIWFId, atmTrunkingBrVccId }
     STATUS current
     DESCRIPTION "Response : Notification that a ATM Trunking Bearer VCC
                  has been torn down successfully.
          Return values - atmTrunkingBrVccRmtIWFIdentifier
                          atmTrunkingBrVccIdentifier"
        ::= { connectionEvents 87 }


END
