Nortel-MsCarrier-MscPassport-DcmeMIB
DEFINITIONS ::= BEGIN



IMPORTS

      OBJECT-TYPE
   FROM RFC-1212

      mscPassportMIBs,
      mscComponents
   FROM Nortel-MsCarrier-MscPassport-UsefulDefinitionsMIB

      Counter32,
      RowPointer,
      DisplayString,
      StorageType,
      RowStatus,
      Gauge32,
      Integer32,
      Unsigned32
   FROM Nortel-MsCarrier-MscPassport-StandardTextualConventionsMIB

      AsciiString,
      Hex,
      NonReplicated,
      EnterpriseDateAndTime,
      PassportCounter64,
      FixedPoint1,
      Link,
      DigitString
   FROM Nortel-MsCarrier-MscPassport-TextualConventionsMIB;




-- LAST-UPDATED   "9909010000Z"
-- ORGANIZATION   "Nortel Networks"
-- CONTACT-INFO   "
--         Nortel Carrier Data Network Management
--         
--         Postal:       P.O. Box 3511, Station C 
--                       Ottawa, Ontario 
--                       Canada  K1Y 4H7
--         
--         via the WEB:  http://www.nortelnetworks.com  
--                       select 'Contact Us' from the menu
--          
--         via phone:    1-800-4NORTEL"
-- DESCRIPTION
--    "The module describing the Nortel MsCarrier MscPassport
--     Dcme Enterprise MIB."

dcmeMIB OBJECT IDENTIFIER ::= { mscPassportMIBs 134 }










-- Dcme/n
-- This component defines the common characteristics of a set of 
-- connections to an International Switching Centre (ISC) equipment.

mscDcme OBJECT IDENTIFIER ::= { mscComponents 129 }



mscDcmeRowStatusTable OBJECT-TYPE
   SYNTAX     SEQUENCE OF MscDcmeRowStatusEntry
   ACCESS     not-accessible
   STATUS     mandatory
   DESCRIPTION
     "This entry controls the addition and deletion of 
      mscDcme components."
::= { mscDcme 1 }

mscDcmeRowStatusEntry OBJECT-TYPE
   SYNTAX     MscDcmeRowStatusEntry
   ACCESS     not-accessible
   STATUS     mandatory
   DESCRIPTION
     "A single entry in the table represents a single 
      mscDcme component."
   INDEX {
      mscDcmeIndex }
::= { mscDcmeRowStatusTable 1 }

MscDcmeRowStatusEntry ::= SEQUENCE {
   mscDcmeRowStatus
      RowStatus,
   mscDcmeComponentName
      DisplayString,
   mscDcmeStorageType
      StorageType,
   mscDcmeIndex
      Integer32 }

mscDcmeRowStatus OBJECT-TYPE
   SYNTAX     RowStatus 
   ACCESS     read-write
   STATUS     mandatory
   DESCRIPTION
     "This variable is used as the basis for SNMP naming of
      mscDcme components.
      These components can be added and deleted."
::= { mscDcmeRowStatusEntry 1 }

mscDcmeComponentName OBJECT-TYPE
   SYNTAX     DisplayString 
   ACCESS     read-only
   STATUS     mandatory
   DESCRIPTION
     "This variable provides the component's string name for
      use with the ASCII Console Interface"
::= { mscDcmeRowStatusEntry 2 }

mscDcmeStorageType OBJECT-TYPE
   SYNTAX     StorageType 
   ACCESS     read-only
   STATUS     mandatory
   DESCRIPTION
     "This variable represents the storage type value for the
      mscDcme tables."
::= { mscDcmeRowStatusEntry 4 }

mscDcmeIndex OBJECT-TYPE
   SYNTAX     Integer32 (1..16)
   ACCESS     not-accessible
   STATUS     mandatory
   DESCRIPTION
     "This variable represents the index for the mscDcme tables."
::= { mscDcmeRowStatusEntry 10 }

mscDcmeProvTable OBJECT-TYPE
   SYNTAX     SEQUENCE OF MscDcmeProvEntry
   ACCESS     not-accessible
   STATUS     mandatory
   DESCRIPTION
     "This group contains the provisionable attributes of a Dcme 
      component."
::= { mscDcme 10 }

mscDcmeProvEntry OBJECT-TYPE
   SYNTAX     MscDcmeProvEntry
   ACCESS     not-accessible
   STATUS     mandatory
   DESCRIPTION
     "An entry in the mscDcmeProvTable."
   INDEX {
      mscDcmeIndex }
::= { mscDcmeProvTable 1 }

MscDcmeProvEntry ::= SEQUENCE {
   mscDcmeCommentText
      AsciiString,
   mscDcmePreestablishedConnections
      Unsigned32,
   mscDcmeTrmThreshold
      Unsigned32,
   mscDcmeTrmSignalChangeInterval
      Unsigned32,
   mscDcmeSpeechAlarmThreshold
      Unsigned32,
   mscDcmeAudio3kHzAlarmThreshold
      Unsigned32,
   mscDcmeUnrestricted64kAlarmThreshold
      Unsigned32,
   mscDcmeAlarmTimeInterval
      Unsigned32,
   mscDcmeMaxUnrestricted64kCalls
      Unsigned32 }

mscDcmeCommentText OBJECT-TYPE
   SYNTAX     AsciiString (SIZE (0..40))
   ACCESS     read-write
   STATUS     mandatory
   DESCRIPTION
     "Use of this attribute is at the discretion of the system administrator. 
      Typically, it specifies the name of the customer that is using this 
      Dcme."
   DEFVAL     { ''H }  -- ""
::= { mscDcmeProvEntry 1 }

mscDcmePreestablishedConnections OBJECT-TYPE
   SYNTAX     Unsigned32 (1..30)
   ACCESS     read-write
   STATUS     mandatory
   DESCRIPTION
     "This attribute specifies the number of Logical Connections (LC) 
      preestablished between each DcmeLink associated with this Dcme 
      and its remote peer, that are established beyond those that are 
      required to carry established connections. Those are the standby 
      LCs to be used for the subsequent user speech or audio 3.1 kHz 
      calls. This attribute should be set to the number of speech and audio 
      3.1 kHz calls expected in a typical burst of calls received from the 
      ISC on one DcmeLink."
   DEFVAL     { 5 }
::= { mscDcmeProvEntry 2 }

mscDcmeTrmThreshold OBJECT-TYPE
   SYNTAX     Unsigned32 (0..30)
   ACCESS     read-write
   STATUS     mandatory
   DESCRIPTION
     "This attribute is used to determine when the DcmeLink may be 
      unable to handle incoming calls from the ISC. If the Dcme fails to 
      replenish the number of preestablished connections the 'No trunk(s) 
      available for 3.1 kHz audio or speech' TRM signal is sent to the 
      ISC."
   DEFVAL     { 1 }
::= { mscDcmeProvEntry 3 }

mscDcmeTrmSignalChangeInterval OBJECT-TYPE
   SYNTAX     Unsigned32 (10..300)
   ACCESS     read-write
   STATUS     mandatory
   DESCRIPTION
     "This attribute specifies a minimum time interval between TRM 
      signal change from 'No trunk(s) available for 3.1 kHz audio or 
      speech' or 'No 64 kbit/s capacity available' to 'DCME normal' 
      signal."
   DEFVAL     { 20 }
::= { mscDcmeProvEntry 4 }

mscDcmeSpeechAlarmThreshold OBJECT-TYPE
   SYNTAX     Unsigned32 (0..1000)
   ACCESS     read-write
   STATUS     mandatory
   DESCRIPTION
     "This attribute specifies how many normal speech calls can be 
      rejected by one dcmeLink within the alarmTimeInterval time before 
      a SET alarm is generated. This alarm is cleared when the number of 
      rejected speech calls is less than speechAlarmThreshold in a 
      subsequent interval. 
      If the value is 0 the rejected speech calls are not monitored."
   DEFVAL     { 0 }
::= { mscDcmeProvEntry 5 }

mscDcmeAudio3kHzAlarmThreshold OBJECT-TYPE
   SYNTAX     Unsigned32 (0..1000)
   ACCESS     read-write
   STATUS     mandatory
   DESCRIPTION
     "This attribute specifies how many audio 3.1 kHz calls can be 
      rejected by one dcmeLink within the alarmTimeInterval time before 
      a SET alarm is generated. This alarm is cleared when the number of 
      rejected audio 3.1 kHz calls is less than audio3kHzAlarmThreshold 
      in a subsequent interval. 
      If the value is 0 the rejected audio 3.1 kHz calls are not monitored."
   DEFVAL     { 0 }
::= { mscDcmeProvEntry 6 }

mscDcmeUnrestricted64kAlarmThreshold OBJECT-TYPE
   SYNTAX     Unsigned32 (0..1000)
   ACCESS     read-write
   STATUS     mandatory
   DESCRIPTION
     "This attribute specifies how many unrestricted 64 kbit/s calls can be 
      rejected by one dcmeLink within the alarmTimeInterval time before 
      a SET alarm is generated. This alarm is cleared when the number of 
      rejected unrestricted 64 kbit/s calls is less than 
      unrestricted64kAlarmThreshold in a subsequent interval. 
      If the value is 0 the rejected unrestricted 64 kbit/s calls are not 
      monitored."
   DEFVAL     { 0 }
::= { mscDcmeProvEntry 7 }

mscDcmeAlarmTimeInterval OBJECT-TYPE
   SYNTAX     Unsigned32 (0..120)
   ACCESS     read-write
   STATUS     mandatory
   DESCRIPTION
     "This attribute specifies the time interval within which the rejected 
      speech calls, audio 3.1 kHz calls, and unrestricted 64 kbit/s calls are 
      monitored. It is used in the conjunction with the 
      speechAlarmThreshold, audio3kHzAlarmThreshold, and 
      unrestricted64kAlarmThreshold attributes."
   DEFVAL     { 5 }
::= { mscDcmeProvEntry 8 }

mscDcmeMaxUnrestricted64kCalls OBJECT-TYPE
   SYNTAX     Unsigned32 (0..420)
   ACCESS     read-write
   STATUS     mandatory
   DESCRIPTION
     "This attribute specifies the maximum number of simultaneous 
      dynamic unrestricted 64 kbit/s calls that can be established. A value 
      of 0 means that no dynamic unrestricted 64 kbit/s calls can be 
      established."
   DEFVAL     { 420 }
::= { mscDcmeProvEntry 9 }

mscDcmeStateTable OBJECT-TYPE
   SYNTAX     SEQUENCE OF MscDcmeStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { mscDcme 11 }

mscDcmeStateEntry OBJECT-TYPE
   SYNTAX     MscDcmeStateEntry
   ACCESS     not-accessible
   STATUS     mandatory
   DESCRIPTION
     "An entry in the mscDcmeStateTable."
   INDEX {
      mscDcmeIndex }
::= { mscDcmeStateTable 1 }

MscDcmeStateEntry ::= SEQUENCE {
   mscDcmeAdminState
      INTEGER,
   mscDcmeOperationalState
      INTEGER,
   mscDcmeUsageState
      INTEGER }

mscDcmeAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { mscDcmeStateEntry 1 }

mscDcmeOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { mscDcmeStateEntry 2 }

mscDcmeUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { mscDcmeStateEntry 3 }

mscDcmeStatsTable OBJECT-TYPE
   SYNTAX     SEQUENCE OF MscDcmeStatsEntry
   ACCESS     not-accessible
   STATUS     mandatory
   DESCRIPTION
     "This group contains the statistics maintained by this Dcme."
::= { mscDcme 13 }

mscDcmeStatsEntry OBJECT-TYPE
   SYNTAX     MscDcmeStatsEntry
   ACCESS     not-accessible
   STATUS     mandatory
   DESCRIPTION
     "An entry in the mscDcmeStatsTable."
   INDEX {
      mscDcmeIndex }
::= { mscDcmeStatsTable 1 }

MscDcmeStatsEntry ::= SEQUENCE {
   mscDcmeTrm64kNotAvailable
      Counter32,
   mscDcmeTrmSpeechNotAvailable
      Counter32 }

mscDcmeTrm64kNotAvailable OBJECT-TYPE
   SYNTAX     Counter32 
   ACCESS     read-only
   STATUS     mandatory
   DESCRIPTION
     "This attribute counts the total number of times the TRM signal was 
      changed to the 'No 64 kbit/s capacity available' signal.
      This counter wraps to zero when it exceeds its maximum."
::= { mscDcmeStatsEntry 1 }

mscDcmeTrmSpeechNotAvailable OBJECT-TYPE
   SYNTAX     Counter32 
   ACCESS     read-only
   STATUS     mandatory
   DESCRIPTION
     "This attribute counts the total number of times the TRM signal was 
      changed to the 'No trunk(s) available for 3.1 kHz audio or speech' 
      signal.
      This counter wraps to zero when it exceeds its maximum."
::= { mscDcmeStatsEntry 2 }

mscDcmeDLinksTable OBJECT-TYPE
   SYNTAX     SEQUENCE OF MscDcmeDLinksEntry
   ACCESS     not-accessible
   STATUS     mandatory
   DESCRIPTION
     "This attribute specifies all of the DcmeLinks which are associated 
      with this Dcme. There can be up to 14 DcmeLinks associated with 
      one Dcme."
::= { mscDcme 419 }

mscDcmeDLinksEntry OBJECT-TYPE
   SYNTAX     MscDcmeDLinksEntry
   ACCESS     not-accessible
   STATUS     mandatory
   DESCRIPTION
     "An entry in the mscDcmeDLinksTable."
   INDEX {
      mscDcmeIndex,
      mscDcmeDLinksValue }
::= { mscDcmeDLinksTable 1 }

MscDcmeDLinksEntry ::= SEQUENCE {
   mscDcmeDLinksValue
      Link,
   mscDcmeDLinksRowStatus
      RowStatus }

mscDcmeDLinksValue OBJECT-TYPE
   SYNTAX     Link 
   ACCESS     read-write
   STATUS     mandatory
   DESCRIPTION
     "This variable represents both the value and the index for the
      mscDcmeDLinksTable."
::= { mscDcmeDLinksEntry 1 }

mscDcmeDLinksRowStatus OBJECT-TYPE
   SYNTAX     RowStatus 
   ACCESS     write-only
   STATUS     mandatory
   DESCRIPTION
     "This variable is used to control the addition and deletion 
      of individual values of the mscDcmeDLinksTable."
::= { mscDcmeDLinksEntry 2 }

mscDcmeActiveDcmeLinksTable OBJECT-TYPE
   SYNTAX     SEQUENCE OF MscDcmeActiveDcmeLinksEntry
   ACCESS     not-accessible
   STATUS     mandatory
   DESCRIPTION
     "This attribute indicates all of the DcmeLink components that are 
      currently active and have registered with this Dcme."
::= { mscDcme 420 }

mscDcmeActiveDcmeLinksEntry OBJECT-TYPE
   SYNTAX     MscDcmeActiveDcmeLinksEntry
   ACCESS     not-accessible
   STATUS     mandatory
   DESCRIPTION
     "An entry in the mscDcmeActiveDcmeLinksTable."
   INDEX {
      mscDcmeIndex,
      mscDcmeActiveDcmeLinksValue }
::= { mscDcmeActiveDcmeLinksTable 1 }

MscDcmeActiveDcmeLinksEntry ::= SEQUENCE {
   mscDcmeActiveDcmeLinksValue
      RowPointer }

mscDcmeActiveDcmeLinksValue OBJECT-TYPE
   SYNTAX     RowPointer 
   ACCESS     read-only
   STATUS     mandatory
   DESCRIPTION
     "This variable represents both the value and the index for the
      mscDcmeActiveDcmeLinksTable."
::= { mscDcmeActiveDcmeLinksEntry 1 }


-- Dcme/n DcmeProfile		
-- This component defines the ISC interface characteristics of the 
-- Dcme component.

mscDcmeProfile OBJECT IDENTIFIER ::= { mscDcme 2 }



mscDcmeProfileRowStatusTable OBJECT-TYPE
   SYNTAX     SEQUENCE OF MscDcmeProfileRowStatusEntry
   ACCESS     not-accessible
   STATUS     mandatory
   DESCRIPTION
     "This entry controls the addition and deletion of 
      mscDcmeProfile components."
::= { mscDcmeProfile 1 }

mscDcmeProfileRowStatusEntry OBJECT-TYPE
   SYNTAX     MscDcmeProfileRowStatusEntry
   ACCESS     not-accessible
   STATUS     mandatory
   DESCRIPTION
     "A single entry in the table represents a single 
      mscDcmeProfile component."
   INDEX {
      mscDcmeIndex,
      mscDcmeProfileIndex }
::= { mscDcmeProfileRowStatusTable 1 }

MscDcmeProfileRowStatusEntry ::= SEQUENCE {
   mscDcmeProfileRowStatus
      RowStatus,
   mscDcmeProfileComponentName
      DisplayString,
   mscDcmeProfileStorageType
      StorageType,
   mscDcmeProfileIndex
      NonReplicated }

mscDcmeProfileRowStatus OBJECT-TYPE
   SYNTAX     RowStatus 
   ACCESS     read-only
   STATUS     mandatory
   DESCRIPTION
     "This variable is used as the basis for SNMP naming of
      mscDcmeProfile components.
      These components cannot be added nor deleted."
::= { mscDcmeProfileRowStatusEntry 1 }

mscDcmeProfileComponentName OBJECT-TYPE
   SYNTAX     DisplayString 
   ACCESS     read-only
   STATUS     mandatory
   DESCRIPTION
     "This variable provides the component's string name for
      use with the ASCII Console Interface"
::= { mscDcmeProfileRowStatusEntry 2 }

mscDcmeProfileStorageType OBJECT-TYPE
   SYNTAX     StorageType 
   ACCESS     read-only
   STATUS     mandatory
   DESCRIPTION
     "This variable represents the storage type value for the
      mscDcmeProfile tables."
::= { mscDcmeProfileRowStatusEntry 4 }

mscDcmeProfileIndex OBJECT-TYPE
   SYNTAX     NonReplicated 
   ACCESS     not-accessible
   STATUS     mandatory
   DESCRIPTION
     "This variable represents the index for the mscDcmeProfile tables."
::= { mscDcmeProfileRowStatusEntry 10 }

mscDcmeProfileLCOpsTable OBJECT-TYPE
   SYNTAX     SEQUENCE OF MscDcmeProfileLCOpsEntry
   ACCESS     not-accessible
   STATUS     mandatory
   DESCRIPTION
     "This group contains attributes used in setting up Switched Logical 
      Connections (SLC) over the network using the Path Oriented 
      Routing System (PORS) between two peer DcmeLink components."
::= { mscDcmeProfile 10 }

mscDcmeProfileLCOpsEntry OBJECT-TYPE
   SYNTAX     MscDcmeProfileLCOpsEntry
   ACCESS     not-accessible
   STATUS     mandatory
   DESCRIPTION
     "An entry in the mscDcmeProfileLCOpsTable."
   INDEX {
      mscDcmeIndex,
      mscDcmeProfileIndex }
::= { mscDcmeProfileLCOpsTable 1 }

MscDcmeProfileLCOpsEntry ::= SEQUENCE {
   mscDcmeProfileSetupPriority
      Unsigned32,
   mscDcmeProfileHoldingPriority
      Unsigned32,
   mscDcmeProfileBumpPreference
      INTEGER,
   mscDcmeProfileRequiredTrafficType
      INTEGER,
   mscDcmeProfilePermittedTrunkTypes
      OCTET STRING,
   mscDcmeProfileRequiredSecurity
      Unsigned32,
   mscDcmeProfileRequiredCustomerParm
      Unsigned32,
   mscDcmeProfilePathAttributeToMinimize
      INTEGER,
   mscDcmeProfileMaximumAcceptableCost
      Unsigned32,
   mscDcmeProfileMaximumAcceptableDelay
      Unsigned32,
   mscDcmeProfileEmissionPriority
      Unsigned32,
   mscDcmeProfileDiscardPriority
      Unsigned32,
   mscDcmeProfilePathFailureAction
      INTEGER,
   mscDcmeProfileOptimization
      INTEGER }

mscDcmeProfileSetupPriority OBJECT-TYPE
   SYNTAX     Unsigned32 (0..4)
   ACCESS     read-write
   STATUS     mandatory
   DESCRIPTION
     "This attribute specifies the priority at which a path is established. 
      Zero is the highest priority and four is the lowest. When PORS 
      establishes a path through the network, it uses the setupPriority 
      attribute to determine its potential for bumping established paths to 
      acquire their bandwidth. The holdingPriority, a complementary 
      attribute of this attribute, indicates the priority a path maintains 
      once it is established. A new path can bump an existing path if the 
      new path's setupPriority is higher (numerically less) than the 
      existing path's holdingPriority."
   DEFVAL     { 2 }
::= { mscDcmeProfileLCOpsEntry 1 }

mscDcmeProfileHoldingPriority OBJECT-TYPE
   SYNTAX     Unsigned32 (0..4)
   ACCESS     read-write
   STATUS     mandatory
   DESCRIPTION
     "This attribute specifies the priority that a path holds once it is 
      established. Zero is the highest priority and four is the lowest. A 
      path's holdingPriority determines its likelihood of being bumped by 
      a new path to acquire its bandwidth. The setupPriority, a 
      complementary attribute, indicates the priority of a path at 
      establishment time. A new path can bump an existing path if the 
      new path's setupPriority is higher (numerically less) than the 
      existing path's holdingPriority."
   DEFVAL     { 2 }
::= { mscDcmeProfileLCOpsEntry 2 }

mscDcmeProfileBumpPreference OBJECT-TYPE
   SYNTAX     INTEGER  {
                 bumpWhenNecessary(0),
                 bumpToObtainBestRoute(1) }
   ACCESS     read-write
   STATUS     mandatory
   DESCRIPTION
     "This attribute specifies when bumping occurs in the route selection 
      process. A connection with higher (numerically less) setupPriority 
      may bump a connection with lower (numerically higher) 
      setupPriority in order to acquire its bandwidth and be established. If 
      bumpPreference is bumpWhenNecessary, bumping occurs only 
      when it is necessary. That is, a connection will bump another 
      connection only if there is no other way for the connection to be 
      established. If bumpPreference is bumpToObtainBestRoute, 
      bumping occurs in order to use the best available route it may have."
   DEFVAL     { bumpWhenNecessary }
::= { mscDcmeProfileLCOpsEntry 3 }

mscDcmeProfileRequiredTrafficType OBJECT-TYPE
   SYNTAX     INTEGER  {
                 voice(0),
                 data(1),
                 video(2),
                 trafficType1(3),
                 trafficType2(4),
                 trafficType3(5),
                 trafficType4(6),
                 trafficType5(7) }
   ACCESS     read-write
   STATUS     mandatory
   DESCRIPTION
     "This attribute specifies the type of traffic transmitted over the path. 
      There are eight possible traffic types, and the path can transmit only 
      one of them. The originating end of the connection determines the 
      type. The voice, data and video traffic types are defined, and five 
      other arbitrary traffic types can be defined by the network 
      administration. This attribute is used in the route selection process 
      to restrict the route to trunks that support this traffic type. The 
      supportedTrafficType trunk attribute lists all the types of traffic 
      allowed on the trunk. For example, if requiredTrafficType is 
      specified as trafficType1, then only trunks that include trafficType1 
      in supportedTrafficType will be candidates for this connection."
   DEFVAL     { voice }
::= { mscDcmeProfileLCOpsEntry 4 }

mscDcmeProfilePermittedTrunkTypes OBJECT-TYPE
   SYNTAX     OCTET STRING (SIZE (1))
   ACCESS     read-write
   STATUS     mandatory
   DESCRIPTION
     "This attribute specifies up to eight types of trunks that can be used 
      on the route. The terrestrial and satellite trunk types are defined, 
      leaving six remaining arbitrary types that can be defined by the 
      network administration. The trunk's type is indicated in the 
      trunkType attribute of the Trunk component. When selecting a 
      route, PORS chooses only trunks whose trunkTypes are in the 
      permittedTrunkTypes for the path.

      Description of bits:
      terrestrial(0)
      satellite(1)
      trunkType1(2)
      trunkType2(3)
      trunkType3(4)
      trunkType4(5)
      trunkType5(6)
      trunkType6(7)"
   DEFVAL     { 'f8'H }
::= { mscDcmeProfileLCOpsEntry 5 }

mscDcmeProfileRequiredSecurity OBJECT-TYPE
   SYNTAX     Unsigned32 (0..7)
   ACCESS     read-write
   STATUS     mandatory
   DESCRIPTION
     "This attribute specifies the required minimum level of security of 
      the trunks on the route. Zero represents the most secure and seven 
      represents the least secure. The trunk's security is indicated by the 
      trunkSecurity attribute of the Trunk component, and has values 
      identical in range and meaning to the requiredSecurity attribute. 
      PORS ensures that any route selected does not contain a trunk 
      whose trunkSecurity attribute is numerically greater than the 
      requiredSecurity."
   DEFVAL     { 4 }
::= { mscDcmeProfileLCOpsEntry 6 }

mscDcmeProfileRequiredCustomerParm OBJECT-TYPE
   SYNTAX     Unsigned32 (0..7)
   ACCESS     read-write
   STATUS     mandatory
   DESCRIPTION
     "This attribute specifies the allowed customer defined parameter of 
      the trunks on the route. The value of requiredCustomerParm ranges 
      from 0 to 7. The meaning of each value is specific to a particular 
      network, thus allowing them to customize the use of their trunks. A 
      complementary trunk attribute, customerParameter, also has a value 
      from zero to seven. The route selection process does not consider 
      trunks whose customerParameter is greater than the 
      requiredCustomerParameter of the path."
   DEFVAL     { 4 }
::= { mscDcmeProfileLCOpsEntry 7 }

mscDcmeProfilePathAttributeToMinimize OBJECT-TYPE
   SYNTAX     INTEGER  {
                 cost(0),
                 delay(1) }
   ACCESS     read-write
   STATUS     mandatory
   DESCRIPTION
     "This attribute specifies whether a route is selected on the basis of 
      minimizing the cost or the delay. Each trunk has a cost and a delay 
      metric associated with it. The cost of a selected route is the sum of 
      the trunk cost metrics for all trunks included in the route. The delay 
      of a selected route is the sum of the trunk delay metrics for all 
      trunks included in the route."
   DEFVAL     { cost }
::= { mscDcmeProfileLCOpsEntry 8 }

mscDcmeProfileMaximumAcceptableCost OBJECT-TYPE
   SYNTAX     Unsigned32 (0..65535)
   ACCESS     read-write
   STATUS     mandatory
   DESCRIPTION
     "This attribute specifies an upper bound on the cost metric of a route, 
      which is the sum of the cost metrics of all trunks on the route. The 
      cost metric is the trunkCost attribute of the Trunk component. If for 
      any trunk the trunkCost is larger than the maximumAcceptableCost, 
      then that trunk is not considered during the route selection. While a 
      shortest route is being selected, the route cost is being compared 
      with the maximumAcceptableCost attribute, and this is done for any 
      minimization criterion. No route is selected if the cost metric of the 
      shortest route is larger than the maximumAcceptableCost."
   DEFVAL     { 1280 }
::= { mscDcmeProfileLCOpsEntry 9 }

mscDcmeProfileMaximumAcceptableDelay OBJECT-TYPE
   SYNTAX     Unsigned32 (0..100000)
   ACCESS     read-write
   STATUS     mandatory
   DESCRIPTION
     "This attribute specifies an upper bound on the delay of a route, 
      which is the sum of the delays of all trunks on the route. It should 
      be provisioned with a reasonable maximum acceptable delay for the 
      end to end one way delay of a 512-byte packet. During its staging, a 
      trunk measures a measuredRoundTripDelay. This delay is divided 
      by two and truncated to an integer number of milliseconds to 
      provide a one way delay which is used to populate the delay in this 
      trunk object in the topological database. The value includes 
      emission, propagation, and queuing delays. A 512-byte packet is 
      used to perform the measurement. 
      If for any trunk the half of the trunk's measuredRoundTripDelay is 
      larger than the maximumAcceptableDelay, then that trunk is not 
      considered during the route selection.
      While a shortest route is being selected, the route delay is being 
      compared with the maximumAcceptableDelay attribute, and this is 
      done for any minimization criterion. No route is selected if the 
      delay metric of the shortest route is larger than the 
      maximumAcceptableDelay."
   DEFVAL     { 100000 }
::= { mscDcmeProfileLCOpsEntry 10 }

mscDcmeProfileEmissionPriority OBJECT-TYPE
   SYNTAX     Unsigned32 (0..2)
   ACCESS     read-write
   STATUS     mandatory
   DESCRIPTION
     "This attribute specifies the urgency with which packets on the path 
      are emitted by the trunks on the route. An emissionPriority of 0 
      indicates the highest emission priority, while 2 indicates the lowest 
      emission priority. Packets with a higher emissionPriority (or 
      numerically less) are serviced and sent out before the packets with a 
      lower emissionPriority (or numerically higher)."
   DEFVAL     { 0 }
::= { mscDcmeProfileLCOpsEntry 11 }

mscDcmeProfileDiscardPriority OBJECT-TYPE
   SYNTAX     Unsigned32 (1..3)
   ACCESS     read-write
   STATUS     mandatory
   DESCRIPTION
     "This attribute specifies the importance of the packets on the path. A 
      discardPriority of 1 is used for paths carrying the most important 
      traffic, and three is used for paths carrying the least important 
      traffic. Packets with lower discardPriority(numerically lower) are 
      discarded after packets with a higher discardPriority(numerically 
      higher)."
   DEFVAL     { 1 }
::= { mscDcmeProfileLCOpsEntry 12 }

mscDcmeProfilePathFailureAction OBJECT-TYPE
   SYNTAX     INTEGER  {
                 disconnectConnection(0),
                 reRoutePath(1) }
   ACCESS     read-write
   STATUS     mandatory
   DESCRIPTION
     "This attribute specifies whether the application can tolerate 
      momentary interruption of a path while a new path is selected. If 
      pathFailureAction is disconnectConnection, the application is 
      informed as soon as possible about a failure by disconnection. If 
      pathFailureAction is reRoutePath, the path may attempt an 
      immediate reroute, provided the failure is a recoverable failure. If 
      rerouting fails, the application is informed of the failure. 
      If pathFailureAction is reRoutePath, the LCo may wait up to 30 
      seconds before informing the service of complete disconnection in 
      order to allow both ends to attempt to reconnect. Note that if PLC 
      components are different at both ends only the calling end is 
      allowed to reconnect.
      All pathTypes respect this attribute. Also on a manualPath with 
      both ends provisioned with independent paths (at least with respect 
      to the failure) this option has the desired effect that the path is 
      rerouted without complete disconnection at both ends."
   DEFVAL     { reRoutePath }
::= { mscDcmeProfileLCOpsEntry 13 }

mscDcmeProfileOptimization OBJECT-TYPE
   SYNTAX     INTEGER  {
                 disabled(0),
                 enabled(1) }
   ACCESS     read-write
   STATUS     mandatory
   DESCRIPTION
     "This attribute specifies whether this connection should attempt to 
      optimize its path when requested by the Rtg Pors component. Every 
      path is optimal when it is established, but as network traffic patterns 
      and configurations change this path may no longer be optimal. The 
      PORS connection manager on a module requests circuits to 
      optimize at the optimizationInterval."
   DEFVAL     { enabled }
::= { mscDcmeProfileLCOpsEntry 14 }

mscDcmeProfileFrOpsTable OBJECT-TYPE
   SYNTAX     SEQUENCE OF MscDcmeProfileFrOpsEntry
   ACCESS     not-accessible
   STATUS     mandatory
   DESCRIPTION
     "This group contains attributes which define how audio data will be 
      carried across the Passport network."
::= { mscDcmeProfile 11 }

mscDcmeProfileFrOpsEntry OBJECT-TYPE
   SYNTAX     MscDcmeProfileFrOpsEntry
   ACCESS     not-accessible
   STATUS     mandatory
   DESCRIPTION
     "An entry in the mscDcmeProfileFrOpsTable."
   INDEX {
      mscDcmeIndex,
      mscDcmeProfileIndex }
::= { mscDcmeProfileFrOpsTable 1 }

MscDcmeProfileFrOpsEntry ::= SEQUENCE {
   mscDcmeProfileVoiceEncoding
      INTEGER,
   mscDcmeProfileMaxVoiceBitRate
      INTEGER,
   mscDcmeProfileMinVoiceBitRate
      INTEGER,
   mscDcmeProfileVoiceTrafficOptimization
      INTEGER,
   mscDcmeProfileSilenceSuppression
      INTEGER,
   mscDcmeProfileSilenceSuppressionFactor
      Unsigned32,
   mscDcmeProfileEchoCancellation
      INTEGER,
   mscDcmeProfileModemFaxEncoding
      INTEGER,
   mscDcmeProfileMaxModemFaxG711G726Rate
      INTEGER,
   mscDcmeProfileMinModemFaxG711G726Rate
      INTEGER,
   mscDcmeProfileFaxIdleSuppressionG711G726
      INTEGER,
   mscDcmeProfileInsertedOutputDelay
      INTEGER,
   mscDcmeProfileIngressAudioGain
      INTEGER,
   mscDcmeProfileEgressAudioGain
      INTEGER,
   mscDcmeProfileSpeechHangoverTime
      Unsigned32,
   mscDcmeProfileComfortNoiseCap
      INTEGER,
   mscDcmeProfileModemFaxSpeechDiscrim
      INTEGER,
   mscDcmeProfileV17EncodedAsG711G726
      INTEGER,
   mscDcmeProfileDtmfRegeneration
      INTEGER,
   mscDcmeProfileMaxFaxRelayRate
      FixedPoint1 }

mscDcmeProfileVoiceEncoding OBJECT-TYPE
   SYNTAX     INTEGER  {
                 g711G726(0),
                 g728at16(1),
                 g729at8(2) }
   ACCESS     read-write
   STATUS     mandatory
   DESCRIPTION
     "This attribute specifies the encoding of voice traffic.
      
      A voiceEncoding setting of g711G726 specifies that either pulse 
      code modulation (PCM) defined by ITU-T G.711 or adaptive 
      differential pulse code modulation (ADPCM) defined by ITU-T 
      G.726 is used to encode voice traffic. The actual encoding 
      performed depends on congestion in the network and the settings of 
      minVoiceG711G726Rate and maxVoiceG711G726Rate. If 
      voiceEncoding is g711G726, the bit rate of voice traffic can change 
      during a call due to congestion in the network. In this case, the 
      minimum and maximum rates that can occur during a call are 
      specified by minVoiceG711G726Rate and maxVoiceG711G726Rate 
      respectively. If voiceEncoding is g711G726, 
      minVoiceG711G726Rate is 64 and maxVoiceG711G726Rate is 64, 
      G.711 (PCM) encoding is always performed on voice traffic on this 
      channel and all voice traffic is carried uncompressed at 64 kbit/s.
      
      A voiceEncoding setting of g728at16 specifies that the Low Delay 
      Coded Excited Linear Predictive Coder (LD-CELP) algorithm 
      defined by ITU-T G.728 is always performed on voice traffic. If 
      voiceEncoding is g728at16, the bit rate of all voice traffic is fixed at 
      16 kbit/s. The minVoiceG711G726Rate and 
      maxVoiceG711G726Rate attributes do not apply if voiceEncoding is 
      g728at16.
      
      A voiceEncoding setting of g729at8 indicates that the Conjugated 
      Structure Algebraic Code Excited Linear Predictive Coder (CS-
      ACELP) algorithm defined by ITU-T G.729 is always performed on 
      voice traffic. If voiceEncoding is g729at8, the bit rate of all voice 
      traffic is fixed at 8 kbit/s. The minVoiceG711G726Rate and 
      maxVoiceG711G726Rate attributes do not apply if voiceEncoding is 
      g729at8."
   DEFVAL     { g728at16 }
::= { mscDcmeProfileFrOpsEntry 1 }

mscDcmeProfileMaxVoiceBitRate OBJECT-TYPE
   SYNTAX     INTEGER  {
                 n64(0),
                 n32(1),
                 n24(2) }
   ACCESS     read-write
   STATUS     mandatory
   DESCRIPTION
     "This attribute specifies the maximum possible bit rate (minimum 
      possible compression rate) during a voice call on this channel when 
      voiceEncoding is g711G726. It applies only to voice traffic, not 
      modem or fax traffic. It also applies only if voiceEncoding is 
      g711G726.
      
      If voiceEncoding is g711G726, the bit rate of voice traffic can 
      change during a call due to congestion in the network. In this case, 
      the minimum and maximum rates that can occur during a call are 
      specified by minVoiceG711G726Rate and maxVoiceG711G726Rate 
      respectively. If voiceEncoding is g711G726, 
      minVoiceG711G726Rate is 64 and maxVoiceG711G726Rate is 64, 
      the G.711 (PCM) algorithm is always performed on voice traffic on 
      this channel and all voice traffic is carried uncompressed at 64 
      kbit/s."
   DEFVAL     { n64 }
::= { mscDcmeProfileFrOpsEntry 2 }

mscDcmeProfileMinVoiceBitRate OBJECT-TYPE
   SYNTAX     INTEGER  {
                 n64(0),
                 n32(1),
                 n24(2) }
   ACCESS     read-write
   STATUS     mandatory
   DESCRIPTION
     "This attribute specifies the minimum possible bit rate (maximum 
      possible compression rate) during a voice call on this channel when 
      voiceEncoding is g711G726. It applies only to voice traffic, not 
      modem or fax traffic. It also applies only if voiceEncoding is 
      g711G726.
      
      If voiceEncoding is g711G726, the bit rate of voice traffic can 
      change during a call due to congestion in the network. In this case, 
      the minimum and maximum rates that can occur during a call are 
      specified by minVoiceG711G726Rate and maxVoiceG711G726Rate 
      respectively. If voiceEncoding is g711G726, 
      minVoiceG711G726Rate is 64 and maxVoiceG711G726Rate is 64, 
      the G.711 (PCM) algorithm is always performed on voice traffic on 
      this channel and all voice traffic is carried uncompressed at 64 
      kbit/s."
   DEFVAL     { n64 }
::= { mscDcmeProfileFrOpsEntry 3 }

mscDcmeProfileVoiceTrafficOptimization OBJECT-TYPE
   SYNTAX     INTEGER  {
                 bandwidth(0),
                 delay(1) }
   ACCESS     read-write
   STATUS     mandatory
   DESCRIPTION
     "This attribute specifies how to optimize voice traffic. If 
      voiceTrafficOptimization is bandwidth, voice traffic is optimized to 
      preserve bandwidth. If voiceTrafficOptimization is delay, voice 
      traffic is optimized to minimize delay."
   DEFVAL     { bandwidth }
::= { mscDcmeProfileFrOpsEntry 4 }

mscDcmeProfileSilenceSuppression OBJECT-TYPE
   SYNTAX     INTEGER  {
                 off(0),
                 on(1),
                 congested(2),
                 slow(3),
                 slowAndCongested(4) }
   ACCESS     read-write
   STATUS     mandatory
   DESCRIPTION
     "This attribute specifies when silence suppression is performed. It 
      applies to both voice and modem calls.
      If silenceSuppression is off, silence suppression is never performed.
      If silenceSuppression is on, silence suppression is always 
      performed. 
      If silenceSuppression is congested, silence suppression is 
      performed only when the network is congested.
      If silenceSuppression is slow, silence suppression begins after 10 to 
      20 seconds without any detected speech or modem traffic.
      If silenceSuppression is slowAndCongested, both the slow and 
      congested options are applied."
   DEFVAL     { on }
::= { mscDcmeProfileFrOpsEntry 5 }

mscDcmeProfileSilenceSuppressionFactor OBJECT-TYPE
   SYNTAX     Unsigned32 (0..60)
   ACCESS     read-write
   STATUS     mandatory
   DESCRIPTION
     "This attribute specifies the expected savings (percent reduction) in 
      required bandwidth if silence suppression is used. If silence 
      suppression is used, the bandwidth required for the connection will 
      be lower than if silence suppression is not used. However, the 
      routing system will not be aware of the unused bandwidth unless 
      that bandwidth is specified by this attribute. 
      If the value specified for the expected savings is too low, then some 
      bandwidth made available by the use of silence suppression will be 
      wasted. If the value specified for the expected savings is too high, 
      then some connections may fail to set up because the routing system 
      will over-calculate the amount of bandwidth available.
      The effectiveness of silence suppression can be influenced by 
      language related speech patterns."
   DEFVAL     { 40 }
::= { mscDcmeProfileFrOpsEntry 6 }

mscDcmeProfileEchoCancellation OBJECT-TYPE
   SYNTAX     INTEGER  {
                 off(0),
                 on(1) }
   ACCESS     read-write
   STATUS     mandatory
   DESCRIPTION
     "This attribute specifies whether echo cancellation is performed on 
      calls using this profile as specified by ITU-T G.165. It applies 
      mainly to voice traffic. Echo cancellation is usually (but not always) 
      disabled during modem and fax calls. If echoCancellation is on, the 
      traffic that is echo cancelled is determined by ITU-T G.165."
   DEFVAL     { off }
::= { mscDcmeProfileFrOpsEntry 7 }

mscDcmeProfileModemFaxEncoding OBJECT-TYPE
   SYNTAX     INTEGER  {
                 g711G726(0),
                 faxRelayOnly(1),
                 faxRelayG711G726(2),
                 useVoiceEncoding(3) }
   ACCESS     read-write
   STATUS     mandatory
   DESCRIPTION
     "This attribute specifies how modem and fax traffic is encoded. 
      Modem and fax traffic are identified by an inband 2100 Hz tone. 
      Prior to the detection of a 2100 Hz tone, all traffic is handled 
      according to voiceEncoding.
      
      If modemFaxEncoding is useVoiceEncoding, 2100 Hz tones are not 
      detected on the channel. In this case, the channel does not 
      differentiate between modem and fax traffic and voice traffic. All 
      traffic is handled according to voiceEncoding. If voiceEncoding is 
      g728at16 or g729at8, modem and fax calls will not work.
      
      If a 2100 Hz tone is detected and modemFaxEncoding is g711G726, 
      all subsequent traffic during a call is encoded using pulse code 
      modulation (PCM) defined by ITU-T G.711 or adaptive differential 
      pulse code modulation (ADPCM) defined by ITU-T G.726. When 
      the 2100 Hz tone is detected, traffic is initially encoded at the rate 
      specified by maxModemFaxG711G726Rate. For the duration of the 
      call, the bit rate can change due to network congestion. In this case, 
      the minimum and maximum rates that can occur during the call are 
      specified by minModemFaxG711G726Rate and 
      maxModemFaxG711G726Rate respectively.
      
      If a 2100 Hz tone is detected and modemFaxEncoding is 
      faxRelayG711G726, encoding switches to G.711 or G.726 at the 
      rate specified in maxModemFaxG711G726Rate, exactly as it does if 
      modemFaxEncoding is g711G726. Until a fax preamble is detected, 
      the rate may fluctuate between maxModemFaxG711G726Rate and 
      minModemFaxG711G726Rate due to network congestion, exactly 
      as it does if modemFaxEncoding is g711G726. If a fax preamble is 
      detected, all subsequent traffic during a call is demodulated and sent 
      through the network as cells at the base rate of the sending machine. 
      Supported demodulation methods are V.29 (up to 9.6 kbit/s) and 
      V.27 (up to 4.8 kbit/s). The modulation and demodulation of fax 
      traffic is called 'fax relay'.
      
      If a 2100 Hz tone is detected and modemFaxEncoding is 
      faxRelayOnly, this channel does not wait for a fax preamble to 
      switch to 'fax relay'. Instead, 'fax relay' is entered immediately. If 
      modemFaxEncoding is faxRelayOnly, modem calls do not work on 
      this Dcme. Therefore, this setting is only appropriate if modem calls 
      are not made on the channel.
      
      The faxRelay feature is required to set modemFaxEncoding to 
      faxRelayG711G726 or faxRelayOnly.
      
      modemFaxEncoding must have the same value at both ends of a 
      Dcme. If modemFaxEncoding is not provisioned with the same 
      values at both ends of a Dcme, the Dcme will not be able to carry 
      the modem and fax traffic successfully."
   DEFVAL     { faxRelayOnly }
::= { mscDcmeProfileFrOpsEntry 9 }

mscDcmeProfileMaxModemFaxG711G726Rate OBJECT-TYPE
   SYNTAX     INTEGER  {
                 n64(0),
                 n32(1) }
   ACCESS     read-write
   STATUS     mandatory
   DESCRIPTION
     "This attribute specifies the maximum possible bit rate (minimum 
      possible compression rate) during a modem call on this channel. It 
      also specifies the maximum possible bit rate (minimum possible 
      compression rate) during a fax call on this channel, but only if 
      faxEncoding is g711G726. maxModemFaxG711G726Rate always 
      applies to modem traffic, and never applies to voice traffic. If 
      faxEncoding is g711G726, maxModemFaxG711G726Rate also 
      applies to fax traffic. If faxEncoding is faxRelay, 
      maxModemFaxG711G726Rate does not apply to fax traffic.
      Rates can change during a call due to congestion in the network."
   DEFVAL     { n64 }
::= { mscDcmeProfileFrOpsEntry 10 }

mscDcmeProfileMinModemFaxG711G726Rate OBJECT-TYPE
   SYNTAX     INTEGER  {
                 n64(0),
                 n32(1) }
   ACCESS     read-write
   STATUS     mandatory
   DESCRIPTION
     "This attribute specifies the minimum possible bit rate (maximum 
      possible compression rate) during a modem call on this channel. It 
      also specifies the minimum possible bit rate (maximum possible 
      compression rate) during a fax call on this channel, but only if 
      faxEncoding is g711G726. minModemFaxG711G726Rate always 
      applies to modem traffic, and never applies to voice traffic. If 
      faxEncoding is g711G726, minModemFaxG711G726Rate also 
      applies to fax traffic. If faxEncoding is faxRelay, 
      minModemFaxG711G726Rate does not apply to fax traffic. 
      Rates can change during a call due to congestion in the network."
   DEFVAL     { n64 }
::= { mscDcmeProfileFrOpsEntry 11 }

mscDcmeProfileFaxIdleSuppressionG711G726 OBJECT-TYPE
   SYNTAX     INTEGER  {
                 off(0),
                 on(1) }
   ACCESS     read-write
   STATUS     mandatory
   DESCRIPTION
     "This attribute specifies whether fax idle suppression is performed on 
      fax traffic on calls using this profile. It only applies to fax traffic, not 
      voice or modem traffic. It also only applies if fax traffic is carried 
      using G.711 or G.726."
   DEFVAL     { off }
::= { mscDcmeProfileFrOpsEntry 12 }

mscDcmeProfileInsertedOutputDelay OBJECT-TYPE
   SYNTAX     INTEGER  {
                 n5(5),
                 n15(15),
                 n22(22),
                 n30(30),
                 n35(35),
                 n40(40),
                 n45(45),
                 n50(50),
                 n75(75),
                 n100(100),
                 n125(125),
                 n150(150) }
   ACCESS     read-write
   STATUS     mandatory
   DESCRIPTION
     "This attribute specifies the amount of added output delay used to 
      compensate for cross network delay variations. It applies to voice, 
      modem and fax traffic. It is required to add output delay so that the 
      statistical variation in the transit time of cells crossing the network 
      does not cause gaps in speech. Backbone networks where high 
      priority traffic consumes a high percentage of trunk bandwidth will 
      require a higher insertedOutputDelay to compensate for the greater 
      cell delay variation (CDV)."
   DEFVAL     { n22 }
::= { mscDcmeProfileFrOpsEntry 13 }

mscDcmeProfileIngressAudioGain OBJECT-TYPE
   SYNTAX     INTEGER (-12..12)
   ACCESS     read-write
   STATUS     mandatory
   DESCRIPTION
     "This attribute specifies the gain in dB that is applied to data coming 
      from outside the network before it is transferred across the network. 
      It applies to voice, modem and fax traffic. For example, ingress gain 
      is applied to audio data coming from a PBX. If ingressAudioGain is 
      negative, a loss is applied.
      
      ingressAudioGain and egressAudioGain are used in loss planning, 
      which is the configuration of the devices in a network to ensure that 
      the signal level from any point in the network to any other point is 
      correct."
   DEFVAL     { 0 }
::= { mscDcmeProfileFrOpsEntry 14 }

mscDcmeProfileEgressAudioGain OBJECT-TYPE
   SYNTAX     INTEGER (-12..12)
   ACCESS     read-write
   STATUS     mandatory
   DESCRIPTION
     "This attribute specifies the gain in dB that is applied to data leaving 
      the network on this route. It applies to voice, modem and fax traffic. 
      For example, egress gain is applied to audio data going to a PBX. If 
      egressAudioGain is negative, a loss is applied.
      
      ingressAudioGain and egressAudioGain are used in loss planning, 
      which is the configuration of the devices in the network to ensure 
      that the signal level from any point in the network to any other point 
      is correct."
   DEFVAL     { 0 }
::= { mscDcmeProfileFrOpsEntry 15 }

mscDcmeProfileSpeechHangoverTime OBJECT-TYPE
   SYNTAX     Unsigned32 (10..500)
   ACCESS     read-write
   STATUS     mandatory
   DESCRIPTION
     "This attribute specifies the time after the end of speech before 
      silence suppression starts. It applies only to voice traffic.
      
      Higher values of speechHangoverTime reduce undesirable clipping 
      but increase bandwidth usage."
   DEFVAL     { 150 }
::= { mscDcmeProfileFrOpsEntry 16 }

mscDcmeProfileComfortNoiseCap OBJECT-TYPE
   SYNTAX     INTEGER (-78 | -65 | -60 | -54 | -52 | -50 | -48 | -46 | -44 | -42 | -40)
   ACCESS     read-write
   STATUS     mandatory
   DESCRIPTION
     "This attribute specifies the maximum level at which comfort noise is 
      generated. The comfort noise is limited by comfortNoiseCap before 
      egressAudioGain is applied. The default value of -40 dBm0 equates 
      to the maximum level of comfort noise available and effectively 
      disables the comfortNoiseCap."
   DEFVAL     { -40 }
::= { mscDcmeProfileFrOpsEntry 17 }

mscDcmeProfileModemFaxSpeechDiscrim OBJECT-TYPE
   SYNTAX     INTEGER  {
                 off(0),
                 on(1) }
   ACCESS     read-write
   STATUS     mandatory
   DESCRIPTION
     "This attribute specifies whether this Dcme differentiates between 
      modemFax traffic and speech. If modemFaxSpeechDiscrim is on 
      and a false 2100 Hz tone is detected, any Vs under this Dcme reverts 
      to speech mode when speech is detected."
   DEFVAL     { on }
::= { mscDcmeProfileFrOpsEntry 18 }

mscDcmeProfileV17EncodedAsG711G726 OBJECT-TYPE
   SYNTAX     INTEGER  {
                 no(0),
                 yes(1) }
   ACCESS     read-write
   STATUS     mandatory
   DESCRIPTION
     "This attribute specifies how services using this Profile negotiate 
      with V.17 fax machines. This attribute is not used unless the 
      modemFaxEncoding, defined in this Profile, is faxRelayG711G726 
      
      If v17EncodedAsG711G726 is no, V.17 fax machines are instructed 
      to use V.29 and V.29 fax traffic sent by fax machines is demodulated 
      and encoded using fax relay.
      
      If v17EncodedAsG711G726 is yes, V.17 fax machines are permitted 
      to use V.17 and V.17 fax traffic sent by fax machines is encoded 
      using G.711 or G.726. The actual encoding performed depends on 
      the minModemFaxG711G726Rate and 
      maxModemFaxG711G726Rate, available in this Profile."
   DEFVAL     { no }
::= { mscDcmeProfileFrOpsEntry 19 }

mscDcmeProfileDtmfRegeneration OBJECT-TYPE
   SYNTAX     INTEGER  {
                 off(0),
                 on(1) }
   ACCESS     read-write
   STATUS     mandatory
   DESCRIPTION
     "This attribute specifies the DTMF regeneration parameter used 
      during negotiation with the remote end across the subnet. 
      
      If dtmfRegeneration is on, it is desired that DTMF tones received 
      from the link are first converted to digits before being sent to the 
      subnet. When a digit is received from the subnet, its respective 
      DTMF tone is desired to be generated before being sent to the link.
      
      If dtmfRegeneration is off, it is desired that DTMF tones are 
      transported transparently as audio."
   DEFVAL     { off }
::= { mscDcmeProfileFrOpsEntry 20 }

mscDcmeProfileMaxFaxRelayRate OBJECT-TYPE
   SYNTAX     FixedPoint1 (24 | 48 | 72 | 96 | 120 | 144)
   ACCESS     read-write
   STATUS     mandatory
   DESCRIPTION
     "This attribute specifies the maximum desired fax relay rate. This 
      attribute only applies if modemFaxEncoding is faxRelayOnly or 
      faxRelayG711G726."
   DEFVAL     { 144 }
::= { mscDcmeProfileFrOpsEntry 21 }


-- DcmeLink/n		
-- This component defines the characteristics of a connection to an 
-- International Switching Centre (ISC). A DcmeLink is a collection of 
-- 64 kbit/s channels on the same physical E1 interface. There is one 
-- DcmeLink per physical link. 

mscDcl OBJECT IDENTIFIER ::= { mscComponents 130 }



mscDclRowStatusTable OBJECT-TYPE
   SYNTAX     SEQUENCE OF MscDclRowStatusEntry
   ACCESS     not-accessible
   STATUS     mandatory
   DESCRIPTION
     "This entry controls the addition and deletion of 
      mscDcl components."
::= { mscDcl 1 }

mscDclRowStatusEntry OBJECT-TYPE
   SYNTAX     MscDclRowStatusEntry
   ACCESS     not-accessible
   STATUS     mandatory
   DESCRIPTION
     "A single entry in the table represents a single 
      mscDcl component."
   INDEX {
      mscDclIndex }
::= { mscDclRowStatusTable 1 }

MscDclRowStatusEntry ::= SEQUENCE {
   mscDclRowStatus
      RowStatus,
   mscDclComponentName
      DisplayString,
   mscDclStorageType
      StorageType,
   mscDclIndex
      Integer32 }

mscDclRowStatus OBJECT-TYPE
   SYNTAX     RowStatus 
   ACCESS     read-write
   STATUS     mandatory
   DESCRIPTION
     "This variable is used as the basis for SNMP naming of
      mscDcl components.
      These components can be added and deleted."
::= { mscDclRowStatusEntry 1 }

mscDclComponentName OBJECT-TYPE
   SYNTAX     DisplayString 
   ACCESS     read-only
   STATUS     mandatory
   DESCRIPTION
     "This variable provides the component's string name for
      use with the ASCII Console Interface"
::= { mscDclRowStatusEntry 2 }

mscDclStorageType OBJECT-TYPE
   SYNTAX     StorageType 
   ACCESS     read-only
   STATUS     mandatory
   DESCRIPTION
     "This variable represents the storage type value for the
      mscDcl tables."
::= { mscDclRowStatusEntry 4 }

mscDclIndex OBJECT-TYPE
   SYNTAX     Integer32 (1..14)
   ACCESS     not-accessible
   STATUS     mandatory
   DESCRIPTION
     "This variable represents the index for the mscDcl tables."
::= { mscDclRowStatusEntry 10 }

mscDclProvTable OBJECT-TYPE
   SYNTAX     SEQUENCE OF MscDclProvEntry
   ACCESS     not-accessible
   STATUS     mandatory
   DESCRIPTION
     "This group contains the provisionable attributes of a DcmeLink."
::= { mscDcl 10 }

mscDclProvEntry OBJECT-TYPE
   SYNTAX     MscDclProvEntry
   ACCESS     not-accessible
   STATUS     mandatory
   DESCRIPTION
     "An entry in the mscDclProvTable."
   INDEX {
      mscDclIndex }
::= { mscDclProvTable 1 }

MscDclProvEntry ::= SEQUENCE {
   mscDclCommentText
      AsciiString,
   mscDclRemoteNpi
      INTEGER,
   mscDclRemoteDna
      DigitString,
   mscDclDcme
      Link,
   mscDclIdlePattern
      Hex,
   mscDclAlternateIdlePattern
      Hex }

mscDclCommentText OBJECT-TYPE
   SYNTAX     AsciiString (SIZE (0..40))
   ACCESS     read-write
   STATUS     mandatory
   DESCRIPTION
     "Use of this attribute is at the discretion of the system administrator. 
      Typically, it specifies the name of the customer that is using this 
      DcmeLink."
   DEFVAL     { ''H }  -- ""
::= { mscDclProvEntry 1 }

mscDclRemoteNpi OBJECT-TYPE
   SYNTAX     INTEGER  {
                 x121(0),
                 e164(1) }
   ACCESS     read-write
   STATUS     mandatory
   DESCRIPTION
     "This attribute specifies the Numbering Plan Indicator used for the 
      remoteDna attribute of this DcmeLink."
   DEFVAL     { e164 }
::= { mscDclProvEntry 2 }

mscDclRemoteDna OBJECT-TYPE
   SYNTAX     DigitString (SIZE (1..15))
   ACCESS     read-write
   STATUS     mandatory
   DESCRIPTION
     "This attribute specifies the Data Network Address (DNA) of the 
      remote DcmeLink. This is the DNA of the peer DcmeLink to which 
      the DcmeLink component establishes its Logical Connection (LC)."
::= { mscDclProvEntry 3 }

mscDclDcme OBJECT-TYPE
   SYNTAX     Link 
   ACCESS     read-write
   STATUS     mandatory
   DESCRIPTION
     "This attribute specifies the Dcme component that this DcmeLink 
      belongs to."
::= { mscDclProvEntry 4 }

mscDclIdlePattern OBJECT-TYPE
   SYNTAX     Hex (0..255)
   ACCESS     read-write
   STATUS     mandatory
   DESCRIPTION
     "This attribute specifies an idlePattern in the channel received from 
      the E1 interface, which is required to determine if the channel is 
      active or not. 
      When the end of the idlePattern is detected it indicates the start of a 
      new speech call.
      When this idlePattern is detected it indicates the end of a speech 
      call.
      When changing this attribute make sure that the 
      alternateIdlePattern attibute is set correctly."
   DEFVAL     { 213 }
::= { mscDclProvEntry 5 }

mscDclAlternateIdlePattern OBJECT-TYPE
   SYNTAX     Hex (0..255)
   ACCESS     read-write
   STATUS     mandatory
   DESCRIPTION
     "This attribute specifies an alternateIdlePattern in the channel 
      received from the E1 interface, after the end of a 64kbit/s call.
      The value of this attribute should be different than the value of the 
      idlePattern attribute only if the ISC is programmed for Even/Odd 
      Bit Inversion (EBI/OBI). This is only the case when the ISC is 
      performing A to Mu or Mu to A Law conversion.
      When the end of the alternateIdlePattern is detected it indicates the 
      start of a new speech call."
   DEFVAL     { 213 }
::= { mscDclProvEntry 6 }

mscDclStateTable OBJECT-TYPE
   SYNTAX     SEQUENCE OF MscDclStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { mscDcl 11 }

mscDclStateEntry OBJECT-TYPE
   SYNTAX     MscDclStateEntry
   ACCESS     not-accessible
   STATUS     mandatory
   DESCRIPTION
     "An entry in the mscDclStateTable."
   INDEX {
      mscDclIndex }
::= { mscDclStateTable 1 }

MscDclStateEntry ::= SEQUENCE {
   mscDclAdminState
      INTEGER,
   mscDclOperationalState
      INTEGER,
   mscDclUsageState
      INTEGER }

mscDclAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { mscDclStateEntry 1 }

mscDclOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { mscDclStateEntry 2 }

mscDclUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { mscDclStateEntry 3 }

mscDclOperTable OBJECT-TYPE
   SYNTAX     SEQUENCE OF MscDclOperEntry
   ACCESS     not-accessible
   STATUS     mandatory
   DESCRIPTION
     "This group provides the operational attributes for the DcmeLink 
      component."
::= { mscDcl 12 }

mscDclOperEntry OBJECT-TYPE
   SYNTAX     MscDclOperEntry
   ACCESS     not-accessible
   STATUS     mandatory
   DESCRIPTION
     "An entry in the mscDclOperTable."
   INDEX {
      mscDclIndex }
::= { mscDclOperTable 1 }

MscDclOperEntry ::= SEQUENCE {
   mscDclActiveSpeechCalls
      Gauge32,
   mscDclActive3kHzCalls
      Gauge32,
   mscDclActive64kCalls
      Gauge32,
   mscDclReceivedTrmSignal
      INTEGER,
   mscDclTransmittedTrmSignal
      INTEGER }

mscDclActiveSpeechCalls OBJECT-TYPE
   SYNTAX     Gauge32 (0..30)
   ACCESS     read-only
   STATUS     mandatory
   DESCRIPTION
     "This attribute indicates the number of speech calls that are currently 
      in progress on this DcmeLink."
   DEFVAL     { 0 }
::= { mscDclOperEntry 1 }

mscDclActive3kHzCalls OBJECT-TYPE
   SYNTAX     Gauge32 (0..30)
   ACCESS     read-only
   STATUS     mandatory
   DESCRIPTION
     "This attribute indicates the number of audio 3.1 kHz calls that are 
      currently in progress on this DcmeLink."
   DEFVAL     { 0 }
::= { mscDclOperEntry 2 }

mscDclActive64kCalls OBJECT-TYPE
   SYNTAX     Gauge32 (0..30)
   ACCESS     read-only
   STATUS     mandatory
   DESCRIPTION
     "This attribute indicates the number of unrestricted 64 kbit/s calls 
      that are currently in progress on this DcmeLink."
   DEFVAL     { 0 }
::= { mscDclOperEntry 3 }

mscDclReceivedTrmSignal OBJECT-TYPE
   SYNTAX     INTEGER  {
                 none000(0),
                 invalid001(1),
                 invalid010(2),
                 invalid011(3),
                 invalid100(4),
                 switchingCentreNormal101(5),
                 maintenanceReleaseAck110(6),
                 dcmeClearOfTraffic111(7) }
   ACCESS     read-only
   STATUS     mandatory
   DESCRIPTION
     "This attribute indicates the last TRM signal received from the ISC.
      The received TRM signal can be one of:
      Invalid (xxx):	 this signal should never be received,
      Switching Centre normal (101): this signal is allways transmitted 
      by the ISC when there is no other signal to be sent,
      Maintenance release ack(110): this signal is transmitted by the ISC 
      if it accepts the maintenance release request,
      Dcme clear of traffic: this signal is transmitted by the ISC if it has 
      accepted the maintenance release request signal and now informs 
      the DCME when all circuits are idle,"
::= { mscDclOperEntry 4 }

mscDclTransmittedTrmSignal OBJECT-TYPE
   SYNTAX     INTEGER  {
                 none000(0),
                 dcmeNormal100(4),
                 no64KbitSCapacity101(5),
                 maintenanceReleaseRequest110(6),
                 noCapacityAvailable111(7) }
   ACCESS     read-only
   STATUS     mandatory
   DESCRIPTION
     "This attribute indicates the last TRM signal transmitted to the ISC.
      The transmitted TRM signal can be one of:
      Dcme normal (100):	 , this signal is allways transmitted by the 
      DCME when there is no other signal to be sent,
      No 64 kbit/s capacity (101): this signal is transmitted by the DCME 
      when it is not able to handle new 64 kbit/s call requests,
      Maintenance release request(110): this signal is transmitted by the 
      DCME when the DCME is to be removed from the service for 
      maintenance,
      No capacity available (111) this signal is transmitted by the DCME 
      when there is bearer capacity available to set up new 3.1 kHz audio 
      or speech calls,"
::= { mscDclOperEntry 5 }

mscDclStatsTable OBJECT-TYPE
   SYNTAX     SEQUENCE OF MscDclStatsEntry
   ACCESS     not-accessible
   STATUS     mandatory
   DESCRIPTION
     "This group contains statistics for the DcmeLink component."
::= { mscDcl 13 }

mscDclStatsEntry OBJECT-TYPE
   SYNTAX     MscDclStatsEntry
   ACCESS     not-accessible
   STATUS     mandatory
   DESCRIPTION
     "An entry in the mscDclStatsTable."
   INDEX {
      mscDclIndex }
::= { mscDclStatsTable 1 }

MscDclStatsEntry ::= SEQUENCE {
   mscDclTotalSpeechCalls
      Counter32,
   mscDclTotal3kHzCalls
      Counter32,
   mscDclTotal64kCalls
      Counter32,
   mscDclRejectedSpeechCalls
      Counter32,
   mscDclRejected3kHzCalls
      Counter32,
   mscDclRejected64kCalls
      Counter32,
   mscDclInvalidTrmSignals
      Counter32 }

mscDclTotalSpeechCalls OBJECT-TYPE
   SYNTAX     Counter32 
   ACCESS     read-only
   STATUS     mandatory
   DESCRIPTION
     "This attribute counts the total number of speech calls that have been 
      handled by this DcmeLink, including rejected calls.
      This counter wraps to zero when it exceeds its maximum."
::= { mscDclStatsEntry 1 }

mscDclTotal3kHzCalls OBJECT-TYPE
   SYNTAX     Counter32 
   ACCESS     read-only
   STATUS     mandatory
   DESCRIPTION
     "This attribute counts the total number of audio 3.1 kHz calls that 
      have been handled by this DcmeLink, including rejected calls.
      This counter wraps to zero when it exceeds its maximum."
::= { mscDclStatsEntry 2 }

mscDclTotal64kCalls OBJECT-TYPE
   SYNTAX     Counter32 
   ACCESS     read-only
   STATUS     mandatory
   DESCRIPTION
     "This attribute counts the total number of unrestricted 64 kbit/s calls 
      that have been handled by this DcmeLink, including rejected calls.
      This counter wraps to zero when it exceeds its maximum."
::= { mscDclStatsEntry 3 }

mscDclRejectedSpeechCalls OBJECT-TYPE
   SYNTAX     Counter32 
   ACCESS     read-only
   STATUS     mandatory
   DESCRIPTION
     "This attribute counts the total number of speech calls that have been 
      rejected by this DcmeLink because there was no preestablished LC 
      available.
      This counter wraps to zero when it exceeds its maximum."
::= { mscDclStatsEntry 4 }

mscDclRejected3kHzCalls OBJECT-TYPE
   SYNTAX     Counter32 
   ACCESS     read-only
   STATUS     mandatory
   DESCRIPTION
     "This attribute counts the total number of audio 3.1 KHz calls that 
      have been rejected by this DcmeLink because there was no 
      preestablished LC available.
      This counter wraps to zero when it exceeds its maximum."
::= { mscDclStatsEntry 5 }

mscDclRejected64kCalls OBJECT-TYPE
   SYNTAX     Counter32 
   ACCESS     read-only
   STATUS     mandatory
   DESCRIPTION
     "This attribute counts the total number of unrestricted 64 kbit/s calls 
      that have been rejected by this DcmeLink.
      This counter wraps to zero when it reaches its maximum."
::= { mscDclStatsEntry 6 }

mscDclInvalidTrmSignals OBJECT-TYPE
   SYNTAX     Counter32 
   ACCESS     read-only
   STATUS     mandatory
   DESCRIPTION
     "This attribute counts the number of invalid TRM/Maintenance 
      signals received from the ISC by this DcmeLink. The most probable 
      cause of an invalid TRM/Maintenance signal is an invalid ISC 
      provisionning or a transmission error.
      The invalid bit settings are 000, 001, 010, 011, 100.
      This counter wraps to zero when it exceeds its maximum."
::= { mscDclStatsEntry 7 }


-- DcmeLink/n DataNetworkAddress
-- This is the description of the DCME link Dna component. It 
-- includes the attributes which apply to all connections established 
-- between DcmeLink and its peer DcmeLink.

mscDclDna OBJECT IDENTIFIER ::= { mscDcl 2 }



mscDclDnaRowStatusTable OBJECT-TYPE
   SYNTAX     SEQUENCE OF MscDclDnaRowStatusEntry
   ACCESS     not-accessible
   STATUS     mandatory
   DESCRIPTION
     "This entry controls the addition and deletion of 
      mscDclDna components."
::= { mscDclDna 1 }

mscDclDnaRowStatusEntry OBJECT-TYPE
   SYNTAX     MscDclDnaRowStatusEntry
   ACCESS     not-accessible
   STATUS     mandatory
   DESCRIPTION
     "A single entry in the table represents a single 
      mscDclDna component."
   INDEX {
      mscDclIndex,
      mscDclDnaIndex }
::= { mscDclDnaRowStatusTable 1 }

MscDclDnaRowStatusEntry ::= SEQUENCE {
   mscDclDnaRowStatus
      RowStatus,
   mscDclDnaComponentName
      DisplayString,
   mscDclDnaStorageType
      StorageType,
   mscDclDnaIndex
      NonReplicated }

mscDclDnaRowStatus OBJECT-TYPE
   SYNTAX     RowStatus 
   ACCESS     read-only
   STATUS     mandatory
   DESCRIPTION
     "This variable is used as the basis for SNMP naming of
      mscDclDna components.
      These components cannot be added nor deleted."
::= { mscDclDnaRowStatusEntry 1 }

mscDclDnaComponentName OBJECT-TYPE
   SYNTAX     DisplayString 
   ACCESS     read-only
   STATUS     mandatory
   DESCRIPTION
     "This variable provides the component's string name for
      use with the ASCII Console Interface"
::= { mscDclDnaRowStatusEntry 2 }

mscDclDnaStorageType OBJECT-TYPE
   SYNTAX     StorageType 
   ACCESS     read-only
   STATUS     mandatory
   DESCRIPTION
     "This variable represents the storage type value for the
      mscDclDna tables."
::= { mscDclDnaRowStatusEntry 4 }

mscDclDnaIndex OBJECT-TYPE
   SYNTAX     NonReplicated 
   ACCESS     not-accessible
   STATUS     mandatory
   DESCRIPTION
     "This variable represents the index for the mscDclDna tables."
::= { mscDclDnaRowStatusEntry 10 }

mscDclDnaAddressTable OBJECT-TYPE
   SYNTAX     SEQUENCE OF MscDclDnaAddressEntry
   ACCESS     not-accessible
   STATUS     mandatory
   DESCRIPTION
     "The Address group contains attributes common to all Dna's. Every 
      Dna used in the network is defined with this group of 2 attributes. 
      The string of address digits is complemented by the type of address 
      or Npi. These attributes are used to interpret the format of the 
      address digits."
::= { mscDclDna 10 }

mscDclDnaAddressEntry OBJECT-TYPE
   SYNTAX     MscDclDnaAddressEntry
   ACCESS     not-accessible
   STATUS     mandatory
   DESCRIPTION
     "An entry in the mscDclDnaAddressTable."
   INDEX {
      mscDclIndex,
      mscDclDnaIndex }
::= { mscDclDnaAddressTable 1 }

MscDclDnaAddressEntry ::= SEQUENCE {
   mscDclDnaNumberingPlanIndicator
      INTEGER,
   mscDclDnaDataNetworkAddress
      DigitString }

mscDclDnaNumberingPlanIndicator OBJECT-TYPE
   SYNTAX     INTEGER  {
                 x121(0),
                 e164(1) }
   ACCESS     read-write
   STATUS     mandatory
   DESCRIPTION
     "This attribute indicates the Numbering Plan Indicator (NPI) of the 
      Dna that is entered. An address may belong to the X.121 or E.164 
      numbering plans. X.121 is used in packet switched data networks."
   DEFVAL     { e164 }
::= { mscDclDnaAddressEntry 1 }

mscDclDnaDataNetworkAddress OBJECT-TYPE
   SYNTAX     DigitString (SIZE (1..15))
   ACCESS     read-write
   STATUS     mandatory
   DESCRIPTION
     "The Dna attribute contains digits which form a unique identifier of 
      the customer interface. It can be compared (approximation only) to 
      a telephone number where each phone number identifies a unique 
      telephone set. Dna digits are selected and assigned by network 
      operators."
::= { mscDclDnaAddressEntry 2 }


-- DcmeLink/n Framer
-- The Framer component controls link layer framing for application 
-- components sending and receiving data on the link interface to the 
-- ISC. It is also through the Framer that an application component is 
-- associated with a specific hardware link interface.
-- 
-- The Framer component provides provisionable attributes related to 
-- datapath aspects of the hardware interface (such as CRC and frame 
-- length). The Framer component also provides a provisionable 
-- attribute which binds the application component to a specific 
-- hardware component.
-- 
-- The Framer component contains operational attributes for link 
-- interface datapath statistics (such as frame counts and aborts).
-- 

mscDclFramer OBJECT IDENTIFIER ::= { mscDcl 3 }



mscDclFramerRowStatusTable OBJECT-TYPE
   SYNTAX     SEQUENCE OF MscDclFramerRowStatusEntry
   ACCESS     not-accessible
   STATUS     mandatory
   DESCRIPTION
     "This entry controls the addition and deletion of 
      mscDclFramer components."
::= { mscDclFramer 1 }

mscDclFramerRowStatusEntry OBJECT-TYPE
   SYNTAX     MscDclFramerRowStatusEntry
   ACCESS     not-accessible
   STATUS     mandatory
   DESCRIPTION
     "A single entry in the table represents a single 
      mscDclFramer component."
   INDEX {
      mscDclIndex,
      mscDclFramerIndex }
::= { mscDclFramerRowStatusTable 1 }

MscDclFramerRowStatusEntry ::= SEQUENCE {
   mscDclFramerRowStatus
      RowStatus,
   mscDclFramerComponentName
      DisplayString,
   mscDclFramerStorageType
      StorageType,
   mscDclFramerIndex
      NonReplicated }

mscDclFramerRowStatus OBJECT-TYPE
   SYNTAX     RowStatus 
   ACCESS     read-only
   STATUS     mandatory
   DESCRIPTION
     "This variable is used as the basis for SNMP naming of
      mscDclFramer components.
      These components cannot be added nor deleted."
::= { mscDclFramerRowStatusEntry 1 }

mscDclFramerComponentName OBJECT-TYPE
   SYNTAX     DisplayString 
   ACCESS     read-only
   STATUS     mandatory
   DESCRIPTION
     "This variable provides the component's string name for
      use with the ASCII Console Interface"
::= { mscDclFramerRowStatusEntry 2 }

mscDclFramerStorageType OBJECT-TYPE
   SYNTAX     StorageType 
   ACCESS     read-only
   STATUS     mandatory
   DESCRIPTION
     "This variable represents the storage type value for the
      mscDclFramer tables."
::= { mscDclFramerRowStatusEntry 4 }

mscDclFramerIndex OBJECT-TYPE
   SYNTAX     NonReplicated 
   ACCESS     not-accessible
   STATUS     mandatory
   DESCRIPTION
     "This variable represents the index for the mscDclFramer tables."
::= { mscDclFramerRowStatusEntry 10 }

mscDclFramerProvTable OBJECT-TYPE
   SYNTAX     SEQUENCE OF MscDclFramerProvEntry
   ACCESS     not-accessible
   STATUS     mandatory
   DESCRIPTION
     "This group contains the base provisioning data for the Framer 
      component. Application or hardware interface specific provisioning 
      data is contained in other provisionable Framer groups."
::= { mscDclFramer 10 }

mscDclFramerProvEntry OBJECT-TYPE
   SYNTAX     MscDclFramerProvEntry
   ACCESS     not-accessible
   STATUS     mandatory
   DESCRIPTION
     "An entry in the mscDclFramerProvTable."
   INDEX {
      mscDclIndex,
      mscDclFramerIndex }
::= { mscDclFramerProvTable 1 }

MscDclFramerProvEntry ::= SEQUENCE {
   mscDclFramerInterfaceName
      Link }

mscDclFramerInterfaceName OBJECT-TYPE
   SYNTAX     Link 
   ACCESS     read-write
   STATUS     mandatory
   DESCRIPTION
     "This attribute contains a hardware component name.
      
      The attribute associates the application with a specific link. This 
      defines the module processor on which Framer's parent component 
      (as well as Framer itself) will run."
::= { mscDclFramerProvEntry 1 }

mscDclFramerStateTable OBJECT-TYPE
   SYNTAX     SEQUENCE OF MscDclFramerStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { mscDclFramer 12 }

mscDclFramerStateEntry OBJECT-TYPE
   SYNTAX     MscDclFramerStateEntry
   ACCESS     not-accessible
   STATUS     mandatory
   DESCRIPTION
     "An entry in the mscDclFramerStateTable."
   INDEX {
      mscDclIndex,
      mscDclFramerIndex }
::= { mscDclFramerStateTable 1 }

MscDclFramerStateEntry ::= SEQUENCE {
   mscDclFramerAdminState
      INTEGER,
   mscDclFramerOperationalState
      INTEGER,
   mscDclFramerUsageState
      INTEGER }

mscDclFramerAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { mscDclFramerStateEntry 1 }

mscDclFramerOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { mscDclFramerStateEntry 2 }

mscDclFramerUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { mscDclFramerStateEntry 3 }


-- DcmeLink/n DcmeVoiceService/n		
-- The DcmeVoiceService component defines the operational 
-- characteristics of the connection to a International Switching Centre 
-- (ISC). One instance of this component is required for each channel 
-- (that is, timeslot) which is part of the DcmeLink.

mscDclVs OBJECT IDENTIFIER ::= { mscDcl 4 }



mscDclVsRowStatusTable OBJECT-TYPE
   SYNTAX     SEQUENCE OF MscDclVsRowStatusEntry
   ACCESS     not-accessible
   STATUS     mandatory
   DESCRIPTION
     "This entry controls the addition and deletion of 
      mscDclVs components."
::= { mscDclVs 1 }

mscDclVsRowStatusEntry OBJECT-TYPE
   SYNTAX     MscDclVsRowStatusEntry
   ACCESS     not-accessible
   STATUS     mandatory
   DESCRIPTION
     "A single entry in the table represents a single 
      mscDclVs component."
   INDEX {
      mscDclIndex,
      mscDclVsIndex }
::= { mscDclVsRowStatusTable 1 }

MscDclVsRowStatusEntry ::= SEQUENCE {
   mscDclVsRowStatus
      RowStatus,
   mscDclVsComponentName
      DisplayString,
   mscDclVsStorageType
      StorageType,
   mscDclVsIndex
      Integer32 }

mscDclVsRowStatus OBJECT-TYPE
   SYNTAX     RowStatus 
   ACCESS     read-write
   STATUS     mandatory
   DESCRIPTION
     "This variable is used as the basis for SNMP naming of
      mscDclVs components.
      These components can be added and deleted."
::= { mscDclVsRowStatusEntry 1 }

mscDclVsComponentName OBJECT-TYPE
   SYNTAX     DisplayString 
   ACCESS     read-only
   STATUS     mandatory
   DESCRIPTION
     "This variable provides the component's string name for
      use with the ASCII Console Interface"
::= { mscDclVsRowStatusEntry 2 }

mscDclVsStorageType OBJECT-TYPE
   SYNTAX     StorageType 
   ACCESS     read-only
   STATUS     mandatory
   DESCRIPTION
     "This variable represents the storage type value for the
      mscDclVs tables."
::= { mscDclVsRowStatusEntry 4 }

mscDclVsIndex OBJECT-TYPE
   SYNTAX     Integer32 (1..31)
   ACCESS     not-accessible
   STATUS     mandatory
   DESCRIPTION
     "This variable represents the index for the mscDclVs tables."
::= { mscDclVsRowStatusEntry 10 }

mscDclVsProvTable OBJECT-TYPE
   SYNTAX     SEQUENCE OF MscDclVsProvEntry
   ACCESS     not-accessible
   STATUS     mandatory
   DESCRIPTION
     "This group contains the provisionable attributes of a DcmeVs 
      component."
::= { mscDclVs 10 }

mscDclVsProvEntry OBJECT-TYPE
   SYNTAX     MscDclVsProvEntry
   ACCESS     not-accessible
   STATUS     mandatory
   DESCRIPTION
     "An entry in the mscDclVsProvTable."
   INDEX {
      mscDclIndex,
      mscDclVsIndex }
::= { mscDclVsProvTable 1 }

MscDclVsProvEntry ::= SEQUENCE {
   mscDclVsVsType
      INTEGER }

mscDclVsVsType OBJECT-TYPE
   SYNTAX     INTEGER  {
                 dynamicVs(0),
                 permanent64kVs(1) }
   ACCESS     read-write
   STATUS     mandatory
   DESCRIPTION
     "This attribute specifies the type of calls offered by this DcmeVs. If 
      the value permanent64kVs is selected the 64 kbit/s call is 
      established on the channel associated with this DcmeVs upon 
      system activation. If this call is cleared due to the subnet failure it is 
      reestablished again by the DcmeLink. If the value dynamicVs is 
      selected this channel can be used to establish user selected calls."
   DEFVAL     { dynamicVs }
::= { mscDclVsProvEntry 1 }

mscDclVsOperTable OBJECT-TYPE
   SYNTAX     SEQUENCE OF MscDclVsOperEntry
   ACCESS     not-accessible
   STATUS     mandatory
   DESCRIPTION
     "This group provides the operational attributes for the 
      DcmeVoiceService component."
::= { mscDclVs 11 }

mscDclVsOperEntry OBJECT-TYPE
   SYNTAX     MscDclVsOperEntry
   ACCESS     not-accessible
   STATUS     mandatory
   DESCRIPTION
     "An entry in the mscDclVsOperTable."
   INDEX {
      mscDclIndex,
      mscDclVsIndex }
::= { mscDclVsOperTable 1 }

MscDclVsOperEntry ::= SEQUENCE {
   mscDclVsStatus
      INTEGER,
   mscDclVsCallType
      INTEGER,
   mscDclVsReceivedAbBits
      INTEGER,
   mscDclVsTransmittedAbBits
      INTEGER }

mscDclVsStatus OBJECT-TYPE
   SYNTAX     INTEGER  {
                 idle(0),
                 seized(1) }
   ACCESS     read-only
   STATUS     mandatory
   DESCRIPTION
     "This attribute indicates the current status of the channel. 
      idle means that there is no call currently active on this channel.
      seized means that the channel has currently an active call."
::= { mscDclVsOperEntry 1 }

mscDclVsCallType OBJECT-TYPE
   SYNTAX     INTEGER  {
                 none(0),
                 speech(1),
                 n31KHz(2),
                 n64KbitS(3) }
   ACCESS     read-only
   STATUS     mandatory
   DESCRIPTION
     "This attribute indicates the type of call that this channel is currently 
      carrying. If no call is active, then it displays the value for the last 
      call."
::= { mscDclVsOperEntry 3 }

mscDclVsReceivedAbBits OBJECT-TYPE
   SYNTAX     INTEGER  {
                 none00(0),
                 normalServiceAvailable01(1),
                 n31KHzRequest10(2),
                 n64KbitSRequest11(3) }
   ACCESS     read-only
   STATUS     mandatory
   DESCRIPTION
     "This attribute indicates the most recently received AB bits."
::= { mscDclVsOperEntry 4 }

mscDclVsTransmittedAbBits OBJECT-TYPE
   SYNTAX     INTEGER  {
                 none00(0),
                 normalServiceAvailable01(1),
                 specialServiceAck10(2),
                 channelOutOfService11(3) }
   ACCESS     read-only
   STATUS     mandatory
   DESCRIPTION
     "This attribute indicates the AB bits currently being transmitted."
::= { mscDclVsOperEntry 5 }

mscDclVsStatsTable OBJECT-TYPE
   SYNTAX     SEQUENCE OF MscDclVsStatsEntry
   ACCESS     not-accessible
   STATUS     mandatory
   DESCRIPTION
     "This group provides the operational attributes for the 
      DcmeVoiceService component."
::= { mscDclVs 12 }

mscDclVsStatsEntry OBJECT-TYPE
   SYNTAX     MscDclVsStatsEntry
   ACCESS     not-accessible
   STATUS     mandatory
   DESCRIPTION
     "An entry in the mscDclVsStatsTable."
   INDEX {
      mscDclIndex,
      mscDclVsIndex }
::= { mscDclVsStatsTable 1 }

MscDclVsStatsEntry ::= SEQUENCE {
   mscDclVsTotalCalls
      Counter32,
   mscDclVsTotalCallSeconds
      Counter32,
   mscDclVsInvalidAbBits
      Counter32 }

mscDclVsTotalCalls OBJECT-TYPE
   SYNTAX     Counter32 
   ACCESS     read-only
   STATUS     mandatory
   DESCRIPTION
     "This attribute counts the call attempts processed on this channel (in 
      both directions). This count includes both successful and 
      unsuccessful calls.
      The value wraps when it exceeds its maximum."
::= { mscDclVsStatsEntry 1 }

mscDclVsTotalCallSeconds OBJECT-TYPE
   SYNTAX     Counter32 
   ACCESS     read-only
   STATUS     mandatory
   DESCRIPTION
     "This attribute counts the total number of seconds that this channel is 
      handling a call. This is regardless of whether the call is successful 
      or not. In other words, this is the amount of time that the channel is 
      not in the idle state.
      The value wraps when it reaches its maximum."
::= { mscDclVsStatsEntry 2 }

mscDclVsInvalidAbBits OBJECT-TYPE
   SYNTAX     Counter32 
   ACCESS     read-only
   STATUS     mandatory
   DESCRIPTION
     "This attribute counts the number of invalid AB bits signals received 
      from the ISC on this channel. The invalid bit setting is 00.
      This counter wraps to zero when it reaches its maximum."
::= { mscDclVsStatsEntry 3 }

mscDclVsStateTable OBJECT-TYPE
   SYNTAX     SEQUENCE OF MscDclVsStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { mscDclVs 13 }

mscDclVsStateEntry OBJECT-TYPE
   SYNTAX     MscDclVsStateEntry
   ACCESS     not-accessible
   STATUS     mandatory
   DESCRIPTION
     "An entry in the mscDclVsStateTable."
   INDEX {
      mscDclIndex,
      mscDclVsIndex }
::= { mscDclVsStateTable 1 }

MscDclVsStateEntry ::= SEQUENCE {
   mscDclVsAdminState
      INTEGER,
   mscDclVsOperationalState
      INTEGER,
   mscDclVsUsageState
      INTEGER }

mscDclVsAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { mscDclVsStateEntry 1 }

mscDclVsOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { mscDclVsStateEntry 2 }

mscDclVsUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { mscDclVsStateEntry 3 }


-- Vsr/n Svs/n Framer
-- The Framer component controls link layer framing for application 
-- components sending and receiving data on a link interface. It is also 
-- through Framer, that an application component is associated with a 
-- specific hardware link interface.
-- The Framer component provides provisionable attributes related to 
-- datapath aspects of the hardware interface rather than interface 
-- specific attributes (such as modem leads and clocking) which are 
-- associated with specific hardware components (such as E1 or DS1).
-- The Framer component also provides a provisionable attribute 
-- which binds the application component to a specific hardware 
-- component.
-- The Framer component contains operational attributes for link 
-- interface datapath statistics (such as frame counts).

mscDclVsFramer OBJECT IDENTIFIER ::= { mscDclVs 2 }



mscDclVsFramerRowStatusTable OBJECT-TYPE
   SYNTAX     SEQUENCE OF MscDclVsFramerRowStatusEntry
   ACCESS     not-accessible
   STATUS     mandatory
   DESCRIPTION
     "This entry controls the addition and deletion of 
      mscDclVsFramer components."
::= { mscDclVsFramer 1 }

mscDclVsFramerRowStatusEntry OBJECT-TYPE
   SYNTAX     MscDclVsFramerRowStatusEntry
   ACCESS     not-accessible
   STATUS     mandatory
   DESCRIPTION
     "A single entry in the table represents a single 
      mscDclVsFramer component."
   INDEX {
      mscDclIndex,
      mscDclVsIndex,
      mscDclVsFramerIndex }
::= { mscDclVsFramerRowStatusTable 1 }

MscDclVsFramerRowStatusEntry ::= SEQUENCE {
   mscDclVsFramerRowStatus
      RowStatus,
   mscDclVsFramerComponentName
      DisplayString,
   mscDclVsFramerStorageType
      StorageType,
   mscDclVsFramerIndex
      NonReplicated }

mscDclVsFramerRowStatus OBJECT-TYPE
   SYNTAX     RowStatus 
   ACCESS     read-only
   STATUS     mandatory
   DESCRIPTION
     "This variable is used as the basis for SNMP naming of
      mscDclVsFramer components.
      These components cannot be added nor deleted."
::= { mscDclVsFramerRowStatusEntry 1 }

mscDclVsFramerComponentName OBJECT-TYPE
   SYNTAX     DisplayString 
   ACCESS     read-only
   STATUS     mandatory
   DESCRIPTION
     "This variable provides the component's string name for
      use with the ASCII Console Interface"
::= { mscDclVsFramerRowStatusEntry 2 }

mscDclVsFramerStorageType OBJECT-TYPE
   SYNTAX     StorageType 
   ACCESS     read-only
   STATUS     mandatory
   DESCRIPTION
     "This variable represents the storage type value for the
      mscDclVsFramer tables."
::= { mscDclVsFramerRowStatusEntry 4 }

mscDclVsFramerIndex OBJECT-TYPE
   SYNTAX     NonReplicated 
   ACCESS     not-accessible
   STATUS     mandatory
   DESCRIPTION
     "This variable represents the index for the mscDclVsFramer tables."
::= { mscDclVsFramerRowStatusEntry 10 }

mscDclVsFramerProvTable OBJECT-TYPE
   SYNTAX     SEQUENCE OF MscDclVsFramerProvEntry
   ACCESS     not-accessible
   STATUS     mandatory
   DESCRIPTION
     "This group contains the base provisioning data for the Framer 
      component. Application or hardware interface specific provisioning 
      data is contained in other provisionable Framer groups."
::= { mscDclVsFramer 10 }

mscDclVsFramerProvEntry OBJECT-TYPE
   SYNTAX     MscDclVsFramerProvEntry
   ACCESS     not-accessible
   STATUS     mandatory
   DESCRIPTION
     "An entry in the mscDclVsFramerProvTable."
   INDEX {
      mscDclIndex,
      mscDclVsIndex,
      mscDclVsFramerIndex }
::= { mscDclVsFramerProvTable 1 }

MscDclVsFramerProvEntry ::= SEQUENCE {
   mscDclVsFramerInterfaceName
      Link }

mscDclVsFramerInterfaceName OBJECT-TYPE
   SYNTAX     Link 
   ACCESS     read-write
   STATUS     mandatory
   DESCRIPTION
     "This attribute contains a hardware component name.
      
      The attribute associates the application with a specific link. This 
      defines the module processor on which Framer's parent component 
      (as well as Framer itself) will run."
::= { mscDclVsFramerProvEntry 1 }

mscDclVsFramerStateTable OBJECT-TYPE
   SYNTAX     SEQUENCE OF MscDclVsFramerStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { mscDclVsFramer 14 }

mscDclVsFramerStateEntry OBJECT-TYPE
   SYNTAX     MscDclVsFramerStateEntry
   ACCESS     not-accessible
   STATUS     mandatory
   DESCRIPTION
     "An entry in the mscDclVsFramerStateTable."
   INDEX {
      mscDclIndex,
      mscDclVsIndex,
      mscDclVsFramerIndex }
::= { mscDclVsFramerStateTable 1 }

MscDclVsFramerStateEntry ::= SEQUENCE {
   mscDclVsFramerAdminState
      INTEGER,
   mscDclVsFramerOperationalState
      INTEGER,
   mscDclVsFramerUsageState
      INTEGER }

mscDclVsFramerAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { mscDclVsFramerStateEntry 1 }

mscDclVsFramerOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { mscDclVsFramerStateEntry 2 }

mscDclVsFramerUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { mscDclVsFramerStateEntry 3 }

mscDclVsFramerStatsTable OBJECT-TYPE
   SYNTAX     SEQUENCE OF MscDclVsFramerStatsEntry
   ACCESS     not-accessible
   STATUS     mandatory
   DESCRIPTION
     "This group contains the operational statistics data for a Framer 
      component."
::= { mscDclVsFramer 15 }

mscDclVsFramerStatsEntry OBJECT-TYPE
   SYNTAX     MscDclVsFramerStatsEntry
   ACCESS     not-accessible
   STATUS     mandatory
   DESCRIPTION
     "An entry in the mscDclVsFramerStatsTable."
   INDEX {
      mscDclIndex,
      mscDclVsIndex,
      mscDclVsFramerIndex }
::= { mscDclVsFramerStatsTable 1 }

MscDclVsFramerStatsEntry ::= SEQUENCE {
   mscDclVsFramerTotalCells
      Unsigned32,
   mscDclVsFramerAudioCells
      Unsigned32,
   mscDclVsFramerSilenceCells
      Unsigned32,
   mscDclVsFramerModemCells
      Unsigned32,
   mscDclVsFramerCurrentEncodingRate
      INTEGER,
   mscDclVsFramerLrcErrors
      Unsigned32,
   mscDclVsFramerFrmLostInNetwork
      Unsigned32,
   mscDclVsFramerFrmUnderRuns
      Unsigned32,
   mscDclVsFramerFrmDumped
      Unsigned32,
   mscDclVsFramerModemSilenceCells
      Counter32,
   mscDclVsFramerCurrentEncoding
      INTEGER,
   mscDclVsFramerTptStatus
      INTEGER,
   mscDclVsFramerFaxRelayCells
      Counter32,
   mscDclVsFramerModemFaxCells
      Unsigned32,
   mscDclVsFramerFaxIdleCells
      Counter32 }

mscDclVsFramerTotalCells OBJECT-TYPE
   SYNTAX     Unsigned32 (0..4294967295)
   ACCESS     read-only
   STATUS     mandatory
   DESCRIPTION
     "This attribute counts the total number of cells received from the 
      interface.
      Each cell contains 44 bytes of data from the DS0 channel. Since a 
      DS0 provides data at 64 kbit/s, each cell contains 5.5 ms of audio 
      data.
      This data flow is measured before compression is performed on the 
      channel.
      This counter wraps to zero after reaching its maximum value."
::= { mscDclVsFramerStatsEntry 1 }

mscDclVsFramerAudioCells OBJECT-TYPE
   SYNTAX     Unsigned32 (0..4294967295)
   ACCESS     read-only
   STATUS     mandatory
   DESCRIPTION
     "This attribute counts the total number of cells containing audio data 
      received from the interface while the channel was seized. A CCS 
      channel is always considered to be seized. Audio data includes cells 
      containing voice as well modem audio, but not silence. 
      A cell contains 44 bytes of data from the DS0 channel(5.5 ms).
      This flow is measured before compression is performed on the 
      channel.
      This counter wraps to zero after reaching its maximum value."
::= { mscDclVsFramerStatsEntry 2 }

mscDclVsFramerSilenceCells OBJECT-TYPE
   SYNTAX     Unsigned32 (0..4294967295)
   ACCESS     read-only
   STATUS     mandatory
   DESCRIPTION
     "This attribute counts the total number of cells containing silence 
      data received from the interface which was not forwarded into the 
      network, thus saving bandwidth. A channel may go into silence due 
      to the operation of the silence suppression feature or for CAS 
      channels when the ABCD signalling bits go idle.
      A cell contains 44 bytes of data from the DS0 channel(5.5 ms).
      This flow is measured before compression is performed on the 
      channel.
      This counter wraps to zero after reaching its maximum value."
::= { mscDclVsFramerStatsEntry 4 }

mscDclVsFramerModemCells OBJECT-TYPE
   SYNTAX     Unsigned32 (0..4294967295)
   ACCESS     read-only
   STATUS     obsolete
   DESCRIPTION
     "This attribute is migrated into modemFaxCells."
::= { mscDclVsFramerStatsEntry 5 }

mscDclVsFramerCurrentEncodingRate OBJECT-TYPE
   SYNTAX     INTEGER  {
                 n640(1),
                 n320(2),
                 n240(3),
                 n160(4),
                 n80(5),
                 n144(6),
                 n120(7),
                 n96(8),
                 n72(9),
                 n63(10),
                 n53(11),
                 n48(12),
                 n24(13),
                 n12(14),
                 n03(15) }
   ACCESS     read-only
   STATUS     obsolete
   DESCRIPTION
     "This attribute has been migrated to currentRate in Operational 
      group."
::= { mscDclVsFramerStatsEntry 6 }

mscDclVsFramerLrcErrors OBJECT-TYPE
   SYNTAX     Unsigned32 (0..4294967295)
   ACCESS     read-only
   STATUS     mandatory
   DESCRIPTION
     "This attribute counts the number of frames received from the 
      network with LRC errors."
::= { mscDclVsFramerStatsEntry 7 }

mscDclVsFramerFrmLostInNetwork OBJECT-TYPE
   SYNTAX     Unsigned32 (0..4294967295)
   ACCESS     read-only
   STATUS     mandatory
   DESCRIPTION
     "This attribute counts the number of frames which the service knows 
      it did not receive from the network although they were sent in to the 
      network from the far end."
::= { mscDclVsFramerStatsEntry 8 }

mscDclVsFramerFrmUnderRuns OBJECT-TYPE
   SYNTAX     Unsigned32 (0..4294967295)
   ACCESS     read-only
   STATUS     mandatory
   DESCRIPTION
     "This attribute counts the number of times that a frame was needed 
      but was not available because it had been delayed too long in the 
      network.
      This error may occur repeatedly if the interface clocks at the two 
      access points to the network are operating at different rates."
::= { mscDclVsFramerStatsEntry 9 }

mscDclVsFramerFrmDumped OBJECT-TYPE
   SYNTAX     Unsigned32 (0..4294967295)
   ACCESS     read-only
   STATUS     mandatory
   DESCRIPTION
     "This attribute counts the number of frames which have been 
      dumped because the output queue grew too large. This can occur if 
      the clock rate on the incoming interface is faster than the clock rate 
      on the outgoing interface and there are no silence periods to absorb 
      the difference, or when a compression rate change occurs.
      This count wraps to zero after reaching its maximum value."
::= { mscDclVsFramerStatsEntry 10 }

mscDclVsFramerModemSilenceCells OBJECT-TYPE
   SYNTAX     Counter32 
   ACCESS     read-only
   STATUS     obsolete
   DESCRIPTION
     "This attribute is migrated into faxIdleCells."
::= { mscDclVsFramerStatsEntry 26 }

mscDclVsFramerCurrentEncoding OBJECT-TYPE
   SYNTAX     INTEGER  {
                 g729(1),
                 g728(2),
                 g723(3),
                 g726(4),
                 g711(5),
                 v22(32),
                 v22bis(33),
                 faxRelay(64),
                 v27(65),
                 v29(66),
                 v17(67),
                 none(255) }
   ACCESS     read-only
   STATUS     obsolete
   DESCRIPTION
     "This attribute has been migrated to currentEncoding in Operational 
      group."
::= { mscDclVsFramerStatsEntry 27 }

mscDclVsFramerTptStatus OBJECT-TYPE
   SYNTAX     INTEGER  {
                 operating(0),
                 rejected(1),
                 monitoring(2),
                 disabled(3) }
   ACCESS     read-only
   STATUS     obsolete
   DESCRIPTION
     "This attribute has been migrated to tptStatus in Operational group."
::= { mscDclVsFramerStatsEntry 28 }

mscDclVsFramerFaxRelayCells OBJECT-TYPE
   SYNTAX     Counter32 
   ACCESS     read-only
   STATUS     mandatory
   DESCRIPTION
     "This attribute counts the total number of fax relay cells sent to the 
      network.
      
      This counter wraps to zero after reaching its maximum value."
::= { mscDclVsFramerStatsEntry 35 }

mscDclVsFramerModemFaxCells OBJECT-TYPE
   SYNTAX     Unsigned32 (0..4294967295)
   ACCESS     read-only
   STATUS     mandatory
   DESCRIPTION
     "This attribute counts the total number of cells containing modem 
      data received from the interface while the channel was seized. A 
      CCS channel is always considered to be seized. Cells are considered 
      to be modem data if a constant energy level above          -25 dBmO 
      is detected for more than 900 ms. An energy level below -36 dBmO 
      for more than 650 ms is required to detect that the modem is no 
      longer present. 
      A cell contains 44 bytes of data from the DS0 channel (5.5 ms).
      This flow is measured before compression is performed on the 
      channel.
      This counter wraps to zero after reaching its maximum value."
::= { mscDclVsFramerStatsEntry 36 }

mscDclVsFramerFaxIdleCells OBJECT-TYPE
   SYNTAX     Counter32 
   ACCESS     read-only
   STATUS     mandatory
   DESCRIPTION
     "This attribute counts the total number of cells containing silent fax 
      data received from the interface which were not forwarded into the 
      network, thus saving bandwidth. A channel may go into silence due 
      to the silence Suppression feature or for CAS channels when the 
      ABCD signalling bits go idle.
      
      A cell contains 44 bytes of data from the DS0 channel (5.5 ms). 
      This flow is measured before compression is performed on the 
      channel.
      
      This counter wraps to zero after reaching its maximum value."
::= { mscDclVsFramerStatsEntry 37 }

mscDclVsFramerOperTable OBJECT-TYPE
   SYNTAX     SEQUENCE OF MscDclVsFramerOperEntry
   ACCESS     not-accessible
   STATUS     mandatory
   DESCRIPTION
     "This group contains the operational data for a Svs Framer."
::= { mscDclVsFramer 16 }

mscDclVsFramerOperEntry OBJECT-TYPE
   SYNTAX     MscDclVsFramerOperEntry
   ACCESS     not-accessible
   STATUS     mandatory
   DESCRIPTION
     "An entry in the mscDclVsFramerOperTable."
   INDEX {
      mscDclIndex,
      mscDclVsIndex,
      mscDclVsFramerIndex }
::= { mscDclVsFramerOperTable 1 }

MscDclVsFramerOperEntry ::= SEQUENCE {
   mscDclVsFramerOpCurrentEncoding
      INTEGER,
   mscDclVsFramerCurrentRate
      INTEGER,
   mscDclVsFramerOpTptStatus
      INTEGER }

mscDclVsFramerOpCurrentEncoding OBJECT-TYPE
   SYNTAX     INTEGER  {
                 g729(1),
                 g728(2),
                 g723(3),
                 g726(4),
                 g711(5),
                 v22(32),
                 v22bis(33),
                 faxRelay(64),
                 v27(65),
                 v29(66),
                 v17(67),
                 none(255) }
   ACCESS     read-only
   STATUS     mandatory
   DESCRIPTION
     "This attribute indicates the encoding currently being performed on 
      this channel. g711 indicates that pulse code modulation (PCM) 
      defined by ITU-T G.711 is being performed. g726 indicates that 
      adaptive differential pulse code modulation (ADPCM) defined by 
      ITU-T G.726 is being performed. g728 indicates that the Low Delay 
      Coded Excited Linear Predictive Coder (LD-CELP) algorithm 
      defined by ITU-T G.728 is being performed. g729 indicates that the 
      Conjunctive Structure Algebraic Code Excited Linear Predictive 
      Coder (CS-ACELP) algorithm defined by ITU-T G.729 is being 
      performed. v27 indicates that the algorithm defined by ITU-T V.27 
      is being performed. v29 indicates that the algorithm defined by 
      ITU-T V.29 is being performed."
::= { mscDclVsFramerOperEntry 1 }

mscDclVsFramerCurrentRate OBJECT-TYPE
   SYNTAX     INTEGER  {
                 n0(0),
                 n640(1),
                 n320(2),
                 n240(3),
                 n160(4),
                 n80(5),
                 n144(6),
                 n120(7),
                 n96(8),
                 n72(9),
                 n63(10),
                 n53(11),
                 n48(12),
                 n24(13),
                 n12(14),
                 n03(15) }
   ACCESS     read-only
   STATUS     mandatory
   DESCRIPTION
     "This attribute indicates the current encoding rate for frames being 
      sent to the network."
::= { mscDclVsFramerOperEntry 2 }

mscDclVsFramerOpTptStatus OBJECT-TYPE
   SYNTAX     INTEGER  {
                 operating(0),
                 monitoring(2),
                 disabled(3) }
   ACCESS     read-only
   STATUS     mandatory
   DESCRIPTION
     "This attribute indicates the current status of the tandem pass through 
      algorithm. If tptStatus is operating, the tandem pass through 
      algorithm is cutting through a voice switch. If tptStatus is 
      monitoring, negotiatedTandemPassThrough is enabled, but the 
      tandem pass through algorithm is not cutting through a voice 
      switch. If tptStatus is disabled, negotiatedTandemPassThrough is 
      disabled."
::= { mscDclVsFramerOperEntry 3 }

mscDclVsFramerNegTable OBJECT-TYPE
   SYNTAX     SEQUENCE OF MscDclVsFramerNegEntry
   ACCESS     not-accessible
   STATUS     mandatory
   DESCRIPTION
     "This group contains the attributes indicating the results of voice 
      networking end to end negotiation."
::= { mscDclVsFramer 17 }

mscDclVsFramerNegEntry OBJECT-TYPE
   SYNTAX     MscDclVsFramerNegEntry
   ACCESS     not-accessible
   STATUS     mandatory
   DESCRIPTION
     "An entry in the mscDclVsFramerNegTable."
   INDEX {
      mscDclIndex,
      mscDclVsIndex,
      mscDclVsFramerIndex }
::= { mscDclVsFramerNegTable 1 }

MscDclVsFramerNegEntry ::= SEQUENCE {
   mscDclVsFramerNegotiatedSilenceSuppression
      INTEGER,
   mscDclVsFramerNegotiatedFisG711G726
      INTEGER,
   mscDclVsFramerNegotiatedDtmfRegeneration
      INTEGER,
   mscDclVsFramerNegotiatedV17AsG711G726
      INTEGER,
   mscDclVsFramerNegotiatedTandemPassThrough
      INTEGER }

mscDclVsFramerNegotiatedSilenceSuppression OBJECT-TYPE
   SYNTAX     INTEGER  {
                 off(0),
                 on(1),
                 congested(2),
                 slow(3),
                 slowAndCongested(4) }
   ACCESS     read-write
   STATUS     mandatory
   DESCRIPTION
     "This attribute indicates the result of negotiating silence suppression 
      with the remote end across the subnet. The parameter used for 
      negotiating with the remote end is provisioned in Vncs Vp 
      silenceSuppression.
      
      If negotiatedSilenceSuppression is off, silence suppression is never 
      performed.
      If negotiatedSilenceSuppression is on, silence suppression is always 
      performed.
      If negotiatedSilenceSuppression is congested, silence suppression is 
      performed only when the network is congested.
      If negotiatedSilenceSuppression is slow, silence suppression begins 
      after 10 to 20 seconds without any speech or audio being detected.
      If negotiatedSilenceSuppression is slowAndCongested, both the 
      slow and congested options are applied."
::= { mscDclVsFramerNegEntry 1 }

mscDclVsFramerNegotiatedFisG711G726 OBJECT-TYPE
   SYNTAX     INTEGER  {
                 off(0),
                 on(1) }
   ACCESS     read-write
   STATUS     mandatory
   DESCRIPTION
     "This attribute indicates the result of negotiating G.711/G.726 fax 
      idle suppression with the remote end across the subnet. The 
      parameter used for negotiating with the remote end is provisioned in 
      Vncs Vp faxIdleSuppressionG711G726."
::= { mscDclVsFramerNegEntry 2 }

mscDclVsFramerNegotiatedDtmfRegeneration OBJECT-TYPE
   SYNTAX     INTEGER  {
                 off(0),
                 on(1) }
   ACCESS     read-write
   STATUS     mandatory
   DESCRIPTION
     "This attribute indicates the result of negotiating DTMF regeneration 
      with the remote end across the subnet. The parameter used for 
      negotiating with the remote end is provisioned in Vncs Vp 
      dtmfRegeneration.
      
      If negotiatedDtmfRegeneration is on, DTMF tones received from 
      the link are first converted to digits before being sent to the subnet. 
      When a digit is received from the subnet, its respective DTMF tone 
      is generated before being sent to the link. 
      
      If negotiatedDtmfRegeneration is off, DTMF tones are transported 
      transparently."
::= { mscDclVsFramerNegEntry 3 }

mscDclVsFramerNegotiatedV17AsG711G726 OBJECT-TYPE
   SYNTAX     INTEGER  {
                 no(0),
                 yes(1) }
   ACCESS     read-only
   STATUS     mandatory
   DESCRIPTION
     "This attribute indicates how this SwitchedVoiceService negotiates 
      with V.17 fax machines, as determined by negotiation with the 
      remote end across the subnet. The parameter used for negotiating 
      with the remote end is provisioned in Vncs Vp 
      v17EncodedAsG711G726.
      
      If negotiatedV17AsG711G726 is no, V.17 fax machines are 
      instructed to use V.29, and V.29 fax traffic sent by fax machines is 
      demodulated and encoded using fax relay.
      
      If negotiatedV17AsG711G726 is yes, V.17 fax machines are 
      permitted to use V.17 and V.17 fax traffic sent by fax machines is 
      encoded using G.711 or G.726, at the rates given in 
      negotiatedRates."
::= { mscDclVsFramerNegEntry 4 }

mscDclVsFramerNegotiatedTandemPassThrough OBJECT-TYPE
   SYNTAX     INTEGER  {
                 disabled(0),
                 enabled(1) }
   ACCESS     read-only
   STATUS     mandatory
   DESCRIPTION
     "This attribute indicates the result of negotiating tandem pass 
      through with the remote end across the subnet. The parameter used 
      for negotiating with the remote end is provisioned in Vncs Vp 
      tandemPassThrough."
::= { mscDclVsFramerNegEntry 5 }

mscDclVsFramerFrmToNetworkTable OBJECT-TYPE
   SYNTAX     SEQUENCE OF MscDclVsFramerFrmToNetworkEntry
   ACCESS     not-accessible
   STATUS     mandatory
   DESCRIPTION
     "This attribute counts the number of frames sent to the network at 
      each encoding rate. Fax relay cells are not included."
::= { mscDclVsFramer 315 }

mscDclVsFramerFrmToNetworkEntry OBJECT-TYPE
   SYNTAX     MscDclVsFramerFrmToNetworkEntry
   ACCESS     not-accessible
   STATUS     mandatory
   DESCRIPTION
     "An entry in the mscDclVsFramerFrmToNetworkTable."
   INDEX {
      mscDclIndex,
      mscDclVsIndex,
      mscDclVsFramerIndex,
      mscDclVsFramerFrmToNetworkIndex }
::= { mscDclVsFramerFrmToNetworkTable 1 }

MscDclVsFramerFrmToNetworkEntry ::= SEQUENCE {
   mscDclVsFramerFrmToNetworkIndex
      INTEGER,
   mscDclVsFramerFrmToNetworkValue
      Unsigned32 }

mscDclVsFramerFrmToNetworkIndex OBJECT-TYPE
   SYNTAX     INTEGER  {
                 n64KbitS(0),
                 n32KbitS(1),
                 n24KbitS(2),
                 n16KbitS(3),
                 n8KbitS(4) }
   ACCESS     not-accessible
   STATUS     mandatory
   DESCRIPTION
     "This variable represents the mscDclVsFramerFrmToNetworkTable
      specific index for the mscDclVsFramerFrmToNetworkTable."
::= { mscDclVsFramerFrmToNetworkEntry 1 }

mscDclVsFramerFrmToNetworkValue OBJECT-TYPE
   SYNTAX     Unsigned32 (0..4294967295)
   ACCESS     read-only
   STATUS     mandatory
   DESCRIPTION
     "This variable represents an individual value for the
      mscDclVsFramerFrmToNetworkTable."
::= { mscDclVsFramerFrmToNetworkEntry 2 }

mscDclVsFramerFrmFromNetworkTable OBJECT-TYPE
   SYNTAX     SEQUENCE OF MscDclVsFramerFrmFromNetworkEntry
   ACCESS     not-accessible
   STATUS     mandatory
   DESCRIPTION
     "This attribute counts the number of frames received from the 
      network at each encoding rate."
::= { mscDclVsFramer 316 }

mscDclVsFramerFrmFromNetworkEntry OBJECT-TYPE
   SYNTAX     MscDclVsFramerFrmFromNetworkEntry
   ACCESS     not-accessible
   STATUS     mandatory
   DESCRIPTION
     "An entry in the mscDclVsFramerFrmFromNetworkTable."
   INDEX {
      mscDclIndex,
      mscDclVsIndex,
      mscDclVsFramerIndex,
      mscDclVsFramerFrmFromNetworkIndex }
::= { mscDclVsFramerFrmFromNetworkTable 1 }

MscDclVsFramerFrmFromNetworkEntry ::= SEQUENCE {
   mscDclVsFramerFrmFromNetworkIndex
      INTEGER,
   mscDclVsFramerFrmFromNetworkValue
      Unsigned32 }

mscDclVsFramerFrmFromNetworkIndex OBJECT-TYPE
   SYNTAX     INTEGER  {
                 n64KbitS(0),
                 n32KbitS(1),
                 n24KbitS(2),
                 n16KbitS(3),
                 n8KbitS(4) }
   ACCESS     not-accessible
   STATUS     mandatory
   DESCRIPTION
     "This variable represents the mscDclVsFramerFrmFromNetworkTable
      specific index for the mscDclVsFramerFrmFromNetworkTable."
::= { mscDclVsFramerFrmFromNetworkEntry 1 }

mscDclVsFramerFrmFromNetworkValue OBJECT-TYPE
   SYNTAX     Unsigned32 (0..4294967295)
   ACCESS     read-only
   STATUS     mandatory
   DESCRIPTION
     "This variable represents an individual value for the
      mscDclVsFramerFrmFromNetworkTable."
::= { mscDclVsFramerFrmFromNetworkEntry 2 }

mscDclVsFramerNEncodingTable OBJECT-TYPE
   SYNTAX     SEQUENCE OF MscDclVsFramerNEncodingEntry
   ACCESS     not-accessible
   STATUS     mandatory
   DESCRIPTION
     "This attribute indicates the results of negotiating audio call 
      encodings for voice, modemFax and fax traffic with the remote end 
      across the subnet. The parameters used for negotiating with the 
      remote end are provisioned in Vncs Vp voiceEncodingChoice and 
      Vncs Vp modemFaxEncodingChoice.
      
      voice traffic is all traffic from the start of a call or speech until a 
      2100 Hz tone or call release. modemFax traffic is all traffic after a 
      2100 Hz tone but before a fax preamble, speech or call release. fax 
      traffic is all traffic after a fax preamble but before speech or call 
      release.
      
      g711 indicates that pulse code modulation (PCM) defined by ITU-T 
      G.711 is the negotiated encoding.
      g726 indicates that Adaptive Differential Pulse Code Modulation 
      (ADPCM) defined by ITU-T G.726 is the negotiated encoding. 
      g711G726 indicates that pulse code modulation (PCM) defined by 
      ITU-T G.711 and Adaptive Differential Pulse Code Modulation 
      (ADPCM) defined by ITU-T G.726 are both negotiated encodings. 
      If negotiatedEncoding is g711G726, the actual encoding performed 
      can be either G.711 or G.726, depending on network congestion.
      g728 indicates that Low Delay Coded Excited Linear Predictive 
      Coder (CS-ACELP) defined by ITU-T G.728 is the negotiated 
      encoding.
      g729 indicates that Conjunctive Structure Algebraic Code Excited 
      Linear Predictive Coder (CS-ACELP) defined by ITU-T G.729 is 
      the negotiated encoding.
      v29V27Relay indicates that fax relay using ITU-T V.29 or ITU-T 
      V.27 is the negotiated encoding.
      v17V29V27Relay indicates that fax relay using ITU-T V.17, ITU-T 
      V.29, or ITU-T V.27 is the negotiated encoding.
      
      If all negotiated encodings are none, the negotiation of audio call 
      encodings is not complete."
::= { mscDclVsFramer 467 }

mscDclVsFramerNEncodingEntry OBJECT-TYPE
   SYNTAX     MscDclVsFramerNEncodingEntry
   ACCESS     not-accessible
   STATUS     mandatory
   DESCRIPTION
     "An entry in the mscDclVsFramerNEncodingTable."
   INDEX {
      mscDclIndex,
      mscDclVsIndex,
      mscDclVsFramerIndex,
      mscDclVsFramerNEncodingIndex }
::= { mscDclVsFramerNEncodingTable 1 }

MscDclVsFramerNEncodingEntry ::= SEQUENCE {
   mscDclVsFramerNEncodingIndex
      INTEGER,
   mscDclVsFramerNEncodingValue
      INTEGER }

mscDclVsFramerNEncodingIndex OBJECT-TYPE
   SYNTAX     INTEGER  {
                 voice(0),
                 modemFax(1),
                 fax(2) }
   ACCESS     not-accessible
   STATUS     mandatory
   DESCRIPTION
     "This variable represents the mscDclVsFramerNEncodingTable
      specific index for the mscDclVsFramerNEncodingTable."
::= { mscDclVsFramerNEncodingEntry 1 }

mscDclVsFramerNEncodingValue OBJECT-TYPE
   SYNTAX     INTEGER  {
                 g729(1),
                 g728(2),
                 g726(4),
                 g711(5),
                 g711G726(31),
                 v29V27Relay(64),
                 v17V29V27Relay(68),
                 none(255) }
   ACCESS     read-write
   STATUS     mandatory
   DESCRIPTION
     "This variable represents an individual value for the
      mscDclVsFramerNEncodingTable."
::= { mscDclVsFramerNEncodingEntry 2 }

mscDclVsFramerNRatesTable OBJECT-TYPE
   SYNTAX     SEQUENCE OF MscDclVsFramerNRatesEntry
   ACCESS     not-accessible
   STATUS     mandatory
   DESCRIPTION
     "This attribute indicates the results of negotiating minimum and 
      maximum rates for voice, modemFax and fax traffic with the 
      remote end across the subnet. The parameters used for negotiating 
      with the remote end are provisioned in Vncs Vp voiceRates and 
      Vncs Vp modemFaxRates."
::= { mscDclVsFramer 479 }

mscDclVsFramerNRatesEntry OBJECT-TYPE
   SYNTAX     MscDclVsFramerNRatesEntry
   ACCESS     not-accessible
   STATUS     mandatory
   DESCRIPTION
     "An entry in the mscDclVsFramerNRatesTable."
   INDEX {
      mscDclIndex,
      mscDclVsIndex,
      mscDclVsFramerIndex,
      mscDclVsFramerNRatesTrafficIndex,
      mscDclVsFramerNRatesRateIndex }
::= { mscDclVsFramerNRatesTable 1 }

MscDclVsFramerNRatesEntry ::= SEQUENCE {
   mscDclVsFramerNRatesTrafficIndex
      INTEGER,
   mscDclVsFramerNRatesRateIndex
      INTEGER,
   mscDclVsFramerNRatesValue
      INTEGER }

mscDclVsFramerNRatesTrafficIndex OBJECT-TYPE
   SYNTAX     INTEGER  {
                 voice(0),
                 modemFax(1),
                 fax(2) }
   ACCESS     not-accessible
   STATUS     mandatory
   DESCRIPTION
     "This variable represents the next to last index for the 
      mscDclVsFramerNRatesTable."
::= { mscDclVsFramerNRatesEntry 1 }

mscDclVsFramerNRatesRateIndex OBJECT-TYPE
   SYNTAX     INTEGER  {
                 min(0),
                 max(1) }
   ACCESS     not-accessible
   STATUS     mandatory
   DESCRIPTION
     "This variable represents the final index for the 
      mscDclVsFramerNRatesTable."
::= { mscDclVsFramerNRatesEntry 2 }

mscDclVsFramerNRatesValue OBJECT-TYPE
   SYNTAX     INTEGER  {
                 n00(0),
                 n03(1),
                 n12(2),
                 n24(3),
                 n48(4),
                 n72(5),
                 n96(6),
                 n120(7),
                 n144(8),
                 n80(66),
                 n160(67),
                 n240(68),
                 n320(69),
                 n640(70) }
   ACCESS     read-write
   STATUS     mandatory
   DESCRIPTION
     "This variable represents an individual value for the
      mscDclVsFramerNRatesTable."
::= { mscDclVsFramerNRatesEntry 3 }


-- Vsr/m Svs/n Framer VfpDebug
-- This component contains debugging attributes for a voice service 
-- running on a DS1V, E1V, 1pDS1V, 1pE1V or J2MV functional 
-- processor.

mscDclVsFramerVfpDebug OBJECT IDENTIFIER ::= { mscDclVsFramer 5 }



mscDclVsFramerVfpDebugRowStatusTable OBJECT-TYPE
   SYNTAX     SEQUENCE OF MscDclVsFramerVfpDebugRowStatusEntry
   ACCESS     not-accessible
   STATUS     mandatory
   DESCRIPTION
     "This entry controls the addition and deletion of 
      mscDclVsFramerVfpDebug components."
::= { mscDclVsFramerVfpDebug 1 }

mscDclVsFramerVfpDebugRowStatusEntry OBJECT-TYPE
   SYNTAX     MscDclVsFramerVfpDebugRowStatusEntry
   ACCESS     not-accessible
   STATUS     mandatory
   DESCRIPTION
     "A single entry in the table represents a single 
      mscDclVsFramerVfpDebug component."
   INDEX {
      mscDclIndex,
      mscDclVsIndex,
      mscDclVsFramerIndex,
      mscDclVsFramerVfpDebugIndex }
::= { mscDclVsFramerVfpDebugRowStatusTable 1 }

MscDclVsFramerVfpDebugRowStatusEntry ::= SEQUENCE {
   mscDclVsFramerVfpDebugRowStatus
      RowStatus,
   mscDclVsFramerVfpDebugComponentName
      DisplayString,
   mscDclVsFramerVfpDebugStorageType
      StorageType,
   mscDclVsFramerVfpDebugIndex
      NonReplicated }

mscDclVsFramerVfpDebugRowStatus OBJECT-TYPE
   SYNTAX     RowStatus 
   ACCESS     read-only
   STATUS     mandatory
   DESCRIPTION
     "This variable is used as the basis for SNMP naming of
      mscDclVsFramerVfpDebug components.
      These components cannot be added nor deleted."
::= { mscDclVsFramerVfpDebugRowStatusEntry 1 }

mscDclVsFramerVfpDebugComponentName OBJECT-TYPE
   SYNTAX     DisplayString 
   ACCESS     read-only
   STATUS     mandatory
   DESCRIPTION
     "This variable provides the component's string name for
      use with the ASCII Console Interface"
::= { mscDclVsFramerVfpDebugRowStatusEntry 2 }

mscDclVsFramerVfpDebugStorageType OBJECT-TYPE
   SYNTAX     StorageType 
   ACCESS     read-only
   STATUS     mandatory
   DESCRIPTION
     "This variable represents the storage type value for the
      mscDclVsFramerVfpDebug tables."
::= { mscDclVsFramerVfpDebugRowStatusEntry 4 }

mscDclVsFramerVfpDebugIndex OBJECT-TYPE
   SYNTAX     NonReplicated 
   ACCESS     not-accessible
   STATUS     mandatory
   DESCRIPTION
     "This variable represents the index for the mscDclVsFramerVfpDebug tables."
::= { mscDclVsFramerVfpDebugRowStatusEntry 10 }


-- Vsr/m Svs/n Framer MvpDebug
-- This component contains debugging attributes on a voice service's 
-- framer running on a 1pE1Mvp, 1pDS1Mvp or 1pTTC2mMvp 
-- functional processor.

mscDclVsFramerMvpDebug OBJECT IDENTIFIER ::= { mscDclVsFramer 6 }



mscDclVsFramerMvpDebugRowStatusTable OBJECT-TYPE
   SYNTAX     SEQUENCE OF MscDclVsFramerMvpDebugRowStatusEntry
   ACCESS     not-accessible
   STATUS     mandatory
   DESCRIPTION
     "This entry controls the addition and deletion of 
      mscDclVsFramerMvpDebug components."
::= { mscDclVsFramerMvpDebug 1 }

mscDclVsFramerMvpDebugRowStatusEntry OBJECT-TYPE
   SYNTAX     MscDclVsFramerMvpDebugRowStatusEntry
   ACCESS     not-accessible
   STATUS     mandatory
   DESCRIPTION
     "A single entry in the table represents a single 
      mscDclVsFramerMvpDebug component."
   INDEX {
      mscDclIndex,
      mscDclVsIndex,
      mscDclVsFramerIndex,
      mscDclVsFramerMvpDebugIndex }
::= { mscDclVsFramerMvpDebugRowStatusTable 1 }

MscDclVsFramerMvpDebugRowStatusEntry ::= SEQUENCE {
   mscDclVsFramerMvpDebugRowStatus
      RowStatus,
   mscDclVsFramerMvpDebugComponentName
      DisplayString,
   mscDclVsFramerMvpDebugStorageType
      StorageType,
   mscDclVsFramerMvpDebugIndex
      NonReplicated }

mscDclVsFramerMvpDebugRowStatus OBJECT-TYPE
   SYNTAX     RowStatus 
   ACCESS     read-only
   STATUS     mandatory
   DESCRIPTION
     "This variable is used as the basis for SNMP naming of
      mscDclVsFramerMvpDebug components.
      These components cannot be added nor deleted."
::= { mscDclVsFramerMvpDebugRowStatusEntry 1 }

mscDclVsFramerMvpDebugComponentName OBJECT-TYPE
   SYNTAX     DisplayString 
   ACCESS     read-only
   STATUS     mandatory
   DESCRIPTION
     "This variable provides the component's string name for
      use with the ASCII Console Interface"
::= { mscDclVsFramerMvpDebugRowStatusEntry 2 }

mscDclVsFramerMvpDebugStorageType OBJECT-TYPE
   SYNTAX     StorageType 
   ACCESS     read-only
   STATUS     mandatory
   DESCRIPTION
     "This variable represents the storage type value for the
      mscDclVsFramerMvpDebug tables."
::= { mscDclVsFramerMvpDebugRowStatusEntry 4 }

mscDclVsFramerMvpDebugIndex OBJECT-TYPE
   SYNTAX     NonReplicated 
   ACCESS     not-accessible
   STATUS     mandatory
   DESCRIPTION
     "This variable represents the index for the mscDclVsFramerMvpDebug tables."
::= { mscDclVsFramerMvpDebugRowStatusEntry 10 }


-- Vsr/n Svs/m Framer PcmCapture
-- This component contains attributes for PCM data capture.

mscDclVsFramerPcmCapture OBJECT IDENTIFIER ::= { mscDclVsFramer 7 }



mscDclVsFramerPcmCaptureRowStatusTable OBJECT-TYPE
   SYNTAX     SEQUENCE OF MscDclVsFramerPcmCaptureRowStatusEntry
   ACCESS     not-accessible
   STATUS     mandatory
   DESCRIPTION
     "This entry controls the addition and deletion of 
      mscDclVsFramerPcmCapture components."
::= { mscDclVsFramerPcmCapture 1 }

mscDclVsFramerPcmCaptureRowStatusEntry OBJECT-TYPE
   SYNTAX     MscDclVsFramerPcmCaptureRowStatusEntry
   ACCESS     not-accessible
   STATUS     mandatory
   DESCRIPTION
     "A single entry in the table represents a single 
      mscDclVsFramerPcmCapture component."
   INDEX {
      mscDclIndex,
      mscDclVsIndex,
      mscDclVsFramerIndex,
      mscDclVsFramerPcmCaptureIndex }
::= { mscDclVsFramerPcmCaptureRowStatusTable 1 }

MscDclVsFramerPcmCaptureRowStatusEntry ::= SEQUENCE {
   mscDclVsFramerPcmCaptureRowStatus
      RowStatus,
   mscDclVsFramerPcmCaptureComponentName
      DisplayString,
   mscDclVsFramerPcmCaptureStorageType
      StorageType,
   mscDclVsFramerPcmCaptureIndex
      NonReplicated }

mscDclVsFramerPcmCaptureRowStatus OBJECT-TYPE
   SYNTAX     RowStatus 
   ACCESS     read-only
   STATUS     mandatory
   DESCRIPTION
     "This variable is used as the basis for SNMP naming of
      mscDclVsFramerPcmCapture components.
      These components cannot be added nor deleted."
::= { mscDclVsFramerPcmCaptureRowStatusEntry 1 }

mscDclVsFramerPcmCaptureComponentName OBJECT-TYPE
   SYNTAX     DisplayString 
   ACCESS     read-only
   STATUS     mandatory
   DESCRIPTION
     "This variable provides the component's string name for
      use with the ASCII Console Interface"
::= { mscDclVsFramerPcmCaptureRowStatusEntry 2 }

mscDclVsFramerPcmCaptureStorageType OBJECT-TYPE
   SYNTAX     StorageType 
   ACCESS     read-only
   STATUS     mandatory
   DESCRIPTION
     "This variable represents the storage type value for the
      mscDclVsFramerPcmCapture tables."
::= { mscDclVsFramerPcmCaptureRowStatusEntry 4 }

mscDclVsFramerPcmCaptureIndex OBJECT-TYPE
   SYNTAX     NonReplicated 
   ACCESS     not-accessible
   STATUS     mandatory
   DESCRIPTION
     "This variable represents the index for the mscDclVsFramerPcmCapture tables."
::= { mscDclVsFramerPcmCaptureRowStatusEntry 10 }


-- ...Lc
-- This component contains all of the operation attributes for a Path 
-- Oriented Logical Connection.

mscDclVsLCo OBJECT IDENTIFIER ::= { mscDclVs 3 }



mscDclVsLCoRowStatusTable OBJECT-TYPE
   SYNTAX     SEQUENCE OF MscDclVsLCoRowStatusEntry
   ACCESS     not-accessible
   STATUS     mandatory
   DESCRIPTION
     "This entry controls the addition and deletion of 
      mscDclVsLCo components."
::= { mscDclVsLCo 1 }

mscDclVsLCoRowStatusEntry OBJECT-TYPE
   SYNTAX     MscDclVsLCoRowStatusEntry
   ACCESS     not-accessible
   STATUS     mandatory
   DESCRIPTION
     "A single entry in the table represents a single 
      mscDclVsLCo component."
   INDEX {
      mscDclIndex,
      mscDclVsIndex,
      mscDclVsLCoIndex }
::= { mscDclVsLCoRowStatusTable 1 }

MscDclVsLCoRowStatusEntry ::= SEQUENCE {
   mscDclVsLCoRowStatus
      RowStatus,
   mscDclVsLCoComponentName
      DisplayString,
   mscDclVsLCoStorageType
      StorageType,
   mscDclVsLCoIndex
      NonReplicated }

mscDclVsLCoRowStatus OBJECT-TYPE
   SYNTAX     RowStatus 
   ACCESS     read-only
   STATUS     mandatory
   DESCRIPTION
     "This variable is used as the basis for SNMP naming of
      mscDclVsLCo components.
      These components cannot be added nor deleted."
::= { mscDclVsLCoRowStatusEntry 1 }

mscDclVsLCoComponentName OBJECT-TYPE
   SYNTAX     DisplayString 
   ACCESS     read-only
   STATUS     mandatory
   DESCRIPTION
     "This variable provides the component's string name for
      use with the ASCII Console Interface"
::= { mscDclVsLCoRowStatusEntry 2 }

mscDclVsLCoStorageType OBJECT-TYPE
   SYNTAX     StorageType 
   ACCESS     read-only
   STATUS     mandatory
   DESCRIPTION
     "This variable represents the storage type value for the
      mscDclVsLCo tables."
::= { mscDclVsLCoRowStatusEntry 4 }

mscDclVsLCoIndex OBJECT-TYPE
   SYNTAX     NonReplicated 
   ACCESS     not-accessible
   STATUS     mandatory
   DESCRIPTION
     "This variable represents the index for the mscDclVsLCo tables."
::= { mscDclVsLCoRowStatusEntry 10 }

mscDclVsLCoPathDataTable OBJECT-TYPE
   SYNTAX     SEQUENCE OF MscDclVsLCoPathDataEntry
   ACCESS     not-accessible
   STATUS     mandatory
   DESCRIPTION
     "This group contains all operational attributes for the path oriented 
      LCo."
::= { mscDclVsLCo 10 }

mscDclVsLCoPathDataEntry OBJECT-TYPE
   SYNTAX     MscDclVsLCoPathDataEntry
   ACCESS     not-accessible
   STATUS     mandatory
   DESCRIPTION
     "An entry in the mscDclVsLCoPathDataTable."
   INDEX {
      mscDclIndex,
      mscDclVsIndex,
      mscDclVsLCoIndex }
::= { mscDclVsLCoPathDataTable 1 }

MscDclVsLCoPathDataEntry ::= SEQUENCE {
   mscDclVsLCoState
      INTEGER,
   mscDclVsLCoOverrideRemoteName
      AsciiString,
   mscDclVsLCoEnd
      INTEGER,
   mscDclVsLCoCostMetric
      Unsigned32,
   mscDclVsLCoDelayMetric
      Unsigned32,
   mscDclVsLCoRoundTripDelay
      Unsigned32,
   mscDclVsLCoSetupPriority
      Unsigned32,
   mscDclVsLCoHoldingPriority
      Unsigned32,
   mscDclVsLCoRequiredTxBandwidth
      Gauge32,
   mscDclVsLCoRequiredRxBandwidth
      Gauge32,
   mscDclVsLCoRequiredTrafficType
      INTEGER,
   mscDclVsLCoPermittedTrunkTypes
      OCTET STRING,
   mscDclVsLCoRequiredSecurity
      Unsigned32,
   mscDclVsLCoRequiredCustomerParameter
      Unsigned32,
   mscDclVsLCoEmissionPriority
      Unsigned32,
   mscDclVsLCoDiscardPriority
      Unsigned32,
   mscDclVsLCoPathType
      INTEGER,
   mscDclVsLCoRetryCount
      Unsigned32,
   mscDclVsLCoPathFailureCount
      Unsigned32,
   mscDclVsLCoReasonForNoRoute
      INTEGER,
   mscDclVsLCoLastTearDownReason
      INTEGER,
   mscDclVsLCoPathFailureAction
      INTEGER,
   mscDclVsLCoBumpPreference
      INTEGER,
   mscDclVsLCoOptimization
      INTEGER,
   mscDclVsLCoPathUpDateTime
      EnterpriseDateAndTime }

mscDclVsLCoState OBJECT-TYPE
   SYNTAX     INTEGER  {
                 pathDown(0),
                 selectingRoute(1),
                 connecting(2),
                 pathUp(3),
                 pathDownRetrying(4) }
   ACCESS     read-only
   STATUS     mandatory
   DESCRIPTION
     "This attribute reflects the current state of the connection. The 
      pathDown state indicates a connection that has no remote end 
      provisioned or the application has not yet signalled for a path. The 
      selectingRoute state occurs when a request has been sent to route 
      selector and it has not yet responded. The connectingState occurs 
      while a path is being established. The pathUp state is the normal 
      operational state of a path. The pathDownRetrying state indicates a 
      path that attempted route selection but received no route and is now 
      waiting to retry route selection again."
::= { mscDclVsLCoPathDataEntry 1 }

mscDclVsLCoOverrideRemoteName OBJECT-TYPE
   SYNTAX     AsciiString (SIZE (0..40))
   ACCESS     read-write
   STATUS     mandatory
   DESCRIPTION
     "If set and the current PLC remoteName is blank this remoteName 
      will override the blank PLC remoteName. Usually you would set 
      this attribute and then lock/unlock the service component which 
      will result in this new overrideRemoteName being used as if it had 
      been provisioned into the PLC remoteName. The advantage of this 
      attribute is that the connection's remoteName can be changed 
      immediately without having to 'activate prov' but the disadvantage 
      is that the overrideRemoteName is not permanent and if the card or 
      switch is reset the override will be lost."
::= { mscDclVsLCoPathDataEntry 2 }

mscDclVsLCoEnd OBJECT-TYPE
   SYNTAX     INTEGER  {
                 calling(0),
                 called(1) }
   ACCESS     read-only
   STATUS     mandatory
   DESCRIPTION
     "This attribute identifies whether this is the calling or called end of 
      the path."
::= { mscDclVsLCoPathDataEntry 3 }

mscDclVsLCoCostMetric OBJECT-TYPE
   SYNTAX     Unsigned32 (0..65535)
   ACCESS     read-only
   STATUS     mandatory
   DESCRIPTION
     "This attribute gives the route's total cost metric. It is calculated as 
      the sum of the cost metric of all trunks in the path at the time the 
      connection was established. The cost metric of a trunk is defined by 
      the trunkCost attribute of the Trunk component. The costMetric for 
      an LCo that is originated and terminated on the same module is 0."
::= { mscDclVsLCoPathDataEntry 4 }

mscDclVsLCoDelayMetric OBJECT-TYPE
   SYNTAX     Unsigned32 (0..100000)
   ACCESS     read-only
   STATUS     mandatory
   DESCRIPTION
     "This attribute gives the total delay of the route as the one way delay 
      for a 512 byte packet. It is calculated as the sum of the delays of all 
      trunks in the path stored in topology at the time the connection was 
      established. The delay for an LCo that is originated and terminated 
      on the same module is 0."
::= { mscDclVsLCoPathDataEntry 5 }

mscDclVsLCoRoundTripDelay OBJECT-TYPE
   SYNTAX     Unsigned32 (0..200000)
   ACCESS     read-only
   STATUS     mandatory
   DESCRIPTION
     "This attribute contains the time taken for a packet (cell) of 44 bytes 
      to be transmitted to the remote LCo and return to this LCo. The 
      number reported is given in milliseconds to the nearest millisecond. 
      A value of one millisecond is reported if the time is less than 1 
      millisecond even though the delay may be less than 1 Millisecond 
      when the LCo is originated and terminated on the same module."
::= { mscDclVsLCoPathDataEntry 6 }

mscDclVsLCoSetupPriority OBJECT-TYPE
   SYNTAX     Unsigned32 (0..4)
   ACCESS     read-only
   STATUS     mandatory
   DESCRIPTION
     "This attribute gives the priority at which the current path is 
      established. Zero is the highest priority and four is the lowest. The 
      holdingPriority, a complementary attribute of this component, 
      indicates the priority a path maintains once it is established."
::= { mscDclVsLCoPathDataEntry 7 }

mscDclVsLCoHoldingPriority OBJECT-TYPE
   SYNTAX     Unsigned32 (0..4)
   ACCESS     read-only
   STATUS     mandatory
   DESCRIPTION
     "This attribute gives the priority at which a path holds its current 
      path once the path is established. Zero is the highest priority and 
      four is the lowest. The setupPriority, a complementary attribute, 
      indicates the priority of a path at establishment time."
::= { mscDclVsLCoPathDataEntry 8 }

mscDclVsLCoRequiredTxBandwidth OBJECT-TYPE
   SYNTAX     Gauge32 (0..4294967295)
   ACCESS     read-only
   STATUS     mandatory
   DESCRIPTION
     "This attribute gives the actual bandwidth (in bits per second) 
      reserved by this path on each of the trunks of its route. This attribute 
      represents the bandwidth for traffic outgoing to the remote end 
      point. The originating end of the connection determines this value."
::= { mscDclVsLCoPathDataEntry 9 }

mscDclVsLCoRequiredRxBandwidth OBJECT-TYPE
   SYNTAX     Gauge32 (0..4294967295)
   ACCESS     read-only
   STATUS     mandatory
   DESCRIPTION
     "This attribute gives the actual bandwidth (in bits per second) 
      reserved by this path on each of trunks of its route. This attribute 
      represents the bandwidth for traffic incoming from the remote end 
      point. The originating end of the connection determines this value"
::= { mscDclVsLCoPathDataEntry 10 }

mscDclVsLCoRequiredTrafficType OBJECT-TYPE
   SYNTAX     INTEGER  {
                 voice(0),
                 data(1),
                 video(2),
                 trafficType1(3),
                 trafficType2(4),
                 trafficType3(5),
                 trafficType4(6),
                 trafficType5(7) }
   ACCESS     read-only
   STATUS     mandatory
   DESCRIPTION
     "This operational attribute indicates the type of traffic transmitted 
      over the path. There are eight possible traffic types, and the path can 
      transmit only one of them. The originating end of the connection 
      determines the type. These are arbitrary designations for traffic 
      type. The voice, data and video traffic types are defined, and five 
      other arbitrary traffic types can be defined by the network 
      administration. This attribute is used in the route selection process 
      to restrict the route to trunks that support this traffic type. The 
      supportedTrafficType trunk attribute lists all the types of traffic 
      allowed on the trunk. For example, if requiredTrafficType is 
      specified as trafficType1 then only trunks that include trafficType1 
      in supportedTrafficType, will be candidates for this connection."
::= { mscDclVsLCoPathDataEntry 11 }

mscDclVsLCoPermittedTrunkTypes OBJECT-TYPE
   SYNTAX     OCTET STRING (SIZE (1))
   ACCESS     read-only
   STATUS     mandatory
   DESCRIPTION
     "This operational attribute lists up to eight types of trunk that can be 
      used on the route. The originating end of the connection determines 
      the types. The terrestrial and satellite trunk types have been 
      defined, leaving six remaining arbitrary types that can be defined by 
      the network administration. The trunk's type is indicated in the 
      trunkType attribute of the Trunk component. When selecting a 
      route, PORS only chooses trunks whose trunkType are in the 
      permittedTrunkTypes for the path.

      Description of bits:
      terrestrial(0)
      satellite(1)
      trunkType1(2)
      trunkType2(3)
      trunkType3(4)
      trunkType4(5)
      trunkType5(6)
      trunkType6(7)"
::= { mscDclVsLCoPathDataEntry 12 }

mscDclVsLCoRequiredSecurity OBJECT-TYPE
   SYNTAX     Unsigned32 (0..7)
   ACCESS     read-only
   STATUS     mandatory
   DESCRIPTION
     "This attribute indicates the required minimum level of security of 
      the trunks on the route. Zero represents the most secure and seven 
      represents the least secure. The trunk's security is indicated by the 
      trunkSecurity attribute of the Trunk component, and has values 
      identical in range and meaning to the requiredSecurity attribute. 
      PORS ensures that any route selected does not contain a trunk 
      whose trunkSecurity attribute is numerically greater than the 
      requiredSecurity."
::= { mscDclVsLCoPathDataEntry 13 }

mscDclVsLCoRequiredCustomerParameter OBJECT-TYPE
   SYNTAX     Unsigned32 (0..7)
   ACCESS     read-only
   STATUS     mandatory
   DESCRIPTION
     "This attribute indicates the allowed customer defined parameter of 
      the trunks on the route.The originating end of the connection 
      determines the customer defined parameter. Its value, a number 
      from zero to seven, is chosen by a network administration to have a 
      meaning specific to their network, thus allowing them to customize 
      the use of their trunks. A complementary trunk attribute, 
      customerParameter, also has a value from zero to seven. The route 
      selection process does not consider trunks whose 
      customerParameter is greater than the requiredCustomerParameter 
      of the path."
::= { mscDclVsLCoPathDataEntry 14 }

mscDclVsLCoEmissionPriority OBJECT-TYPE
   SYNTAX     Unsigned32 (0..2)
   ACCESS     read-only
   STATUS     mandatory
   DESCRIPTION
     "This attribute indicates the urgency with which packets on the path 
      are emitted by the trunks on the route. The originating end of the 
      connection selects the emissionPriority. EmissionPriority of zero 
      indicates the highest emission priority, while two indicates the 
      lowest emission priority. Packets with a higher emissionPriority (or 
      numerically less) are serviced and sent out before the packets of 
      lower emissionPriority (or numerically higher)."
::= { mscDclVsLCoPathDataEntry 15 }

mscDclVsLCoDiscardPriority OBJECT-TYPE
   SYNTAX     Unsigned32 (1..3)
   ACCESS     read-only
   STATUS     mandatory
   DESCRIPTION
     "This attribute indicates the importance of the packets on the 
      path.The originating end of the connection sets discardPriority. One 
      is used for paths carrying the most important traffic, and three is 
      used for paths carrying the least important traffic. Packets with 
      lower discardPriority(numerically lower) are discarded after 
      packets with a higher discardPriority(numerically higher)."
::= { mscDclVsLCoPathDataEntry 16 }

mscDclVsLCoPathType OBJECT-TYPE
   SYNTAX     INTEGER  {
                 normal(0),
                 manual(1),
                 forced(2) }
   ACCESS     read-only
   STATUS     mandatory
   DESCRIPTION
     "This attribute indicates whether the path for this PLC was 
      determined automatically or by static provisioning. Normal 
      pathTypes are selected automatically by Route Selector.The other 
      pathTypes are both manual pathTypes where the operator must 
      specify, through provisioning, a static route termed the manualPath. 
      A manual pathType connection is nearly identical to a normal path 
      type connection with the exception that the route is pre-provisioned. 
      For a manual pathType, bandwidth reservations are respected along 
      the path exactly as in a normal path. The last type, the forced 
      pathType, is also a manual path but regardless of the bandwidth 
      available the route is granted provided the trunks are operational 
      and there are sufficient Logical Channels (LChs).
      
      The forced pathType could result in over committing the reserved 
      bandwidth allowed on a trunk. A better way to achieve the effects of 
      a forced pathType is to use a manual pathType with setupPriority = 
      0 and holdingPriority = 0. In this manner the path will reserve 
      correct bandwidth and it will bump other paths if required while not 
      being bumped itself."
::= { mscDclVsLCoPathDataEntry 17 }

mscDclVsLCoRetryCount OBJECT-TYPE
   SYNTAX     Unsigned32 (0..255)
   ACCESS     read-only
   STATUS     mandatory
   DESCRIPTION
     "This attribute is the count of the number of times the path chosen 
      during route selection could not be instantiated. This count should 
      be three or below if the network is performing adequately. A high 
      value indicates that the route selection is often performed using an 
      out-of-date view of available network bandwidth and/or topology.
      This attribute will only increase at the calling end of the connection.
      This attribute is reset each time a path reconnects and stops 
      counting when it reaches its maximum value."
::= { mscDclVsLCoPathDataEntry 18 }

mscDclVsLCoPathFailureCount OBJECT-TYPE
   SYNTAX     Unsigned32 (0..65535)
   ACCESS     read-only
   STATUS     mandatory
   DESCRIPTION
     "This attribute is the count of the number of times the path has 
      successfully connected. It is set to zero the first time the path is up. 
      If a path fails anytime after connecting this count will be 
      incremented when the path is up again. Failed route requests do not 
      count in this statistic. See retryCount above. This attribute stops 
      counting at its maximum value."
::= { mscDclVsLCoPathDataEntry 19 }

mscDclVsLCoReasonForNoRoute OBJECT-TYPE
   SYNTAX     INTEGER  {
                 none(0),
                 destinationNameTooLong(1),
                 destinationNotSpecified(2),
                 unknownDestinationName(3),
                 incorrectDestination(4),
                 incorrectDestinationEndPoint(5),
                 unknownSource(6),
                 unknownDestination(7),
                 sameNode(8),
                 routeCostTooMuch(9),
                 routesDelayTooLong(10),
                 attributesNotMet(11),
                 anError(12),
                 attributeProfileProblem(13),
                 manualPathIndexProblem(14) }
   ACCESS     read-only
   STATUS     mandatory
   DESCRIPTION
     "This attribute is the route selection's reasonForNoRoute and 
      provides a brief reason for which a route was not selected. The 
      reasons are essentially self-explanatory. Perhaps two reasons for no 
      route require some explanation. The reason 
      unknownRemoteNodeName is issued when the remote node name 
      is not in the topological database. The reason plcAttributesNotMet 
      is issued when there is no network connectivity at a level specified 
      by the PLC attributes. This reason is also issued when there is no 
      physical connectivity between two end nodes."
   DEFVAL     { none }
::= { mscDclVsLCoPathDataEntry 20 }

mscDclVsLCoLastTearDownReason OBJECT-TYPE
   SYNTAX     INTEGER  {
                 none(0),
                 normalShutDown(1),
                 insufficientTxLcOrBandwidth(2),
                 insufficientRxLcOrBandwidth(3),
                 trunkFailure(4),
                 trunkCardFailure(5),
                 operatorForced(6),
                 lostLcnClash(7),
                 networkCongestion(8),
                 trunkNotFound(9),
                 farEndNotFound(10),
                 wrongModuleReached(11),
                 farEndBusy(12),
                 callLoopedBack(13),
                 unknownReason(14),
                 farEndNotReady(15),
                 remoteNameMismatch(16),
                 serviceTypeMismatch(17),
                 reconnectFromFarEnd(18),
                 bumped(19),
                 accessCardFailure(20),
                 optimized(21),
                 overrideRemoteName(22),
                 trunkOrFarEndDidNotSupportMode(23) }
   ACCESS     read-only
   STATUS     mandatory
   DESCRIPTION
     "This attribute reflects the last tear down reason for a connection 
      (LCo). In many cases this displays the reason for a momentary 
      service interruption. This attribute applies to the last path failure 
      only. If a path is no longer up, this may give an indication to the 
      reason that the path has failed. In many cases an alarm will also be 
      generated with more specific information. The following is a brief 
      description of the reasons:
      none - This path has no information for the teardown this is typical 
      of a path provisioned with no remoteName that has not been up.
      normalShutDown - This path has gone down due to normal call 
      termination.
      insufficientTxLcOrBandwidth - At present there is either no 
      available bandwidth or logical channel numbers available on one or 
      more of the trunks for this path in the transmit direction.
      insufficientRxLcOrBandwidth - At present there is either no 
      available bandwidth or logical channel numbers available on one or 
      more of the trunks for this path in the receive direction.
      trunkFailure- A trunk on the path has failed or has gone down due 
      to a provisioning change of a critical attribute.
      trunkCardFailure- A trunk FP card has failed along the path.
      accessCardFailure- The FP on which the peer access service was 
      running has failed.
      operatorForced- The path has terminated due to the operator 
      locking a trunk along the path.
      lostLcnClash- The path has terminated because the PA's at both 
      ends of an intermediate trunk have allocated the same LC to 
      different calls. When this happens both calls must go down and then 
      try to come up again a fraction of a second later (effectively 
      ensuring that they will now be assigned different LC's). It is normal 
      to get the odd clash especially when the PA's usedLC is 
      approaching the PA's maxLC.
      networkCongestion - The path has failed due to control information 
      being lost and not recoverable.
      trunkNotFound - Occurs on a manual path usually. Check for 
      trunks not up or names provisioned incorrectly.
      farEndNotFound - The far end is not provisioned or is not up. 
      Check remote Name.
      wrongModuleReached - This may occur on a manual path. Check 
      provisioning for correct trunk and service names. For a normal 
      path, the network Topology may be changing check remoteName.
      farEndBusy - The far end has been reached but it is busy. Check 
      remoteName and remote end provisioning.
      callLoopedBack - This LCo is provisioned to call itself. Re-
      provision since this is invalid.
      unknownReason - The failure was not resolved.
      farEndNotReady - The remote end was reached but the connection 
      was refused due to the remote end not being enabled.
      remoteNameMismatch - The remote end has alarmed and rejected 
      this setup due to remoteName provisioning.
      serviceTypeMismatch - The remote Service Type does not match 
      this service type. Check provisioning.
      reconnectFromFarEnd - The remote end re-established this 
      connection. Check the remote end lastTearDownReason to 
      determine the real reason.
      bumped - Another call bumped this path from a trunk to get 
      bandwidth (or an LC) which it required to come up. This other path 
      had a higher setupPriority than this path's holdingPriority hence it 
      was allowed to steal the bandwidth (or LC) from this path.
      optimized - This call has been rerouted due to the optimization 
      feature. The call is still active this just indicates why the path 
      changed.
      trunkOrFarEndDidNotSupportMode - This call was unable to 
      complete because a mode required by the service was not supported 
      by one of the trunks the route went through or by the far end service 
      it connected to. Currently the only mode that this applies to is the 
      map/mux mode on TRUNK PA ATM component. Map mode was 
      required by the application (CES/FrAtm etc.) but was not available 
      on the TRUNK PA ATM component through which the call was 
      routed or the far end CES/FrAtm component did not specify the 
      same mode."
   DEFVAL     { none }
::= { mscDclVsLCoPathDataEntry 21 }

mscDclVsLCoPathFailureAction OBJECT-TYPE
   SYNTAX     INTEGER  {
                 disconnectConnection(0),
                 reRoutePath(1) }
   ACCESS     read-only
   STATUS     mandatory
   DESCRIPTION
     "This attribute displays whether the application is set to tolerate 
      momentary interruption of a path while a new path is selected. If 
      disconnectConnection is displayed, the application is informed as 
      soon as possible about a failure by disconnection. If the attribute 
      displays reRoutePath, the path may attempt an immediate reroute, 
      provided the failure is a recoverable failure. If rerouting fails the 
      application is informed of the failure. 
      With this option set to reRoutePath the LCo may wait up to 30 
      seconds before informing the service of complete disconnection in 
      order to allow both ends to attempt to reconnect. Note that if PLC 
      components are different at both ends only the calling end is 
      allowed to reconnect.
      
      All pathTypes respect this attribute. Also on a manualPath with 
      both ends provisioned with independent paths (at least with respect 
      to the failure) this option will have the desired effect that the path is 
      rerouted without complete disconnection at both ends"
::= { mscDclVsLCoPathDataEntry 22 }

mscDclVsLCoBumpPreference OBJECT-TYPE
   SYNTAX     INTEGER  {
                 bumpWhenNecessary(0),
                 bumpToObtainBestRoute(1) }
   ACCESS     read-only
   STATUS     mandatory
   DESCRIPTION
     "This attribute specifies when bumping will occur during route 
      selection process. Bumping may occur when necessary or always. It 
      will be necessary for a connection to bump if there is not enough 
      resources for the connection to be established and these resources 
      are occupied by a connection whose setupPriority is lower 
      (numerically higher) than the connection's setupPriority. A 
      connection may also always bump in order to obtain the best route."
::= { mscDclVsLCoPathDataEntry 23 }

mscDclVsLCoOptimization OBJECT-TYPE
   SYNTAX     INTEGER  {
                 disabled(0),
                 enabled(1) }
   ACCESS     read-only
   STATUS     mandatory
   DESCRIPTION
     "This attribute is used to specify whether this connection should 
      attempt to optimize its path when requested by the routing PORS 
      component. Every path is as optimal as it can be when it is 
      established, but as network traffic patterns and configurations 
      change this path may no longer be as optimal as it could be. The 
      PORS connection manager on a module requests circuits to 
      optimize at the optimization interval."
::= { mscDclVsLCoPathDataEntry 24 }

mscDclVsLCoPathUpDateTime OBJECT-TYPE
   SYNTAX     EnterpriseDateAndTime (SIZE (0 | 19))
   ACCESS     read-only
   STATUS     mandatory
   DESCRIPTION
     "This is the time stamp when the current path was established or 
      reestablished."
::= { mscDclVsLCoPathDataEntry 25 }

mscDclVsLCoStatsTable OBJECT-TYPE
   SYNTAX     SEQUENCE OF MscDclVsLCoStatsEntry
   ACCESS     not-accessible
   STATUS     mandatory
   DESCRIPTION
     "This group contains the operational statistics attributes for the path 
      oriented LCo."
::= { mscDclVsLCo 11 }

mscDclVsLCoStatsEntry OBJECT-TYPE
   SYNTAX     MscDclVsLCoStatsEntry
   ACCESS     not-accessible
   STATUS     mandatory
   DESCRIPTION
     "An entry in the mscDclVsLCoStatsTable."
   INDEX {
      mscDclIndex,
      mscDclVsIndex,
      mscDclVsLCoIndex }
::= { mscDclVsLCoStatsTable 1 }

MscDclVsLCoStatsEntry ::= SEQUENCE {
   mscDclVsLCoPktsToNetwork
      PassportCounter64,
   mscDclVsLCoBytesToNetwork
      PassportCounter64,
   mscDclVsLCoPktsFromNetwork
      PassportCounter64,
   mscDclVsLCoBytesFromNetwork
      PassportCounter64 }

mscDclVsLCoPktsToNetwork OBJECT-TYPE
   SYNTAX     PassportCounter64 
   ACCESS     read-only
   STATUS     mandatory
   DESCRIPTION
     "This attribute counts the number of packets transmitted to the 
      network over this Logical Connection."
::= { mscDclVsLCoStatsEntry 1 }

mscDclVsLCoBytesToNetwork OBJECT-TYPE
   SYNTAX     PassportCounter64 
   ACCESS     read-only
   STATUS     mandatory
   DESCRIPTION
     "This attribute counts the number of bytes sent to the network over 
      this Logical Connection."
::= { mscDclVsLCoStatsEntry 2 }

mscDclVsLCoPktsFromNetwork OBJECT-TYPE
   SYNTAX     PassportCounter64 
   ACCESS     read-only
   STATUS     mandatory
   DESCRIPTION
     "This attribute counts the number of packets received from the 
      remote LCo via the network."
::= { mscDclVsLCoStatsEntry 3 }

mscDclVsLCoBytesFromNetwork OBJECT-TYPE
   SYNTAX     PassportCounter64 
   ACCESS     read-only
   STATUS     mandatory
   DESCRIPTION
     "This attribute counts the number of bytes received from the remote 
      LCo via the network."
::= { mscDclVsLCoStatsEntry 4 }

mscDclVsLCoPathTable OBJECT-TYPE
   SYNTAX     SEQUENCE OF MscDclVsLCoPathEntry
   ACCESS     not-accessible
   STATUS     mandatory
   DESCRIPTION
     "This attribute contains the trunk component names over which the 
      path has been instantiated and the remote end point name 
      terminating the path."
::= { mscDclVsLCo 264 }

mscDclVsLCoPathEntry OBJECT-TYPE
   SYNTAX     MscDclVsLCoPathEntry
   ACCESS     not-accessible
   STATUS     mandatory
   DESCRIPTION
     "An entry in the mscDclVsLCoPathTable."
   INDEX {
      mscDclIndex,
      mscDclVsIndex,
      mscDclVsLCoIndex,
      mscDclVsLCoPathValue }
::= { mscDclVsLCoPathTable 1 }

MscDclVsLCoPathEntry ::= SEQUENCE {
   mscDclVsLCoPathValue
      AsciiString }

mscDclVsLCoPathValue OBJECT-TYPE
   SYNTAX     AsciiString (SIZE (0..40))
   ACCESS     read-only
   STATUS     mandatory
   DESCRIPTION
     "This variable represents both the value and the index for the
      mscDclVsLCoPathTable."
::= { mscDclVsLCoPathEntry 1 }




-- 
-- Version and Compliance statements
-- 



-- Object-Group Statement:
-- A list of all current accessible leaf objects.

-- OBJECTS { mscDcmeProfilePathFailureAction,
--           mscDcmeProfileVoiceEncoding,
--           mscDcmeProfileRequiredTrafficType,
--           mscDcmeProfileHoldingPriority,
--           mscDcmeProfileComfortNoiseCap,
--           mscDcmeProfileMaximumAcceptableDelay,
--           mscDclVsStatus,
--           mscDcmeProfileMaximumAcceptableCost,
--           mscDclStorageType,
--           mscDcmeUsageState,
--           mscDclRejected3kHzCalls,
--           mscDclVsLCoSetupPriority,
--           mscDclTransmittedTrmSignal,
--           mscDclDnaComponentName,
--           mscDclVsFramerVfpDebugComponentName,
--           mscDcmeProfilePermittedTrunkTypes,
--           mscDclVsLCoBytesFromNetwork,
--           mscDclReceivedTrmSignal,
--           mscDclVsLCoRowStatus,
--           mscDclFramerAdminState,
--           mscDclVsLCoOptimization,
--           mscDcmeUnrestricted64kAlarmThreshold,
--           mscDclVsFramerCurrentRate,
--           mscDclVsFramerRowStatus,
--           mscDcmeTrm64kNotAvailable,
--           mscDcmeOperationalState,
--           mscDclAdminState,
--           mscDclVsFramerFrmFromNetworkValue,
--           mscDclFramerRowStatus,
--           mscDcmeTrmSpeechNotAvailable,
--           mscDcmeProfileFaxIdleSuppressionG711G726,
--           mscDclVsLCoCostMetric,
--           mscDclRowStatus,
--           mscDclVsLCoLastTearDownReason,
--           mscDclVsLCoRetryCount,
--           mscDclVsLCoEmissionPriority,
--           mscDclVsFramerComponentName,
--           mscDclVsFramerNEncodingValue,
--           mscDclFramerUsageState,
--           mscDcmeProfileSpeechHangoverTime,
--           mscDclVsComponentName,
--           mscDclVsFramerNegotiatedV17AsG711G726,
--           mscDcmeAlarmTimeInterval,
--           mscDcmeProfileBumpPreference,
--           mscDclUsageState,
--           mscDclVsLCoBytesToNetwork,
--           mscDcmeProfileMaxModemFaxG711G726Rate,
--           mscDclVsReceivedAbBits,
--           mscDclFramerInterfaceName,
--           mscDcmeProfileDtmfRegeneration,
--           mscDcmeProfileIngressAudioGain,
--           mscDclVsFramerSilenceCells,
--           mscDcmeProfileSilenceSuppression,
--           mscDclFramerOperationalState,
--           mscDcmeProfileV17EncodedAsG711G726,
--           mscDclVsFramerMvpDebugRowStatus,
--           mscDclActive3kHzCalls,
--           mscDclVsFramerFrmUnderRuns,
--           mscDclOperationalState,
--           mscDclDnaDataNetworkAddress,
--           mscDcmeTrmSignalChangeInterval,
--           mscDcmeDLinksRowStatus,
--           mscDcmeProfileEgressAudioGain,
--           mscDclVsLCoPktsToNetwork,
--           mscDclVsLCoRequiredSecurity,
--           mscDclVsLCoPathFailureCount,
--           mscDclDnaStorageType,
--           mscDcmeProfileComponentName,
--           mscDcmeProfileMinModemFaxG711G726Rate,
--           mscDclVsLCoOverrideRemoteName,
--           mscDcmeDLinksValue,
--           mscDclIdlePattern,
--           mscDclVsLCoReasonForNoRoute,
--           mscDclVsLCoDiscardPriority,
--           mscDcmeTrmThreshold,
--           mscDclRejectedSpeechCalls,
--           mscDclVsFramerFrmToNetworkValue,
--           mscDclVsLCoPathFailureAction,
--           mscDclVsFramerNegotiatedFisG711G726,
--           mscDclVsLCoRequiredTxBandwidth,
--           mscDclVsLCoHoldingPriority,
--           mscDclTotal3kHzCalls,
--           mscDclVsFramerStorageType,
--           mscDclVsFramerVfpDebugStorageType,
--           mscDclCommentText,
--           mscDclVsFramerPcmCaptureRowStatus,
--           mscDclVsLCoPathType,
--           mscDclVsStorageType,
--           mscDclDnaRowStatus,
--           mscDclVsVsType,
--           mscDclFramerStorageType,
--           mscDclVsLCoEnd,
--           mscDcmeProfileMinVoiceBitRate,
--           mscDclVsLCoPermittedTrunkTypes,
--           mscDcmeProfileModemFaxSpeechDiscrim,
--           mscDclVsFramerAdminState,
--           mscDclVsFramerFaxRelayCells,
--           mscDcmeComponentName,
--           mscDclVsLCoRoundTripDelay,
--           mscDcmeProfileStorageType,
--           mscDclVsAdminState,
--           mscDclVsUsageState,
--           mscDcmeProfileRequiredSecurity,
--           mscDclDnaNumberingPlanIndicator,
--           mscDclVsLCoRequiredRxBandwidth,
--           mscDclVsFramerMvpDebugComponentName,
--           mscDclVsFramerOpCurrentEncoding,
--           mscDclVsFramerFaxIdleCells,
--           mscDclActive64kCalls,
--           mscDclVsRowStatus,
--           mscDcmeProfileSetupPriority,
--           mscDclDcme,
--           mscDcmeProfileOptimization,
--           mscDclActiveSpeechCalls,
--           mscDcmeProfileMaxVoiceBitRate,
--           mscDclVsTransmittedAbBits,
--           mscDclVsFramerUsageState,
--           mscDclVsFramerTotalCells,
--           mscDclInvalidTrmSignals,
--           mscDclVsLCoPktsFromNetwork,
--           mscDclVsLCoDelayMetric,
--           mscDclRemoteDna,
--           mscDcmeProfileSilenceSuppressionFactor,
--           mscDclVsFramerFrmLostInNetwork,
--           mscDcmeProfileRowStatus,
--           mscDcmeSpeechAlarmThreshold,
--           mscDclVsLCoPathUpDateTime,
--           mscDcmeActiveDcmeLinksValue,
--           mscDclAlternateIdlePattern,
--           mscDcmeMaxUnrestricted64kCalls,
--           mscDclFramerComponentName,
--           mscDclVsFramerNegotiatedTandemPassThrough,
--           mscDcmeProfileEmissionPriority,
--           mscDclVsFramerOperationalState,
--           mscDclVsFramerFrmDumped,
--           mscDcmeProfileModemFaxEncoding,
--           mscDclComponentName,
--           mscDcmeCommentText,
--           mscDclVsLCoRequiredTrafficType,
--           mscDclTotal64kCalls,
--           mscDclVsLCoBumpPreference,
--           mscDcmeProfileEchoCancellation,
--           mscDclVsFramerMvpDebugStorageType,
--           mscDclVsFramerOpTptStatus,
--           mscDclVsLCoPathValue,
--           mscDclTotalSpeechCalls,
--           mscDclRejected64kCalls,
--           mscDcmeProfileRequiredCustomerParm,
--           mscDclVsFramerVfpDebugRowStatus,
--           mscDclVsFramerLrcErrors,
--           mscDclVsOperationalState,
--           mscDcmeProfileDiscardPriority,
--           mscDclVsFramerNegotiatedSilenceSuppression,
--           mscDcmeStorageType,
--           mscDclVsLCoComponentName,
--           mscDclRemoteNpi,
--           mscDclVsLCoRequiredCustomerParameter,
--           mscDclVsFramerModemFaxCells,
--           mscDcmeProfileMaxFaxRelayRate,
--           mscDclVsFramerInterfaceName,
--           mscDclVsFramerPcmCaptureComponentName,
--           mscDclVsFramerPcmCaptureStorageType,
--           mscDclVsLCoState,
--           mscDcmePreestablishedConnections,
--           mscDcmeAudio3kHzAlarmThreshold,
--           mscDclVsTotalCalls,
--           mscDclVsFramerAudioCells,
--           mscDcmeAdminState,
--           mscDcmeProfileInsertedOutputDelay,
--           mscDclVsFramerNegotiatedDtmfRegeneration,
--           mscDcmeProfileVoiceTrafficOptimization,
--           mscDclVsTotalCallSeconds,
--           mscDcmeProfilePathAttributeToMinimize,
--           mscDcmeRowStatus,
--           mscDclVsCallType,
--           mscDclVsFramerNRatesValue,
--           mscDclVsLCoStorageType,
--           mscDclVsInvalidAbBits }
-- STATUS  mandatory
-- DESCRIPTION
--   "A list of all current accessible leaf objects."

dcmeGroup OBJECT IDENTIFIER ::= { dcmeMIB 1 }
dcmeGroupCA OBJECT IDENTIFIER ::= { dcmeGroup 1 }
dcmeGroupCA02 OBJECT IDENTIFIER ::= { dcmeGroupCA 3 }
dcmeGroupCA02A OBJECT IDENTIFIER ::= { dcmeGroupCA02 2 }



-- Agent-Capabilities Statement:

-- PRODUCT-RELEASE "MscPassport Release 1.2 Dcme."
-- STATUS          mandatory
-- DESCRIPTION     "Carrier Passport Dcme MIB: MIB Version CA02A,
--                  Software Version CA02S9C."
-- SUPPORTS        Nortel-MsCarrier-MscPassport-DcmeMIB
--    INCLUDES     { dcmeGroupCA02A }

dcmeCapabilities OBJECT IDENTIFIER ::= { dcmeMIB 3 }
dcmeCapabilitiesCA OBJECT IDENTIFIER ::= { dcmeCapabilities 1 }
dcmeCapabilitiesCA02 OBJECT IDENTIFIER ::= { dcmeCapabilitiesCA 3 }
dcmeCapabilitiesCA02A OBJECT IDENTIFIER ::= { dcmeCapabilitiesCA02 2 }





END
