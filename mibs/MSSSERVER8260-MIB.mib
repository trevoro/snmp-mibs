MSSSERVER8260-MIB DEFINITIONS ::= BEGIN

IMPORTS
   OBJECT-TYPE
         FROM RFC-1212
   proElsSubSysEventMsg
         FROM PROTEON-MIB
   enterprises
         FROM RFC1155-SMI
   TRAP-TYPE
         FROM RFC-1215;

--  MSSSERVER8260-MIB MODULE-IDENTITY
--            LAST-UPDATED "9711101200Z"
--            ORGANIZATION "IBM Corporation"
--            CONTACT-INFO
--            " Florian K Kandefer
--               Postal:  IBM Corporation
--                        800 Park Offices Drive
--                        Research Triangle Park, NC 27709
--                        US
--               Tel:     +1 919 254 0685
--               Fax:     +1 919 254 0391
--               E-mail:  kandefer@vnet.ibm.com     "
--            DESCRIPTION
--             " MSS Server 8260 Enterprise MIB
--
--               This MIB defines the enterprise specific management objects
--               IBM Nways Multiprotocol Switched Services Server (MSS Server
--               blade that uses the 8260 backplane).
--
--               This MIB is defined in the SNMP version 1 SMI format.
--
--               MIB Version:
--
--                1)  This is the first version of this MIB "
--                2)  Added PCMCIA definition for notPresent
--                3)  Added PCMCIA definition for FLASH card
-- ===============
-- | Definitions |
-- ===============

--  PC adapter indicates a PCMCIA adapter.

-- =============
-- | Reminders |
-- =============

-- o The DisplayString data type is ASCII characters.
-- o An implementation that conforms to this MIB shall implement all
--   variables for each mandatory group.
-- o If an Optional Group is implemented, all variables of that group
--   must be implemented.

-- ========
-- | OID's|
-- ========

ibm            OBJECT IDENTIFIER ::= { enterprises 2 }

ibmProd        OBJECT IDENTIFIER ::= { ibm 6 }

nwaysMSS       OBJECT IDENTIFIER ::= { ibmProd 118 }

mssServer8260  OBJECT IDENTIFIER ::= { nwaysMSS 3 }

-- ===============================
-- | Groups in MSSSERVER8260-MIB |
-- ===============================

mss8260Prod         OBJECT IDENTIFIER ::= { mssServer8260 1 }

mss8260PCAdapter    OBJECT IDENTIFIER ::= { mssServer8260 2 }


-- =====================
-- || The mss8260Prod ||
-- =====================
-- The mss8260Prod group is MANDATORY for all implementations of the
-- MSSSERVER8260-MIB. All implementations that claim conformance to this
-- MIB shall implement this group.

mss8260ResetFlag  OBJECT-TYPE
   SYNTAX  INTEGER {
           noreset (1),
           reboot  (2)}
   ACCESS  read-write
   STATUS  mandatory
   DESCRIPTION
        "The flag that controls the reset process in this blade.
        This variable shall assume a value of noreset(1) in
        the absence of a request for a reset from the management
        application. This variable shall assume a value of reboot(2) if the
        management application requests that this blade execute
        a complete hardware reboot which reloads the code load from
        storage."
   DEFVAL { noreset }
   ::= {mss8260Prod 1}

mss8260DRAMinstalled  OBJECT-TYPE
   SYNTAX  INTEGER
   ACCESS  read-only
   STATUS  mandatory
   DESCRIPTION
        "The total amount of dynamic RAM installed on this blade.
        The amount is in units of megabytes."
   ::= {mss8260Prod 2}

mss8260NotifyStatus  OBJECT-TYPE
   SYNTAX  INTEGER {
           enabled  (1),
           disabled (2)}
   ACCESS  read-write
   STATUS  mandatory
   DESCRIPTION
        "The status of the trap reporting service in this blade. This
        variable shall assume a value of enabled(1) if this blade is
        permitted to send traps. This variable shall assume a value of
        disabled(2) if this blade is prohibited from sending traps."
   DEFVAL { enabled }
   ::= {mss8260Prod 3}

mss8260TempThresholdStatus  OBJECT-TYPE
   SYNTAX  INTEGER {
           normal   (1),
           warning  (2),
           shutdown (3)}
   ACCESS  read-only
   STATUS  mandatory
   DESCRIPTION
        "The status of the temperature in this blade. This variable
        shall assume a value of normal(1) if the temperature is within
        proper operating range for this blade. This variable shall
        assume a value of warning(2) if the temperature becomes elevated
        but this blade can still operate. This variable shall assume
        a value of shutdown(3) if the temperature is beyond the operating
        limits of this blade."
   ::= {mss8260Prod 4}


-- ================================
-- || The mss8260PCAdapter group ||
-- ================================
-- The mss8260PCAdapter group is MANDATORY for all implementations of the
-- MSSSERVER8260-MIB. All implementations that claim conformance to this
-- MIB shall implement this group.

mss8260PCAdapNumSlot  OBJECT-TYPE
   SYNTAX  INTEGER
   ACCESS  read-only
   STATUS  mandatory
   DESCRIPTION
        "The number of PC adapter slots available for this blade."
   ::= {mss8260PCAdapter 1}

mss8260PCAdapTable  OBJECT-TYPE
   SYNTAX  SEQUENCE OF Mss8260PCAdapEntry
   ACCESS  not-accessible
   STATUS  mandatory
   DESCRIPTION
        "A table of PC adapters entries. The number of entries is
        given by the value of mss8260PCAdapNumSlot."
   ::= {mss8260PCAdapter 2}

mss8260PCAdapEntry   OBJECT-TYPE
   SYNTAX  Mss8260PCAdapEntry
   ACCESS  not-accessible
   STATUS  mandatory
   DESCRIPTION
        "A PC adapter entry containing objects to describe the
        operational aspects of the PC adapter on this blade."
   INDEX  {mss8260PCAdapSlotNum}
   ::= {mss8260PCAdapTable 1}

Mss8260PCAdapEntry  ::=
   SEQUENCE {
        mss8260PCAdapSlotNum
           INTEGER,
        mss8260PCAdapType
           INTEGER
   }

mss8260PCAdapSlotNum   OBJECT-TYPE
   SYNTAX  INTEGER
   ACCESS  read-only
   STATUS  mandatory
   DESCRIPTION
        "The relative slot location at which the adapter is attached to
        this blade.  Slots are numbered from 1 to 2 (bottom to top)
        when facing this blade. This variable serves as the index
        for the mss8260PCAdapTable."
   ::= {mss8260PCAdapEntry 1}

mss8260PCAdapType  OBJECT-TYPE
   SYNTAX  INTEGER {
           unknown     (1),
           harddrive   (2),
           modem       (3),
           notPresent  (4),
           flashcard   (5)}
   ACCESS  read-only
   STATUS  mandatory
   DESCRIPTION
        "The type of PC adapter that is inserted into this slot.
        The variable shall assume a value of unknown(1) if the adapter
        in the slot is not supported by this blade. The variable
        shall assume a value of harddrive(2) if the slot contains a PC disk
        drive. The variable shall assume a value of modem(3) if the
        slot contains a PC data/fax/voice modem. The variable shall
        assume a value of flashcard(5) if the slot contains a PC flash card.
        This variable shall assume a value of notPresent(4), when a
        PC card is not plugged into the corrisponding slot.
        "
   ::= {mss8260PCAdapEntry 2}

-- ======================
-- || Trap Definitions ||
-- ======================

mssServer8260ELSTrapV2  TRAP-TYPE
   ENTERPRISE   mssServer8260
    VARIABLES    { proElsSubSysEventMsg }
    DESCRIPTION
        "The trap announces an Event Logging System (ELS) event
        occurred. The variable proElsSubSysEventMsg provides a textual
        description of the event. The variable is in one of two
        formats. If ELS timestamping is enabled, the format is
        hr:min:sec subsys_name.event_num: message_text. An example
        would be 09:32:56 IP.008: no rte 9.7.1.8 -> 9.7.4.3 dsc.
        If ELS timestamping is disabled, the format is
        subsys_name.event_num: message_text. An example would be
        IP.008: no rte 9.7.1.8 -> 9.7.4.3 dsc."
   ::= 2

mss8260PCAdapTypeChg  TRAP-TYPE
   ENTERPRISE   mssServer8260
    VARIABLES    { mss8260PCAdapType }
    DESCRIPTION
        "The trap announces a change in the type of PC card. It shall be
        sent if the value of the mss8260PCAdapType changes and
        mss8260NotifyStatus has a value of enabled(1)."
   ::= 3

mss8260TempThresholdChg TRAP-TYPE
   ENTERPRISE   mssServer8260
   VARIABLES    { mss8260TempThresholdStatus }
   DESCRIPTION
        "The trap announces a change in the temperature of the blade.
        It shall be sent if the value of the mss8260TempThreshold changes
        and mss8260NotifyStatus has a value of enabled(1)."
   ::= 4

END
