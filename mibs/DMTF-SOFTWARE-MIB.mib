DMTF-SOFTWARE-MIB DEFINITIONS ::= BEGIN

IMPORTS
	OBJECT-TYPE, NOTIFICATION-TYPE,
	MODULE-IDENTITY, enterprises, Counter32, Counter64, Gauge32, Integer32
		FROM SNMPv2-SMI
	Dmi-Date,DmiString,
	dmiEventDateTime,dmiCompId,dmiEventSeverity,
	dmiEventStateKey,dmiEventAssociatedGroup,
	dmiEventSystem,dmiEventSubSystem
		FROM DMTF-DMI-MIB;

DmiCounter		::= Counter32
DmiCounter64		::= Counter64
DmiGauge		::= Gauge32
DmiInteger		::= Integer32
DmiOctetstring		::= OCTET STRING
DmiCompId		::= INTEGER
DmiGroupId		::= INTEGER

dmtf                	OBJECT IDENTIFIER ::= { enterprises 412 }
dmtfStdMifs         	OBJECT IDENTIFIER ::= { dmtf 2 }
dmtfDynOids         	OBJECT IDENTIFIER ::= { dmtf 3 }


dmtfSoftwareMIF MODULE-IDENTITY
     LAST-UPDATED "9710221800Z"
     ORGANIZATION "Desktop Management Task Force"
     CONTACT-INFO
          "         DMTF Technical Advisory Committee

		    Mailstop JF2-53
                    2111 N.E. 25th Avenue
                    Hillsboro, OR 97124

		    Phone: +1 503 264-9300
                    Email: dmtf-info@dmtf.org
          "
     DESCRIPTION
          "This MIB is a translation of the DMTF Software MIF,
          based on the translation rules defined by the
          DMTF DMI to SNMP Mapping Standard, Version 1.0.

	  DMI-based systems running a DMI-to-SNMP Mapping
          Agent provide the ability to access DMI component
          instrumentation via SNMP protocol operations.
          "
::= { dmtfStdMifs 3 }

SdmtfAttributeDependencies ::= SEQUENCE {
	dmtfAttributeDependenciesState INTEGER,
	index	DmiInteger,
	class	DmiString,
	attributeID	DmiInteger,
	minimumValue	DmiString,
	maximumValue	DmiString,
	dependencyType	DmiInteger,
	setNumber	DmiInteger
}

dmtfAttributeDependenciesTable OBJECT-TYPE
	SYNTAX		SEQUENCE OF SdmtfAttributeDependencies
	MAX-ACCESS	not-accessible
	STATUS		current
	DESCRIPTION	"This group identifies dependencies that this component has
on the value of attributes in particular groups."
	::= { dmtfSoftwareMIF 10 }

dmtfAttributeDependenciesEntry OBJECT-TYPE
	SYNTAX		SdmtfAttributeDependencies
	MAX-ACCESS	not-accessible
	STATUS		current
	DESCRIPTION	"This group identifies dependencies that this component has
on the value of attributes in particular groups."
	INDEX		{ DmiCompId,DmiGroupId, index }
	::= { dmtfAttributeDependenciesTable 1 }


dmtfAttributeDependenciesState OBJECT-TYPE
	SYNTAX		INTEGER {
		active(1),
		notInService(2),
		notReady(3),
		createAndGo(4),
		createAndWait(5),
		destroy(6)
	}
	MAX-ACCESS	read-write
	STATUS		current
	REFERENCE "'DMTF|Attribute Dependencies|001' 0"
	::= { dmtfAttributeDependenciesEntry 0 }

index OBJECT-TYPE
	SYNTAX		DmiInteger
	MAX-ACCESS	read-only
	STATUS		current
	DESCRIPTION	"Index of this attribute dependency entry."
	REFERENCE "'DMTF|Attribute Dependencies|001' 1"
	::= { dmtfAttributeDependenciesEntry 1 }

class OBJECT-TYPE
	SYNTAX		DmiString
	MAX-ACCESS	read-only
	STATUS		current
	DESCRIPTION	"Class string for the group containing the dependent attribute."
	REFERENCE "'DMTF|Attribute Dependencies|001' 2"
	::= { dmtfAttributeDependenciesEntry 2 }

attributeID OBJECT-TYPE
	SYNTAX		DmiInteger
	MAX-ACCESS	read-only
	STATUS		current
	DESCRIPTION	"Attribute identifier for the dependent attribute."
	REFERENCE "'DMTF|Attribute Dependencies|001' 3"
	::= { dmtfAttributeDependenciesEntry 3 }

minimumValue OBJECT-TYPE
	SYNTAX		DmiString
	MAX-ACCESS	read-only
	STATUS		current
	DESCRIPTION	"Minimum value for this dependent attribute."
	REFERENCE "'DMTF|Attribute Dependencies|001' 4"
	::= { dmtfAttributeDependenciesEntry 4 }

maximumValue OBJECT-TYPE
	SYNTAX		DmiString
	MAX-ACCESS	read-only
	STATUS		current
	DESCRIPTION	"Maximum value for this dependent attribute."
	REFERENCE "'DMTF|Attribute Dependencies|001' 5"
	::= { dmtfAttributeDependenciesEntry 5 }

dependencyType OBJECT-TYPE
	SYNTAX		INTEGER {
		excluded(1),
		required(2),
		oneOfASetRequired(3)
	}
	MAX-ACCESS	read-only
	STATUS		current
	DESCRIPTION	"The type of this dependency."
	REFERENCE "'DMTF|Attribute Dependencies|001' 6"
	::= { dmtfAttributeDependenciesEntry 6 }

setNumber OBJECT-TYPE
	SYNTAX		DmiInteger
	MAX-ACCESS	read-only
	STATUS		current
	DESCRIPTION	"The number of the set to which this dependency belongs."
	REFERENCE "'DMTF|Attribute Dependencies|001' 7"
	::= { dmtfAttributeDependenciesEntry 7 }

SdmtfComponentDependencies ::= SEQUENCE {
	dmtfComponentDependenciesState INTEGER,
	index	DmiInteger,
	manufacturer	DmiString,
	product	DmiString,
	minimumVersion	DmiString,
	maximumVersion	DmiString,
	dependencyType	DmiInteger,
	setNumber	DmiInteger
}

dmtfComponentDependenciesTable OBJECT-TYPE
	SYNTAX		SEQUENCE OF SdmtfComponentDependencies
	MAX-ACCESS	not-accessible
	STATUS		current
	DESCRIPTION	"This group identifies dependencies this component has on
other components."
	::= { dmtfSoftwareMIF 9 }

dmtfComponentDependenciesEntry OBJECT-TYPE
	SYNTAX		SdmtfComponentDependencies
	MAX-ACCESS	not-accessible
	STATUS		current
	DESCRIPTION	"This group identifies dependencies this component has on
other components."
	INDEX		{ DmiCompId,DmiGroupId, index }
	::= { dmtfComponentDependenciesTable 1 }


dmtfComponentDependenciesState OBJECT-TYPE
	SYNTAX		INTEGER {
		active(1),
		notInService(2),
		notReady(3),
		createAndGo(4),
		createAndWait(5),
		destroy(6)
	}
	MAX-ACCESS	read-write
	STATUS		current
	REFERENCE "'DMTF|Component Dependencies|001' 0"
	::= { dmtfComponentDependenciesEntry 0 }

index OBJECT-TYPE
	SYNTAX		DmiInteger
	MAX-ACCESS	read-only
	STATUS		current
	DESCRIPTION	"Index of this component dependency entry."
	REFERENCE "'DMTF|Component Dependencies|001' 1"
	::= { dmtfComponentDependenciesEntry 1 }

manufacturer OBJECT-TYPE
	SYNTAX		DmiString
	MAX-ACCESS	read-only
	STATUS		current
	DESCRIPTION	"Manufacturer of dependent product."
	REFERENCE "'DMTF|Component Dependencies|001' 2"
	::= { dmtfComponentDependenciesEntry 2 }

product OBJECT-TYPE
	SYNTAX		DmiString
	MAX-ACCESS	read-only
	STATUS		current
	DESCRIPTION	"Name of dependent product."
	REFERENCE "'DMTF|Component Dependencies|001' 3"
	::= { dmtfComponentDependenciesEntry 3 }

minimumVersion OBJECT-TYPE
	SYNTAX		DmiString
	MAX-ACCESS	read-only
	STATUS		current
	DESCRIPTION	"Minimum version of dependent component."
	REFERENCE "'DMTF|Component Dependencies|001' 4"
	::= { dmtfComponentDependenciesEntry 4 }

maximumVersion OBJECT-TYPE
	SYNTAX		DmiString
	MAX-ACCESS	read-only
	STATUS		current
	DESCRIPTION	"Maximum version of dependent component."
	REFERENCE "'DMTF|Component Dependencies|001' 5"
	::= { dmtfComponentDependenciesEntry 5 }

dependencyType OBJECT-TYPE
	SYNTAX		INTEGER {
		excluded(1),
		required(2),
		oneOfASetRequired(3)
	}
	MAX-ACCESS	read-only
	STATUS		current
	DESCRIPTION	"The type of this dependency."
	REFERENCE "'DMTF|Component Dependencies|001' 6"
	::= { dmtfComponentDependenciesEntry 6 }

setNumber OBJECT-TYPE
	SYNTAX		DmiInteger
	MAX-ACCESS	read-only
	STATUS		current
	DESCRIPTION	"The number of the set to which this dependency belongs."
	REFERENCE "'DMTF|Component Dependencies|001' 7"
	::= { dmtfComponentDependenciesEntry 7 }

SdmtfEquivalence ::= SEQUENCE {
	dmtfEquivalenceState INTEGER,
	index	DmiInteger,
	manufacturer	DmiString,
	product	DmiString,
	minimumVersion	DmiString,
	maximumVersion	DmiString
}

dmtfEquivalenceTable OBJECT-TYPE
	SYNTAX		SEQUENCE OF SdmtfEquivalence
	MAX-ACCESS	not-accessible
	STATUS		current
	DESCRIPTION	"This group identifies equivalent components."
	::= { dmtfSoftwareMIF 4 }

dmtfEquivalenceEntry OBJECT-TYPE
	SYNTAX		SdmtfEquivalence
	MAX-ACCESS	not-accessible
	STATUS		current
	DESCRIPTION	"This group identifies equivalent components."
	INDEX		{ DmiCompId,DmiGroupId, index }
	::= { dmtfEquivalenceTable 1 }


dmtfEquivalenceState OBJECT-TYPE
	SYNTAX		INTEGER {
		active(1),
		notInService(2),
		notReady(3),
		createAndGo(4),
		createAndWait(5),
		destroy(6)
	}
	MAX-ACCESS	read-write
	STATUS		current
	REFERENCE "'DMTF|Equivalence|001' 0"
	::= { dmtfEquivalenceEntry 0 }

index OBJECT-TYPE
	SYNTAX		DmiInteger
	MAX-ACCESS	read-only
	STATUS		current
	DESCRIPTION	"Index of this equivalence entry"
	REFERENCE "'DMTF|Equivalence|001' 1"
	::= { dmtfEquivalenceEntry 1 }

manufacturer OBJECT-TYPE
	SYNTAX		DmiString
	MAX-ACCESS	read-only
	STATUS		current
	DESCRIPTION	"Manufacturer of equivalent product."
	REFERENCE "'DMTF|Equivalence|001' 2"
	::= { dmtfEquivalenceEntry 2 }

product OBJECT-TYPE
	SYNTAX		DmiString
	MAX-ACCESS	read-only
	STATUS		current
	DESCRIPTION	"Name of equivalent product."
	REFERENCE "'DMTF|Equivalence|001' 3"
	::= { dmtfEquivalenceEntry 3 }

minimumVersion OBJECT-TYPE
	SYNTAX		DmiString
	MAX-ACCESS	read-only
	STATUS		current
	DESCRIPTION	"Minimum version of the equivalent product."
	REFERENCE "'DMTF|Equivalence|001' 4"
	::= { dmtfEquivalenceEntry 4 }

maximumVersion OBJECT-TYPE
	SYNTAX		DmiString
	MAX-ACCESS	read-only
	STATUS		current
	DESCRIPTION	"Maximum version of the equivalent product."
	REFERENCE "'DMTF|Equivalence|001' 5"
	::= { dmtfEquivalenceEntry 5 }

SdmtfFileList ::= SEQUENCE {
	dmtfFileListState INTEGER,
	locationIndex	DmiInteger,
	fileName	DmiString,
	description	DmiString
}

dmtfFileListTable OBJECT-TYPE
	SYNTAX		SEQUENCE OF SdmtfFileList
	MAX-ACCESS	not-accessible
	STATUS		current
	DESCRIPTION	"This group describes the files included in this software
product."
	::= { dmtfSoftwareMIF 11 }

dmtfFileListEntry OBJECT-TYPE
	SYNTAX		SdmtfFileList
	MAX-ACCESS	not-accessible
	STATUS		current
	DESCRIPTION	"This group describes the files included in this software
product."
	INDEX		{ DmiCompId,DmiGroupId, locationIndex, fileName }
	::= { dmtfFileListTable 1 }


dmtfFileListState OBJECT-TYPE
	SYNTAX		INTEGER {
		active(1),
		notInService(2),
		notReady(3),
		createAndGo(4),
		createAndWait(5),
		destroy(6)
	}
	MAX-ACCESS	read-write
	STATUS		current
	REFERENCE "'DMTF|File List|001' 0"
	::= { dmtfFileListEntry 0 }

locationIndex OBJECT-TYPE
	SYNTAX		DmiInteger
	MAX-ACCESS	read-only
	STATUS		current
	DESCRIPTION	"The location of this file as an index into the location table."
	REFERENCE "'DMTF|File List|001' 1"
	::= { dmtfFileListEntry 1 }

fileName OBJECT-TYPE
	SYNTAX		DmiString
	MAX-ACCESS	read-only
	STATUS		current
	DESCRIPTION	"The name of this file."
	REFERENCE "'DMTF|File List|001' 2"
	::= { dmtfFileListEntry 2 }

description OBJECT-TYPE
	SYNTAX		DmiString
	MAX-ACCESS	read-only
	STATUS		current
	DESCRIPTION	"Description of this file."
	REFERENCE "'DMTF|File List|001' 3"
	::= { dmtfFileListEntry 3 }

SdmtfInstallationLogFiles ::= SEQUENCE {
	dmtfInstallationLogFilesState INTEGER,
	locationIndex	DmiInteger,
	fileName	DmiString,
	description	DmiString
}

dmtfInstallationLogFilesTable OBJECT-TYPE
	SYNTAX		SEQUENCE OF SdmtfInstallationLogFiles
	MAX-ACCESS	not-accessible
	STATUS		current
	DESCRIPTION	"This group describes installation log files used by this
software component."
	::= { dmtfSoftwareMIF 13 }

dmtfInstallationLogFilesEntry OBJECT-TYPE
	SYNTAX		SdmtfInstallationLogFiles
	MAX-ACCESS	not-accessible
	STATUS		current
	DESCRIPTION	"This group describes installation log files used by this
software component."
	INDEX		{ DmiCompId,DmiGroupId, locationIndex, fileName }
	::= { dmtfInstallationLogFilesTable 1 }


dmtfInstallationLogFilesState OBJECT-TYPE
	SYNTAX		INTEGER {
		active(1),
		notInService(2),
		notReady(3),
		createAndGo(4),
		createAndWait(5),
		destroy(6)
	}
	MAX-ACCESS	read-write
	STATUS		current
	REFERENCE "'DMTF|Installation Log Files|001' 0"
	::= { dmtfInstallationLogFilesEntry 0 }

locationIndex OBJECT-TYPE
	SYNTAX		DmiInteger
	MAX-ACCESS	read-only
	STATUS		current
	DESCRIPTION	"The location of this log file, as an index into the location
table."
	REFERENCE "'DMTF|Installation Log Files|001' 1"
	::= { dmtfInstallationLogFilesEntry 1 }

fileName OBJECT-TYPE
	SYNTAX		DmiString
	MAX-ACCESS	read-only
	STATUS		current
	DESCRIPTION	"The unqualified file name of this log file."
	REFERENCE "'DMTF|Installation Log Files|001' 2"
	::= { dmtfInstallationLogFilesEntry 2 }

description OBJECT-TYPE
	SYNTAX		DmiString
	MAX-ACCESS	read-only
	STATUS		current
	DESCRIPTION	"Description of this log file."
	REFERENCE "'DMTF|Installation Log Files|001' 3"
	::= { dmtfInstallationLogFilesEntry 3 }

SdmtfInstallation ::= SEQUENCE {
	dmtfInstallationState INTEGER,
	installationType	DmiInteger,
	installationIdentifier	DmiString,
	description	DmiString,
	installedSize	DmiInteger,
	commandLine	DmiString,
	locationIndex	DmiInteger
}

dmtfInstallationTable OBJECT-TYPE
	SYNTAX		SEQUENCE OF SdmtfInstallation
	MAX-ACCESS	not-accessible
	STATUS		current
	DESCRIPTION	"This group contains information to allow installation, updating
and de-installation of this software component."
	::= { dmtfSoftwareMIF 12 }

dmtfInstallationEntry OBJECT-TYPE
	SYNTAX		SdmtfInstallation
	MAX-ACCESS	not-accessible
	STATUS		current
	DESCRIPTION	"This group contains information to allow installation, updating
and de-installation of this software component."
	INDEX		{ DmiCompId,DmiGroupId, installationType, installationIdentifier }
	::= { dmtfInstallationTable 1 }


dmtfInstallationState OBJECT-TYPE
	SYNTAX		INTEGER {
		active(1),
		notInService(2),
		notReady(3),
		createAndGo(4),
		createAndWait(5),
		destroy(6)
	}
	MAX-ACCESS	read-write
	STATUS		current
	REFERENCE "'DMTF|Installation|001' 0"
	::= { dmtfInstallationEntry 0 }

installationType OBJECT-TYPE
	SYNTAX		INTEGER {
		other(1),
		install(2),
		deInstall(3)
	}
	MAX-ACCESS	read-only
	STATUS		current
	DESCRIPTION	"The type of this installation process."
	REFERENCE "'DMTF|Installation|001' 1"
	::= { dmtfInstallationEntry 1 }

installationIdentifier OBJECT-TYPE
	SYNTAX		DmiString
	MAX-ACCESS	read-only
	STATUS		current
	DESCRIPTION	"The name of this installation process."
	REFERENCE "'DMTF|Installation|001' 2"
	::= { dmtfInstallationEntry 2 }

description OBJECT-TYPE
	SYNTAX		DmiString
	MAX-ACCESS	read-only
	STATUS		current
	DESCRIPTION	"Explanatory text about this installation process."
	REFERENCE "'DMTF|Installation|001' 3"
	::= { dmtfInstallationEntry 3 }

installedSize OBJECT-TYPE
	SYNTAX		DmiInteger
	MAX-ACCESS	read-only
	STATUS		current
	DESCRIPTION	"For an install procedure, the disk space used by this product
in kilobytes. For a de-install procedure, the disk space freed by this procedure
in kilobytes."
	REFERENCE "'DMTF|Installation|001' 4"
	::= { dmtfInstallationEntry 4 }

commandLine OBJECT-TYPE
	SYNTAX		DmiString
	MAX-ACCESS	read-only
	STATUS		current
	DESCRIPTION	"Executable name and parameters for install or de-install."
	REFERENCE "'DMTF|Installation|001' 5"
	::= { dmtfInstallationEntry 5 }

locationIndex OBJECT-TYPE
	SYNTAX		DmiInteger
	MAX-ACCESS	read-only
	STATUS		current
	DESCRIPTION	"Index into location table for the executable specified in
Command Line."
	REFERENCE "'DMTF|Installation|001' 6"
	::= { dmtfInstallationEntry 6 }

SdmtfLocation ::= SEQUENCE {
	dmtfLocationState INTEGER,
	index	DmiInteger,
	locationType	DmiInteger,
	path	DmiString
}

dmtfLocationTable OBJECT-TYPE
	SYNTAX		SEQUENCE OF SdmtfLocation
	MAX-ACCESS	not-accessible
	STATUS		current
	DESCRIPTION	"This group identifies the various locations where parts of
a software product have been installed."
	::= { dmtfSoftwareMIF 3 }

dmtfLocationEntry OBJECT-TYPE
	SYNTAX		SdmtfLocation
	MAX-ACCESS	not-accessible
	STATUS		current
	DESCRIPTION	"This group identifies the various locations where parts of
a software product have been installed."
	INDEX		{ DmiCompId,DmiGroupId, index }
	::= { dmtfLocationTable 1 }


dmtfLocationState OBJECT-TYPE
	SYNTAX		INTEGER {
		active(1),
		notInService(2),
		notReady(3),
		createAndGo(4),
		createAndWait(5),
		destroy(6)
	}
	MAX-ACCESS	read-write
	STATUS		current
	REFERENCE "'DMTF|Location|001' 0"
	::= { dmtfLocationEntry 0 }

index OBJECT-TYPE
	SYNTAX		DmiInteger
	MAX-ACCESS	read-only
	STATUS		current
	DESCRIPTION	"Index of this location entry."
	REFERENCE "'DMTF|Location|001' 1"
	::= { dmtfLocationEntry 1 }

locationType OBJECT-TYPE
	SYNTAX		INTEGER {
		unknown(1),
		other(2),
		productBaseDirectory(3),
		productExecutablesDirectory(4),
		productLibraryDirectory(5),
		productConfigurationDirectory(6),
		productIncludeDirectory(7),
		productWorkingDirectory(8),
		productLogDirectory(9),
		sharedBaseDirectory(10),
		sharedExecutablesDirectory(11),
		sharedLibraryDirectory(12),
		sharedIncludeDirectory(13),
		systemBaseDirectory(14),
		systemExecutablesDirectory(15),
		systemLibraryDirectory(16),
		systemConfigurationDirectory(17),
		systemIncludeDirectory(18),
		systemLogDirectory(19)
	}
	MAX-ACCESS	read-only
	STATUS		current
	DESCRIPTION	"The type of this location entry"
	REFERENCE "'DMTF|Location|001' 2"
	::= { dmtfLocationEntry 2 }

path OBJECT-TYPE
	SYNTAX		DmiString
	MAX-ACCESS	read-write
	STATUS		current
	DESCRIPTION	"The path to this location."
	REFERENCE "'DMTF|Location|001' 3"
	::= { dmtfLocationEntry 3 }

SdmtfMaintenance ::= SEQUENCE {
	manufacturer	DmiString,
	product	DmiString,
	version	DmiString,
	componentID	DmiInteger
}

dmtfMaintenanceTable OBJECT-TYPE
	SYNTAX		SEQUENCE OF SdmtfMaintenance
	MAX-ACCESS	not-accessible
	STATUS		current
	DESCRIPTION	"This group identifies the component to which this maintenance
is applied."
	::= { dmtfSoftwareMIF 6 }

dmtfMaintenanceEntry OBJECT-TYPE
	SYNTAX		SdmtfMaintenance
	MAX-ACCESS	not-accessible
	STATUS		current
	DESCRIPTION	"This group identifies the component to which this maintenance
is applied."
	INDEX		{ DmiCompId,DmiGroupId }
	::= { dmtfMaintenanceTable 1 }


manufacturer OBJECT-TYPE
	SYNTAX		DmiString
	MAX-ACCESS	read-only
	STATUS		current
	DESCRIPTION	"Manufacturer of updated component."
	REFERENCE "'DMTF|Maintenance|001' 1"
	::= { dmtfMaintenanceEntry 1 }

product OBJECT-TYPE
	SYNTAX		DmiString
	MAX-ACCESS	read-only
	STATUS		current
	DESCRIPTION	"Product name for updated component."
	REFERENCE "'DMTF|Maintenance|001' 2"
	::= { dmtfMaintenanceEntry 2 }

version OBJECT-TYPE
	SYNTAX		DmiString
	MAX-ACCESS	read-only
	STATUS		current
	DESCRIPTION	"Version number for updated component."
	REFERENCE "'DMTF|Maintenance|001' 3"
	::= { dmtfMaintenanceEntry 3 }

componentID OBJECT-TYPE
	SYNTAX		DmiInteger
	MAX-ACCESS	read-only
	STATUS		current
	DESCRIPTION	"Component ID of updated component."
	REFERENCE "'DMTF|Maintenance|001' 4"
	::= { dmtfMaintenanceEntry 4 }

SdmtfSoftwareComponentInformation ::= SEQUENCE {
	majorVersion	DmiString,
	minorVersion	DmiString,
	revision	DmiString,
	build	DmiString,
	targetOperatingSystem	DmiInteger,
	languageEdition	DmiString,
	identificationCode	DmiString,
	installableState	DmiInteger,
	executableState	DmiInteger
}

dmtfSoftwareComponentInformationTable OBJECT-TYPE
	SYNTAX		SEQUENCE OF SdmtfSoftwareComponentInformation
	MAX-ACCESS	not-accessible
	STATUS		current
	DESCRIPTION	"Contains additional identifying information about this software
component."
	::= { dmtfSoftwareMIF 1 }

dmtfSoftwareComponentInformationEntry OBJECT-TYPE
	SYNTAX		SdmtfSoftwareComponentInformation
	MAX-ACCESS	not-accessible
	STATUS		current
	DESCRIPTION	"Contains additional identifying information about this software
component."
	INDEX		{ DmiCompId,DmiGroupId }
	::= { dmtfSoftwareComponentInformationTable 1 }


majorVersion OBJECT-TYPE
	SYNTAX		DmiString
	MAX-ACCESS	read-only
	STATUS		current
	DESCRIPTION	"Major version of this software component."
	REFERENCE "'DMTF|Software Component Information|002' 1"
	::= { dmtfSoftwareComponentInformationEntry 1 }

minorVersion OBJECT-TYPE
	SYNTAX		DmiString
	MAX-ACCESS	read-only
	STATUS		current
	DESCRIPTION	"Minor version of this software component."
	REFERENCE "'DMTF|Software Component Information|002' 2"
	::= { dmtfSoftwareComponentInformationEntry 2 }

revision OBJECT-TYPE
	SYNTAX		DmiString
	MAX-ACCESS	read-only
	STATUS		current
	DESCRIPTION	"Revision of this software component."
	REFERENCE "'DMTF|Software Component Information|002' 3"
	::= { dmtfSoftwareComponentInformationEntry 3 }

build OBJECT-TYPE
	SYNTAX		DmiString
	MAX-ACCESS	read-only
	STATUS		current
	DESCRIPTION	"Manufacturers internal identifier for this compilation."
	REFERENCE "'DMTF|Software Component Information|002' 4"
	::= { dmtfSoftwareComponentInformationEntry 4 }

targetOperatingSystem OBJECT-TYPE
	SYNTAX		INTEGER {
		other(0),
		dOS(1),
		mACOS(2),
		oS2(3),
		uNIX(4),
		wIN16(5),
		wIN32(6),
		oPENVMS(7),
		netWare(8),
		wIN9x(9),
		wINNT(10)
	}
	MAX-ACCESS	read-only
	STATUS		current
	DESCRIPTION	"The operating system for which this software component is
intended."
	REFERENCE "'DMTF|Software Component Information|002' 5"
	::= { dmtfSoftwareComponentInformationEntry 5 }

languageEdition OBJECT-TYPE
	SYNTAX		DmiString
	MAX-ACCESS	read-only
	STATUS		current
	DESCRIPTION	"This identifies the language edition of this component."
	REFERENCE "'DMTF|Software Component Information|002' 6"
	::= { dmtfSoftwareComponentInformationEntry 6 }

identificationCode OBJECT-TYPE
	SYNTAX		DmiString
	MAX-ACCESS	read-only
	STATUS		current
	DESCRIPTION	"Stock Keeping Unit (SKU) or Part Number for this software
component."
	REFERENCE "'DMTF|Software Component Information|002' 7"
	::= { dmtfSoftwareComponentInformationEntry 7 }

installableState OBJECT-TYPE
	SYNTAX		INTEGER {
		unknown(1),
		installable(2),
		notInstallable(3)
	}
	MAX-ACCESS	read-only
	STATUS		current
	DESCRIPTION	"Specifies whether this component describes a software product
installed for the purpose of further distribution."
	REFERENCE "'DMTF|Software Component Information|002' 8"
	::= { dmtfSoftwareComponentInformationEntry 8 }

executableState OBJECT-TYPE
	SYNTAX		INTEGER {
		unknown(1),
		executable(2),
		notExecutable(3)
	}
	MAX-ACCESS	read-only
	STATUS		current
	DESCRIPTION	"Specifies whether this component describes a software product
which is executable."
	REFERENCE "'DMTF|Software Component Information|002' 9"
	::= { dmtfSoftwareComponentInformationEntry 9 }

SdmtfSoftwareSignature ::= SEQUENCE {
	dmtfSoftwareSignatureState INTEGER,
	fileName	DmiString,
	fileSize	DmiInteger,
	fileDateAndTime	Dmi-Date,
	fileChecksum	DmiInteger,
	fileCRC1	DmiInteger,
	fileCRC2	DmiInteger,
	fileLocation	DmiInteger
}

dmtfSoftwareSignatureTable OBJECT-TYPE
	SYNTAX		SEQUENCE OF SdmtfSoftwareSignature
	MAX-ACCESS	not-accessible
	STATUS		current
	DESCRIPTION	"The Software Signature Group contains information that can
be used to detect this software component."
	::= { dmtfSoftwareMIF 2 }

dmtfSoftwareSignatureEntry OBJECT-TYPE
	SYNTAX		SdmtfSoftwareSignature
	MAX-ACCESS	not-accessible
	STATUS		current
	DESCRIPTION	"The Software Signature Group contains information that can
be used to detect this software component."
	INDEX		{ DmiCompId,DmiGroupId, fileName, fileLocation }
	::= { dmtfSoftwareSignatureTable 1 }


dmtfSoftwareSignatureState OBJECT-TYPE
	SYNTAX		INTEGER {
		active(1),
		notInService(2),
		notReady(3),
		createAndGo(4),
		createAndWait(5),
		destroy(6)
	}
	MAX-ACCESS	read-write
	STATUS		current
	REFERENCE "'DMTF|Software Signature|002' 0"
	::= { dmtfSoftwareSignatureEntry 0 }

fileName OBJECT-TYPE
	SYNTAX		DmiString
	MAX-ACCESS	read-only
	STATUS		current
	DESCRIPTION	"The name of a file that can be examined to detect this software
component."
	REFERENCE "'DMTF|Software Signature|002' 1"
	::= { dmtfSoftwareSignatureEntry 1 }

fileSize OBJECT-TYPE
	SYNTAX		DmiInteger
	MAX-ACCESS	read-only
	STATUS		current
	DESCRIPTION	"The size in bytes of a file that can be examined to detect
this software component."
	REFERENCE "'DMTF|Software Signature|002' 2"
	::= { dmtfSoftwareSignatureEntry 2 }

fileDateAndTime OBJECT-TYPE
	SYNTAX		Dmi-Date
	MAX-ACCESS	read-only
	STATUS		current
	DESCRIPTION	"The date and time of a file that can be examined to detect
this software component."
	REFERENCE "'DMTF|Software Signature|002' 3"
	::= { dmtfSoftwareSignatureEntry 3 }

fileChecksum OBJECT-TYPE
	SYNTAX		DmiInteger
	MAX-ACCESS	read-only
	STATUS		current
	DESCRIPTION	"The checksum for the first 32 bytes of this file."
	REFERENCE "'DMTF|Software Signature|002' 4"
	::= { dmtfSoftwareSignatureEntry 4 }

fileCRC1 OBJECT-TYPE
	SYNTAX		DmiInteger
	MAX-ACCESS	read-only
	STATUS		current
	DESCRIPTION	"The 16-bit CRC (ITU-T) on the middle 512k of this file."
	REFERENCE "'DMTF|Software Signature|002' 5"
	::= { dmtfSoftwareSignatureEntry 5 }

fileCRC2 OBJECT-TYPE
	SYNTAX		DmiInteger
	MAX-ACCESS	read-only
	STATUS		current
	DESCRIPTION	"The 16-bit CRC (ITU-T) on the middle 512k of this file, modulo
3."
	REFERENCE "'DMTF|Software Signature|002' 6"
	::= { dmtfSoftwareSignatureEntry 6 }

fileLocation OBJECT-TYPE
	SYNTAX		DmiInteger
	MAX-ACCESS	read-only
	STATUS		current
	DESCRIPTION	"The location of this file, as an index into the location
table."
	REFERENCE "'DMTF|Software Signature|002' 7"
	::= { dmtfSoftwareSignatureEntry 7 }

SdmtfSubcomponents ::= SEQUENCE {
	dmtfSubcomponentsState INTEGER,
	manufacturer	DmiString,
	product	DmiString,
	version	DmiString,
	componentID	DmiInteger,
	installationInformation	DmiString
}

dmtfSubcomponentsTable OBJECT-TYPE
	SYNTAX		SEQUENCE OF SdmtfSubcomponents
	MAX-ACCESS	not-accessible
	STATUS		current
	DESCRIPTION	"This group identifies subcomponents of this component."
	::= { dmtfSoftwareMIF 8 }

dmtfSubcomponentsEntry OBJECT-TYPE
	SYNTAX		SdmtfSubcomponents
	MAX-ACCESS	not-accessible
	STATUS		current
	DESCRIPTION	"This group identifies subcomponents of this component."
	INDEX		{ DmiCompId,DmiGroupId, manufacturer, product, version }
	::= { dmtfSubcomponentsTable 1 }


dmtfSubcomponentsState OBJECT-TYPE
	SYNTAX		INTEGER {
		active(1),
		notInService(2),
		notReady(3),
		createAndGo(4),
		createAndWait(5),
		destroy(6)
	}
	MAX-ACCESS	read-write
	STATUS		current
	REFERENCE "'DMTF|Subcomponents|001' 0"
	::= { dmtfSubcomponentsEntry 0 }

manufacturer OBJECT-TYPE
	SYNTAX		DmiString
	MAX-ACCESS	read-only
	STATUS		current
	DESCRIPTION	"Manufacturer of this subcomponent."
	REFERENCE "'DMTF|Subcomponents|001' 1"
	::= { dmtfSubcomponentsEntry 1 }

product OBJECT-TYPE
	SYNTAX		DmiString
	MAX-ACCESS	read-only
	STATUS		current
	DESCRIPTION	"Name of this subcomponent."
	REFERENCE "'DMTF|Subcomponents|001' 2"
	::= { dmtfSubcomponentsEntry 2 }

version OBJECT-TYPE
	SYNTAX		DmiString
	MAX-ACCESS	read-only
	STATUS		current
	DESCRIPTION	"Version of this subcomponent."
	REFERENCE "'DMTF|Subcomponents|001' 3"
	::= { dmtfSubcomponentsEntry 3 }

componentID OBJECT-TYPE
	SYNTAX		DmiInteger
	MAX-ACCESS	read-write
	STATUS		current
	DESCRIPTION	"ComponentID of subcomponent after installation. A zero value
indicates that this subcomponent is not installed."
	REFERENCE "'DMTF|Subcomponents|001' 4"
	::= { dmtfSubcomponentsEntry 4 }

installationInformation OBJECT-TYPE
	SYNTAX		DmiString
	MAX-ACCESS	read-only
	STATUS		current
	DESCRIPTION	"Instructions used to install this subcomponent."
	REFERENCE "'DMTF|Subcomponents|001' 5"
	::= { dmtfSubcomponentsEntry 5 }

SdmtfSupersededComponents ::= SEQUENCE {
	dmtfSupersededComponentsState INTEGER,
	index	DmiInteger,
	manufacturer	DmiString,
	product	DmiString,
	minimumVersion	DmiString,
	maximumVersion	DmiString
}

dmtfSupersededComponentsTable OBJECT-TYPE
	SYNTAX		SEQUENCE OF SdmtfSupersededComponents
	MAX-ACCESS	not-accessible
	STATUS		current
	DESCRIPTION	"This group identifies superseded components."
	::= { dmtfSoftwareMIF 5 }

dmtfSupersededComponentsEntry OBJECT-TYPE
	SYNTAX		SdmtfSupersededComponents
	MAX-ACCESS	not-accessible
	STATUS		current
	DESCRIPTION	"This group identifies superseded components."
	INDEX		{ DmiCompId,DmiGroupId, index }
	::= { dmtfSupersededComponentsTable 1 }


dmtfSupersededComponentsState OBJECT-TYPE
	SYNTAX		INTEGER {
		active(1),
		notInService(2),
		notReady(3),
		createAndGo(4),
		createAndWait(5),
		destroy(6)
	}
	MAX-ACCESS	read-write
	STATUS		current
	REFERENCE "'DMTF|Superseded Components|001' 0"
	::= { dmtfSupersededComponentsEntry 0 }

index OBJECT-TYPE
	SYNTAX		DmiInteger
	MAX-ACCESS	read-only
	STATUS		current
	DESCRIPTION	"Index of this superseded component entry."
	REFERENCE "'DMTF|Superseded Components|001' 1"
	::= { dmtfSupersededComponentsEntry 1 }

manufacturer OBJECT-TYPE
	SYNTAX		DmiString
	MAX-ACCESS	read-only
	STATUS		current
	DESCRIPTION	"Manufacturer of superseded component."
	REFERENCE "'DMTF|Superseded Components|001' 2"
	::= { dmtfSupersededComponentsEntry 2 }

product OBJECT-TYPE
	SYNTAX		DmiString
	MAX-ACCESS	read-only
	STATUS		current
	DESCRIPTION	"Name of superseded component."
	REFERENCE "'DMTF|Superseded Components|001' 3"
	::= { dmtfSupersededComponentsEntry 3 }

minimumVersion OBJECT-TYPE
	SYNTAX		DmiString
	MAX-ACCESS	read-only
	STATUS		current
	DESCRIPTION	"Minimum version of the superseded component."
	REFERENCE "'DMTF|Superseded Components|001' 4"
	::= { dmtfSupersededComponentsEntry 4 }

maximumVersion OBJECT-TYPE
	SYNTAX		DmiString
	MAX-ACCESS	read-only
	STATUS		current
	DESCRIPTION	"Maximum version of the superseded component."
	REFERENCE "'DMTF|Superseded Components|001' 5"
	::= { dmtfSupersededComponentsEntry 5 }

SdmtfSupport ::= SEQUENCE {
	dmtfSupportState INTEGER,
	index	DmiInteger,
	locale	DmiString,
	description	DmiString,
	contactInformation	DmiString,
	supportType	DmiInteger
}

dmtfSupportTable OBJECT-TYPE
	SYNTAX		SEQUENCE OF SdmtfSupport
	MAX-ACCESS	not-accessible
	STATUS		current
	DESCRIPTION	"This group contains information about obtaining product service."
	::= { dmtfSoftwareMIF 14 }

dmtfSupportEntry OBJECT-TYPE
	SYNTAX		SdmtfSupport
	MAX-ACCESS	not-accessible
	STATUS		current
	DESCRIPTION	"This group contains information about obtaining product service."
	INDEX		{ DmiCompId,DmiGroupId, index }
	::= { dmtfSupportTable 1 }


dmtfSupportState OBJECT-TYPE
	SYNTAX		INTEGER {
		active(1),
		notInService(2),
		notReady(3),
		createAndGo(4),
		createAndWait(5),
		destroy(6)
	}
	MAX-ACCESS	read-write
	STATUS		current
	REFERENCE "'DMTF|Support|001' 0"
	::= { dmtfSupportEntry 0 }

index OBJECT-TYPE
	SYNTAX		DmiInteger
	MAX-ACCESS	read-only
	STATUS		current
	DESCRIPTION	"Index of this support entry."
	REFERENCE "'DMTF|Support|001' 1"
	::= { dmtfSupportEntry 1 }

locale OBJECT-TYPE
	SYNTAX		DmiString
	MAX-ACCESS	read-only
	STATUS		current
	DESCRIPTION	"Locale where this support resource is applicable."
	REFERENCE "'DMTF|Support|001' 2"
	::= { dmtfSupportEntry 2 }

description OBJECT-TYPE
	SYNTAX		DmiString
	MAX-ACCESS	read-only
	STATUS		current
	DESCRIPTION	"Description of this support resource."
	REFERENCE "'DMTF|Support|001' 3"
	::= { dmtfSupportEntry 3 }

contactInformation OBJECT-TYPE
	SYNTAX		DmiString
	MAX-ACCESS	read-only
	STATUS		current
	DESCRIPTION	"Contact information for this support resource."
	REFERENCE "'DMTF|Support|001' 4"
	::= { dmtfSupportEntry 4 }

supportType OBJECT-TYPE
	SYNTAX		INTEGER {
		other(1),
		phone(2),
		fax(3),
		bBS(4),
		onlineService(5),
		webPage(6),
		fTP(7),
		eMail(8)
	}
	MAX-ACCESS	read-only
	STATUS		current
	DESCRIPTION	"Type of this support resource."
	REFERENCE "'DMTF|Support|001' 5"
	::= { dmtfSupportEntry 5 }

SdmtfVerification ::= SEQUENCE {
	requestedTestLevel	DmiInteger,
	highestPossibleResult	DmiInteger,
	testResult	DmiInteger,
	testDate	Dmi-Date,
	testMessage	DmiString
}

dmtfVerificationTable OBJECT-TYPE
	SYNTAX		SEQUENCE OF SdmtfVerification
	MAX-ACCESS	not-accessible
	STATUS		current
	DESCRIPTION	"This group will verify the possible existence and/or correct
operation of the component."
	::= { dmtfSoftwareMIF 7 }

dmtfVerificationEntry OBJECT-TYPE
	SYNTAX		SdmtfVerification
	MAX-ACCESS	not-accessible
	STATUS		current
	DESCRIPTION	"This group will verify the possible existence and/or correct
operation of the component."
	INDEX		{ DmiCompId,DmiGroupId }
	::= { dmtfVerificationTable 1 }


requestedTestLevel OBJECT-TYPE
	SYNTAX		INTEGER {
		noneVerificationTestingDisabled(1),
		minimalVerifyAllSignatureFilesArePresent(2),
		fullVerifyOperation(3)
	}
	MAX-ACCESS	read-write
	STATUS		current
	DESCRIPTION	"The verification test level that will be performed. Set this
value to 1 to disable further verification testing."
	REFERENCE "'DMTF|Verification|001' 1"
	::= { dmtfVerificationEntry 1 }

highestPossibleResult OBJECT-TYPE
	SYNTAX		INTEGER {
		failureSeeTheTestMessageForDetails(1),
		someSignatureFilesArePresent(2),
		allSignatureFilesArePresent(3),
		allFilesPresent(4),
		primaryExecutablePassesVerificationProcedure(5),
		allExecutablesPassVerificationProcedure(6)
	}
	MAX-ACCESS	read-only
	STATUS		current
	DESCRIPTION	"The highest possible verification result that can be returned
by this component."
	REFERENCE "'DMTF|Verification|001' 2"
	::= { dmtfVerificationEntry 2 }

testResult OBJECT-TYPE
	SYNTAX		INTEGER {
		failureSeeTheTestMessageForDetails(1),
		someSignatureFilesArePresent(2),
		allSignatureFilesArePresent(3),
		allFilesPresent(4),
		primaryExecutablePassesVerificationProcedure(5),
		allExecutablesPassVerificationProcedure(6)
	}
	MAX-ACCESS	read-only
	STATUS		current
	DESCRIPTION	"Verification test result returned by this component."
	REFERENCE "'DMTF|Verification|001' 3"
	::= { dmtfVerificationEntry 3 }

testDate OBJECT-TYPE
	SYNTAX		Dmi-Date
	MAX-ACCESS	read-only
	STATUS		current
	DESCRIPTION	"The date and time when the last verification test was completed."
	REFERENCE "'DMTF|Verification|001' 4"
	::= { dmtfVerificationEntry 4 }

testMessage OBJECT-TYPE
	SYNTAX		DmiString
	MAX-ACCESS	read-only
	STATUS		current
	DESCRIPTION	"Additional message reported by the verification instrumentation."
	REFERENCE "'DMTF|Verification|001' 5"
	::= { dmtfVerificationEntry 5 }

END
