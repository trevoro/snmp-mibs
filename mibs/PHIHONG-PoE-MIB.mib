-- phihong080218
-- Feb 18 08' added poeSystemStatus and poeSystemOverheatTrap

PHIHONG-PoE-MIB DEFINITIONS ::= BEGIN

IMPORTS
        MODULE-IDENTITY,OBJECT-TYPE,Gauge32,NOTIFICATION-TYPE
                FROM SNMPv2-SMI
        DisplayString,TruthValue 
                FROM SNMPv2-TC
        IpAddress, enterprises
                FROM SNMPv2-SMI; 


phihong                 OBJECT IDENTIFIER ::= { iso org(3) dod(6) internet(1) private(4) enterprises(1) 24852 }
poeProduct              OBJECT IDENTIFIER ::= { phihong 2 }


-------------------------------------------------------------------
     -- PowerOverEthernet Product group
-------------------------------------------------------------------

poeProductsPart OBJECT-TYPE
        SYNTAX  DisplayString
        MAX-ACCESS  read-only
        STATUS  current
        DESCRIPTION  
                "the POE controller Part."
        ::= { poeProduct 1 }


-------------------------------------------------------------------
poeSystem               OBJECT IDENTIFIER ::= { poeProduct 2 }

--------------- PowerOverEthernet System definitions --------------

poeSystemActionHubReset OBJECT-TYPE
        SYNTAX  INTEGER {  
                        ready(0),
                        reset(1)
                }
        MAX-ACCESS  write-only
        STATUS  current
        DESCRIPTION  
                "Reset the POE controller."
        ::= { poeSystem  1 }
        
poeSystemActionHubRestoreFactoryDefault OBJECT-TYPE
        SYNTAX  INTEGER {
                        ready(0),
                        restore(1)
                        }
        MAX-ACCESS  write-only
        STATUS  current
        DESCRIPTION  
                "Restore Factory Default to flash.
                resetpassword means when users forget the password,they can use this entry, 
                and all of the snmp module parameters will be set to default values."
        ::= { poeSystem  2 }
    
poeSystemActionHubSaveConfiguration OBJECT-TYPE
        SYNTAX  INTEGER {
                        ready(0),
                        save(1)
                }
        MAX-ACCESS  write-only
        STATUS  current
        DESCRIPTION  
                "Save the POE parameters to flash"
        ::= { poeSystem  3 }

poeSystemAllPortPowerEnable OBJECT-TYPE
        SYNTAX  INTEGER {
                        ready(0),
                        disable(1),
                        enable(2)
                }
        MAX-ACCESS  write-only
        STATUS  current
        DESCRIPTION  
                "Enables power supply in all port.
                Setting this object at a value enable(2) enables power 
                and detection mechanism for all port.
                Setting this object at a value disable(1) disables power
                for all port."
        ::= { poeSystem  4 }

poeSystemHWVersion OBJECT-TYPE
        SYNTAX  DisplayString   
        MAX-ACCESS  read-only
        STATUS  current
        DESCRIPTION  
                "System hardware version for the Main board"
        ::= { poeSystem  6 }
        
poeSystemNumberOfChannel OBJECT-TYPE
        SYNTAX  INTEGER 
        MAX-ACCESS  read-only
        STATUS  current
        DESCRIPTION  
                "Number of ports in the system"
        ::= { poeSystem  7 }

poeSystemProductPartNumber OBJECT-TYPE
        SYNTAX   DisplayString
        MAX-ACCESS  read-only
        STATUS  current
        DESCRIPTION  
                "System  Part Number for  PowerHub "
        ::= { poeSystem  8 }


         
poeSystemFirmwareVersion OBJECT-TYPE
        SYNTAX  DisplayString   
        MAX-ACCESS  read-only
        STATUS  current
        DESCRIPTION  
                "System firmware version for the POE"
        ::= { poeSystem 10 }

poeSystemDescription OBJECT-TYPE
        SYNTAX  DisplayString (SIZE (0..10))  
        MAX-ACCESS  read-write
        STATUS  current
        DESCRIPTION  
                "System Description 10 characters "
        ::= { poeSystem 11 }

poeSystemConsumptionPower OBJECT-TYPE
        SYNTAX  INTEGER
        UNITS  "Watts"
        MAX-ACCESS  read-only
        STATUS  current
        DESCRIPTION
                "Measured usage power expressed in Watts."
        ::= { poeSystem 12 }

poeSystemControlACPower OBJECT-TYPE
        SYNTAX  INTEGER    
        UNITS  "Watts"
        MAX-ACCESS  read-write
        STATUS  current
        DESCRIPTION  
                "describes the maximum available power in Watts to be 
                supplied by the AC backup source to this device."
        ::= { poeSystem 13 }

poeSystemControlDCPower OBJECT-TYPE
        SYNTAX  INTEGER    
        UNITS  "Watts"
        MAX-ACCESS  read-write
        STATUS  current
        DESCRIPTION  
                "describes the maximum available power in Watts to be 
                supplied by the DC backup source to this device."
        ::= { poeSystem 14 }

poeSystemControlBothPower OBJECT-TYPE
        SYNTAX  INTEGER    
        UNITS  "Watts"
        MAX-ACCESS  read-write
        STATUS  current
        DESCRIPTION  
                "describes the maximum available power in Watts to be 
                supplied by Both AC and DC backup source to this device."
        ::= { poeSystem 15 }

poeSystemParameters OBJECT-TYPE
        SYNTAX  DisplayString (SIZE (3))  
        MAX-ACCESS  read-write
        STATUS  current
        DESCRIPTION  
                "1st char:Knokoff enable,2nd char:AC Disconnect enable,3th char:Disable Power Management"
        ::= { poeSystem 16 }

poeSystemSnmpVersion OBJECT-TYPE
 SYNTAX  DisplayString   
 MAX-ACCESS  read-only
 STATUS  current
 DESCRIPTION  
  " The software version for the SNMP device"
 ::= { poeSystem 17 }

poeSystemPerPortPowerEnable OBJECT-TYPE
        SYNTAX  DisplayString (SIZE (48))
        MAX-ACCESS  read-write
        STATUS  current
        DESCRIPTION  
                "Enables power supply in all port.
                Setting this object at a value enable(2) enables power 
                and detection mechanism for all port.
                Setting this object at a value disable(1) disables power
                for all port."
        ::= { poeSystem  18 }

poeSystemStatus  OBJECT-TYPE
        SYNTAX  INTEGER {
                        normal(0),
                        overheat(1)
                }
        MAX-ACCESS  read-only
        STATUS  current
        DESCRIPTION  
                "The status of the POE."
        ::= { poeSystem  19 }
-------------------------------------------------------------------
poePortTable OBJECT-TYPE
        SYNTAX  SEQUENCE OF PoePortEntry
        MAX-ACCESS  not-accessible
        STATUS  current
        DESCRIPTION
                ""
        ::= { poeProduct 3 }

--------------- PowerOverEthernet Port definitions ----------------

poePortEntry OBJECT-TYPE
        SYNTAX  PoePortEntry
        MAX-ACCESS  not-accessible
        STATUS  current
        DESCRIPTION
                "port entry containing data regarding a particular port"
        INDEX   { poePortIndex } 
        ::= { poePortTable 1 }

PoePortEntry ::=
        SEQUENCE {
                poePortIndex
                        INTEGER,
                poePortPowerEnable
                        INTEGER,
                poePortControlMaxPower
                        INTEGER,
                poePortDescription
                        DisplayString,
                poePortDetectionStatus
                        INTEGER,
                poePortPowerClassifications
                        INTEGER, 
                poePortPowerDetectionControl
                        INTEGER,
                poePortPowerPriority
                        INTEGER,
                poePortPower
                        INTEGER,
                poePortVoltage
                        DisplayString,
                poePortCurrent
                        INTEGER,
                poePortResistance
                        INTEGER,
                poePortFlags
                        DisplayString,
                poePortBypassFlags
                        DisplayString,
                poePortUseClassificationforPowerLimit
                        INTEGER,
                poePortLegacyDetection
                    INTEGER
                }
poePortIndex OBJECT-TYPE
        SYNTAX  INTEGER (1..2147483647)
        MAX-ACCESS  read-only
        STATUS  current
        DESCRIPTION
                "A unique value for each port."
       ::= { poePortEntry 1 }

poePortPowerEnable OBJECT-TYPE
        SYNTAX  INTEGER {
                        disable(1),
                        enable(2)
                }
        MAX-ACCESS  read-write
        STATUS  current
        DESCRIPTION
                "Enables power supply on this port.
                Setting this object at a value enable(2) enables power 
                and detection mechanism for this port.
                Setting this object at a value disable(1) disables power
                for this port."
        ::= { poePortEntry 2 }

poePortControlMaxPower OBJECT-TYPE
        SYNTAX  INTEGER 
        UNITS "mWatts"
        MAX-ACCESS  read-write
        STATUS  current
        DESCRIPTION  
                "This command specifies the max  power in [mWatts] to that port.
                IF you set this value it will take out this port from the auto mode. 
                The value MUST be more then 0"
        ::= { poePortEntry 3 }



poePortDescription OBJECT-TYPE
        SYNTAX  DisplayString (SIZE (0..10))   
        MAX-ACCESS  read-write
        STATUS  current
        DESCRIPTION  
                "Port Description 10 characters "
        ::= { poePortEntry 6 }

poePortDetectionStatus OBJECT-TYPE
        
        SYNTAX  INTEGER {    
                        off(0),
                        discR(1), 
                discC(2),
                        class(3),
                        rampUp(4),
                        ramPOEown(5),
                        sampleI(8),
                        sampleV(9)
                        }
        MAX-ACCESS  read-only
        STATUS  current
        DESCRIPTION
                " Port Detection, show the detection status of each port"
        ::= { poePortEntry 7 }

poePortPowerClassifications OBJECT-TYPE
        SYNTAX  INTEGER {
                        class0(1),
                        class1(2),
                        class2(3),
                        class3(4),
                        class4(5)
                }
        MAX-ACCESS  read-only
        STATUS  current
        DESCRIPTION
                "Port Power Classifications, show the classification of each port"
        ::= { poePortEntry 8 }

poePortPowerDetectionControl OBJECT-TYPE
        SYNTAX  INTEGER {
                        disabled(1),
                        enabled(2)
                }
        MAX-ACCESS  read-write
        STATUS  current
        DESCRIPTION  
                "Port Power Detection Control, enable or disable the Power Limit for Management"
        ::= { poePortEntry 9 }

poePortPowerPriority OBJECT-TYPE
        SYNTAX  INTEGER {
                        critical(1),
                        high(2),
                        low(3)
                }
        MAX-ACCESS  read-write
        STATUS  current
        DESCRIPTION
                "Port Power Priority, show the priority of each port"
        ::= { poePortEntry 10 }

poePortPower OBJECT-TYPE
        SYNTAX  INTEGER 
        UNITS "mWattes"
        MAX-ACCESS  read-only
        STATUS  current
        DESCRIPTION
                "Port Actual Power (in mWattes)."
        ::= { poePortEntry 11 }

poePortVoltage OBJECT-TYPE
        SYNTAX  DisplayString
        UNITS "dVoltage"
        MAX-ACCESS  read-only
        STATUS  current
        DESCRIPTION
                "Port Voltage (in dVoltage)."
        ::= { poePortEntry 12 }

poePortCurrent OBJECT-TYPE
        SYNTAX  INTEGER 
        UNITS "mAmps"
        MAX-ACCESS  read-only
        STATUS  current
        DESCRIPTION
                "Port Current (in mAmps)."
        ::= { poePortEntry 13 }

poePortResistance OBJECT-TYPE
        SYNTAX  INTEGER 
        UNITS "ohms"
        MAX-ACCESS  read-only
        STATUS  current
        DESCRIPTION
                "Port Resistance (in ohms)."
        ::= { poePortEntry 14 }
     
poePortFlags OBJECT-TYPE
        SYNTAX  DisplayString (SIZE (5))
        MAX-ACCESS  read-only
        STATUS  current
        DESCRIPTION
                "1st char:classification(0-3),2nd char:Port bypass detection enable,3th char:Port bypass classifiation enable,4th cahr:Port bypass powerup enable,5th char:Port bypass sampling enable."
        ::= { poePortEntry 15 }
        
poePortBypassFlags OBJECT-TYPE
        SYNTAX  DisplayString (SIZE (4))
        MAX-ACCESS  read-write
        STATUS  current
        DESCRIPTION
                "1st char:Port bypass detection enable,2nd char:Port bypass classifiation enable,3th cahr:Port bypass powerup enable,4th char:Port bypass sampling enable."
        ::= { poePortEntry 16 }

poePortUseClassificationforPowerLimit OBJECT-TYPE
    SYNTAX  INTEGER {
                        disabled(1),
                        enabled(2)
                }
    MAX-ACCESS  read-write
        STATUS  current
        DESCRIPTION
         " Use Port classification for power limit , enable or disable the Port classification for power limit."
    ::= { poePortEntry 17 }

poePortLegacyDetection OBJECT-TYPE
    SYNTAX  INTEGER {
                        disabled(1),
                        enabled(2)
                }
    MAX-ACCESS  read-write
        STATUS  current
        DESCRIPTION
         " Use Port legacy detection , enable or disable the Port legacy detection."
    ::= { poePortEntry 18 }


--------------- PowerOverEthernet Port definitions ----------------


poeTrapsControlTable OBJECT-TYPE
        SYNTAX  SEQUENCE OF PoeTrapsControlEntry
        MAX-ACCESS  not-accessible
        STATUS  current
        DESCRIPTION
                "A table of objects that display and control the Traps on a PSM  device."
        ::= { poeProduct 4 }

poeTrapsControlEntry OBJECT-TYPE
        SYNTAX  PoeTrapsControlEntry
        MAX-ACCESS  not-accessible
        STATUS  current
        DESCRIPTION
                "A set of objects that control the Trap events."
        INDEX  { poeTrapsControlGroupIndex }
        ::= { poeTrapsControlTable 1 }

PoeTrapsControlEntry ::=
        SEQUENCE {
                poeTrapsControlGroupIndex
                        INTEGER,
                poeTrapsControlEnable
                        INTEGER
        }

poeTrapsControlGroupIndex OBJECT-TYPE
        SYNTAX  INTEGER (0..65535)
        MAX-ACCESS  not-accessible
        STATUS  current
        DESCRIPTION
                "This variable uniquely identifies the group."
        ::= { poeTrapsControlEntry 1 }

poeTrapsControlEnable  OBJECT-TYPE
        SYNTAX  INTEGER {
                        trapsDisabled (1),
                        trapsEnabled (2)
                }
        MAX-ACCESS  read-write
        STATUS  current
        DESCRIPTION  
                "Enable Traps from Agent"
        ::= { poeTrapsControlEntry 2 }  

--
-- Traps Section
-- 
poeTraps        OBJECT IDENTIFIER ::= { poeProduct 5 }

-- PowerOverEthernet Traps definitions 

poePortHWFailTrap NOTIFICATION-TYPE
         OBJECTS     { poeTrapsControlGroupIndex,poePortVoltage}
         STATUS      current
         DESCRIPTION "This trap indicate UV0v failure /UV0v Spike failure /Device A2d failure."
          ::= { poeTraps 1 }
poePortPeakOverCurrentTrap NOTIFICATION-TYPE
         OBJECTS     { poeTrapsControlGroupIndex,poePortCurrent }
         STATUS      current
         DESCRIPTION "This trap indicate peak over current failure."
          ::= { poeTraps 2 }
poePortOverloadTrap NOTIFICATION-TYPE
         OBJECTS     { poeTrapsControlGroupIndex,poePortDetectionStatus }
         STATUS      current
         DESCRIPTION "This trap indicate overload failure. If you put at least 400mA on the
                      output, you will see if your traps work"
          ::= { poeTraps 3 }
poePortDiscoveryFailTrap NOTIFICATION-TYPE
         OBJECTS     { poeTrapsControlGroupIndex,poePortVoltage}
         STATUS      current
         DESCRIPTION "This trap indicate Discovery failure/ Discovery VA2 failure/Discovery RA2 failure/Sample Discovery A2d Failure."
          ::= { poeTraps 4 }
poePortClassificationFailTrap NOTIFICATION-TYPE
         OBJECTS     { poeTrapsControlGroupIndex,poePortVoltage}
         STATUS      current
         DESCRIPTION "This trap indicate Class Violation failure/ Classification A2d failure."
          ::= { poeTraps 5 }
poePortDisconnectTrap NOTIFICATION-TYPE
         OBJECTS     { poeTrapsControlGroupIndex,poePortDetectionStatus }
         STATUS      current
         DESCRIPTION "This trap indicate port is disconnected."
          ::= { poeTraps 6 }
poePortVoltageFailTrap NOTIFICATION-TYPE
         OBJECTS     { poeTrapsControlGroupIndex,poePortVoltage }
         STATUS      current
         DESCRIPTION "This trap indicate if PSM Port is no voltage failure."
          ::= { poeTraps 7 }
poeSystemOverheatTrap NOTIFICATION-TYPE
         OBJECTS     { poeTrapsControlGroupIndex }
         STATUS      current
         DESCRIPTION "This trap indicate if PSM is overheat."
          ::= { poeTraps 8 }
   

END
