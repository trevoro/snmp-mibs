IBM-SYSTEM-LMSENSOR-MIB DEFINITIONS ::= BEGIN

IMPORTS
   OBJECT-TYPE
      FROM RFC-1212

   TRAP-TYPE
      FROM RFC-1215

   ibmSystemLMSensor,
   Boolean, Uint8, Sint8, Uint16, Sint16, Uint32,
   Sint32, Uint64, Sint64, Real32, Real64, String, Datetime
      FROM IBM-SYSTEM-MIB;

ibmSystemTemperatureSensorTable OBJECT-TYPE
   SYNTAX         SEQUENCE OF IbmSystemTemperatureSensorEntry
   ACCESS         not-accessible
   STATUS         mandatory
   DESCRIPTION    "The IBMPSG_TemperatureSensor class represents an IBM managed Temperature Sensor."
   REFERENCE      "IBMPSG_TemperatureSensor"
::= { ibmSystemLMSensor 1 }

ibmSystemTemperatureSensorEntry OBJECT-TYPE
   SYNTAX         IbmSystemTemperatureSensorEntry
   ACCESS         not-accessible
   STATUS         mandatory
   DESCRIPTION    "A sequence of temperature sensor entries"
   INDEX          { ibmSystemTemperatureSensorKeyIndex }
::= { ibmSystemTemperatureSensorTable 1 }

IbmSystemTemperatureSensorEntry ::= SEQUENCE
{
   ibmSystemTemperatureSensorKeyIndex String,   
   ibmSystemTemperatureSensorCurrentReading Sint32,
   ibmSystemTemperatureSensorNominalReading Sint32,
   ibmSystemTemperatureSensorNormalMax Sint32,
   ibmSystemTemperatureSensorNormalMin Sint32,
   ibmSystemTemperatureSensorMaxReadable Sint32,
   ibmSystemTemperatureSensorMinReadable Sint32,
   ibmSystemTemperatureSensorResolution Uint32,
   ibmSystemTemperatureSensorTolerance Sint32,
   ibmSystemTemperatureSensorAccuracy Sint32,
   ibmSystemTemperatureSensorLowerThresholdNonCritical Sint32,
   ibmSystemTemperatureSensorUpperThresholdNonCritical Sint32,
   ibmSystemTemperatureSensorLowerThresholdCritical Sint32,
   ibmSystemTemperatureSensorUpperThresholdCritical Sint32,
   ibmSystemTemperatureSensorLowerThresholdFatal Sint32,
   ibmSystemTemperatureSensorUpperThresholdFatal Sint32,
   ibmSystemTemperatureSensorTempLocation Uint32,
   ibmSystemTemperatureSensorEventsEnabled Boolean,
   ibmSystemTemperatureSensorPollingInterval Uint64,
   ibmSystemTemperatureSensorEventAutoClearEnabled Boolean,
   ibmSystemTemperatureSensorStatus String
}

ibmSystemTemperatureSensorKeyIndex OBJECT-TYPE
   SYNTAX         String
   ACCESS         read-only
   STATUS         mandatory
   DESCRIPTION    "The index used by this table"
   REFERENCE      "IBMPSG_TemperatureSensor.KeyIndex"
::= { ibmSystemTemperatureSensorEntry 1 }

ibmSystemTemperatureSensorCurrentReading OBJECT-TYPE
   SYNTAX         Sint32
   ACCESS         read-only
   STATUS         mandatory
   DESCRIPTION    "The current Celcius temperature reading for this sensor"
   REFERENCE      "IBMPSG_TemperatureSensor.CurrentReading"
::= { ibmSystemTemperatureSensorEntry 2 }

ibmSystemTemperatureSensorNominalReading OBJECT-TYPE
   SYNTAX         Sint32
   ACCESS         read-only
   STATUS         mandatory
   DESCRIPTION    "The nominal Celcius temperature reading for this sensor"
   REFERENCE      "IBMPSG_TemperatureSensor.NominalReading"
::= { ibmSystemTemperatureSensorEntry 3 }

ibmSystemTemperatureSensorNormalMax OBJECT-TYPE
   SYNTAX         Sint32
   ACCESS         read-only
   STATUS         mandatory
   DESCRIPTION    "The normal maximum Celcius temperature reading for this sensor"
   REFERENCE      "IBMPSG_TemperatureSensor.NormalMax"
::= { ibmSystemTemperatureSensorEntry 4 }

ibmSystemTemperatureSensorNormalMin OBJECT-TYPE
   SYNTAX         Sint32
   ACCESS         read-only
   STATUS         mandatory
   DESCRIPTION    "The normal minimum Celcius temperature reading for this sensor"
   REFERENCE      "IBMPSG_TemperatureSensor.NormalMin"
::= { ibmSystemTemperatureSensorEntry 5 }

ibmSystemTemperatureSensorMaxReadable OBJECT-TYPE
   SYNTAX         Sint32
   ACCESS         read-only
   STATUS         mandatory
   DESCRIPTION    "The maximum readable Celcius temperature reading for this sensor"
   REFERENCE      "IBMPSG_TemperatureSensor.MaxReadable"
::= { ibmSystemTemperatureSensorEntry 6 }

ibmSystemTemperatureSensorMinReadable OBJECT-TYPE
   SYNTAX         Sint32
   ACCESS         read-only
   STATUS         mandatory
   DESCRIPTION    "The minimum readalbe Celcius temperature reading for this sensor"
   REFERENCE      "IBMPSG_TemperatureSensor.MinReadable"
::= { ibmSystemTemperatureSensorEntry 7 }

ibmSystemTemperatureSensorResolution OBJECT-TYPE
   SYNTAX         Uint32
   ACCESS         read-only
   STATUS         mandatory
   DESCRIPTION    "The resolution in Celcius of the temperature reading for this sensor"
   REFERENCE      "IBMPSG_TemperatureSensor.Resolution"
::= { ibmSystemTemperatureSensorEntry 8 }

ibmSystemTemperatureSensorTolerance OBJECT-TYPE
   SYNTAX         Sint32
   ACCESS         read-only
   STATUS         mandatory
   DESCRIPTION    "The tolerance in Celcius of the temperature reading for this sensor"
   REFERENCE      "IBMPSG_TemperatureSensor.Tolerance"
::= { ibmSystemTemperatureSensorEntry 9 }

ibmSystemTemperatureSensorAccuracy OBJECT-TYPE
   SYNTAX         Sint32
   ACCESS         read-only
   STATUS         mandatory
   DESCRIPTION    "The degree of accuracy in Celcius of the temperature reading for this sensor"
   REFERENCE      "IBMPSG_TemperatureSensor.Accuracy"
::= { ibmSystemTemperatureSensorEntry 10 }

ibmSystemTemperatureSensorLowerThresholdNonCritical OBJECT-TYPE
   SYNTAX         Sint32
   ACCESS         read-only
   STATUS         mandatory
   DESCRIPTION    "The lower non-critical threshold in Celcius for this sensor"
   REFERENCE      "IBMPSG_TemperatureSensor.LowerThresholdNonCritical"
::= { ibmSystemTemperatureSensorEntry 11 }

ibmSystemTemperatureSensorUpperThresholdNonCritical OBJECT-TYPE
   SYNTAX         Sint32
   ACCESS         read-only
   STATUS         mandatory
   DESCRIPTION    "The upper non-critical threshold in Celcius for this sensor"
   REFERENCE      "IBMPSG_TemperatureSensor.UpperThresholdNonCritical"
::= { ibmSystemTemperatureSensorEntry 12 }

ibmSystemTemperatureSensorLowerThresholdCritical OBJECT-TYPE
   SYNTAX         Sint32
   ACCESS         read-only
   STATUS         mandatory
   DESCRIPTION    "The lower critical threshold in Celcius for this sensor"
   REFERENCE      "IBMPSG_TemperatureSensor.LowerThresholdCritical"
::= { ibmSystemTemperatureSensorEntry 13 }

ibmSystemTemperatureSensorUpperThresholdCritical OBJECT-TYPE
   SYNTAX         Sint32
   ACCESS         read-only
   STATUS         mandatory
   DESCRIPTION    "The upper critical threshold in Celcius for this sensor"
   REFERENCE      "IBMPSG_TemperatureSensor.UpperThresholdCritical"
::= { ibmSystemTemperatureSensorEntry 14 }

ibmSystemTemperatureSensorLowerThresholdFatal OBJECT-TYPE
   SYNTAX         Sint32
   ACCESS         read-only
   STATUS         mandatory
   DESCRIPTION    "The lower fatal threshold in Celcius for this sensor"
   REFERENCE      "IBMPSG_TemperatureSensor.LowerThresholdFatal"
::= { ibmSystemTemperatureSensorEntry 15 }

ibmSystemTemperatureSensorUpperThresholdFatal OBJECT-TYPE
   SYNTAX         Sint32
   ACCESS         read-only
   STATUS         mandatory
   DESCRIPTION    "The upper fatal threshold in Celcius for this sensor"
   REFERENCE      "IBMPSG_TemperatureSensor.UpperThresholdFatal"
::= { ibmSystemTemperatureSensorEntry 16 }

ibmSystemTemperatureSensorTempLocation OBJECT-TYPE
   SYNTAX         Uint32
   ACCESS         read-only
   STATUS         mandatory
   DESCRIPTION    "The current temperature sensor location"
   REFERENCE      "IBMPSG_TemperatureSensor.TempLocation"
::= { ibmSystemTemperatureSensorEntry 17 }

ibmSystemTemperatureSensorEventsEnabled OBJECT-TYPE
   SYNTAX         Boolean
   ACCESS         read-only
   STATUS         mandatory
   DESCRIPTION    "Event generation status [True | False]"
   REFERENCE      "IBMPSG_TemperatureSensor.EventsEnabled"
::= { ibmSystemTemperatureSensorEntry 18 }

ibmSystemTemperatureSensorPollingInterval OBJECT-TYPE
   SYNTAX         Uint64
   ACCESS         read-only
   STATUS         mandatory
   DESCRIPTION    "Polling interval is measured in seconds.  Value of zero 
                   indicates do it once and quit.  Minimum polling interval
                   is ten seconds."
   REFERENCE      "IBMPSG_TemperatureSensor.PollingInterval"
::= { ibmSystemTemperatureSensorEntry 19 }

ibmSystemTemperatureSensorEventAutoClearEnabled OBJECT-TYPE
   SYNTAX         Boolean
   ACCESS         read-only
   STATUS         mandatory
   DESCRIPTION    "False means that events are only generated on state changes.
                   True means that events are generated on state changes and 
                   periodically when the object is in a non-normal state."
   REFERENCE      "IBMPSG_TemperatureSensor.EventAutoClearEnabled"
::= { ibmSystemTemperatureSensorEntry 20 }

ibmSystemTemperatureSensorStatus OBJECT-TYPE
   SYNTAX         String
   ACCESS         read-only
   STATUS         mandatory
   DESCRIPTION    "The Status property is a string indicating the current status 
                   of the object. Various operational and non-operational statuses
                   can be defined. Operational statuses are OK, Degraded and Pred
                   Fail. Pred Fail indicates that an element may be functioning 
                   properly but predicting a failure in the near future. An example
                   is a SMART-enabled hard drive. Non-operational statuses can also
                   be specified. These are Error, Starting, Stopping and Service. 
                   The latter, Service, could apply during mirror-resilvering of a 
                   disk, reload of a user permissions list, or other administrative
                   work. Not all such work is on-line, yet the managed element is 
                   neither OK nor in one of the other states. 
                   Ok    = Normal
                   Error = Critical"

   REFERENCE      "IBMPSG_TemperatureSensor.Status"
::= { ibmSystemTemperatureSensorEntry 21 }

ibmSystemVoltageSensorTable OBJECT-TYPE
   SYNTAX         SEQUENCE OF IbmSystemVoltageSensorEntry
   ACCESS         not-accessible
   STATUS         mandatory
   DESCRIPTION    "The IBMPSG_VoltageSensor class represents an IBM managed voltage Sensor."
   REFERENCE      "IBMPSG_VoltageSensor"
::= { ibmSystemLMSensor 2 }

ibmSystemVoltageSensorEntry OBJECT-TYPE
   SYNTAX         IbmSystemVoltageSensorEntry
   ACCESS         not-accessible
   STATUS         mandatory
   DESCRIPTION    "A sequence of voltage sensor readings"
   INDEX          { ibmSystemVoltageSensorKeyIndex }
::= { ibmSystemVoltageSensorTable 1 }

IbmSystemVoltageSensorEntry ::= SEQUENCE
{
   ibmSystemVoltageSensorKeyIndex String,   
   ibmSystemVoltageSensorCurrentReading Sint32,
   ibmSystemVoltageSensorNominalReading Sint32,
   ibmSystemVoltageSensorNormalMax Sint32,
   ibmSystemVoltageSensorNormalMin Sint32,
   ibmSystemVoltageSensorMaxReadable Sint32,
   ibmSystemVoltageSensorMinReadable Sint32,
   ibmSystemVoltageSensorResolution Uint32,
   ibmSystemVoltageSensorTolerance Sint32,
   ibmSystemVoltageSensorAccuracy Sint32,
   ibmSystemVoltageSensorLowerThresholdNonCritical Sint32,
   ibmSystemVoltageSensorUpperThresholdNonCritical Sint32,
   ibmSystemVoltageSensorLowerThresholdCritical Sint32,
   ibmSystemVoltageSensorUpperThresholdCritical Sint32,
   ibmSystemVoltageSensorLowerThresholdFatal Sint32,
   ibmSystemVoltageSensorUpperThresholdFatal Sint32,
   ibmSystemVoltageSensorVoltageType Uint32,
   ibmSystemVoltageSensorEventsEnabled Boolean,
   ibmSystemVoltageSensorPollingInterval Uint64,
   ibmSystemVoltageSensorEventAutoClearEnabled Boolean,
   ibmSystemVoltageSensorStatus String
}

ibmSystemVoltageSensorKeyIndex OBJECT-TYPE
   SYNTAX         String
   ACCESS         read-only
   STATUS         mandatory
   DESCRIPTION    "The index used by this table"
   REFERENCE      "IBMPSG_VoltageSensor.KeyIndex"
::= { ibmSystemVoltageSensorEntry 1 }

ibmSystemVoltageSensorCurrentReading OBJECT-TYPE
   SYNTAX         Sint32
   ACCESS         read-only
   STATUS         mandatory
   DESCRIPTION    "The current voltage reading for this sensor"
   REFERENCE      "IBMPSG_VoltageSensor.CurrentReading"
::= { ibmSystemVoltageSensorEntry 2 }

ibmSystemVoltageSensorNominalReading OBJECT-TYPE
   SYNTAX         Sint32
   ACCESS         read-only
   STATUS         mandatory
   DESCRIPTION    "The nominal voltage reading for this sensor"
   REFERENCE      "IBMPSG_VoltageSensor.NominalReading"
::= { ibmSystemVoltageSensorEntry 3 }

ibmSystemVoltageSensorNormalMax OBJECT-TYPE
   SYNTAX         Sint32
   ACCESS         read-only
   STATUS         mandatory
   DESCRIPTION    "The normal maximum voltage reading for this sensor"
   REFERENCE      "IBMPSG_VoltageSensor.NormalMax"
::= { ibmSystemVoltageSensorEntry 4 }

ibmSystemVoltageSensorNormalMin OBJECT-TYPE
   SYNTAX         Sint32
   ACCESS         read-only
   STATUS         mandatory
   DESCRIPTION    "The normal minimum voltage reading for this sensor"
   REFERENCE      "IBMPSG_VoltageSensor.NormalMin"
::= { ibmSystemVoltageSensorEntry 5 }

ibmSystemVoltageSensorMaxReadable OBJECT-TYPE
   SYNTAX         Sint32
   ACCESS         read-only
   STATUS         mandatory
   DESCRIPTION    "The maximum voltage reading for this sensor"
   REFERENCE      "IBMPSG_VoltageSensor.MaxReadable"
::= { ibmSystemVoltageSensorEntry 6 }

ibmSystemVoltageSensorMinReadable OBJECT-TYPE
   SYNTAX         Sint32
   ACCESS         read-only
   STATUS         mandatory
   DESCRIPTION    "The minimum voltage reading for this sensor"
   REFERENCE      "IBMPSG_VoltageSensor.MinReadable"
::= { ibmSystemVoltageSensorEntry 7 }

ibmSystemVoltageSensorResolution OBJECT-TYPE
   SYNTAX         Uint32
   ACCESS         read-only
   STATUS         mandatory
   DESCRIPTION    "The resolution of the voltage reading for this sensor"
   REFERENCE      "IBMPSG_VoltageSensor.Resolution"
::= { ibmSystemVoltageSensorEntry 8 }

ibmSystemVoltageSensorTolerance OBJECT-TYPE
   SYNTAX         Sint32
   ACCESS         read-only
   STATUS         mandatory
   DESCRIPTION    "The tolerance of the voltage reading for this sensor"
   REFERENCE      "IBMPSG_VoltageSensor.Tolerance"
::= { ibmSystemVoltageSensorEntry 9 }

ibmSystemVoltageSensorAccuracy OBJECT-TYPE
   SYNTAX         Sint32
   ACCESS         read-only
   STATUS         mandatory
   DESCRIPTION    "The accuracy of the voltage reading for this sensor"
   REFERENCE      "IBMPSG_VoltageSensor.Accuracy"
::= { ibmSystemVoltageSensorEntry 10 }

ibmSystemVoltageSensorLowerThresholdNonCritical OBJECT-TYPE
   SYNTAX         Sint32
   ACCESS         read-only
   STATUS         mandatory
   DESCRIPTION    "The non-critical lower threshold voltage reading for this sensor"
   REFERENCE      "IBMPSG_VoltageSensor.LowerThresholdNonCritical"
::= { ibmSystemVoltageSensorEntry 11 }

ibmSystemVoltageSensorUpperThresholdNonCritical OBJECT-TYPE
   SYNTAX         Sint32
   ACCESS         read-only
   STATUS         mandatory
   DESCRIPTION    "The non-critical upper threshold voltage reading for this sensor"
   REFERENCE      "IBMPSG_VoltageSensor.UpperThresholdNonCritical"
::= { ibmSystemVoltageSensorEntry 12 }

ibmSystemVoltageSensorLowerThresholdCritical OBJECT-TYPE
   SYNTAX         Sint32
   ACCESS         read-only
   STATUS         mandatory
   DESCRIPTION    "The critical lower threshold voltage reading for this sensor"
   REFERENCE      "IBMPSG_VoltageSensor.LowerThresholdCritical"
::= { ibmSystemVoltageSensorEntry 13 }

ibmSystemVoltageSensorUpperThresholdCritical OBJECT-TYPE
   SYNTAX         Sint32
   ACCESS         read-only
   STATUS         mandatory
   DESCRIPTION    "The non-critical upper threshold voltage reading for this sensor"
   REFERENCE      "IBMPSG_VoltageSensor.UpperThresholdCritical"
::= { ibmSystemVoltageSensorEntry 14 }

ibmSystemVoltageSensorLowerThresholdFatal OBJECT-TYPE
   SYNTAX         Sint32
   ACCESS         read-only
   STATUS         mandatory
   DESCRIPTION    "The fatal lower threshold voltage reading for this sensor"
   REFERENCE      "IBMPSG_VoltageSensor.LowerThresholdFatal"
::= { ibmSystemVoltageSensorEntry 15 }

ibmSystemVoltageSensorUpperThresholdFatal OBJECT-TYPE
   SYNTAX         Sint32
   ACCESS         read-only
   STATUS         mandatory
   DESCRIPTION    "The fatal upper threshold voltage reading for this sensor"
   REFERENCE      "IBMPSG_VoltageSensor.UpperThresholdFatal"
::= { ibmSystemVoltageSensorEntry 16 }

ibmSystemVoltageSensorVoltageType OBJECT-TYPE
   SYNTAX         Uint32
   ACCESS         read-only
   STATUS         mandatory
   DESCRIPTION    "The Voltage Description"
   REFERENCE      "IBMPSG_VoltageSensor.VoltageType"
::= { ibmSystemVoltageSensorEntry 17 }

ibmSystemVoltageSensorEventsEnabled OBJECT-TYPE
   SYNTAX         Boolean
   ACCESS         read-only
   STATUS         mandatory
   DESCRIPTION    "Event generation status. [True | False]"
   REFERENCE      "IBMPSG_VoltageSensor.EventsEnabled"
::= { ibmSystemVoltageSensorEntry 18 }

ibmSystemVoltageSensorPollingInterval OBJECT-TYPE
   SYNTAX         Uint64
   ACCESS         read-only
   STATUS         mandatory
   DESCRIPTION    "Polling interval is measured in seconds.  Value of zero
                   indicates do it once and quit.  Minimum polling interval
                   is ten seconds."
   REFERENCE      "IBMPSG_VoltageSensor.PollingInterval"
::= { ibmSystemVoltageSensorEntry 19 }

ibmSystemVoltageSensorEventAutoClearEnabled OBJECT-TYPE
   SYNTAX         Boolean
   ACCESS         read-only
   STATUS         mandatory
   DESCRIPTION    "False means that events are only generated on state changes.
                  True means that events are generated on state changes and 
                  periodically when the object is in a non-normal state. [True | False]"
   REFERENCE      "IBMPSG_VoltageSensor.EventAutoClearEnabled"
::= { ibmSystemVoltageSensorEntry 20 }

ibmSystemVoltageSensorStatus OBJECT-TYPE
   SYNTAX         String
   ACCESS         read-only
   STATUS         mandatory
   DESCRIPTION    "The Status property is a string indicating the current status 
                   of the object. Various operational and non-operational statuses
                   can be defined. Operational statuses are OK, Degraded and Pred
                   Fail. Pred Fail indicates that an element may be functioning 
                   properly but predicting a failure in the near future. An example
                   is a SMART-enabled hard drive. Non-operational statuses can also
                   be specified. These are Error, Starting, Stopping and Service. 
                   The latter, Service, could apply during mirror-resilvering of a
                   disk, reload of a user permissions list, or other administrative
                   work. Not all such work is on-line, yet the managed element is 
                   neither OK nor in one of the other states.
                   OK    = Normal
                   Error = Critical"
   REFERENCE      "IBMPSG_VoltageSensor.Status"
::= { ibmSystemVoltageSensorEntry 21 }

ibmSystemFanTable OBJECT-TYPE
   SYNTAX         SEQUENCE OF IbmSystemFanEntry
   ACCESS         not-accessible
   STATUS         mandatory
   DESCRIPTION    "The IBMPSG_Fan class represents an IBM managed fan sensor."
   REFERENCE      "IBMPSG_Fan"
::= { ibmSystemLMSensor 3 }

ibmSystemFanEntry OBJECT-TYPE
   SYNTAX         IbmSystemFanEntry
   ACCESS         not-accessible
   STATUS         mandatory
   DESCRIPTION    "A sequence of fan sensor readings"
   INDEX          { ibmSystemFanKeyIndex }
::= { ibmSystemFanTable 1 }

IbmSystemFanEntry ::= SEQUENCE
{
   ibmSystemFanKeyIndex String,
   ibmSystemFanVariableSpeed Boolean,
   ibmSystemFanDesiredSpeed String,
   ibmSystemFanActiveCooling Boolean,
   ibmSystemFanFanType Uint32,
   ibmSystemFanEventsEnabled Boolean,
   ibmSystemFanPollingInterval Uint64,
   ibmSystemFanEventAutoClearEnabled Boolean,
   ibmSystemFanStatus String
}

ibmSystemFanKeyIndex OBJECT-TYPE
   SYNTAX         String
   ACCESS         read-only
   STATUS         mandatory
   DESCRIPTION    "The index used by this table"
   REFERENCE      "IBMPSG_Fan.KeyIndex"
::= { ibmSystemFanEntry 1 }

ibmSystemFanVariableSpeed OBJECT-TYPE
   SYNTAX         Boolean
   ACCESS         read-only
   STATUS         mandatory
   DESCRIPTION    "States if this fan supports variable speeds [True | False]"
   REFERENCE      "IBMPSG_Fan.VariableSpeed"
::= { ibmSystemFanEntry 2 }

ibmSystemFanDesiredSpeed OBJECT-TYPE
   SYNTAX         String
   ACCESS         read-only
   STATUS         mandatory
   DESCRIPTION    "The desired speed in revolutions per minute for this fan"
   REFERENCE      "IBMPSG_Fan.DesiredSpeed"
::= { ibmSystemFanEntry 3 }

ibmSystemFanActiveCooling OBJECT-TYPE
   SYNTAX         Boolean
   ACCESS         read-only
   STATUS         mandatory
   DESCRIPTION    "States if this fan supports active cooling [True | False]"
   REFERENCE      "IBMPSG_Fan.ActiveCooling"
::= { ibmSystemFanEntry 4 }

ibmSystemFanFanType OBJECT-TYPE
   SYNTAX         Uint32
   ACCESS         read-only
   STATUS         mandatory
   DESCRIPTION    "The current fan type."
   REFERENCE      "IBMPSG_Fan.FanType"
::= { ibmSystemFanEntry 5 }

ibmSystemFanEventsEnabled OBJECT-TYPE
   SYNTAX         Boolean
   ACCESS         read-only
   STATUS         mandatory
   DESCRIPTION    "Event generation status. [True | False]"
   REFERENCE      "IBMPSG_Fan.EventsEnabled"
::= { ibmSystemFanEntry 6 }

ibmSystemFanPollingInterval OBJECT-TYPE
   SYNTAX         Uint64
   ACCESS         read-only
   STATUS         mandatory
   DESCRIPTION    "Polling interval is measured in seconds.  Value of zero indicates 
                   do it once and quit.  Minimum polling interval is ten seconds."
   REFERENCE      "IBMPSG_Fan.PollingInterval"
::= { ibmSystemFanEntry 7 }

ibmSystemFanEventAutoClearEnabled OBJECT-TYPE
   SYNTAX         Boolean
   ACCESS         read-only
   STATUS         mandatory
   DESCRIPTION    "False means that events are only generated on state changes.  True
                   means that events are generated on state changes and periodically 
                   when the object is in a non-normal state."
   REFERENCE      "IBMPSG_Fan.EventAutoClearEnabled"
::= { ibmSystemFanEntry 8 }

ibmSystemFanStatus OBJECT-TYPE
   SYNTAX         String
   ACCESS         read-only
   STATUS         mandatory
   DESCRIPTION    "The Status property is a string indicating the current
                   status of the object. Various operational and non-operational
                   statuses can be defined. Operational statuses are OK, Degraded
                   and Pred Fail. Pred Fail indicates that an element may be
                   functioning properly but predicting a failure in the near
                   future. An example is a SMART-enabled hard drive. Non-operational
                   statuses can also be specified. These are Error, Starting,
                   Stopping and Service. The latter, Service, could apply during
                   mirror-resilvering of a disk, reload of a user permissions list,
                   or other administrative work. Not all such work is on-line, yet
                   the managed element is neither OK nor in one of the other states.
                   OK    = Normal
                   Error = Critical"
   REFERENCE      "IBMPSG_Fan.Status"
::= { ibmSystemFanEntry 9 }

ibmSystemSystemEnclosureTable OBJECT-TYPE
   SYNTAX         SEQUENCE OF IbmSystemSystemEnclosureEntry
   ACCESS         not-accessible
   STATUS         mandatory
   DESCRIPTION    "The IBMPSG_SystemEnclosure class represents an IBM chassis sensor."
   REFERENCE      "IBMPSG_SystemEnclosure"
::= { ibmSystemLMSensor 4 }

ibmSystemSystemEnclosureEntry OBJECT-TYPE
   SYNTAX         IbmSystemSystemEnclosureEntry
   ACCESS         not-accessible
   STATUS         mandatory
   DESCRIPTION    "A sequence of enclosure readings"
   INDEX          { ibmSystemSystemEnclosureKeyIndex }
::= { ibmSystemSystemEnclosureTable 1 }

IbmSystemSystemEnclosureEntry ::= SEQUENCE
{
   ibmSystemSystemEnclosureKeyIndex String,   
   ibmSystemSystemEnclosureIntrusionStatus Uint32,
   ibmSystemSystemEnclosureIntrusionType Uint32,
   ibmSystemSystemEnclosureEventsEnabled Boolean,
   ibmSystemSystemEnclosurePollingInterval Uint64,
   ibmSystemSystemEnclosureACLineStatus Uint16,
   ibmSystemSystemEnclosureDockingStatus Uint16,
   ibmSystemSystemEnclosureEventAutoClearEnabled Boolean,
   ibmSystemSystemEnclosureStatus String
}

ibmSystemSystemEnclosureKeyIndex OBJECT-TYPE
   SYNTAX         String
   ACCESS         read-only
   STATUS         mandatory
   DESCRIPTION    "The index used by this table"
   REFERENCE      "IBMPSG_SystemEnclosure.KeyIndex"
::= { ibmSystemSystemEnclosureEntry 1 }

ibmSystemSystemEnclosureIntrusionStatus OBJECT-TYPE
   SYNTAX         Uint32
   ACCESS         read-only
   STATUS         mandatory
   DESCRIPTION    "The intrusion status"
   REFERENCE      "IBMPSG_SystemEnclosure.IntrusionStatus"
::= { ibmSystemSystemEnclosureEntry 2 }

ibmSystemSystemEnclosureIntrusionType OBJECT-TYPE
   SYNTAX         Uint32
   ACCESS         read-only
   STATUS         mandatory
   DESCRIPTION    "The intrusion type"
   REFERENCE      "IBMPSG_SystemEnclosure.IntrusionType"
::= { ibmSystemSystemEnclosureEntry 3 }

ibmSystemSystemEnclosureEventsEnabled OBJECT-TYPE
   SYNTAX         Boolean
   ACCESS         read-only
   STATUS         mandatory
   DESCRIPTION    "Event generation enabled status. [True | False]"
   REFERENCE      "IBMPSG_SystemEnclosure.EventsEnabled"
::= { ibmSystemSystemEnclosureEntry 4 }

ibmSystemSystemEnclosurePollingInterval OBJECT-TYPE
   SYNTAX         Uint64
   ACCESS         read-only
   STATUS         mandatory
   DESCRIPTION    "Polling interval is measured in seconds.  Value of zero indicates
                   do it once and quit.  Minimum polling interval is ten seconds."
   REFERENCE      "IBMPSG_SystemEnclosure.PollingInterval"
::= { ibmSystemSystemEnclosureEntry 5 }

ibmSystemSystemEnclosureACLineStatus OBJECT-TYPE
   SYNTAX         Uint16
   ACCESS         read-only
   STATUS         mandatory
   DESCRIPTION    "This group defines status information about the AC line in the notebook"
   REFERENCE      "IBMPSG_SystemEnclosure.ACLineStatus"
::= { ibmSystemSystemEnclosureEntry 7 }

ibmSystemSystemEnclosureDockingStatus OBJECT-TYPE
   SYNTAX         Uint16
   ACCESS         read-only
   STATUS         mandatory
   DESCRIPTION    "This defines whether system is docked or not"
   REFERENCE      "IBMPSG_SystemEnclosure.DockingStatus"
::= { ibmSystemSystemEnclosureEntry 6 }

ibmSystemSystemEnclosureEventAutoClearEnabled OBJECT-TYPE
   SYNTAX         Boolean
   ACCESS         read-only
   STATUS         mandatory
   DESCRIPTION    "False means that events are only generated on state changes.  True
                   means that events are generated on state changes and periodically 
                   when the object is in a non-normal state. [True | False]"
   REFERENCE      "IBMPSG_SystemEnclosure.EventAutoClearEnabled"
::= { ibmSystemSystemEnclosureEntry 8 }

ibmSystemSystemEnclosureStatus OBJECT-TYPE
   SYNTAX         String
   ACCESS         read-only
   STATUS         mandatory
   DESCRIPTION    "The Status property is a string indicating the current status of 
                   the object. Various operational and non-operational statuses can 
                   be defined. Operational statuses are OK, Degraded and Pred Fail. 
                   Pred Fail indicates that an element may be functioning properly 
                   but predicting a failure in the near future. An example is a 
                   SMART-enabled hard drive. Non-operational statuses can also be 
                   specified. These are Error, Starting, Stopping and Service. The 
                   latter, Service, could apply during mirror-resilvering of a disk, 
                   reload of a user permissions list, or other administrative work. 
                   Not all such work is on-line, yet the managed element is neither 
                   OK nor in one of the other states.
                   OK     = Normal
                   Error  = Critical"
   REFERENCE      "IBMPSG_SystemEnclosure.Status"
::= { ibmSystemSystemEnclosureEntry 9 }

ibmSystemTachometerTable OBJECT-TYPE
   SYNTAX         SEQUENCE OF IbmSystemTachometerEntry
   ACCESS         not-accessible
   STATUS         mandatory
   DESCRIPTION    "The IBMPSG_Tachometer class represents an IBM managed Fan speed Sensor."
   REFERENCE      "IBMPSG_Tachometer"
::= { ibmSystemLMSensor 5 }

ibmSystemTachometerEntry OBJECT-TYPE
   SYNTAX         IbmSystemTachometerEntry
   ACCESS         not-accessible
   STATUS         mandatory
   DESCRIPTION    "A sequence of fan enclosure readings"
   INDEX          { ibmSystemTachometerKeyIndex }
::= { ibmSystemTachometerTable 1 }

IbmSystemTachometerEntry ::= SEQUENCE
{
   ibmSystemTachometerKeyIndex String,   
   ibmSystemTachometerCurrentReading Sint32,
   ibmSystemTachometerNominalReading Sint32,
   ibmSystemTachometerNormalMax Sint32,
   ibmSystemTachometerNormalMin Sint32,
   ibmSystemTachometerMaxReadable Sint32,
   ibmSystemTachometerMinReadable Sint32,
   ibmSystemTachometerResolution Uint32,
   ibmSystemTachometerTolerance Sint32,
   ibmSystemTachometerLowerThresholdNonCritical Sint32,
   ibmSystemTachometerUpperThresholdNonCritical Sint32,
   ibmSystemTachometerLowerThresholdCritical Sint32,
   ibmSystemTachometerUpperThresholdCritical Sint32,
   ibmSystemTachometerLowerThresholdFatal Sint32,
   ibmSystemTachometerUpperThresholdFatal Sint32,
   ibmSystemTachometerFanDescrip Uint32,
   ibmSystemTachometerFanType Uint32,
   ibmSystemTachometerEventsEnabled Boolean,
   ibmSystemTachometerEventAutoClearEnabled Boolean,
   ibmSystemTachometerStatus String
}

ibmSystemTachometerKeyIndex OBJECT-TYPE
   SYNTAX         String
   ACCESS         read-only
   STATUS         mandatory
   DESCRIPTION    "The index used by this table"
   REFERENCE      "IBMPSG_Tachometer.KeyIndex"
::= { ibmSystemTachometerEntry 1 }

ibmSystemTachometerCurrentReading OBJECT-TYPE
   SYNTAX         Sint32
   ACCESS         read-only
   STATUS         mandatory
   DESCRIPTION    "The current fan reading in revolutions per minute for this sensor"
   REFERENCE      "IBMPSG_Tachometer.CurrentReading"
::= { ibmSystemTachometerEntry 2 }

ibmSystemTachometerNominalReading OBJECT-TYPE
   SYNTAX         Sint32
   ACCESS         read-only
   STATUS         mandatory
   DESCRIPTION    "The nominal fan reading in revolutions per minute for this sensor"
   REFERENCE      "IBMPSG_Tachometer.NominalReading"
::= { ibmSystemTachometerEntry 3 }

ibmSystemTachometerNormalMax OBJECT-TYPE
   SYNTAX         Sint32
   ACCESS         read-only
   STATUS         mandatory
   DESCRIPTION    "The normal maximum fan reading in revolutions per minute for this sensor"
   REFERENCE      "IBMPSG_Tachometer.NormalMax"
::= { ibmSystemTachometerEntry 4 }

ibmSystemTachometerNormalMin OBJECT-TYPE
   SYNTAX         Sint32
   ACCESS         read-only
   STATUS         mandatory
   DESCRIPTION    "The normal minimum fan reading in revolutions per minute for this sensor"
   REFERENCE      "IBMPSG_Tachometer.NormalMin"
::= { ibmSystemTachometerEntry 5 }

ibmSystemTachometerMaxReadable OBJECT-TYPE
   SYNTAX         Sint32
   ACCESS         read-only
   STATUS         mandatory
   DESCRIPTION    "The maximum readable fan reading in revolutions per minute for this sensor"
   REFERENCE      "IBMPSG_Tachometer.MaxReadable"
::= { ibmSystemTachometerEntry 6 }

ibmSystemTachometerMinReadable OBJECT-TYPE
   SYNTAX         Sint32
   ACCESS         read-only
   STATUS         mandatory
   DESCRIPTION    "The minimum readable fan reading in revolutions per minute for this sensor"
   REFERENCE      "IBMPSG_Tachometer.MinReadable"
::= { ibmSystemTachometerEntry 7 }

ibmSystemTachometerResolution OBJECT-TYPE
   SYNTAX         Uint32
   ACCESS         read-only
   STATUS         mandatory
   DESCRIPTION    "The resolution of this fan reading in revolutions per minute for this sensor"
   REFERENCE      "IBMPSG_Tachometer.Resolution"
::= { ibmSystemTachometerEntry 8 }

ibmSystemTachometerTolerance OBJECT-TYPE
   SYNTAX         Sint32
   ACCESS         read-only
   STATUS         mandatory
   DESCRIPTION    "The tolerance of this fan reading in revolutions per minute for this sensor"
   REFERENCE      "IBMPSG_Tachometer.Tolerance"
::= { ibmSystemTachometerEntry 9 }

ibmSystemTachometerLowerThresholdNonCritical OBJECT-TYPE
   SYNTAX         Sint32
   ACCESS         read-only
   STATUS         mandatory
   DESCRIPTION    "The non-critical lower threshold fan reading in revolutions per minute for this sensor"
   REFERENCE      "IBMPSG_Tachometer.LowerThresholdNonCritical"
::= { ibmSystemTachometerEntry 10 }

ibmSystemTachometerUpperThresholdNonCritical OBJECT-TYPE
   SYNTAX         Sint32
   ACCESS         read-only
   STATUS         mandatory
   DESCRIPTION    "The non-critical upper threshold fan reading in revolutions per minute for this sensor"
   REFERENCE      "IBMPSG_Tachometer.UpperThresholdNonCritical"
::= { ibmSystemTachometerEntry 11 }

ibmSystemTachometerLowerThresholdCritical OBJECT-TYPE
   SYNTAX         Sint32
   ACCESS         read-only
   STATUS         mandatory
   DESCRIPTION    "The critical lower threshold fan reading in revolutions per minute for this sensor"
   REFERENCE      "IBMPSG_Tachometer.LowerThresholdCritical"
::= { ibmSystemTachometerEntry 12 }

ibmSystemTachometerUpperThresholdCritical OBJECT-TYPE
   SYNTAX         Sint32
   ACCESS         read-only
   STATUS         mandatory
   DESCRIPTION    "The critical upper threshold fan reading in revolutions per minute for this sensor"
   REFERENCE      "IBMPSG_Tachometer.UpperThresholdCritical"
::= { ibmSystemTachometerEntry 13 }

ibmSystemTachometerLowerThresholdFatal OBJECT-TYPE
   SYNTAX         Sint32
   ACCESS         read-only
   STATUS         mandatory
   DESCRIPTION    "The fatal lower threshold fan reading in revolutions per minute for this sensor"
   REFERENCE      "IBMPSG_Tachometer.LowerThresholdFatal"
::= { ibmSystemTachometerEntry 14 }

ibmSystemTachometerUpperThresholdFatal OBJECT-TYPE
   SYNTAX         Sint32
   ACCESS         read-only
   STATUS         mandatory
   DESCRIPTION    "The fatal upper threshold fan reading in revolutions per minute for this sensor"
   REFERENCE      "IBMPSG_Tachometer.UpperThresholdFatal"
::= { ibmSystemTachometerEntry 15 }

ibmSystemTachometerFanDescrip OBJECT-TYPE
   SYNTAX         Uint32
   ACCESS         read-only
   STATUS         mandatory
   DESCRIPTION    "The Fan Description."
   REFERENCE      "IBMPSG_Tachometer.FanDescrip"
::= { ibmSystemTachometerEntry 16 }

ibmSystemTachometerFanType OBJECT-TYPE
   SYNTAX         Uint32
   ACCESS         read-only
   STATUS         mandatory
   DESCRIPTION    "The current fan type."
   REFERENCE      "IBMPSG_Tachometer.FanType"
::= { ibmSystemTachometerEntry 17 }

ibmSystemTachometerEventsEnabled OBJECT-TYPE
   SYNTAX         Boolean
   ACCESS         read-only
   STATUS         mandatory
   DESCRIPTION    "Event generation status."
   REFERENCE      "IBMPSG_Tachometer.EventsEnabled"
::= { ibmSystemTachometerEntry 18 }

ibmSystemTachometerEventAutoClearEnabled OBJECT-TYPE
   SYNTAX         Boolean
   ACCESS         read-only
   STATUS         mandatory
   DESCRIPTION    "False means that events are only generated on state changes.  True means
                   that events are generated on state changes and periodically when the 
                   object is in a non-normal state."
   REFERENCE      "IBMPSG_Tachometer.EventAutoClearEnabled"
::= { ibmSystemTachometerEntry 19 }

ibmSystemTachometerStatus OBJECT-TYPE
   SYNTAX         String
   ACCESS         read-only
   STATUS         mandatory
   DESCRIPTION    "The Status property is a string indicating the current status of the
                   object. Various operational and non-operational statuses can be defined.
                   Operational statuses are OK, Degraded and Pred Fail. Pred Fail indicates
                   that an element may be functioning properly but predicting a failure in
                   the near future. An example is a SMART-enabled hard drive. Non-operational
                   statuses can also be specified. These are Error, Starting, Stopping and
                   Service. The latter, Service, could apply during mirror-resilvering of a
                   disk, reload of a user permissions list, or other administrative work. Not
                   all such work is on-line, yet the managed element is neither OK nor in one
                   of the other states.
                   OK     = Normal
                   Error  = Critical"
   REFERENCE      "IBMPSG_Tachometer.Status"
::= { ibmSystemTachometerEntry 20 }


END
