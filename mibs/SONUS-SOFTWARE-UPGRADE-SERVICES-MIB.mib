--
-- This SMIv2 module has been generated by smidump 0.2-cvs. Do not edit.
--

SONUS-SOFTWARE-UPGRADE-SERVICES-MIB DEFINITIONS ::= BEGIN

IMPORTS
    Counter32, Integer32, MODULE-IDENTITY, NOTIFICATION-TYPE, 
    OBJECT-TYPE
        FROM SNMPv2-SMI
    DateAndTime, DisplayString, TEXTUAL-CONVENTION
        FROM SNMPv2-TC
    sonusEventClass, sonusEventDescription, sonusEventLevel, 
    sonusShelfIndex
        FROM SONUS-COMMON-MIB
    sonusServicesMIBs
        FROM SONUS-SMI;

sonusSoftwareUpgradeServicesMIB MODULE-IDENTITY
    LAST-UPDATED    "200104180000Z"
    ORGANIZATION    
            "Sonus Networks, Inc."
    CONTACT-INFO    
            "   Customer Support    
             Sonus Networks, Inc,
             5 carlisle Road
             Westford, MA 01886
             USA
             
             Tel: 978-692-8999
             Fax: 978-392-9118
             E-mail: cs.snmp@sonusnet.com"
    DESCRIPTION     
            "The MIB Module for Software Upgrade Configuration."
    ::= { sonusServicesMIBs 11 }


SonusSoftwareUpgradeState ::= TEXTUAL-CONVENTION
    STATUS          current
    DESCRIPTION     
            "Represents the different states in LSWU FSM. (Internal use only)"
    SYNTAX          INTEGER { idle(0), query(1), init(2), delay1(3), 
                        start(4), sxOne(5), waitSync(6), sxTwoTx(7), 
                        sxTwoRx(8), sxTwoWait(9), variant(10), 
                        prepare(11), stopCalls(12), firstPns(13), 
                        cnsReset(14), spsReset(15), pnsReset(16), 
                        sxDelay(17), done(18) }

sonusSoftwareUpgradeServicesMIBObjects OBJECT IDENTIFIER
    ::= { sonusSoftwareUpgradeServicesMIB 1 }

sonusSwUpgradeShelfAdmnTable OBJECT-TYPE
    SYNTAX          SEQUENCE OF SonusSwUpgradeShelfAdmnEntry
    MAX-ACCESS      not-accessible
    STATUS          current
    DESCRIPTION     
            "This table specifies the software upgrade configuration."
    ::= { sonusSoftwareUpgradeServicesMIBObjects 1 }

sonusSwUpgradeShelfAdmnEntry OBJECT-TYPE
    SYNTAX          SonusSwUpgradeShelfAdmnEntry
    MAX-ACCESS      not-accessible
    STATUS          current
    DESCRIPTION     
            ""
    INDEX           { sonusSwUpgradeShelfAdmnShelfIndex }
    ::= { sonusSwUpgradeShelfAdmnTable 1 }

SonusSwUpgradeShelfAdmnEntry ::=
    SEQUENCE {
        sonusSwUpgradeShelfAdmnShelfIndex Integer32,
        sonusSwUpgradeShelfAdmnInit     INTEGER,
        sonusSwUpgradeShelfAdmnUpgradeNow INTEGER,
        sonusSwUpgradeShelfAdmnHalt     INTEGER,
        sonusSwUpgradeShelfAdmnCommitDirectory      INTEGER,
        sonusSwUpgradeShelfAdmnDirectory DisplayString,
        sonusSwUpgradeShelfAdmnOverrideFeatureCheck           INTEGER
    }

sonusSwUpgradeShelfAdmnShelfIndex OBJECT-TYPE
    SYNTAX          Integer32 (1..6)
    MAX-ACCESS      read-only
    STATUS          current
    DESCRIPTION     
            "The shelf index of this software upgrade entry."
    ::= { sonusSwUpgradeShelfAdmnEntry 1 }

sonusSwUpgradeShelfAdmnInit OBJECT-TYPE
    SYNTAX          INTEGER { ready(1), initialize(2) }
    MAX-ACCESS      read-write
    STATUS          current
    DESCRIPTION     
            "Initialize the software upgrade, verify software image
             availability, check for unsupported features.  The feature
             check can be disabled by setting
             sonusSwUpgradeShelfAdmnOverrideFeatureCheck in the same
             request.
             
             This MIB object can only be set through the CLI, and only
             by a user with admin privileges; it always reads as ready(1)."
    DEFVAL          { ready }
    ::= { sonusSwUpgradeShelfAdmnEntry 2 }

sonusSwUpgradeShelfAdmnUpgradeNow OBJECT-TYPE
    SYNTAX          INTEGER { ready(1), upgrade(2) }
    MAX-ACCESS      read-write
    STATUS          current
    DESCRIPTION     
            "Initiate the software upgrade of the specified shelf now.
             
             This MIB object can only be set through the CLI, and only
             by a user with admin privileges; it always reads as ready(1)."
    DEFVAL          { ready }
    ::= { sonusSwUpgradeShelfAdmnEntry 3 }

sonusSwUpgradeShelfAdmnHalt OBJECT-TYPE
    SYNTAX          INTEGER { ready(1), halt(2) }
    MAX-ACCESS      read-write
    STATUS          current
    DESCRIPTION     
            "Halt the software upgrade in progress.
             
             This MIB object can only be set through the CLI, and only
             by a user with admin privileges; it always reads as ready(1)."
    DEFVAL          { ready }
    ::= { sonusSwUpgradeShelfAdmnEntry 4 }

sonusSwUpgradeShelfAdmnCommitDirectory OBJECT-TYPE
    SYNTAX          INTEGER { ready(1), commit(2) }
    MAX-ACCESS      read-write
    STATUS          current
    DESCRIPTION     
            "Commit the new software distribution directory name into NVS.
             
             This MIB object can only be set by a user with admin
             privileges; it always reads as ready(1)."
    DEFVAL          { ready }
    ::= { sonusSwUpgradeShelfAdmnEntry 5 }

sonusSwUpgradeShelfAdmnDirectory OBJECT-TYPE
    SYNTAX          DisplayString (SIZE(0..15))
    MAX-ACCESS      read-write
    STATUS          current
    DESCRIPTION     
            "The new software distribution directory name.
             
             This MIB object can only be set by a user with admin
             privileges."
    ::= { sonusSwUpgradeShelfAdmnEntry 6 }

sonusSwUpgradeShelfAdmnOverrideFeatureCheck OBJECT-TYPE
    SYNTAX          INTEGER { ready(1), override(2) }
    MAX-ACCESS      read-write
    STATUS          current
    DESCRIPTION     
            "Ignore the check for unsupported features (i.e. features
             that would prevent a software upgrade from occurring) during
             initialization.  This MIB object must be set with
             sonusSwUpgradeShelfAdmnInit in the same request.
             
             This MIB object can only be set through the CLI, and only
             by a user with admin privileges; it always reads as ready(1)."
    DEFVAL          { ready }
    ::= { sonusSwUpgradeShelfAdmnEntry 7 }

sonusSwUpgradeShelfStatTable OBJECT-TYPE
    SYNTAX          SEQUENCE OF SonusSwUpgradeShelfStatEntry
    MAX-ACCESS      not-accessible
    STATUS          current
    DESCRIPTION     
            "This table contains status information about the software upgrade 
             on a shelf."
    ::= { sonusSoftwareUpgradeServicesMIBObjects 2 }

sonusSwUpgradeShelfStatEntry OBJECT-TYPE
    SYNTAX          SonusSwUpgradeShelfStatEntry
    MAX-ACCESS      not-accessible
    STATUS          current
    DESCRIPTION     
            ""
    INDEX           { sonusSwUpgradeShelfStatShelfIndex }
    ::= { sonusSwUpgradeShelfStatTable 1 }

SonusSwUpgradeShelfStatEntry ::=
    SEQUENCE {
        sonusSwUpgradeShelfStatShelfIndex Integer32,
        sonusSwUpgradeShelfStatStatus   INTEGER,
        sonusSwUpgradeShelfStatCurSlot  Integer32,
        sonusSwUpgradeShelfStatSlotRemain Integer32,
        sonusSwUpgradeShelfStatGroupRemain  Integer32,
        sonusSwUpgradeShelfStatDuration Counter32,
        sonusSwUpgradeShelfStatStartTime DateAndTime,
        sonusSwUpgradeShelfStatLastReason INTEGER,
        sonusSwUpgradeShelfStatLastState SonusSoftwareUpgradeState,
        sonusSwUpgradeShelfStatState    SonusSoftwareUpgradeState
    }

sonusSwUpgradeShelfStatShelfIndex OBJECT-TYPE
    SYNTAX          Integer32 (1..6)
    MAX-ACCESS      read-only
    STATUS          current
    DESCRIPTION     
            "Identifies the target shelf within the node."
    ::= { sonusSwUpgradeShelfStatEntry 1 }

sonusSwUpgradeShelfStatStatus OBJECT-TYPE
    SYNTAX          INTEGER { idle(1), busy(2), complete(3), 
                        incomplete(4), commitRequired(5) }
    MAX-ACCESS      read-only
    STATUS          current
    DESCRIPTION     
            "Indicates the software upgrade status of the shelf."
    ::= { sonusSwUpgradeShelfStatEntry 2 }

sonusSwUpgradeShelfStatCurSlot OBJECT-TYPE
    SYNTAX          Integer32 (1..16)
    MAX-ACCESS      read-only
    STATUS          current
    DESCRIPTION     
            "Identifies the slot currently being upgraded with new software."
    ::= { sonusSwUpgradeShelfStatEntry 3 }

sonusSwUpgradeShelfStatSlotRemain OBJECT-TYPE
    SYNTAX          Integer32 (1..16)
    MAX-ACCESS      read-only
    STATUS          current
    DESCRIPTION     
            "Identifies number of slots within the shelf remained to be upgraded."
    ::= { sonusSwUpgradeShelfStatEntry 4 }

sonusSwUpgradeShelfStatGroupRemain OBJECT-TYPE
    SYNTAX          Integer32
    MAX-ACCESS      read-only
    STATUS          current
    DESCRIPTION     
            ""
    ::= { sonusSwUpgradeShelfStatEntry 5 }

sonusSwUpgradeShelfStatDuration OBJECT-TYPE
    SYNTAX          Counter32
    MAX-ACCESS      read-only
    STATUS          current
    DESCRIPTION     
            "Indicates the duration of the software upgrade in seconds."
    ::= { sonusSwUpgradeShelfStatEntry 6 }

sonusSwUpgradeShelfStatStartTime OBJECT-TYPE
    SYNTAX          DateAndTime
    MAX-ACCESS      read-only
    STATUS          current
    DESCRIPTION     
            "Indicates the start time of the software upgrade"
    ::= { sonusSwUpgradeShelfStatEntry 7 }

sonusSwUpgradeShelfStatLastReason OBJECT-TYPE
    SYNTAX          INTEGER { none(0), successfulCompletion(1), 
                        initTimeout(2), manualHalt(3), 
                        upgradeNotRequired(4), fileUnavailable(5), 
                        parametersNotSaved(6), flashUpdateInProgress(7), 
                        redundSlotActive(8), switchover1Timeout(9), 
                        sync1Timeout(10), switchover2Timeout(11), 
                        sync2Timeout(12), rebootTimeout(13), 
                        mnsNotSynced(14), notActive(15), 
                        internalTimerUnavailable(16), 
                        internalQueryTimeout(17), 
                        internalResourceUnavailable(18), 
                        internalRtmError(19), mnsSwitchover(20) }
    MAX-ACCESS      read-only
    STATUS          current
    DESCRIPTION     
            "Indicates the exit reason of the last live software upgrade."
    ::= { sonusSwUpgradeShelfStatEntry 8 }

sonusSwUpgradeShelfStatLastState OBJECT-TYPE
    SYNTAX          SonusSoftwareUpgradeState
    MAX-ACCESS      read-only
    STATUS          current
    DESCRIPTION     
            "Indicates the last state of the LSWU FSM. (Internal use only)"
    ::= { sonusSwUpgradeShelfStatEntry 9 }

sonusSwUpgradeShelfStatState OBJECT-TYPE
    SYNTAX          SonusSoftwareUpgradeState
    MAX-ACCESS      read-only
    STATUS          current
    DESCRIPTION     
            "Indicates the current state of the LSWU FSM. (Internal use only)"
    ::= { sonusSwUpgradeShelfStatEntry 10 }

sonusSwUpgradeSlotStatTable OBJECT-TYPE
    SYNTAX          SEQUENCE OF SonusSwUpgradeSlotStatEntry
    MAX-ACCESS      not-accessible
    STATUS          current
    DESCRIPTION     
            "This table contains status information about the software upgrade 
             on a shelf."
    ::= { sonusSoftwareUpgradeServicesMIBObjects 3 }

sonusSwUpgradeSlotStatEntry OBJECT-TYPE
    SYNTAX          SonusSwUpgradeSlotStatEntry
    MAX-ACCESS      not-accessible
    STATUS          current
    DESCRIPTION     
            ""
    INDEX           { sonusSwUpgradeSlotStatShelfIndex, 
                      sonusSwUpgradeSlotStatSlotIndex }
    ::= { sonusSwUpgradeSlotStatTable 1 }

SonusSwUpgradeSlotStatEntry ::=
    SEQUENCE {
        sonusSwUpgradeSlotStatShelfIndex Integer32,
        sonusSwUpgradeSlotStatSlotIndex Integer32,
        sonusSwUpgradeSlotStatStatus    INTEGER,
        sonusSwUpgradeSlotStatUpgrade   INTEGER,
        sonusSwUpgradeSlotStatVersion   DisplayString
    }

sonusSwUpgradeSlotStatShelfIndex OBJECT-TYPE
    SYNTAX          Integer32 (1..6)
    MAX-ACCESS      read-only
    STATUS          current
    DESCRIPTION     
            "Identifies the target shelf within the node."
    ::= { sonusSwUpgradeSlotStatEntry 1 }

sonusSwUpgradeSlotStatSlotIndex OBJECT-TYPE
    SYNTAX          Integer32 (1..16)
    MAX-ACCESS      read-only
    STATUS          current
    DESCRIPTION     
            "Identifies the target slot within the shelf."
    ::= { sonusSwUpgradeSlotStatEntry 2 }

sonusSwUpgradeSlotStatStatus OBJECT-TYPE
    SYNTAX          INTEGER { idle(1), busy(2), complete(3), unknown(4) }
    MAX-ACCESS      read-only
    STATUS          current
    DESCRIPTION     
            "Identifies the software upgrade status of a slot."
    ::= { sonusSwUpgradeSlotStatEntry 3 }

sonusSwUpgradeSlotStatUpgrade OBJECT-TYPE
    SYNTAX          INTEGER { none(1), smooth(2), disrupt(3), 
                        unavailable(4), unknown(5) }
    MAX-ACCESS      read-only
    STATUS          current
    DESCRIPTION     
            ""
    ::= { sonusSwUpgradeSlotStatEntry 4 }

sonusSwUpgradeSlotStatVersion OBJECT-TYPE
    SYNTAX          DisplayString (SIZE(0..15))
    MAX-ACCESS      read-only
    STATUS          current
    DESCRIPTION     
            "The software version available for upgrade on the slot."
    ::= { sonusSwUpgradeSlotStatEntry 5 }

sonusSoftwareUpgradeServicesMIBNotifications OBJECT IDENTIFIER
    ::= { sonusSoftwareUpgradeServicesMIB 2 }

sonusSoftwareUpgradeServicesMIBNotificationsPrefix OBJECT IDENTIFIER
    ::= { sonusSoftwareUpgradeServicesMIBNotifications 0 }

sonusSoftwareUpgradeServicesMIBNotificationsObjects OBJECT IDENTIFIER
    ::= { sonusSoftwareUpgradeServicesMIBNotifications 1 }

sonusSoftwareUpgradeInitiatedNotification NOTIFICATION-TYPE
    OBJECTS         { sonusShelfIndex, sonusSwUpgradeShelfAdmnDirectory, 
                      sonusEventDescription, sonusEventClass, 
                      sonusEventLevel }
    STATUS          current
    DESCRIPTION     
            "This trap indicates that a software upgrade to the
             specified Software Path directory has been initiated
             by the user for this shelf."
    ::= { sonusSoftwareUpgradeServicesMIBNotificationsPrefix 1 }

sonusSoftwareUpgradeTerminatedNotification NOTIFICATION-TYPE
    OBJECTS         { sonusShelfIndex, sonusSwUpgradeShelfAdmnDirectory, 
                      sonusSwUpgradeShelfStatLastReason, 
                      sonusEventDescription, sonusEventClass, 
                      sonusEventLevel }
    STATUS          current
    DESCRIPTION     
            "This trap indicates that a software upgrade to the
             specified Software Path directory has terminated in
             this shelf for the specified reason."
    ::= { sonusSoftwareUpgradeServicesMIBNotificationsPrefix 2 }

sonusSoftwareUpgradeSucceededNotification NOTIFICATION-TYPE
    OBJECTS         { sonusShelfIndex, sonusSwUpgradeShelfAdmnDirectory, 
                      sonusSwUpgradeShelfStatLastReason, 
                      sonusEventDescription, sonusEventClass, 
                      sonusEventLevel }
    STATUS          current
    DESCRIPTION     
            "This trap indicates that a software upgrade to the
             specified Software Path directory has succeeded in
             this shelf for the specified reason."
    ::= { sonusSoftwareUpgradeServicesMIBNotificationsPrefix 3 }

END -- end of module SONUS-SOFTWARE-UPGRADE-SERVICES-MIB.
