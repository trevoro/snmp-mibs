Wellfleet-SYSL-MIB DEFINITIONS ::= BEGIN

-- Created by mdl2asn version 3.1
-- Creation date: Wed Aug 30 16:48:55 EDT 1995


    IMPORTS

      IpAddress, Counter
        FROM RFC1155-SMI
      OBJECT-TYPE
        FROM RFC-1212
      DisplayString
        FROM RFC1213-MIB
      wfSyslogGroup
        FROM Wellfleet-COMMON-MIB;


    wfSyslog	OBJECT IDENTIFIER ::= { wfSyslogGroup 1 }

    wfSyslogDelete OBJECT-TYPE
        SYNTAX	INTEGER {
    		    created(1),
    		    deleted(2)
    		}
        ACCESS	read-write
        STATUS	mandatory
        DESCRIPTION
                "A flag to indicate SYSLOG instance deletion
                If this flag is set to delete then the syslog
                subsystem and all associated MIB information
                will be deleted from the router."
        DEFVAL	{ created }
        ::= { wfSyslog 1 }

    wfSyslogDisable OBJECT-TYPE
        SYNTAX	INTEGER {
    		    enabled(1),
    		    disabled(2)
    		}
        ACCESS	read-write
        STATUS	mandatory
        DESCRIPTION
                "Enables or Disables SYSLOG Subsystem
                Note:  Even if this attribute is set to SYSLOG_BASE_ENABLED
                a remote host must be configured and enabled with
                associated enabled filters before the syslog subsystem will
                begin filtering and forwarding messages"
        DEFVAL	{ enabled }
        ::= { wfSyslog 2 }

    wfSyslogOperState OBJECT-TYPE
        SYNTAX	INTEGER {
    		    up(1),
    		    down(2)
    		}
        ACCESS	read-only
        STATUS	mandatory
        DESCRIPTION
                "This field indicates the actual stat of the syslog
                subsystem.  If it is equal to SYSLOG_UP, then the
                subsystem is currently filtering and forwarding
                syslog messages.  If it is SYSLOG_DOWN then it is
                not forwarding messages because of several
                possiblities:
                1) No hosts are configured for the subsystem,
                     2) No hosts are enabled
                3) Hosts are enabled but have no respective
                   filters enabled"
        DEFVAL	{ down }
        ::= { wfSyslog 3 }

    wfSyslogMaxHosts OBJECT-TYPE
        SYNTAX	INTEGER(1..10)
        ACCESS	read-write
        STATUS	mandatory
        DESCRIPTION
                "Number of remote hosts allowed to be configured"
        DEFVAL	{ 5 }
        ::= { wfSyslog 4 }

    wfSyslogPollTimer OBJECT-TYPE
        SYNTAX	INTEGER(5..610000)
        ACCESS	read-write
        STATUS	mandatory
        DESCRIPTION
                "Timer used to determine the iteration that log files
                are polled for new messages by the syslog application"
        DEFVAL	{ 5 }
        ::= { wfSyslog 5 }

    wfSyslogActTimeSeqHosts OBJECT-TYPE
        SYNTAX	INTEGER
        ACCESS	read-only
        STATUS	mandatory
        DESCRIPTION
                "This attribute is used to keep track of the current
                number of ACTIVE hosts configured for time sequencing. If a
                management station attempts to configure more hosts
                (wfSyslogTimeSeqHosts and wfSyslogNonSeqHosts) than
                wfSyslogMaxHosts allows, then the wfSyslogHostState
                for that host record will be set to SYSLOG_HOST_INACTIVE.
                 "
        ::= { wfSyslog 6 }

    wfSyslogActNonSeqHosts OBJECT-TYPE
        SYNTAX	INTEGER
        ACCESS	read-only
        STATUS	mandatory
        DESCRIPTION
                "This attribute is used to keep track of the current
                number of ACTIVE hosts that are NOT configured for time sequencing.
                If a management station attempts to configure more hosts
                (wfSyslogTimeSeqHosts and wfSyslogNonSeqHosts) than
                wfSyslogMaxHosts allows, then the wfSyslogHostState
                for that host record will be set to SYSLOG_HOST_INACTIVE.
                 "
        ::= { wfSyslog 7 }

    wfSyslogTotalMsgFwds OBJECT-TYPE
        SYNTAX	Counter
        ACCESS	read-only
        STATUS	mandatory
        DESCRIPTION
                "Counter used to track the total number of UDP syslog
                messages sent"
        ::= { wfSyslog 8 }

    wfSyslogHostTable OBJECT-TYPE
        SYNTAX	SEQUENCE OF WfSyslogHostEntry
        ACCESS	not-accessible
        STATUS	mandatory
        DESCRIPTION
                "Table containing remote host records"
        ::= { wfSyslogGroup 2 }

    wfSyslogHostEntry OBJECT-TYPE
        SYNTAX	WfSyslogHostEntry
        ACCESS	not-accessible
        STATUS	mandatory
        DESCRIPTION
                "Information concerning a specific remote host entry"
        INDEX	{ wfSyslogHostDest }
        ::= { wfSyslogHostTable 1 }

    WfSyslogHostEntry ::= SEQUENCE {
    	    wfSyslogHostDelete
    		INTEGER,
    	    wfSyslogHostDisable
    		INTEGER,
    	    wfSyslogHostDest
    		IpAddress,
    	    wfSyslogHostUDPPort
    		INTEGER,
    	    wfSyslogHostLogFacility
    		INTEGER,
    	    wfSyslogHostTimeSeqEnable
    		INTEGER,
    	    wfSyslogHostOperState
    		INTEGER,
    	    wfSyslogHostMsgFwds
    		Counter
        }

    wfSyslogHostDelete OBJECT-TYPE
        SYNTAX	INTEGER {
    		    created(1),
    		    deleted(2)
    		}
        ACCESS	read-write
        STATUS	mandatory
        DESCRIPTION
                "A flag to indicate SYSLOG instance deletion
                If this flag is set to delete then it is the
                application's responsibility to delete the
                record and the respective filter table records"
        DEFVAL	{ created }
        ::= { wfSyslogHostEntry 1 }

    wfSyslogHostDisable OBJECT-TYPE
        SYNTAX	INTEGER {
    		    enabled(1),
    		    disabled(2)
    		}
        ACCESS	read-write
        STATUS	mandatory
        DESCRIPTION
                "Enables or Disables syslog messaging for this remote
                host"
        DEFVAL	{ enabled }
        ::= { wfSyslogHostEntry 2 }

    wfSyslogHostDest OBJECT-TYPE
        SYNTAX	IpAddress
        ACCESS	read-only
        STATUS	mandatory
        DESCRIPTION
                "IP address of the remote host"
        ::= { wfSyslogHostEntry 3 }

    wfSyslogHostUDPPort OBJECT-TYPE
        SYNTAX	INTEGER
        ACCESS	read-write
        STATUS	mandatory
        DESCRIPTION
                "UDP port of the remote host"
        DEFVAL	{ 514 }
        ::= { wfSyslogHostEntry 4 }

    wfSyslogHostLogFacility OBJECT-TYPE
        SYNTAX	INTEGER {
    		    local0(128),
    		    local1(136),
    		    local2(144),
    		    local3(152),
    		    local4(160),
    		    local5(168),
    		    local6(176),
    		    local7(184)
    		}
        ACCESS	read-write
        STATUS	mandatory
        DESCRIPTION
                "Facility type to use in encoding the priority of the
                syslog message
                    LOG_LOCAL0  ->  SYSLOG_LOG_FACILITY_LOCAL0
                    LOG_LOCAL1  ->  SYSLOG_LOG_FACILITY_LOCAL1
                        .
                        .
                    LOG_LOCAL7  ->  SYSLOG_LOG_FACILITY_LOCAL7"
        DEFVAL	{ local7 }
        ::= { wfSyslogHostEntry 5 }

    wfSyslogHostTimeSeqEnable OBJECT-TYPE
        SYNTAX	INTEGER {
    		    enabled(1),
    		    disabled(2)
    		}
        ACCESS	read-write
        STATUS	mandatory
        DESCRIPTION
                "If wfSyslogLogTimeSeqEnable is set to enabled then
                the syslog application will transmit the messages to the
                remote host in time sequenced order(This is not
                guaranteed however because the UDP transport mechanism is
                connectionless, an thus, unreliable.  The possibility
                exists for messages to be lost or delivered out of sequence )
                If this attribute is disabled then messages will be sent
                to the remote host in the order that they occur on each
                slot( i.e. no aggragation of the messages across slots
                will be performed )
                NOTE: If this value is changed while this host is
                  enabled then the possiblity exists such that
                 the remote host could receive duplicate log messages
                  or worse log messages may not be sent to the remote host.
                  The best procedure to follow would be to disable
                  the the remote host's MIB record, then set this value
                      and then enable this host's MIB record again."
        DEFVAL	{ disabled }
        ::= { wfSyslogHostEntry 6 }

    wfSyslogHostOperState OBJECT-TYPE
        SYNTAX	INTEGER {
    		    active(1),
    		    inactive(2)
    		}
        ACCESS	read-only
        STATUS	mandatory
        DESCRIPTION
                "Used to track the state of the host record.  If too
                many hosts are configured with entity filters then this
                value will be set to inactive by the syslog application."
        DEFVAL	{ inactive }
        ::= { wfSyslogHostEntry 7 }

    wfSyslogHostMsgFwds OBJECT-TYPE
        SYNTAX	Counter
        ACCESS	read-only
        STATUS	mandatory
        DESCRIPTION
                "Counter used to track the number of UDP syslog
                messages sent to this remote host"
        ::= { wfSyslogHostEntry 8 }

    wfSyslogEntityFilterTable OBJECT-TYPE
        SYNTAX	SEQUENCE OF WfSyslogEntFltrEntry
        ACCESS	not-accessible
        STATUS	mandatory
        DESCRIPTION
                "Table containing filter records for associated remote hostss"
        ::= { wfSyslogGroup 3 }

    wfSyslogEntFltrEntry OBJECT-TYPE
        SYNTAX	WfSyslogEntFltrEntry
        ACCESS	not-accessible
        STATUS	mandatory
        DESCRIPTION
                "This table is used to filter out messages by filtering
                them on a per entity basis, per remote host.  This table
                is indexed with the remote host's IP address that is to
                receive the filtered messages, a value that represents
                the entity type to filter messages on and an entity filter
                index.  All messages are passed through this filter table.
                If an instance of this table exists for a remote host, then
                a message will then be checked to see if the
                entity type of the message is equal to one specified
                in this table.  If not then it is not forwarded.  If it
                does equal the one specified in this table then the filters
                for that entity instance are applied to that message.
                Example:


                Entity    Log Event  Severity  Slot Filter
                 Type    LWBnd UPBnd   Mask    LWBnd UPBnd
                -------  -----------  ------   -----------
                88(FTP)   2      8   ''    3      6 -->All FTP log msgs
                      of value 2,3,4,5,
                     6,7,8 occurring
                     on slots 3,4,5,6
                     will be forwarded
                2( IP )   0     255   'fw'    4   4 --> All IP log msgs
                     of level
                     fault and warning
                                                             occurring on slot
                     4 will be forwarded

                 -------------------------------------------------------------
                NOTE:  A wildcard entity filter will only be used if the
                       there are no other 'non-wildcard' filters( i.e. IP,
                       FTP etc. ) enabled for the wildcard entity filter's
                       remote host.

                255(WC)    Ignored   'fwd'   4  5 --> All log msgs
                     of level fault,
                                                             warning and debug
                     occurring on slots
                     4 and 5 will be
                                                             forwarded "
        INDEX	{ wfSyslogEntFltrHostIndex,
    		  wfSyslogEntFltrNum,
    		  wfSyslogEntFltrIndex }
        ::= { wfSyslogEntityFilterTable 1 }

    WfSyslogEntFltrEntry ::= SEQUENCE {
    	    wfSyslogEntFltrDelete
    		INTEGER,
    	    wfSyslogEntFltrDisable
    		INTEGER,
    	    wfSyslogEntFltrHostIndex
    		IpAddress,
    	    wfSyslogEntFltrNum
    		INTEGER,
    	    wfSyslogEntFltrIndex
    		INTEGER,
    	    wfSyslogEntFltrOperState
    		INTEGER,
    	    wfSyslogEntFltrLogEvtLowBnd
    		INTEGER,
    	    wfSyslogEntFltrLogEvtUppBnd
    		INTEGER,
    	    wfSyslogEntFltrSevMask
    		DisplayString,
    	    wfSyslogEntFltrSlotLowBnd
    		INTEGER,
    	    wfSyslogEntFltrSlotUppBnd
    		INTEGER,
    	    wfSyslogEntFltrFaultMap
    		INTEGER,
    	    wfSyslogEntFltrWarningMap
    		INTEGER,
    	    wfSyslogEntFltrInfoMap
    		INTEGER,
    	    wfSyslogEntFltrTraceMap
    		INTEGER,
    	    wfSyslogEntFltrDebugMap
    		INTEGER,
    	    wfSyslogEntFltrName
    		DisplayString
        }

    wfSyslogEntFltrDelete OBJECT-TYPE
        SYNTAX	INTEGER {
    		    created(1),
    		    deleted(2)
    		}
        ACCESS	read-write
        STATUS	mandatory
        DESCRIPTION
                "A flag to indicate SYSLOG instance deletion
                If this flag is set to delete then it is the
                application's responsibility to delete the
                record and the respective filter table records"
        DEFVAL	{ created }
        ::= { wfSyslogEntFltrEntry 1 }

    wfSyslogEntFltrDisable OBJECT-TYPE
        SYNTAX	INTEGER {
    		    enabled(1),
    		    disabled(2)
    		}
        ACCESS	read-write
        STATUS	mandatory
        DESCRIPTION
                "Enables or Disables syslog filtering for this
                entity record"
        DEFVAL	{ enabled }
        ::= { wfSyslogEntFltrEntry 2 }

    wfSyslogEntFltrHostIndex OBJECT-TYPE
        SYNTAX	IpAddress
        ACCESS	read-only
        STATUS	mandatory
        DESCRIPTION
                "Remote Host IP address, used to associate this filter with
                a remote host in the SYSLOG_HOST_TABLE"
        ::= { wfSyslogEntFltrEntry 3 }

    wfSyslogEntFltrNum OBJECT-TYPE
        SYNTAX	INTEGER
        ACCESS	read-only
        STATUS	mandatory
        DESCRIPTION
                "Entity type to use as filter
                NOTE:  Entities are listed with their numerical mappings
                in the documentation titled 'Event Messages for Wellfleet
                Routers'
                NOTE2: If entity type is WILDCARD(255) then the attributes
                wfSyslogEntFltrLogEvtLowBnd and wfSyslogEntFltrLogEvtUppBnd will
                be ignored and wfSyslogEntFltrSevMask will be used."
        ::= { wfSyslogEntFltrEntry 4 }

    wfSyslogEntFltrIndex OBJECT-TYPE
        SYNTAX	INTEGER
        ACCESS	read-only
        STATUS	mandatory
        DESCRIPTION
                "Entity Filter Index.  Used to distinguish filters of the
                same entity type"
        ::= { wfSyslogEntFltrEntry 5 }

    wfSyslogEntFltrOperState OBJECT-TYPE
        SYNTAX	INTEGER {
    		    active(1),
    		    inactive(2)
    		}
        ACCESS	read-only
        STATUS	mandatory
        DESCRIPTION
                "This field indicates the actual stat of the syslog
                filter.  If it is equal to SYSLOG_FILTER_ACTIVE, then the
                subsystem is currently filtering events against this
                filter.  If it is SYSLOG_FILTER_INACTIVE then the subsystem is
                not filtering events against this filter because of several
                possiblities:
                1) Filter's host is not activ,
                     2) Filter does not have event range configured
                3) Filter does not have severity mask configured
                4) Slot's residing in system do not fall within
                        filter's slot range"
        DEFVAL	{ inactive }
        ::= { wfSyslogEntFltrEntry 6 }

    wfSyslogEntFltrLogEvtLowBnd OBJECT-TYPE
        SYNTAX	INTEGER
        ACCESS	read-write
        STATUS	mandatory
        DESCRIPTION
                "Lower boundary for the log event entity filter, see
                SYSLOG_ENTITY_FILTER_TABLE for more complete description
                NOTE:  Event numerical mappings are found in
                /include/<ENTITY>_edl.h"
        ::= { wfSyslogEntFltrEntry 7 }

    wfSyslogEntFltrLogEvtUppBnd OBJECT-TYPE
        SYNTAX	INTEGER
        ACCESS	read-write
        STATUS	mandatory
        DESCRIPTION
                "Upper boundary for the log event entity filter, see
                SYSLOG_ENTITY_FILTER_TABLE for more complete description"
        DEFVAL	{ 255 }
        ::= { wfSyslogEntFltrEntry 8 }

    wfSyslogEntFltrSevMask OBJECT-TYPE
        SYNTAX	DisplayString
        ACCESS	read-write
        STATUS	mandatory
        DESCRIPTION
                "Filter used to filter out log messages by error level
                (i.e. fault, informational, warning, trace and debug.
                This filter is used only if no values are specified for
                wfSyslogEntFltrLogEvtLowBnd, or if this entity type is of type
                WILDCARD(255)"
        ::= { wfSyslogEntFltrEntry 9 }

    wfSyslogEntFltrSlotLowBnd OBJECT-TYPE
        SYNTAX	INTEGER
        ACCESS	read-write
        STATUS	mandatory
        DESCRIPTION
                "Lower boundary for the entity slot filter, see
                SYSLOG_ENTITY_FILTER_TABLE for more complete description"
        ::= { wfSyslogEntFltrEntry 10 }

    wfSyslogEntFltrSlotUppBnd OBJECT-TYPE
        SYNTAX	INTEGER
        ACCESS	read-write
        STATUS	mandatory
        DESCRIPTION
                "Upper boundary for the entity slot filter, see
                SYSLOG_ENTITY_FILTER_TABLE for more complete description"
        ::= { wfSyslogEntFltrEntry 11 }

    wfSyslogEntFltrFaultMap OBJECT-TYPE
        SYNTAX	INTEGER {
    		    emerg(1),
    		    alert(2),
    		    crit(3),
    		    err(4),
    		    warning(5),
    		    notice(6),
    		    info(7),
    		    debug(8)
    		}
        ACCESS	read-write
        STATUS	mandatory
        DESCRIPTION
                "Value to Map System Fault log messages to"
        DEFVAL	{ crit }
        ::= { wfSyslogEntFltrEntry 12 }

    wfSyslogEntFltrWarningMap OBJECT-TYPE
        SYNTAX	INTEGER {
    		    emerg(1),
    		    alert(2),
    		    crit(3),
    		    err(4),
    		    warning(5),
    		    notice(6),
    		    info(7),
    		    debug(8)
    		}
        ACCESS	read-write
        STATUS	mandatory
        DESCRIPTION
                "Value to Map System Warning log messages to"
        DEFVAL	{ warning }
        ::= { wfSyslogEntFltrEntry 13 }

    wfSyslogEntFltrInfoMap OBJECT-TYPE
        SYNTAX	INTEGER {
    		    emerg(1),
    		    alert(2),
    		    crit(3),
    		    err(4),
    		    warning(5),
    		    notice(6),
    		    info(7),
    		    debug(8)
    		}
        ACCESS	read-write
        STATUS	mandatory
        DESCRIPTION
                "Value to Map System Info log messages to"
        DEFVAL	{ info }
        ::= { wfSyslogEntFltrEntry 14 }

    wfSyslogEntFltrTraceMap OBJECT-TYPE
        SYNTAX	INTEGER {
    		    emerg(1),
    		    alert(2),
    		    crit(3),
    		    err(4),
    		    warning(5),
    		    notice(6),
    		    info(7),
    		    debug(8)
    		}
        ACCESS	read-write
        STATUS	mandatory
        DESCRIPTION
                "Value to Map System Trace log messages to"
        DEFVAL	{ debug }
        ::= { wfSyslogEntFltrEntry 15 }

    wfSyslogEntFltrDebugMap OBJECT-TYPE
        SYNTAX	INTEGER {
    		    emerg(1),
    		    alert(2),
    		    crit(3),
    		    err(4),
    		    warning(5),
    		    notice(6),
    		    info(7),
    		    debug(8)
    		}
        ACCESS	read-write
        STATUS	mandatory
        DESCRIPTION
                "Value to Map System Debug log messages to"
        DEFVAL	{ debug }
        ::= { wfSyslogEntFltrEntry 16 }

    wfSyslogEntFltrName OBJECT-TYPE
        SYNTAX	DisplayString
        ACCESS	read-write
        STATUS	mandatory
        DESCRIPTION
                "Text name supplied by the user for this filter.
                 It will default so the entity name/index"
        ::= { wfSyslogEntFltrEntry 17 }


    END  -- Wellfleet-SYSL-MIB
