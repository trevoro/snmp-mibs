-- ZyXEL Communications Corporation
-- Private Enterprise MIB definition 
  
-- This file describes the ZyXEL Communications Corporation Enterprise MIB.
-- It contains ZyXEL products OIDs, and common managed objects.

-- $Log: ZYXEL-STP-MIB.mib $                                                
-- Revision 1.10  2015/04/02 01:12:13  Alan                                                
-- include zyMstpInstanceId from ZYXEL-MSTP-MIB                                                
-- Revision 1.9  2015/03/16 02:46:43  Alan                                                
-- Add ifIndex src                                                
-- Revision 1.8  2015/03/13 08:19:23  Lun                                                
-- support root guard trap.                                                
-- Revision 1.7  2015/02/16 07:11:06  Kevin                                                
-- clear warning, renaming identifier name for SMI.V2                                                
-- Revision 1.6  2015/02/06 06:14:12  Lun                                                
-- support root guard.                                                
-- Revision 1.5  2013/12/06 07:08:52  ccho 
-- remove uncessary imports 
-- Revision 1.4  2012/09/19 07:46:59  Kevin 
-- if it's leaf node, revise the vender name from zyxel to zy 
-- Revision 1.3  2012/08/22 09:49:30  Kevin 
-- clean warning for SNMPc 
-- Revision 1.2  2012/07/05 06:24:42  Kevin 
-- 1. upgrade from SNMP to SNMPv2  
-- 2. clean warning 
-- Revision 1.1  2012/05/30 07:50:47  Kevin 
-- Initial revision 

ZYXEL-STP-MIB DEFINITIONS ::= BEGIN

    IMPORTS
	OBJECT-TYPE, Integer32
		FROM SNMPv2-SMI			-- RFC2578	
		
	MODULE-IDENTITY
		FROM SNMPv2-SMI
	
	EnabledStatus
		FROM  P-BRIDGE-MIB
     
    dot1dBasePort
       	FROM BRIDGE-MIB 
	
	ifIndex
    	FROM IF-MIB					-- RFC2863
		
	zyMstpInstanceId
		FROM ZYXEL-MSTP-MIB
     
	esMgmt			
		FROM ZYXEL-ES-SMI;

	zyxelStp MODULE-IDENTITY
		LAST-UPDATED	"201207010000Z"    
		ORGANIZATION "Enterprise Solution ZyXEL"     
		CONTACT-INFO
			""	   
		DESCRIPTION
			"The subtree for Spanning Tree Protocol (STP)"
		::= { esMgmt 79 }

	zyxelStpSetup     			OBJECT IDENTIFIER ::= { zyxelStp 1 }
	zyxelStpStatus				OBJECT IDENTIFIER ::= { zyxelStp 2 }
	zyxelStpNotifications       OBJECT IDENTIFIER ::= { zyxelStp 3 }
  
-- *******************************************************************
-- *
-- * zyxelStpSetup
-- *
-- *******************************************************************

-- zyxelStpMode
		zyStpMode OBJECT-TYPE
        SYNTAX  INTEGER{
			rstp(1),
			mrstp(2),
			mstp (3)
		}
        MAX-ACCESS  read-write
        STATUS  current
        DESCRIPTION
                    "Activate one of the spanning tree protocol modes on the Switch. "
        ::= { zyxelStpSetup 1 }
		
-- zyxelStpRstpState
		zyStpRstpState	OBJECT-TYPE
		SYNTAX			EnabledStatus
        MAX-ACCESS  		read-write
        STATUS  		current
        DESCRIPTION
                    "Enable/Disable rapid spanning tree protocol. 
					You must also activate rapid spanning tree protocol mode on the switch."
        ::= { zyxelStpSetup 2}	
                                  
-- zyxelStpRootGuardRstpTable
		zyxelStpRootGuardRstpTable	OBJECT-TYPE
		SYNTAX	SEQUENCE OF	ZyxelStpRootGuardRstpPortEntry
		MAX-ACCESS  not-accessible
		STATUS  current
		DESCRIPTION
                 	"A table cantains RSTP Root Guard configuration."
		::= { zyxelStpSetup 3 }		                                  
				                              
-- zyxelStpRootGuardRstpPortEntry		
		zyxelStpRootGuardRstpPortEntry	OBJECT-TYPE                           
		SYNTAX	ZyxelStpRootGuardRstpPortEntry                           
		MAX-ACCESS	not-accessible                           
		STATUS	current
        DESCRIPTION    	
					"A entry cantains RSTP Root Guard port configuration."	
		INDEX          	{ dot1dBasePort }						
		::= { zyxelStpRootGuardRstpTable 1 }			               
		
		ZyxelStpRootGuardRstpPortEntry ::=
           SEQUENCE {
        	zyStpRootGuardRstpState		EnabledStatus
           }  
           
-- zyStpRootGuardRstpState           
        zyStpRootGuardRstpState	OBJECT-TYPE	
        SYNTAX  EnabledStatus
        MAX-ACCESS  read-write
        STATUS  current
        DESCRIPTION
                      	"Enabled/Disabled RSTP Root Guard on the indicated port."
        ::= { zyxelStpRootGuardRstpPortEntry 1 }


-- zyxelStpRootGuardMrstpTable
		zyxelStpRootGuardMrstpTable	OBJECT-TYPE
		SYNTAX	SEQUENCE OF	ZyxelStpRootGuardMrstpPortEntry
		MAX-ACCESS  not-accessible
		STATUS  current
		DESCRIPTION
                 	"A table cantains MRSTP Root Guard configuration."
		::= { zyxelStpSetup 4 }		                                  
				                              
-- zyxelStpRootGuardMrstpPortEntry		
		zyxelStpRootGuardMrstpPortEntry	OBJECT-TYPE                           
		SYNTAX	ZyxelStpRootGuardMrstpPortEntry                           
		MAX-ACCESS	not-accessible                           
		STATUS	current
        DESCRIPTION    	
					"A entry cantains MRSTP Root Guard port configuration."	
		INDEX          	{ dot1dBasePort }						
		::= { zyxelStpRootGuardMrstpTable 1 }			               
		
		ZyxelStpRootGuardMrstpPortEntry ::=
           SEQUENCE {
        	zyStpRootGuardMrstpState		EnabledStatus
           }  
           
-- zyStpRootGuardMrstpState           
        zyStpRootGuardMrstpState	OBJECT-TYPE	
        SYNTAX  EnabledStatus
        MAX-ACCESS  read-write
        STATUS  current
        DESCRIPTION
                      	"Enabled/Disabled MRSTP Root Guard on the indicated port."
        ::= { zyxelStpRootGuardMrstpPortEntry 1 }
               
               
-- zyxelStpRootGuardMstpTable
		zyxelStpRootGuardMstpTable	OBJECT-TYPE
		SYNTAX	SEQUENCE OF	ZyxelStpRootGuardMstpPortEntry
		MAX-ACCESS  not-accessible
		STATUS  current
		DESCRIPTION
                 	"A table cantains MSTP Root Guard configuration."
		::= { zyxelStpSetup 5 }		                                  
				                              
-- zyxelStpRootGuardMstpPortEntry		
		zyxelStpRootGuardMstpPortEntry	OBJECT-TYPE                           
		SYNTAX	ZyxelStpRootGuardMstpPortEntry                           
		MAX-ACCESS	not-accessible                           
		STATUS	current
        DESCRIPTION    	
					"A entry cantains MSTP Root Guard port configuration."	
		INDEX          	{ dot1dBasePort }						
		::= { zyxelStpRootGuardMstpTable 1 }			               
		
		ZyxelStpRootGuardMstpPortEntry ::=
           SEQUENCE {
        	zyStpRootGuardMstpState		EnabledStatus
           }  
           
-- zyStpRootGuardMstpState           
        zyStpRootGuardMstpState	OBJECT-TYPE	
        SYNTAX  EnabledStatus
        MAX-ACCESS  read-write
        STATUS  current
        DESCRIPTION
                      	"Enabled/Disabled MSTP Root Guard on the indicated port."
        ::= { zyxelStpRootGuardMstpPortEntry 1 }         
                                          

--****************************************************************
-- TEXTUAL-CONVENTIONs
--****************************************************************
		MstiOrCistInstanceIndex ::= TEXTUAL-CONVENTION
      		STATUS       current
    		DESCRIPTION                                                    
	            "This textual convention is an extension of the
	            MstiInstanceIndex convention.  This extension permits the
	            additional value of zero, which means Common and Internal
	            Spanning Tree (CIST)."
            SYNTAX      Integer32 (0..16)         
-- *******************************************************************
-- *                                                                                                                                                                                                          
-- * zyxelStpStatus
-- *
-- *******************************************************************
		zyxelStpRootGuardTable	OBJECT-TYPE
		SYNTAX	SEQUENCE OF	ZyxelStpRootGuardEntry
		MAX-ACCESS  not-accessible
		STATUS  current
		DESCRIPTION
                 	"A table cantains Root Guard status."    
        ::= { zyxelStpStatus 1 } 
                	
		
		zyxelStpRootGuardEntry	OBJECT-TYPE
		SYNTAX	ZyxelStpRootGuardEntry                           
		MAX-ACCESS	not-accessible                           
		STATUS	current
        DESCRIPTION    	
					"A entry cantains Root Guard status."
		INDEX	{ zyStpRootGuardInstance, dot1dBasePort }
		::= { zyxelStpRootGuardTable 1 }
		
		ZyxelStpRootGuardEntry ::=
        	SEQUENCE {
       			zyStpRootGuardInstance   		MstiOrCistInstanceIndex,
       			zyStpRootGuardStatus			INTEGER 		
          	}  
          	
        zyStpRootGuardInstance	OBJECT-TYPE	  	
        SYNTAX	MstiOrCistInstanceIndex      			        
     	MAX-ACCESS      not-accessible
        STATUS      	current
        DESCRIPTION
        ""    
        ::= { zyxelStpRootGuardEntry 1 }  	
         	
        zyStpRootGuardStatus	OBJECT-TYPE	  	
        SYNTAX      INTEGER {
           forwarding(0),
           rootInconsistent(1)
        }			        
     	MAX-ACCESS      read-only
        STATUS      	current
        DESCRIPTION
        ""    
        ::= { zyxelStpRootGuardEntry 2 }
        
-- *******************************************************************
-- *                                                                                                                                                                                                          
-- * zyxelStpNotifications
-- *
-- *******************************************************************
-- zyStpRootGuardDetect
   		zyStpRootGuardDetect NOTIFICATION-TYPE
   		OBJECTS {
               		zyStpMode, 		
                	zyMstpInstanceId,
                	ifIndex  
        }	
        STATUS  current
        DESCRIPTION
               ""     
        ::= { zyxelStpNotifications 1} 

-- zyStpRootGuardRecovered 
		zyStpRootGuardRecovered NOTIFICATION-TYPE   
        OBJECTS {
               		zyStpMode, 		
                	zyMstpInstanceId,
                	ifIndex  
        }	
        STATUS  current
        DESCRIPTION
               ""     
        ::= { zyxelStpNotifications 2}
        
END
