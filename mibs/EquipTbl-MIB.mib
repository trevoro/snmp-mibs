EquipTbl-MIB

--FORCE-INCLUDE <mib.h>
--FORCE-INCLUDE <snmpdefs.h>
--FORCE-INCLUDE "mibhand.h"

     DEFINITIONS  ::=  BEGIN

IMPORTS
     OBJECT-TYPE, Counter32, Integer32	FROM  SNMPv2-SMI
	 DateAndTime						FROM  SNMPv2-TC
	 TruthValue							FROM  SNMPv2-TC
     chrComHwNe							FROM  Chromatis-MIB
     DisplayString						FROM  RFC1213-MIB;

-- The NE Attributes leafs

chrComHwNeId		 OBJECT-TYPE
     SYNTAX      INTEGER  (0..65535)
     MAX-ACCESS  read-only
     STATUS      current
     DESCRIPTION
     "A unique ID of each NE, given to NE in its installation."
--DEFAULT  get-function-async   MNIL_GetRoutine
--DEFAULT  next-function-async  MNIL_NextRoutine
--DEFAULT  set-function-async   MNIL_SetRoutine
--DEFAULT  test-function-async  MNIL_TestRoutine
--DEFAULT  cookie  "NeAttrib"
     ::= { chrComHwNe  1 }

chrComHwNeType  OBJECT-TYPE
     SYNTAX      INTEGER {
						metropolis2000(1),
						metropolis2500(2),
						metropolis4000(3),
						metropolis4500(4)
						 }
     MAX-ACCESS  read-only
     STATUS      current
     DESCRIPTION
     "Metropolis2000 - Terminal
	  Metropolis2500 - Enhanced Terminal
	  Metropolis4000 - Standard HE
	  Metropolis4500 - Enhanced HE."
--DEFAULT  get-function-async   MNIL_GetRoutine
--DEFAULT  next-function-async  MNIL_NextRoutine
--DEFAULT  set-function-async   MNIL_SetRoutine
--DEFAULT  test-function-async  MNIL_TestRoutine
--DEFAULT  cookie  "NeAttrib"
     ::= { chrComHwNe  2 }

chrComHwNeRunningSwVersion		OBJECT-TYPE
	SYNTAX		DisplayString   (SIZE (0..9))
	MAX-ACCESS	read-only
	STATUS		current
	DESCRIPTION
		"The NE running SW Version - represented by XX.YY.ZZZ "
--DEFAULT  get-function-async   MNIL_GetRoutine
--DEFAULT  next-function-async  MNIL_NextRoutine
--DEFAULT  set-function-async   MNIL_SetRoutine
--DEFAULT  test-function-async  MNIL_TestRoutine
--DEFAULT  cookie  "NeAttrib"
	::= { chrComHwNe  3 }

chrComHwNeAvailableSwVersion	OBJECT-TYPE
	SYNTAX		DisplayString	(SIZE (0..18))
	MAX-ACCESS	read-only
	STATUS		current
	DESCRIPTION
		"List of SW versions that might be switched with the current running one -
                          represented by list of: XX.YY.ZZZ "
--DEFAULT  get-function-async   MNIL_GetRoutine
--DEFAULT  next-function-async  MNIL_NextRoutine
--DEFAULT  set-function-async   MNIL_SetRoutine
--DEFAULT  test-function-async  MNIL_TestRoutine
--DEFAULT  cookie  "NeAttrib"
	::= { chrComHwNe  4 }

chrComHwNeNextSessionSwVersion	OBJECT-TYPE
	SYNTAX		DisplayString	(SIZE (0..9))
	MAX-ACCESS	read-write
	STATUS		current
	DESCRIPTION
		"The SW Version that shall be switched with the current running one - 
                          represented by XX.YY.ZZZ "
--DEFAULT  get-function-async   MNIL_GetRoutine
--DEFAULT  next-function-async  MNIL_NextRoutine
--DEFAULT  set-function-async   MNIL_SetRoutine
--DEFAULT  test-function-async  MNIL_TestRoutine
--DEFAULT  cookie  "NeAttrib"
	::= { chrComHwNe  5 }

chrComHwNeRunningConfigurationSet	OBJECT-TYPE
	SYNTAX		DisplayString	(SIZE (0..12))
	MAX-ACCESS	read-only
	STATUS		current
	DESCRIPTION
		"The current configuration file "
--DEFAULT  get-function-async   MNIL_GetRoutine
--DEFAULT  next-function-async  MNIL_NextRoutine
--DEFAULT  set-function-async   MNIL_SetRoutine
--DEFAULT  test-function-async  MNIL_TestRoutine
--DEFAULT  cookie  "NeAttrib"
	::= { chrComHwNe  6 }

chrComHwNeAvailableConfigurationSets	OBJECT-TYPE
	SYNTAX		DisplayString	(SIZE (0..120))
	MAX-ACCESS	read-only
	STATUS		current
	DESCRIPTION
		"List configuration files that might be switched with the current
		 one used by the running software."
--DEFAULT  get-function-async   MNIL_GetRoutine
--DEFAULT  next-function-async  MNIL_NextRoutine
--DEFAULT  set-function-async   MNIL_SetRoutine
--DEFAULT  test-function-async  MNIL_TestRoutine
--DEFAULT  cookie  "NeAttrib"
	::= { chrComHwNe  7 }

chrComHwNeNextSessionConfigurationSet	OBJECT-TYPE
	SYNTAX		DisplayString	(SIZE (0..12))
	MAX-ACCESS	read-write
	STATUS		current
	DESCRIPTION
		"The configuration file that shall be switched with the current one."
--DEFAULT  get-function-async   MNIL_GetRoutine
--DEFAULT  next-function-async  MNIL_NextRoutine
--DEFAULT  set-function-async   MNIL_SetRoutine
--DEFAULT  test-function-async  MNIL_TestRoutine
--DEFAULT  cookie  "NeAttrib"
	::= { chrComHwNe  8 }

chrComHwNeTimeofDay		OBJECT-TYPE
	SYNTAX		DateAndTime
	MAX-ACCESS	read-write
	STATUS		current
	DESCRIPTION
		"The NE Time of Day represented by - MM-DD-YYYY HH:MM:SS"
--DEFAULT  get-function-async   MNIL_GetRoutine
--DEFAULT  next-function-async  MNIL_NextRoutine
--DEFAULT  set-function-async   MNIL_SetRoutine
--DEFAULT  test-function-async  MNIL_TestRoutine
--DEFAULT  cookie  "NeAttrib"
	::= { chrComHwNe  9 }

chrComHwNeDailyPMStartOfTime		OBJECT-TYPE
	SYNTAX		Integer32		(0..23)
	MAX-ACCESS	read-write
	STATUS		current
	DESCRIPTION
		"Describes the PM loging start time "
--DEFAULT  get-function-async   MNIL_GetRoutine
--DEFAULT  next-function-async  MNIL_NextRoutine
--DEFAULT  set-function-async   MNIL_SetRoutine
--DEFAULT  test-function-async  MNIL_TestRoutine
--DEFAULT  cookie  "NeAttrib"
	::= { chrComHwNe  10 }

chrComHwNeCriticalAlarmCounter	OBJECT-TYPE
	SYNTAX		Counter32
	MAX-ACCESS	read-only
	STATUS		current
	DESCRIPTION
		"Specifies the number of Critical Alarms for the NE. "
--DEFAULT  get-function-async   MNIL_GetRoutine
--DEFAULT  next-function-async  MNIL_NextRoutine
--DEFAULT  set-function-async   MNIL_SetRoutine
--DEFAULT  test-function-async  MNIL_TestRoutine
--DEFAULT  cookie  "NeAttrib"
	::= { chrComHwNe  11  }

chrComHwNeMajorAlarmCounter	OBJECT-TYPE
	SYNTAX		Counter32
	MAX-ACCESS	read-only
	STATUS		current
	DESCRIPTION
		"Specifies the number of Major Alarms for the NE. "
--DEFAULT  get-function-async   MNIL_GetRoutine
--DEFAULT  next-function-async  MNIL_NextRoutine
--DEFAULT  set-function-async   MNIL_SetRoutine
--DEFAULT  test-function-async  MNIL_TestRoutine
--DEFAULT  cookie  "NeAttrib"
	::= { chrComHwNe  12  }

chrComHwNeMinorAlarmCounter	OBJECT-TYPE
	SYNTAX		Counter32
	MAX-ACCESS	read-only
	STATUS		current
	DESCRIPTION
		"Specifies the number of Minor Alarms for the NE. "
--DEFAULT  get-function-async   MNIL_GetRoutine
--DEFAULT  next-function-async  MNIL_NextRoutine
--DEFAULT  set-function-async   MNIL_SetRoutine
--DEFAULT  test-function-async  MNIL_TestRoutine
--DEFAULT  cookie  "NeAttrib"
	::= { chrComHwNe  13  }

chrComHwNeDetectionFaultStabilizationTime	OBJECT-TYPE
	SYNTAX		Integer32		(0..50)
	MAX-ACCESS	read-write
	STATUS		current
	DESCRIPTION
		"The time the NE waits before reporting an occurrence of alarm
		 to the NMS."
--DEFAULT  get-function-async   MNIL_GetRoutine
--DEFAULT  next-function-async  MNIL_NextRoutine
--DEFAULT  set-function-async   MNIL_SetRoutine
--DEFAULT  test-function-async  MNIL_TestRoutine
--DEFAULT  cookie  "NeAttrib"
	::= { chrComHwNe  14  }

chrComHwNeRemovalFaultStabilizationTime	OBJECT-TYPE
	SYNTAX		Integer32		(0..150)
	MAX-ACCESS	read-write
	STATUS		current
	DESCRIPTION
		"The time the NE waits before reporting clearing of alarm to NMS."
--DEFAULT  get-function-async   MNIL_GetRoutine
--DEFAULT  next-function-async  MNIL_NextRoutine
--DEFAULT  set-function-async   MNIL_SetRoutine
--DEFAULT  test-function-async  MNIL_TestRoutine
--DEFAULT  cookie  "NeAttrib"
	::= { chrComHwNe  15  }

chrComHwNeAlarmCutOffStatus	OBJECT-TYPE
	SYNTAX		TruthValue
	MAX-ACCESS	read-only
	STATUS		current
	DESCRIPTION
		"Alarm Cut Off current status. "
--DEFAULT  get-function-async   MNIL_GetRoutine
--DEFAULT  next-function-async  MNIL_NextRoutine
--DEFAULT  set-function-async   MNIL_SetRoutine
--DEFAULT  test-function-async  MNIL_TestRoutine
--DEFAULT  cookie  "NeAttrib"
	::= { chrComHwNe  16  }

chrComHwNeAtmfM4NeSuppressZeroStats	OBJECT-TYPE
	SYNTAX		TruthValue
	MAX-ACCESS	read-write
	STATUS		current
	DESCRIPTION
		"When the vaule of this type is true, no PM entry will be created
		 in any of the historical statistics tables for intervals in which
		 all counts are zero"
--DEFAULT  get-function-async   MNIL_GetRoutine
--DEFAULT  next-function-async  MNIL_NextRoutine
--DEFAULT  set-function-async   MNIL_SetRoutine
--DEFAULT  test-function-async  MNIL_TestRoutine
--DEFAULT  cookie  "NeAttrib"
	::= { chrComHwNe  17  }

chrComHwNeResetPMCountersAction	OBJECT-TYPE
	SYNTAX		TruthValue
	MAX-ACCESS	read-write
	STATUS		current
	DESCRIPTION
		"This action enables resetting all preformance management
		counters currently measured by the NE (reset all xxxCurrentTable
		primitives). 
		Note that PM might be reset also per entity (e.g. per one specifc Sonet
		Line interface).
		This value is set to True for activation of the reset action.
		On completion the NE sets back to False."
--DEFAULT  get-function-async   MNIL_GetRoutine
--DEFAULT  next-function-async  MNIL_NextRoutine
--DEFAULT  set-function-async   MNIL_SetRoutine
--DEFAULT  test-function-async  MNIL_TestRoutine
--DEFAULT  cookie  "NeAttrib"
	::= { chrComHwNe  18  }

chrComHwNeACOActivationAction	OBJECT-TYPE
	SYNTAX		TruthValue
	MAX-ACCESS	read-write
	STATUS		current
	DESCRIPTION
		"Alarm Cut Off activation operation.
		This value is set to True for activation of the ACO action.
		On completion the NE sets back to False."
--DEFAULT  get-function-async   MNIL_GetRoutine
--DEFAULT  next-function-async  MNIL_NextRoutine
--DEFAULT  set-function-async   MNIL_SetRoutine
--DEFAULT  test-function-async  MNIL_TestRoutine
--DEFAULT  cookie  "NeAttrib"
	::= { chrComHwNe  19  }

chrComHwNeAtmCbrRatesList 	OBJECT-TYPE
	SYNTAX		OCTET STRING	(SIZE (0..128))
	MAX-ACCESS 	read-write
	STATUS 		current
	DESCRIPTION
		"This vector includes 32 CBR peak cell
		rates that are supported in the network."
--DEFAULT  get-function-async   MNIL_GetRoutine
--DEFAULT  next-function-async  MNIL_NextRoutine
--DEFAULT  set-function-async   MNIL_SetRoutine
--DEFAULT  test-function-async  MNIL_TestRoutine
--DEFAULT  cookie  "NeAttrib"
	::= { chrComHwNe  20  }

chrComHwNeAtmRtVbrRatesList 	OBJECT-TYPE
	SYNTAX		OCTET STRING	(SIZE (0..64))
	MAX-ACCESS 	read-write
	STATUS 		current
	DESCRIPTION
		"This vector includes the 16 RT-VBR Sustainable
		cell rates that are supported in the network."
--DEFAULT  get-function-async   MNIL_GetRoutine
--DEFAULT  next-function-async  MNIL_NextRoutine
--DEFAULT  set-function-async   MNIL_SetRoutine
--DEFAULT  test-function-async  MNIL_TestRoutine
--DEFAULT  cookie  "NeAttrib"
	::= { chrComHwNe  21  }

chrComHwNeMaxPathPM	OBJECT-TYPE
	SYNTAX		Integer32		(0..65535)
	MAX-ACCESS	read-only
	STATUS		current
	DESCRIPTION
		"The maximum number of paths for which PM might be collected."
--DEFAULT  get-function-async   MNIL_GetRoutine
--DEFAULT  next-function-async  MNIL_NextRoutine
--DEFAULT  set-function-async   MNIL_SetRoutine
--DEFAULT  test-function-async  MNIL_TestRoutine
--DEFAULT  cookie  "NeAttrib"
	::= { chrComHwNe  22  }

chrComHwNeCurrentPathPM	OBJECT-TYPE
	SYNTAX		Integer32		(0..65535)
	MAX-ACCESS	read-only
	STATUS		current
	DESCRIPTION
		"The actual number of paths for which PM is currently collected."
--DEFAULT  get-function-async   MNIL_GetRoutine
--DEFAULT  next-function-async  MNIL_NextRoutine
--DEFAULT  set-function-async   MNIL_SetRoutine
--DEFAULT  test-function-async  MNIL_TestRoutine
--DEFAULT  cookie  "NeAttrib"
	::= { chrComHwNe  23  }

chrComHwNeGlobalSubnetID 	OBJECT-TYPE
	SYNTAX		OCTET STRING	(SIZE (0..8))
	MAX-ACCESS 	read-write
	STATUS 		current
	DESCRIPTION
		"Array of two entries: Subnet #1 Global ID, Subnet #2 Global ID."
--DEFAULT  get-function-async   MNIL_GetRoutine
--DEFAULT  next-function-async  MNIL_NextRoutine
--DEFAULT  set-function-async   MNIL_SetRoutine
--DEFAULT  test-function-async  MNIL_TestRoutine
--DEFAULT  cookie  "NeAttrib"
	::= { chrComHwNe  24  }



END
