ChrComPmSonetSNT-LFE-Day-MIB

--FORCE-INCLUDE	<mib.h>
--FORCE-INCLUDE	<snmpdefs.h>
--FORCE-INCLUDE	"mibhand.h"

	DEFINITIONS  ::=  BEGIN

IMPORTS
	OBJECT-TYPE, Counter32			FROM  SNMPv2-SMI
	Integer32, Unsigned32			FROM  SNMPv2-SMI
	chrComPmSonet				FROM  Chromatis-MIB
	chrComIfifIndex					FROM  ChrComIfifTable-MIB
	TruthValue				FROM  ChrTyp-MIB
	Gauge32				FROM  SNMPv2-SMI;

-- chrComPmSonetSNT-LFE-Day Table

chrComPmSonetSNT-LFE-DayTable		OBJECT-TYPE
	SYNTAX		SEQUENCE OF ChrComPmSonetSNT-LFE-DayEntry
	MAX-ACCESS	not-accessible
	STATUS		current
	DESCRIPTION
	""
	::= { chrComPmSonet 9}

chrComPmSonetSNT-LFE-DayEntry		OBJECT-TYPE
	SYNTAX		ChrComPmSonetSNT-LFE-DayEntry
	MAX-ACCESS	not-accessible
	STATUS		current
	DESCRIPTION
	""
	INDEX  {  chrComIfifIndex, chrComPmSonetDayNumber }

--DEFAULT  get-function-async  MNIL_GetRoutine
--DEFAULT  set-function-async  MNIL_SetRoutine
--DEFAULT  next-function-async MNIL_NextRoutine
--DEFAULT  test-function-async MNIL_TestRoutine
--DEFAULT  cookie "SNT-LFE-Day"
	::= { chrComPmSonetSNT-LFE-DayTable  1 }

ChrComPmSonetSNT-LFE-DayEntry  ::=
	SEQUENCE  {
	chrComPmSonetDayNumber		Unsigned32	(1..2),
	chrComPmSonetSuspectedInterval	TruthValue,
	chrComPmSonetElapsedTime		Unsigned32	(0..4294967295),
	chrComPmSonetSuppressedIntrvls	Gauge32			(0..4294967295),
	chrComPmSonetES			Gauge32			(0..4294967295),
	chrComPmSonetSES			Gauge32			(0..4294967295),
	chrComPmSonetCV			Gauge32			(0..4294967295),
	chrComPmSonetUAS			Gauge32			(0..4294967295),
	chrComPmSonetThresholdProfIndex	Unsigned32	(0..4294967295),
	chrComPmSonetResetPmCountersAction	TruthValue
}

chrComPmSonetDayNumber 	OBJECT-TYPE
	SYNTAX		Unsigned32	(1..2)
	MAX-ACCESS 	read-only
	STATUS 		current
	DESCRIPTION
	""
	::= { chrComPmSonetSNT-LFE-DayEntry  1 }

chrComPmSonetSuspectedInterval 	OBJECT-TYPE
	SYNTAX		TruthValue
	MAX-ACCESS 	read-only
	STATUS 		current
	DESCRIPTION
	""
	::= { chrComPmSonetSNT-LFE-DayEntry  2 }

chrComPmSonetElapsedTime 	OBJECT-TYPE
	SYNTAX		Unsigned32	(0..4294967295)
	MAX-ACCESS 	read-only
	STATUS 		current
	DESCRIPTION
	""
	::= { chrComPmSonetSNT-LFE-DayEntry  3 }

chrComPmSonetSuppressedIntrvls 	OBJECT-TYPE
	SYNTAX		Gauge32			(0..4294967295)
	MAX-ACCESS 	read-only
	STATUS 		current
	DESCRIPTION
	""
	::= { chrComPmSonetSNT-LFE-DayEntry  4 }

chrComPmSonetES 	OBJECT-TYPE
	SYNTAX		Gauge32			(0..4294967295)
	MAX-ACCESS 	read-only
	STATUS 		current
	DESCRIPTION
	""
	::= { chrComPmSonetSNT-LFE-DayEntry  5 }

chrComPmSonetSES 	OBJECT-TYPE
	SYNTAX		Gauge32			(0..4294967295)
	MAX-ACCESS 	read-only
	STATUS 		current
	DESCRIPTION
	""
	::= { chrComPmSonetSNT-LFE-DayEntry  6 }

chrComPmSonetCV 	OBJECT-TYPE
	SYNTAX		Gauge32			(0..4294967295)
	MAX-ACCESS 	read-only
	STATUS 		current
	DESCRIPTION
	""
	::= { chrComPmSonetSNT-LFE-DayEntry  7 }

chrComPmSonetUAS 	OBJECT-TYPE
	SYNTAX		Gauge32			(0..4294967295)
	MAX-ACCESS 	read-only
	STATUS 		current
	DESCRIPTION
	""
	::= { chrComPmSonetSNT-LFE-DayEntry  8 }

chrComPmSonetThresholdProfIndex 	OBJECT-TYPE
	SYNTAX		Unsigned32	(0..4294967295)
	MAX-ACCESS 	read-only
	STATUS 		current
	DESCRIPTION
	""
	::= { chrComPmSonetSNT-LFE-DayEntry  9 }

chrComPmSonetResetPmCountersAction 	OBJECT-TYPE
	SYNTAX		TruthValue
	MAX-ACCESS 	read-write
	STATUS 		current
	DESCRIPTION
	""
	::= { chrComPmSonetSNT-LFE-DayEntry  10 }


END
