DQLEXT-MIB 

   --FORCE-INCLUDE <mib.h>
   --FORCE-INCLUDE <snmpdefs.h>
   --FORCE-INCLUDE <snmpstat.h>
   --FORCE-INCLUDE "mibproto.h"
 
	DEFINITIONS ::= BEGIN

	IMPORTS
		MODULE-IDENTITY, OBJECT-TYPE, Integer32
			FROM SNMPv2-SMI
		DisplayString, RowStatus
			FROM SNMPv2-TC
		dqlExt
			FROM APENT-MIB;

--DQLEXT MIB

    apDqlExtMib MODULE-IDENTITY
	   LAST-UPDATED "9710092000Z" -- Thu October 9 20:00:00 EST 1997
	   ORGANIZATION "ArrowPoint Communications Inc."
	   CONTACT-INFO
	   "                      
	   Postal:               ArrowPoint Communications Inc.
				                 50 Nagog Park
				                 Acton, Massachusetts 01720
	   Tel:                   +1 978-206-3000  option 1
	   E-Mail:                support@arrowpoint.com"
       DESCRIPTION
	  "The MIB module used to describe the ArrowPoint Communications
	  Domain Qualifier Lists (DQLs)"
      ::= { dqlExt 1}


apDqlTable OBJECT-TYPE
	SYNTAX          SEQUENCE OF APDqlEntry
	MAX-ACCESS      not-accessible
	STATUS          current
	DESCRIPTION
		"A list of DQLs"
	::= { dqlExt 2 }

apDqlEntry OBJECT-TYPE
	SYNTAX          APDqlEntry
	MAX-ACCESS      not-accessible
	STATUS          current
	DESCRIPTION
		"A group of information uniquely identifying an DQL. One entry
         exists for each DQL"
	INDEX   { apDqlName }
	::= { apDqlTable 1 }

APDqlEntry ::= SEQUENCE {
	apDqlStatus			RowStatus,
	apDqlName			DisplayString,
	apDqlDescription	DisplayString
}


apDqlStatus OBJECT-TYPE
	SYNTAX          RowStatus
	MAX-ACCESS      read-create
	STATUS          current
	DESCRIPTION      
		"Status entry for this row "
	::= {apDqlEntry 1}

apDqlName OBJECT-TYPE
	SYNTAX          DisplayString (SIZE(1..31))
	MAX-ACCESS      read-create
	STATUS          current
	DESCRIPTION     
			"The name of the DQL"
	::= {apDqlEntry 2}

apDqlDescription OBJECT-TYPE
	SYNTAX          DisplayString (SIZE(0..63))
	MAX-ACCESS      read-create
	STATUS          current
	DESCRIPTION     
			"An DQL description"
	::= {apDqlEntry 3}

apDqlDomainTable OBJECT-TYPE
	SYNTAX          SEQUENCE OF APDqlDomainEntry
	MAX-ACCESS      not-accessible
	STATUS          current
	DESCRIPTION
		"A list of domain names associated with an DQL"
	::= { dqlExt 3 }

apDqlDomainEntry OBJECT-TYPE
	SYNTAX          APDqlDomainEntry
	MAX-ACCESS      not-accessible
	STATUS          current
	DESCRIPTION
		"Information uniquely identifying a domain name within an DQL"
	INDEX   { apDqlName,apDqlDomainName }
	::= { apDqlDomainTable 1 }

APDqlDomainEntry ::= SEQUENCE {
	apDqlDomainStatus		RowStatus,
	apDqlDomainName			DisplayString,
	apDqlDomainDescription	DisplayString,
	apDqlDomainBucketIndex  Integer32
}

apDqlDomainStatus OBJECT-TYPE
	SYNTAX          RowStatus
	MAX-ACCESS      read-create
	STATUS          current
	DESCRIPTION      
		"Status entry for this row"
	::= {apDqlDomainEntry 1}

apDqlDomainName OBJECT-TYPE
	SYNTAX			DisplayString (SIZE(0..63))
	MAX-ACCESS      read-create
	STATUS          current
	DESCRIPTION     
			"The Domain Name"
	::= {apDqlDomainEntry 2}

apDqlDomainDescription OBJECT-TYPE
	SYNTAX          DisplayString (SIZE(0..63))
	MAX-ACCESS      read-create
	STATUS          current
	DESCRIPTION      
		"Description of this domain name"
	::= {apDqlDomainEntry 3}

apDqlDomainBucketIndex OBJECT-TYPE
	SYNTAX          Integer32 (0..10000)
	MAX-ACCESS      read-create
	STATUS          current
	DESCRIPTION      
		"Index of the domain name in the DQL list"
	DEFVAL          {0}
	::= {apDqlDomainEntry 4}

END
