-- Version 2.15.1.1, modified 2001-05-31 17:27:19-04

        ALC-OPT-MIB DEFINITIONS ::= BEGIN

        IMPORTS
            Counter,
            Gauge, enterprises
                FROM RFC1155-SMI

            OBJECT-TYPE
                FROM RFC-1212;

        -- Codex MIB Group definitions

                      codex OBJECT IDENTIFIER ::= { enterprises 449 }
         cdxProductSpecific OBJECT IDENTIFIER ::= { codex 2 }
                    cdx6500 OBJECT IDENTIFIER ::= { cdxProductSpecific 1 }

      cdx6500Configuration  OBJECT IDENTIFIER ::= { cdx6500 2 }
    cdx6500CfgProtocolGroup OBJECT IDENTIFIER ::= { cdx6500Configuration 1 }
cdx6500PCTPortProtocolGroup OBJECT IDENTIFIER ::= { cdx6500CfgProtocolGroup 1 }

          cdx6500Statistics OBJECT IDENTIFIER ::= { cdx6500 3 }
   cdx6500StatProtocolGroup OBJECT IDENTIFIER ::= { cdx6500Statistics 1 }
cdx6500PSTPortProtocolGroup OBJECT IDENTIFIER ::= { cdx6500StatProtocolGroup 1 }

            cdx6500Controls OBJECT IDENTIFIER ::= { cdx6500 4 }

        -- Textual Conventions

        DisplayString ::= OCTET STRING
        -- This data type is used to model textual information taken
        -- from the NVT ASCII character set.  By convention, objects
        -- with this syntax are declared as having SIZE (0..255)


        -- The ALC Port Configuration Table

        cdx6500PPCTALCCfgTable OBJECT IDENTIFIER ::=
            { cdx6500PCTPortProtocolGroup 27 }

        cdx6500PPCTALCPortTable OBJECT-TYPE
            SYNTAX SEQUENCE OF Cdx6500PPCTALCPortEntry
            ACCESS not-accessible
            STATUS mandatory
            DESCRIPTION
                "This table contains ALC Port configuration parameters"
            ::= { cdx6500PPCTALCCfgTable 1 }

        cdx6500PPCTALCPortEntry OBJECT-TYPE
            SYNTAX Cdx6500PPCTALCPortEntry
            ACCESS not-accessible
            STATUS mandatory
            DESCRIPTION
                "Entries in the ALC Port Configuration Table."
            INDEX { alcPCfgPortNumber }
        ::= { cdx6500PPCTALCPortTable 1 }

        Cdx6500PPCTALCPortEntry ::=
            SEQUENCE {
                alcPCfgPortNumber
                    INTEGER,
                alcPCfgPortType
                    INTEGER,
                alcPCfgSubtype
                    INTEGER,
                alcPCfgPortControl
                    INTEGER,
                alcPCfgClockSource
                    INTEGER,
                alcPCfgClockSpeed
                    INTEGER,
                alcPCfgPollDelayTimer
                    INTEGER,
                alcPCfgHostTimeout
                    INTEGER,
                alcPCfgMaxMesgSize
                    INTEGER,
                alcPCfgMinIntrvlBetweenPolls
                    INTEGER,
                alcPCfgRtsCtsTimeout
                    INTEGER,
                alcPCfgLeadPadChar
                    OCTET STRING,
                alcPCfgNumLeadPadChars
                    INTEGER,
                alcPCfgTrailPadChar
                    OCTET STRING,
                alcPCfgNumTrailPadChars
                    INTEGER,
                alcPCfgALCLineOptions
                    DisplayString,
                alcPCfgConnType
                    INTEGER,
                alcPCfgAcallMnemonic
                    DisplayString,
                alcPCfgCallingAddress
                    DisplayString,
                alcPCfgCUD
                    DisplayString,
                alcPCfgNumOfBuffers
                    INTEGER,
                alcPCfgInHeader
                    DisplayString,
                alcPCfgOutHeader
                    DisplayString,
                alcPCfgReconnectTimeout
                    INTEGER,
                alcPCfgInactivityTimeout
                    INTEGER,
                alcPCfgDebounceTimeout
                    INTEGER,
                alcPCfgParity
                    INTEGER,
                alcPCfgConnOptions
                    DisplayString,
                alcPCfgAvailableMesg
                    DisplayString,
                alcPCfgUnavailableMesg
                    DisplayString
            }

        alcPCfgPortNumber OBJECT-TYPE
            SYNTAX INTEGER (1..54)
            ACCESS read-only
            STATUS mandatory
            DESCRIPTION
                "Port number of this port."
        ::= { cdx6500PPCTALCPortEntry 1 }

        alcPCfgPortType OBJECT-TYPE
            SYNTAX INTEGER {
                    alc  (31)
                    }
            ACCESS read-only
            STATUS mandatory
            DESCRIPTION
                "Port Type of this port."
        ::= { cdx6500PPCTALCPortEntry 2 }

        alcPCfgSubtype OBJECT-TYPE
            SYNTAX INTEGER {
                    alcHpad (1),
                    alcTpad (2)
                    }
            ACCESS read-only
            STATUS mandatory
            DESCRIPTION
                "This is the ALC port subtype.
                 alcHpad - Host PAD.
                 alcTpad - Terminal PAD."
        ::= { cdx6500PPCTALCPortEntry 3 }

        alcPCfgPortControl OBJECT-TYPE
            SYNTAX INTEGER {
                    simp    (1),
                    emri    (4),
                    emdc    (5),
                    dtr     (13),
                    alcDte (15)
                    }
            ACCESS read-only
            STATUS mandatory
            DESCRIPTION
                "Specify any of the following port control options:
                 simp    : Simple connection with no control signal handshake.
                 dtr     : Connection with DTR control signal handshake.
                 emri    : Port emulates a modem and does dial-in/out handshake
                           with RI.
                 emdc    : Port emulates a modem and does dial-in/out handshake
                           with DCD.
                 alcDte : DTE emulation with RTS/CTS handshake."
        ::= { cdx6500PPCTALCPortEntry 4 }

        alcPCfgClockSource OBJECT-TYPE
            SYNTAX INTEGER {
                    int (1),
                    ext (2)
                    }
            ACCESS read-only
            STATUS mandatory
            DESCRIPTION
                "int : Internal clock source.
                 ext : External clock source."
        ::= { cdx6500PPCTALCPortEntry 5 }

        alcPCfgClockSpeed OBJECT-TYPE
            SYNTAX INTEGER {
                    clkspd1200  (1),
                    clkspd2400  (2),
                    clkspd4800  (3),
                    clkspd9600  (4),
                    clkspd19200 (5),
                    clkspd38400 (6)
                    }
            ACCESS read-only
            STATUS mandatory
            DESCRIPTION
                "This is the speed of the port in bits per second, 
                 when using internal clocking."
        ::= { cdx6500PPCTALCPortEntry 6 }

        alcPCfgPollDelayTimer OBJECT-TYPE
            SYNTAX INTEGER (50..100000)
            ACCESS read-only
            STATUS mandatory
            DESCRIPTION
                "This is the delay in milliseconds to impose between poll 
                 cycles if no interchanges are polled. Valid on TPAD lines 
                 only."
        ::= { cdx6500PPCTALCPortEntry 7 }

        alcPCfgHostTimeout OBJECT-TYPE
            SYNTAX INTEGER (50..10000)
            ACCESS read-only
            STATUS mandatory
            DESCRIPTION
                "On a poll coerced line, the host is considered to be down 
                 if a poll is not received within this time, specified in 
                 milliseconds. Valid on HPAD lines only."
        ::= { cdx6500PPCTALCPortEntry 8 }

        alcPCfgMaxMesgSize OBJECT-TYPE
            SYNTAX INTEGER (10..10000)
            ACCESS read-only
            STATUS mandatory
            DESCRIPTION
                "This specifies the maximum size of messages that can be sent
                 or received on this line excluding padding characters. TPAD 
                 may receive multiple messages in a frame, HPAD may transmit 
                 multiple messages in a frame."
        ::= { cdx6500PPCTALCPortEntry 9 }

        alcPCfgMinIntrvlBetweenPolls OBJECT-TYPE
            SYNTAX INTEGER (0..100000)
            ACCESS read-only
            STATUS mandatory
            DESCRIPTION
                "The minimum length of time, in milliseconds, between polls 
                 issued on this line. Valid on TPAD lines only."
        ::= { cdx6500PPCTALCPortEntry 10 }

        alcPCfgRtsCtsTimeout OBJECT-TYPE
            SYNTAX INTEGER (50..10000)
            ACCESS read-only
            STATUS mandatory
            DESCRIPTION
                "The time in milliseconds, within which CTS must be raised 
                 following the RTS signal."
        ::= { cdx6500PPCTALCPortEntry 11 }

        alcPCfgLeadPadChar OBJECT-TYPE
            SYNTAX OCTET STRING
            ACCESS read-only
            STATUS mandatory
            DESCRIPTION
                "This is the character to use when inserting leading padding 
                 characters."
        ::= { cdx6500PPCTALCPortEntry 12 }

        alcPCfgNumLeadPadChars OBJECT-TYPE
            SYNTAX INTEGER (0..100)
            ACCESS read-only
            STATUS mandatory
            DESCRIPTION
                "This is the number of leading padding characters to use."
        ::= { cdx6500PPCTALCPortEntry 13 }

        alcPCfgTrailPadChar OBJECT-TYPE
            SYNTAX OCTET STRING
            ACCESS read-only
            STATUS mandatory
            DESCRIPTION
                "This is the character to use when inserting trailing padding 
                 characters."
        ::= { cdx6500PPCTALCPortEntry 14 }

        alcPCfgNumTrailPadChars OBJECT-TYPE
            SYNTAX INTEGER (0..100)
            ACCESS read-only
            STATUS mandatory
            DESCRIPTION
                "This is the number of trailing padding characters to use."
        ::= { cdx6500PPCTALCPortEntry 15 }

        alcPCfgALCLineOptions OBJECT-TYPE
            SYNTAX DisplayString (SIZE(4..71))
            ACCESS read-only
            STATUS mandatory
            DESCRIPTION
                "Select options on this ALC port as follows:
                 NONE       : no option specified
                 EMB_SYNC   : Sychronization characters are inserted between 
                              messages in the same frame.
                 MASK8      : Indicates that the `8' bit is treated as zero 
                              when examining interchange addresses on this line.
                 COERCE     : Poll coercion is used.
                 CLASH      : Poll responses will be aborted if a poll is 
                              received whilst a response to a previous poll is 
                              being transmitted.
                 RFRTM      : Responses will be generated to Response and 
                              Forward RTM messages.
                 RZRTM      : Responses will be generated to enquiry RTM 
                              messages.
                 SOFT_SYNC  : Selects software synchronization.
                 NULLS      : Nulls are allowed in the data stream.
                 BACKTOBACK : Frames may be received back to back.
                 Any combination of the above maybe specified by summing
                 (e.g. NULLS+BACKTOBACK. . .)."
        ::= { cdx6500PPCTALCPortEntry 16 }

        alcPCfgConnType OBJECT-TYPE
            SYNTAX INTEGER {
                    none (1),
                    x25  (2),
                    nc   (100)
                   }
            ACCESS read-only
            STATUS mandatory
            DESCRIPTION
                "none : No connection.
                 x25  : Connection type is X.25.
                 nc   : Skipped during configuration"
        ::= { cdx6500PPCTALCPortEntry 17 }

        alcPCfgAcallMnemonic OBJECT-TYPE
            SYNTAX DisplayString (SIZE(0..8))
            ACCESS read-only
            STATUS mandatory
            DESCRIPTION
                "This is the mnemonic to be used to establish the call when 
                 the call request is issued. The mnemonic must be defined in
                 the mnemonic table. If no mnemonic is specified, ALP PAD will
                 wait for the call. It consists of 0-8 alphanumeric characters,
                 and the space character is used to blank the field."
        ::= { cdx6500PPCTALCPortEntry 18 }

        alcPCfgCallingAddress OBJECT-TYPE
            SYNTAX DisplayString (SIZE(0..15))
            ACCESS read-only
            STATUS mandatory
            DESCRIPTION
                "The calling address to be used in outbound calls. It consists 
                 of 0-15 BCD digits, and the space character is used to blank 
                 the field."
        ::= { cdx6500PPCTALCPortEntry 19 }

        alcPCfgCUD OBJECT-TYPE
            SYNTAX DisplayString (SIZE(2..47))
            ACCESS read-only
            STATUS mandatory
            DESCRIPTION
                "The Call User Data field to be used in outbound calls. It 
                 consists of a list of up to 16 hexadecimal numbers between 0 
                 and FF, separated by commas."
        ::= { cdx6500PPCTALCPortEntry 20 }

        alcPCfgNumOfBuffers OBJECT-TYPE
            SYNTAX INTEGER (1..1000)
            ACCESS read-only
            STATUS mandatory
            DESCRIPTION
                "This defines the number of buffers that are available for data
                 transfer in each direction. Each buffer will hold one message."
        ::= { cdx6500PPCTALCPortEntry 21 }

        alcPCfgInHeader OBJECT-TYPE
            SYNTAX DisplayString (SIZE(2..53))
            ACCESS read-only
            STATUS mandatory
            DESCRIPTION
                "This data is assumed to be at the start of all messages 
                 received from X.25. If IA and/or TA are specified in the 
                 header, the values associated with these positions are 
                 checked against the IA and TA associated with the header is 
                 then removed from the message, and replaced by the IA and 
                 TA associated with the connection."
        ::= { cdx6500PPCTALCPortEntry 22 }

        alcPCfgOutHeader OBJECT-TYPE
            SYNTAX DisplayString (SIZE(2..53))
            ACCESS read-only
            STATUS mandatory
            DESCRIPTION
                "This data is prefixed to all messages sent to X.25. If IA 
                 and/or TA are specified in the header, the IA and TA 
                 associated with the connection are inserted into the 
                 outgoing message at the positions specified by the header.
                 The IA and TA received from ALC are removed and replaced with 
                 the OUT Header."
        ::= { cdx6500PPCTALCPortEntry 23 }

        alcPCfgReconnectTimeout OBJECT-TYPE
            SYNTAX INTEGER (1..1000)
            ACCESS read-only
            STATUS mandatory
            DESCRIPTION
                "The time in seconds between attempts to establish an X.25 
                 virtual circuit when the ALP connection is enabled, or after 
                 the SVC has been cleared."
        ::= { cdx6500PPCTALCPortEntry 24 }

        alcPCfgInactivityTimeout OBJECT-TYPE
            SYNTAX INTEGER (0..1000)
            ACCESS read-only
            STATUS mandatory
            DESCRIPTION
                "The time in seconds after which the call is cleared if no 
                 data is transmitted or received. A value of 0 disables the 
                 timer."
        ::= { cdx6500PPCTALCPortEntry 25 }

        alcPCfgDebounceTimeout OBJECT-TYPE
            SYNTAX INTEGER (0..1000)
            ACCESS read-only
            STATUS mandatory
            DESCRIPTION
                "This defines the time in seconds for which the PAD waits 
                 before implementing the shutdown action. If the time out is 0,
                 shutdown occurs immediately."
        ::= { cdx6500PPCTALCPortEntry 26 }

        alcPCfgParity OBJECT-TYPE
            SYNTAX INTEGER {
                    none (1),
                    odd  (2),
                    nc   (100) 
                   }
            ACCESS read-only
            STATUS mandatory
            DESCRIPTION
                "none : No parity will be used.
                 odd  : All messages sent to X.25 will have odd parity.
                 nc   : Skipped during configuration"
        ::= { cdx6500PPCTALCPortEntry 27 }

        alcPCfgConnOptions OBJECT-TYPE
            SYNTAX DisplayString (SIZE(3..32))
            ACCESS read-only
            STATUS mandatory
            DESCRIPTION
                "Options controlling the behaviour of the connection.  
                 NONE     : No options are specified.
                 HDR      : ALP PAD discards all data messages incoming from the
                            network in which the constant parts of the IN Header
                            do not match the header  of the message.
                 ALCSD    : If this option is specified and the SVC goes down, 
                            then the ALC entity is shutdown.
                 CSD      : If this option is specified and the ALC entity goes 
                            down, then the associated call is cleared.
                 FLOW     : If the number of free buffers decreases to 20% of 
                            its maximum, then flow control is imposed on the 
                            receiver. It is released when the number of free 
                            buffers reaches 50% of its maximum. If the option 
                            is not set, messages received when there are no 
                            buffers available will be discarded. Note that 
                            flow control requests from X.25 are always acted 
                            upon, regardless of the setting of this option.
                 USE_ADDR : The address in the received message is used when 
                            the message is passed to ALC, and address checking 
                            is turned off.
                 Any combination of the above maybe specified by summing
                 (e.g. FLOW+USE_ADDR+. . .)."
        ::= { cdx6500PPCTALCPortEntry 28 }

        alcPCfgAvailableMesg OBJECT-TYPE
            SYNTAX DisplayString (SIZE(0..62))
            ACCESS read-only
            STATUS mandatory
            DESCRIPTION
                "This specifies the text of a message that is broadcast
                 to the ALC entity associated with this connection after 
                 a message from that terminal has been discarded due to 
                 the X.25 VC being down.  This message is only sent
                 if an Unavailable message has previously been sent to one 
                 of the terminals associated with this connection.  
                 If no message is defined, none is sent.
                 The space character is used to blank this field.
                 Note that this is only used on TPAD configurations."
        ::= { cdx6500PPCTALCPortEntry 29 }

        alcPCfgUnavailableMesg OBJECT-TYPE
            SYNTAX DisplayString (SIZE(0..62))
            ACCESS read-only
            STATUS mandatory
            DESCRIPTION
                 "This specifies the text of a message that is sent to a 
                 terminal when a message from that terminal is discarded 
                 because the X.25 VC is down. If no message is defined, 
                 none is sent.
                 The space character is used to blank this field.
                 Note that this is only used on TPAD configurations."
        ::= { cdx6500PPCTALCPortEntry 30 }

        -- ALC Interchange Configuration Objects

        cdx6500PPCTALCInterchangeTable OBJECT-TYPE
            SYNTAX SEQUENCE OF Cdx6500PPCTALCInterchangeEntry
            ACCESS not-accessible
            STATUS mandatory
            DESCRIPTION
                "This table contains ALC Interchange configuration parameters"
            ::= { cdx6500PPCTALCCfgTable 2 }

        cdx6500PPCTALCInterchangeEntry OBJECT-TYPE
            SYNTAX Cdx6500PPCTALCInterchangeEntry
            ACCESS not-accessible
            STATUS mandatory
            DESCRIPTION
                "Entries in the ALC Interchange Configuration Table."
            INDEX { alcICfgPortNumber,
                    alcICfgInterchangeAddress }
        ::= { cdx6500PPCTALCInterchangeTable 1 }

        Cdx6500PPCTALCInterchangeEntry ::=
            SEQUENCE {
                alcICfgPortNumber
                    INTEGER,
                alcICfgInterchangeAddress
                    OCTET STRING,
                alcICfgOptionOnInvalidCCC
                    INTEGER,
                alcICfgGenTerminalAddress
                    OCTET STRING,
                alcICfgHostTimeout
                    INTEGER,
                alcICfgMaxComponentsPerFrame
                    INTEGER,
                alcICfgFastPollCycleCount
                    INTEGER,
                alcICfgSlowPollCycleCount
                    INTEGER,
                alcICfgN1Counter
                    INTEGER,
                alcICfgN2Counter
                    INTEGER,
                alcICfgT1Timeout
                    INTEGER,
                alcICfgT2Timeout
                    INTEGER,
                alcICfgReenterMessage
                    DisplayString,
                alcICfgStartMessage
                    DisplayString,
                alcICfgStopMessage
                    DisplayString,
                alcICfgOptions
                    DisplayString,
                alcICfgValidTAList
                    DisplayString,
                alcICfgConnType
                    INTEGER,
                alcICfgAcallMnemonic
                    DisplayString,
                alcICfgCallingAddress
                    DisplayString,
                alcICfgCUD
                    DisplayString,
                alcICfgNumOfBuffers
                    INTEGER,
                alcICfgInHeader
                    DisplayString,
                alcICfgOutHeader
                    DisplayString,
                alcICfgReconnectTimeout
                    INTEGER,
                alcICfgInactivityTimeout
                    INTEGER,
                alcICfgDebounceTimeout
                    INTEGER,
                alcICfgParity
                    INTEGER,
                alcICfgConnOptions
                    DisplayString,
                alcICfgAvailableMesg
                    DisplayString,
                alcICfgUnavailableMesg
                    DisplayString
            }

        alcICfgPortNumber OBJECT-TYPE
            SYNTAX INTEGER (1..54)
            ACCESS read-only
            STATUS mandatory
            DESCRIPTION
                "Port number of this port."
        ::= { cdx6500PPCTALCInterchangeEntry 1 }

        alcICfgInterchangeAddress OBJECT-TYPE
            SYNTAX OCTET STRING (SIZE(1))
            ACCESS read-only
            STATUS mandatory
            DESCRIPTION
                "The address of the interchange.
                 Addresses 0D,0F,1D,2D,3D and 3F are illegal as they are used 
                 as line control characters."
        ::= { cdx6500PPCTALCInterchangeEntry 2 }

        alcICfgOptionOnInvalidCCC OBJECT-TYPE
            SYNTAX INTEGER {
                    discard (2),
                    resend  (3),
                    reenter (4),
                    ignore  (5)
                    }
            ACCESS read-only
            STATUS mandatory
            DESCRIPTION
                "The action to be taken on receipt of a message with an 
                 invalid ccc.
                 discard : Discard the message
                 ignore  : Treat the message as correct.
                 reenter : (TPAD only) The configured `re-enter' message is 
                           sent  to the terminal.
                 resend  : (TPAD only) A resend request message is sent to the
                           terminal."
        ::= { cdx6500PPCTALCInterchangeEntry 3 }

        alcICfgGenTerminalAddress OBJECT-TYPE
            SYNTAX OCTET STRING
            ACCESS read-only
            STATUS mandatory
            DESCRIPTION
                "Specifies the terminal address to which broadcast messages are
                 sent when the GTA option is specified."
        ::= { cdx6500PPCTALCInterchangeEntry 4 }

        alcICfgHostTimeout OBJECT-TYPE
            SYNTAX INTEGER (50..100000)
            ACCESS read-only
            STATUS mandatory
            DESCRIPTION
                "The host is considered to be down if a poll is not received 
                 within this period, which is specified in milliseconds."
        ::= { cdx6500PPCTALCInterchangeEntry 5 }

        alcICfgMaxComponentsPerFrame OBJECT-TYPE
            SYNTAX INTEGER (1..100)
            ACCESS read-only
            STATUS mandatory
            DESCRIPTION
                "Specifies the maximum number of message segments transmitted 
                 in one frame (HPAD) or expected in one frame (TPAD)."
        ::= { cdx6500PPCTALCInterchangeEntry 6 }

        alcICfgFastPollCycleCount OBJECT-TYPE
            SYNTAX INTEGER (1..255)
            ACCESS read-only
            STATUS mandatory
            DESCRIPTION
                "The polling rate for an interchange in fast poll. 
                 A poll is issued to this interchange once in every n poll 
                 cycles on the line."
        ::= { cdx6500PPCTALCInterchangeEntry 7 }

        alcICfgSlowPollCycleCount OBJECT-TYPE
            SYNTAX INTEGER (1..255)
            ACCESS read-only
            STATUS mandatory
            DESCRIPTION
                "The polling rate for an interchange in slow poll.
                 One slow poll IA is polled every n poll cycles on the line."
        ::= { cdx6500PPCTALCInterchangeEntry 8 }

        alcICfgN1Counter OBJECT-TYPE
            SYNTAX INTEGER (1..100)
            ACCESS read-only
            STATUS mandatory
            DESCRIPTION
                "The number of polls that can be sent without receiving a 
                 response before the interchange enters slow poll."
        ::= { cdx6500PPCTALCInterchangeEntry 9 }

        alcICfgN2Counter OBJECT-TYPE
            SYNTAX INTEGER (1..100)
            ACCESS read-only
            STATUS mandatory
            DESCRIPTION
                "The number of good poll responses required before the 
                 interchange enters fast poll."
        ::= { cdx6500PPCTALCInterchangeEntry 10 }

        alcICfgT1Timeout OBJECT-TYPE
            SYNTAX INTEGER (100..100000)
            ACCESS read-only
            STATUS mandatory
            DESCRIPTION
                "The time, in milliseconds, within which an interchange must 
                 start responding to a poll."
        ::= { cdx6500PPCTALCInterchangeEntry 11 }

        alcICfgT2Timeout OBJECT-TYPE
            SYNTAX INTEGER (100..100000)
            ACCESS read-only
            STATUS mandatory
            DESCRIPTION
                "The time, in milliseconds, within which an interchange must 
                 complete its transmission."
        ::= { cdx6500PPCTALCInterchangeEntry 12 }

        alcICfgReenterMessage OBJECT-TYPE
            SYNTAX DisplayString (SIZE(0..64))
            ACCESS read-only
            STATUS mandatory
            DESCRIPTION
                "This specifies the text of a message sent to terminals when 
                 a message with an incorrect ccc is received and the action on
                 receipt of an invalid ccc is REENTER. Note that some terminals
                 may require control characters at the start of the message."
        ::= { cdx6500PPCTALCInterchangeEntry 13 }

        alcICfgStartMessage OBJECT-TYPE
            SYNTAX DisplayString (SIZE(0..64))
            ACCESS read-only
            STATUS mandatory
            DESCRIPTION
                "This specifies the text of a message sent to terminals when 
                 polling of this interchange is started and the STST option is
                 configured. Note that some terminals may require control 
                 characters at the start of the message."
        ::= { cdx6500PPCTALCInterchangeEntry 14 }

        alcICfgStopMessage OBJECT-TYPE
            SYNTAX DisplayString (SIZE(0..64))
            ACCESS read-only
            STATUS mandatory
            DESCRIPTION
                "This specifies the text of a message sent to terminals when 
                 polling of this interchange is stopped and the STST option is 
                 configured. Note that some terminals may require control 
                 characters at the start of the message."
        ::= { cdx6500PPCTALCInterchangeEntry 15 }

        alcICfgOptions OBJECT-TYPE
            SYNTAX DisplayString (SIZE(3..21))
            ACCESS read-only
            STATUS mandatory
            DESCRIPTION
                "Select options on this ALC Interchange as follows :
                 NONE   : no option specified
                 GTA    : (TPAD only) Indicates that there is a general 
                          terminal address which may be used for broadcasting 
                          to all terminals on the interchange.
                 NOPOLL : (TPAD only) Indicates that this interchange is not to
                          be polled.
                 RESET  : Indicates that the interchange is capable of handling
                          ALC Reset messages.
                 STST   : (TPAD only) Indicates that the configured start and 
                          stop messages should be transmitted when polling is 
                          started or stopped.
                 Any combination of the above maybe specified by summing
                 (e.g. GTA+NOPOLL+. . .)."
        ::= { cdx6500PPCTALCInterchangeEntry 16 }

        alcICfgValidTAList OBJECT-TYPE
            SYNTAX DisplayString
            ACCESS read-only
            STATUS mandatory
            DESCRIPTION
                "A list of hexadecimal numbers between 1 and 3F separated by 
                 commas. /f or /r after each is used to indicate forward or 
                 reverse abort respectively. Ranges may be specified by 
                 separating two addresses by a dash `-'. 
                 Note that the addresses 0D, 1D, 2D, 3D and 3F are illegal. 
                 The list of terminal addresses that may be configured on the 
                 line, including the forward or reverse abort settings for each
                 terminal."
        ::= { cdx6500PPCTALCInterchangeEntry 17 }

        alcICfgConnType OBJECT-TYPE
            SYNTAX INTEGER {
                    none (1),
                    x25  (2),
                    nc   (100)
                   }
            ACCESS read-only
            STATUS mandatory
            DESCRIPTION
                "none : No connection.
                 x25  : Connection type is X.25.
                 nc   : Skipped during configuration"
        ::= { cdx6500PPCTALCInterchangeEntry 18 }

        alcICfgAcallMnemonic OBJECT-TYPE
            SYNTAX DisplayString (SIZE(0..8))
            ACCESS read-only
            STATUS mandatory
            DESCRIPTION
                "This is the mnemonic to be used to establish the call when 
                 the call request is issued. The mnemonic must be defined in
                 the mnemonic table. If no mnemonic is specified, ALP PAD will
                 wait for the call. It consists of 0-8 alphanumeric characters,
                 and the space character is used to blank the field."
        ::= { cdx6500PPCTALCInterchangeEntry 19 }

        alcICfgCallingAddress OBJECT-TYPE
            SYNTAX DisplayString (SIZE(0..15))
            ACCESS read-only
            STATUS mandatory
            DESCRIPTION
                "The calling address to be used in outbound calls. It consists 
                 of 0-15 BCD digits, and the space character is used to blank 
                 the field."
        ::= { cdx6500PPCTALCInterchangeEntry 20 }

        alcICfgCUD OBJECT-TYPE
            SYNTAX DisplayString (SIZE(2..47))
            ACCESS read-only
            STATUS mandatory
            DESCRIPTION
                "The Call User Data field to be used in outbound calls. It 
                 consists of a list of up to 16 hexadecimal numbers between 0 
                 and FF, separated by commas."
        ::= { cdx6500PPCTALCInterchangeEntry 21 }

        alcICfgNumOfBuffers OBJECT-TYPE
            SYNTAX INTEGER (1..1000)
            ACCESS read-only
            STATUS mandatory
            DESCRIPTION
                "This defined the number of buffers that are available for data
                 transfer in each direction. Each buffer will hold one message."
        ::= { cdx6500PPCTALCInterchangeEntry 22 }

        alcICfgInHeader OBJECT-TYPE
            SYNTAX DisplayString (SIZE(2..53))
            ACCESS read-only
            STATUS mandatory
            DESCRIPTION
                "This data is assumed to be at the start of all messages 
                 received from X.25. If IA and/or TA are specified in the 
                 header, the values associated with these positions are 
                 checked against the IA and TA associated with the header is 
                 then removed from the message, and replaced by the IA and 
                 TA associated with the connection."
        ::= { cdx6500PPCTALCInterchangeEntry 23 }

        alcICfgOutHeader OBJECT-TYPE
            SYNTAX DisplayString (SIZE(2..53))
            ACCESS read-only
            STATUS mandatory
            DESCRIPTION
                "This data is prefixed to all messages sent to X.25. If IA 
                 and/or TA are specified in the header, the IA and TA 
                 associated with the connection are inserted into the 
                 outgoing message at the positions specified by the header.
                 The IA and TA received from ALC are removed and replaced with 
                 the OUT Header."
        ::= { cdx6500PPCTALCInterchangeEntry 24 }

        alcICfgReconnectTimeout OBJECT-TYPE
            SYNTAX INTEGER (1..1000)
            ACCESS read-only
            STATUS mandatory
            DESCRIPTION
                "The time in seconds between attempts to establish an X.25 
                 virtual circuit when the ALP connection is enabled, or after 
                 the SVC has been cleared."
        ::= { cdx6500PPCTALCInterchangeEntry 25 }

        alcICfgInactivityTimeout OBJECT-TYPE
            SYNTAX INTEGER (0..1000)
            ACCESS read-only
            STATUS mandatory
            DESCRIPTION
                "The time in seconds after which the call is cleared if no 
                 data is transmitted or received. A value of 0 disables the 
                 timer."
        ::= { cdx6500PPCTALCInterchangeEntry 26 }

        alcICfgDebounceTimeout OBJECT-TYPE
            SYNTAX INTEGER (0..1000)
            ACCESS read-only
            STATUS mandatory
            DESCRIPTION
                "This defines the time in seconds for which the PAD waits 
                 before implementing the shutdown action. If the time out is 0,
                 shutdown occurs immediately."
        ::= { cdx6500PPCTALCInterchangeEntry 27 }

        alcICfgParity OBJECT-TYPE
            SYNTAX INTEGER {
                    none (1),
                    odd  (2),
                    nc   (100)
                   }
            ACCESS read-only
            STATUS mandatory
            DESCRIPTION
                "none : No parity will be used.
                 odd  : All messages sent to X.25 will have odd parity.
                 nc   : Skipped during configuration"
        ::= { cdx6500PPCTALCInterchangeEntry 28 }

        alcICfgConnOptions OBJECT-TYPE
            SYNTAX DisplayString (SIZE(3..32))
            ACCESS read-only
            STATUS mandatory
            DESCRIPTION
                "Options controlling the behaviour of the connection.  
                 NONE     : No options are specified.
                 HDR      : ALP PAD discards all data messages incoming from the
                            network in which the constant parts of the IN Header
                            do not match the header  of the message.
                 ALCSD    : If this option is specified and the SVC goes down, 
                            then the ALC entity is shutdown.
                 CSD      : If this option is specified and the ALC entity goes 
                            down, then the associated call is cleared.
                 FLOW     : If the number of free buffers decreases to 20% of 
                            its maximum, then flow control is imposed on the 
                            receiver. It is released when the number of free 
                            buffers reaches 50% of its maximum. If the option 
                            is not set, messages received when there are no 
                            buffers available will be discarded. Note that 
                            flow control requests from X.25 are always acted 
                            upon, regardless of the setting of this option.
                 USE_ADDR : The address in the received message is used when 
                            the message is passed to ALC, and address checking 
                            is turned off.
                 Any combination of the above maybe specified by summing
                 (e.g. FLOW+USE_ADDR+. . .)."
        ::= { cdx6500PPCTALCInterchangeEntry 29 }

        alcICfgAvailableMesg OBJECT-TYPE
            SYNTAX DisplayString (SIZE(0..62))
            ACCESS read-only
            STATUS mandatory
            DESCRIPTION
                "This specifies the text of a message that is broadcast
                 to the ALC entity associated with this connection after 
                 a message from that terminal has been discarded due to 
                 the X.25 VC being down.  This message is only sent
                 if an Unavailable message has previously been sent to one 
                 of the terminals associated with this connection.  
                 If no message is defined, none is sent.
                 The space character is used to blank this field.
                 Note that this is only used on TPAD configurations."
        ::= { cdx6500PPCTALCInterchangeEntry 30 }

        alcICfgUnavailableMesg OBJECT-TYPE
            SYNTAX DisplayString (SIZE(0..62))
            ACCESS read-only
            STATUS mandatory
            DESCRIPTION
                 "This specifies the text of a message that is sent to a 
                 terminal when a message from that terminal is discarded 
                 because the X.25 VC is down. If no message is defined, 
                 none is sent.
                 The space character is used to blank this field.
                 Note that this is only used on TPAD configurations."
        ::= { cdx6500PPCTALCInterchangeEntry 31 }

        -- ALC Terminal Configuration Objects

        cdx6500PPCTALCTerminalTable OBJECT-TYPE
            SYNTAX SEQUENCE OF Cdx6500PPCTALCTerminalEntry
            ACCESS not-accessible
            STATUS mandatory
            DESCRIPTION
                "This table contains ALC Terminal configuration parameters"
            ::= { cdx6500PPCTALCCfgTable 3 }

        cdx6500PPCTALCTerminalEntry OBJECT-TYPE
            SYNTAX Cdx6500PPCTALCTerminalEntry
            ACCESS not-accessible
            STATUS mandatory
            DESCRIPTION
                "Entries in the ALC Terminal Configuration Table."
            INDEX { alcTCfgPortNumber,
                    alcTCfgInterchangeAddress,
                    alcTCfgTerminalAddress }
        ::= { cdx6500PPCTALCTerminalTable 1 }

        Cdx6500PPCTALCTerminalEntry ::=
            SEQUENCE {
                alcTCfgPortNumber
                    INTEGER,
                alcTCfgInterchangeAddress
                    OCTET STRING,
                alcTCfgTerminalAddress
                    OCTET STRING,
                alcTCfgConnType
                    INTEGER,
                alcTCfgAcallMnemonic
                    DisplayString,
                alcTCfgCallingAddress
                    DisplayString,
                alcTCfgCUD
                    DisplayString,
                alcTCfgNumOfBuffers
                    INTEGER,
                alcTCfgInHeader
                    DisplayString,
                alcTCfgOutHeader
                    DisplayString,
                alcTCfgReconnectTimeout
                    INTEGER,
                alcTCfgInactivityTimeout
                    INTEGER,
                alcTCfgDebounceTimeout
                    INTEGER,
                alcTCfgParity
                    INTEGER,
                alcTCfgConnOptions
                    DisplayString,
                alcTCfgAvailableMesg
                    DisplayString,
                alcTCfgUnavailableMesg
                    DisplayString
            }

        alcTCfgPortNumber OBJECT-TYPE
            SYNTAX INTEGER (1..54)
            ACCESS read-only
            STATUS mandatory
            DESCRIPTION
                "Port number of this port."
        ::= { cdx6500PPCTALCTerminalEntry 1 }

        alcTCfgInterchangeAddress OBJECT-TYPE
            SYNTAX OCTET STRING (SIZE(1))
            ACCESS read-only
            STATUS mandatory
            DESCRIPTION
                "The address of the interchange.
                 Addresses 0D,0F,1D,2D,3D and 3F are illegal as they are used 
                 as line control characters."
        ::= { cdx6500PPCTALCTerminalEntry 2 }

        alcTCfgTerminalAddress OBJECT-TYPE
            SYNTAX OCTET STRING (SIZE(1))
            ACCESS read-only
            STATUS mandatory
            DESCRIPTION
                "Address identifying this terminal."
        ::= { cdx6500PPCTALCTerminalEntry 3 }

        alcTCfgConnType OBJECT-TYPE
            SYNTAX INTEGER {
                    none (1),
                    x25  (2),
                    nc   (100)
                   }
            ACCESS read-only
            STATUS mandatory
            DESCRIPTION
                "none : No connection type.
                 x25  : Connection type is X.25.
                 nc   : Skipped during configuration"
        ::= { cdx6500PPCTALCTerminalEntry 4 }

        alcTCfgAcallMnemonic OBJECT-TYPE
            SYNTAX DisplayString (SIZE(0..8))
            ACCESS read-only
            STATUS mandatory
            DESCRIPTION
                "This is the mnemonic to be used to establish the call when 
                 the call request is issued. The mnemonic must be defined in
                 the mnemonic table. If no mnemonic is specified, ALP PAD will
                 wait for the call. It consists of 0-8 alphanumeric characters,
                 and the space character is used to blank the field."
        ::= { cdx6500PPCTALCTerminalEntry 5 }

        alcTCfgCallingAddress OBJECT-TYPE
            SYNTAX DisplayString (SIZE(0..15))
            ACCESS read-only
            STATUS mandatory
            DESCRIPTION
                "The calling address to be used in outbound calls. It consists 
                 of 0-15 BCD digits, and the space character is used to blank 
                 the field."
        ::= { cdx6500PPCTALCTerminalEntry 6 }

        alcTCfgCUD OBJECT-TYPE
            SYNTAX DisplayString (SIZE(2..47))
            ACCESS read-only
            STATUS mandatory
            DESCRIPTION
                "The Call User Data field to be used in outbound calls. It 
                 consists of a list of up to 16 hexadecimal numbers between 0 
                 and FF, separated by commas."
        ::= { cdx6500PPCTALCTerminalEntry 7 }

        alcTCfgNumOfBuffers OBJECT-TYPE
            SYNTAX INTEGER (1..1000)
            ACCESS read-only
            STATUS mandatory
            DESCRIPTION
                "This defined the number of buffers that are available for data
                 transfer in each direction. Each buffer will hold one message."
        ::= { cdx6500PPCTALCTerminalEntry 8 }

        alcTCfgInHeader OBJECT-TYPE
            SYNTAX DisplayString (SIZE(2..53))
            ACCESS read-only
            STATUS mandatory
            DESCRIPTION
                "This data is assumed to be at the start of all messages 
                 received from X.25. If IA and/or TA are specified in the 
                 header, the values associated with these positions are 
                 checked against the IA and TA associated with the header is 
                 then removed from the message, and replaced by the IA and 
                 TA associated with the connection."
        ::= { cdx6500PPCTALCTerminalEntry 9 }

        alcTCfgOutHeader OBJECT-TYPE
            SYNTAX DisplayString (SIZE(2..53))
            ACCESS read-only
            STATUS mandatory
            DESCRIPTION
                "This data is prefixed to all messages sent to X.25. If IA 
                 and/or TA are specified in the header, the IA and TA 
                 associated with the connection are inserted into the 
                 outgoing message at the positions specified by the header.
                 The IA and TA received from ALC are removed and replaced with 
                 the OUT Header."
        ::= { cdx6500PPCTALCTerminalEntry 10 }

        alcTCfgReconnectTimeout OBJECT-TYPE
            SYNTAX INTEGER (1..1000)
            ACCESS read-only
            STATUS mandatory
            DESCRIPTION
                "The time in seconds between attempts to establish an X.25 
                 virtual circuit when the ALP connection is enabled, or after 
                 the SVC has been cleared."
        ::= { cdx6500PPCTALCTerminalEntry 11 }

        alcTCfgInactivityTimeout OBJECT-TYPE
            SYNTAX INTEGER (0..1000)
            ACCESS read-only
            STATUS mandatory
            DESCRIPTION
                "The time in seconds after which the call is cleared if no 
                 data is transmitted or received. A value of 0 disables the 
                 timer."
        ::= { cdx6500PPCTALCTerminalEntry 12 }

        alcTCfgDebounceTimeout OBJECT-TYPE
            SYNTAX INTEGER (0..1000)
            ACCESS read-only
            STATUS mandatory
            DESCRIPTION
                "This defines the time in seconds for which the PAD waits 
                 before implementing the shutdown action. If the time out is 0,
                 shutdown occurs immediately."
        ::= { cdx6500PPCTALCTerminalEntry 13 }

        alcTCfgParity OBJECT-TYPE
            SYNTAX INTEGER {
                    none (1),
                    odd  (2),
                    nc   (100)
                   }
            ACCESS read-only
            STATUS mandatory
            DESCRIPTION
                "none : No parity will be used.
                 odd  : All messages sent to X.25 will have odd parity.
                 nc   : Skipped during configuration"
        ::= { cdx6500PPCTALCTerminalEntry 14 }

        alcTCfgConnOptions OBJECT-TYPE
            SYNTAX DisplayString (SIZE(3..32))
            ACCESS read-only
            STATUS mandatory
            DESCRIPTION
                "Options controlling the behaviour of the connection.  
                 NONE     : No options are specified.
                 HDR      : ALP PAD discards all data messages incoming from the
                            network in which the constant parts of the IN Header
                            do not match the header  of the message.
                 ALCSD    : If this option is specified and the SVC goes down, 
                            then the ALC entity is shutdown.
                 CSD      : If this option is specified and the ALC entity goes 
                            down, then the associated call is cleared.
                 FLOW     : If the number of free buffers decreases to 20% of 
                            its maximum, then flow control is imposed on the 
                            receiver. It is released when the number of free 
                            buffers reaches 50% of its maximum. If the option 
                            is not set, messages received when there are no 
                            buffers available will be discarded. Note that 
                            flow control requests from X.25 are always acted 
                            upon, regardless of the setting of this option.
                 USE_ADDR : The address in the received message is used when 
                            the message is passed to ALC, and address checking 
                            is turned off.
                 Any combination of the above maybe specified by summing
                 (e.g. FLOW+USE_ADDR+. . .)."
        ::= { cdx6500PPCTALCTerminalEntry 15 }

        alcTCfgAvailableMesg OBJECT-TYPE
            SYNTAX DisplayString (SIZE(0..62))
            ACCESS read-only
            STATUS mandatory
            DESCRIPTION
                "This specifies the text of a message that is broadcast
                 to the ALC entity associated with this connection after 
                 a message from that terminal has been discarded due to 
                 the X.25 VC being down.  This message is only sent
                 if an Unavailable message has previously been sent to one 
                 of the terminals associated with this connection.  
                 If no message is defined, none is sent.
                 The space character is used to blank this field.
                 Note that this is only used on TPAD configurations."
        ::= { cdx6500PPCTALCTerminalEntry 16 }

        alcTCfgUnavailableMesg OBJECT-TYPE
            SYNTAX DisplayString (SIZE(0..62))
            ACCESS read-only
            STATUS mandatory
            DESCRIPTION
                 "This specifies the text of a message that is sent to a 
                 terminal when a message from that terminal is discarded 
                 because the X.25 VC is down. If no message is defined, 
                 none is sent.
                 The space character is used to blank this field.
                 Note that this is only used on TPAD configurations."
        ::= { cdx6500PPCTALCTerminalEntry 17 }

        -- ALC Port Statistics Table

        cdx6500PPSTALCStatsTable OBJECT IDENTIFIER ::=
            { cdx6500PSTPortProtocolGroup 28 }

        cdx6500PPSTALCPortTable OBJECT-TYPE
            SYNTAX SEQUENCE OF Cdx6500PPSTALCPortEntry
            ACCESS not-accessible
            STATUS mandatory
            DESCRIPTION
                "This table contains ALC Port Statistics parameters."
          ::= { cdx6500PPSTALCStatsTable 1 }
          
        cdx6500PPSTALCPortEntry OBJECT-TYPE
            SYNTAX Cdx6500PPSTALCPortEntry
            ACCESS not-accessible
            STATUS mandatory
            DESCRIPTION
                "Entries in the ALC Port Statistics Table."
            INDEX { alcPStatsPortNumber }
        ::= { cdx6500PPSTALCPortTable 1 }
          
        Cdx6500PPSTALCPortEntry ::=
            SEQUENCE {
                alcPStatsPortNumber
                    INTEGER,
                alcPStatsPortType
                    INTEGER,
                alcPStatsPortState
                    INTEGER,
                alcPStatsFramesIn
                    Counter,
                alcPStatsFramesOut
                    Counter,
                alcPStatsDataMesgsIn
                    Counter,
                alcPStatsDataMesgsOut
                    Counter,
                alcPStatsCharsIn
                    Counter,
                alcPStatsCharsOut
                    Counter,
                alcPStatsPolls
                    Counter,
                alcPStatsGAs
                    Counter,
                alcPStatsResets
                    Counter,
                alcPStatsDiscardBadIAIn
                    Counter,
                alcPStatsDiscardBadIAOut
                    Counter,
                alcPStatsMaxQSizeOut
                    INTEGER,
                alcPStatsCCCErrors
                    Counter,
                alcPStatsSignalLosses
                    Counter,
                alcPStatsOverlengthFrames
                    Counter,
                alcPStatsPortStatus
                    INTEGER,
                alcPStatsConnState
                    INTEGER,
                alcPStatsALCMesgsIn
                    Counter,
                alcPStatsALCMesgsOut
                    Counter,
                alcPStatsX25MesgsIn
                    Counter,
                alcPStatsX25MesgsOut
                    Counter,
                alcPStatsALCCharsIn
                    Counter,
                alcPStatsALCCharsOut
                    Counter,
                alcPStatsX25CharsIn
                    Counter,
                alcPStatsX25CharsOut
                    Counter,
                alcPStatsALCDiscardedMesgsEntityDown
                    Counter,
                alcPStatsX25DiscardedMesgsEntityDown
                    Counter,
                alcPStatsX25DiscardedMesgsBadALCAddr
                    Counter,
                alcPStatsX25DiscardedMesgsBadHeader
                    Counter,
                alcPStatsX25DiscardedMesgsTooLong
                    Counter,
                alcPStatsALCDiscardedMesgsQFull
                    Counter,
                alcPStatsX25DiscardedMesgsQFull
                    Counter,
                alcPStatsCurrTxALCQSize
                    INTEGER,
                alcPStatsCurrTxX25QSize
                    INTEGER,
                alcPStatsMaxTxALCQSize
                    INTEGER,
                alcPStatsMaxTxX25QSize
                    INTEGER
            }

        alcPStatsPortNumber OBJECT-TYPE
            SYNTAX INTEGER (1..54)
            ACCESS read-only
            STATUS mandatory
            DESCRIPTION
                "Port number of this port."
        ::= { cdx6500PPSTALCPortEntry 1 }

        alcPStatsPortType OBJECT-TYPE
            SYNTAX INTEGER {
                    alc  (31)
                    }
            ACCESS read-only
            STATUS mandatory
            DESCRIPTION
                "Port type of this port."
        ::= { cdx6500PPSTALCPortEntry 2 }

        alcPStatsPortState OBJECT-TYPE
            SYNTAX INTEGER {
                    offline    (1),
                    online     (2),
                    timedOut  (7),
                    pending    (8),
                    connecting (9),
                    flowCtrl  (11),
                    na         (100)
                    }
            ACCESS read-only
            STATUS mandatory
            DESCRIPTION
                "Current Port State.
                 connecting:The line has been enabled by the operator, 
                            but polling has not yet been established.
                 online    :The line is active.
                 offline   :The line has been disabled by the operator.
                 pending   :The line is inactive because of conditions 
                            detected by ALP PAD (X.25 virtual circuit not
                            active).
                 timedOut :The line is not being polled. This will be 
                            displayed on poll coerced HPAD lines only.
                 flowCtrl :The application (ALP PAD) has imposed flow 
                            control on the line.
                 na        :Value not Available"
        ::= { cdx6500PPSTALCPortEntry 3 }

        alcPStatsFramesIn OBJECT-TYPE
            SYNTAX Counter
            ACCESS read-only
            STATUS mandatory
            DESCRIPTION
                "Number of frames received."
        ::= { cdx6500PPSTALCPortEntry 4 }

        alcPStatsFramesOut OBJECT-TYPE
            SYNTAX Counter
            ACCESS read-only
            STATUS mandatory
            DESCRIPTION
                "Number of frames transmitted."
        ::= { cdx6500PPSTALCPortEntry 5 }

        alcPStatsDataMesgsIn OBJECT-TYPE
            SYNTAX Counter
            ACCESS read-only
            STATUS mandatory
            DESCRIPTION
                "Number of data messages received."
        ::= { cdx6500PPSTALCPortEntry 6 }

        alcPStatsDataMesgsOut OBJECT-TYPE
            SYNTAX Counter
            ACCESS read-only
            STATUS mandatory
            DESCRIPTION
                "Number of data messages transmitted."
        ::= { cdx6500PPSTALCPortEntry 7 }

        alcPStatsCharsIn OBJECT-TYPE
            SYNTAX Counter
            ACCESS read-only
            STATUS mandatory
            DESCRIPTION
                "Number of characters received."
        ::= { cdx6500PPSTALCPortEntry 8 }

        alcPStatsCharsOut OBJECT-TYPE
            SYNTAX Counter
            ACCESS read-only
            STATUS mandatory
            DESCRIPTION
                "Number of characters transmitted."
        ::= { cdx6500PPSTALCPortEntry 9 }

        alcPStatsPolls OBJECT-TYPE
            SYNTAX Counter
            ACCESS read-only
            STATUS mandatory
            DESCRIPTION
                "Number of polls transmitted or received."
        ::= { cdx6500PPSTALCPortEntry 10 }

        alcPStatsGAs OBJECT-TYPE
            SYNTAX Counter
            ACCESS read-only
            STATUS mandatory
            DESCRIPTION
                "Number of Go Ahead messages transmitted or received."
        ::= { cdx6500PPSTALCPortEntry 11 }

        alcPStatsResets OBJECT-TYPE
            SYNTAX Counter
            ACCESS read-only
            STATUS mandatory
            DESCRIPTION
                "Number of Reset messages transmitted or received."
        ::= { cdx6500PPSTALCPortEntry 12 }

        alcPStatsDiscardBadIAIn OBJECT-TYPE
            SYNTAX Counter
            ACCESS read-only
            STATUS mandatory
            DESCRIPTION
                "Number of received messages discarded due to bad 
                 Interchange Address."
        ::= { cdx6500PPSTALCPortEntry 13 }

        alcPStatsDiscardBadIAOut OBJECT-TYPE
            SYNTAX Counter
            ACCESS read-only
            STATUS mandatory
            DESCRIPTION
                "Number of transmitted messages discarded due to bad
                 Interchange Address."
        ::= { cdx6500PPSTALCPortEntry 14 }

        alcPStatsMaxQSizeOut OBJECT-TYPE
            SYNTAX INTEGER
            ACCESS read-only
            STATUS mandatory
            DESCRIPTION
                "Maximum transmit queue size."
        ::= { cdx6500PPSTALCPortEntry 15 }

        alcPStatsCCCErrors OBJECT-TYPE
            SYNTAX Counter
            ACCESS read-only
            STATUS mandatory
            DESCRIPTION
                "Number of messages received with an invalid checksum."
        ::= { cdx6500PPSTALCPortEntry 16 }

        alcPStatsSignalLosses OBJECT-TYPE
            SYNTAX Counter
            ACCESS read-only
            STATUS mandatory
            DESCRIPTION
                "Number of Signal Losses."
        ::= { cdx6500PPSTALCPortEntry 17 }

        alcPStatsOverlengthFrames OBJECT-TYPE
            SYNTAX Counter
            ACCESS read-only
            STATUS mandatory
            DESCRIPTION
                "Number of overlength frames received."
        ::= { cdx6500PPSTALCPortEntry 18 }

        alcPStatsPortStatus OBJECT-TYPE
            SYNTAX INTEGER {
                    disabled (1),
                    enabled  (2),
                    busyOut  (3),
                    up       (4),
                    down     (5),
                    na       (100)
                    }
            ACCESS read-only
            STATUS mandatory
            DESCRIPTION
                "Current Port Status.
                 na         :Value not Available"
        ::= { cdx6500PPSTALCPortEntry 19 }

        alcPStatsConnState OBJECT-TYPE
            SYNTAX INTEGER {
                    online     (1),
                    offline    (2),
                    connecting (3),
                    inactive   (4),
                    pending    (5),
                    na         (100)
                    }
            ACCESS read-only
            STATUS mandatory
            DESCRIPTION
                "Current state of the connection.
                 online    :The connection is available for data transfer.
                 offline   :The connection has been disabled by an operator.
                 connecting:The ALP PAD is attempting to make the X.25
                            virtual circuit available for use.
                 inactive  :The inactivity timer has expired, so the virtual
                            circuit has been dropped. Data received from ALC
                            will cause the connection to be re-established.
                 pending   :The CSD option has been configured and the ALC
                            entity is currently down; hence the ALP PAD has
                            disabled the virtual circuit.
                 na        :Value not Available"
        ::= { cdx6500PPSTALCPortEntry 20 }

        alcPStatsALCMesgsIn OBJECT-TYPE
            SYNTAX Counter
            ACCESS read-only
            STATUS mandatory
            DESCRIPTION
                "The number of messages received from ALC."
        ::= { cdx6500PPSTALCPortEntry 21 }

        alcPStatsALCMesgsOut OBJECT-TYPE
            SYNTAX Counter
            ACCESS read-only
            STATUS mandatory
            DESCRIPTION
                "The number of messages transmitted to ALC."
        ::= { cdx6500PPSTALCPortEntry 22 }

        alcPStatsX25MesgsIn OBJECT-TYPE
            SYNTAX Counter
            ACCESS read-only
            STATUS mandatory
            DESCRIPTION
                "The number of messages received from X.25."
        ::= { cdx6500PPSTALCPortEntry 23 }

        alcPStatsX25MesgsOut OBJECT-TYPE
            SYNTAX Counter
            ACCESS read-only
            STATUS mandatory
            DESCRIPTION
                "The number of messages transmitted to X.25."
        ::= { cdx6500PPSTALCPortEntry 24 }

        alcPStatsALCCharsIn OBJECT-TYPE
            SYNTAX Counter
            ACCESS read-only
            STATUS mandatory
            DESCRIPTION
                "The number of characters received from ALC."
        ::= { cdx6500PPSTALCPortEntry 25 }

        alcPStatsALCCharsOut OBJECT-TYPE
            SYNTAX Counter
            ACCESS read-only
            STATUS mandatory
            DESCRIPTION
                "The number of characters transmitted to ALC."
        ::= { cdx6500PPSTALCPortEntry 26 }

        alcPStatsX25CharsIn OBJECT-TYPE
            SYNTAX Counter
            ACCESS read-only
            STATUS mandatory
            DESCRIPTION
                "The number of characters received from X.25."
        ::= { cdx6500PPSTALCPortEntry 27 }

        alcPStatsX25CharsOut OBJECT-TYPE
            SYNTAX Counter
            ACCESS read-only
            STATUS mandatory
            DESCRIPTION
                "The number of characters transmitted to X.25."
        ::= { cdx6500PPSTALCPortEntry 28 }

        alcPStatsALCDiscardedMesgsEntityDown OBJECT-TYPE
            SYNTAX Counter
            ACCESS read-only
            STATUS mandatory
            DESCRIPTION
                "The number of messages received by ALC for which the 
                 destination entity is unable to process the data."
        ::= { cdx6500PPSTALCPortEntry 29 }

        alcPStatsX25DiscardedMesgsEntityDown OBJECT-TYPE
            SYNTAX Counter
            ACCESS read-only
            STATUS mandatory
            DESCRIPTION
                "The number of messages received by X.25 for which the 
                 destination entity is unable to process the data."
        ::= { cdx6500PPSTALCPortEntry 30 }

        alcPStatsX25DiscardedMesgsBadALCAddr OBJECT-TYPE
            SYNTAX Counter
            ACCESS read-only
            STATUS mandatory
            DESCRIPTION
                "The number of messages received from X.25 for which the
                 addresses specified do not match those associated with 
                 the connection."
        ::= { cdx6500PPSTALCPortEntry 31 }

        alcPStatsX25DiscardedMesgsBadHeader OBJECT-TYPE
            SYNTAX Counter
            ACCESS read-only
            STATUS mandatory
            DESCRIPTION
                "The number of messages received by X.25 of which the IN
                 header configured does not match the header present in the
                 message."
        ::= { cdx6500PPSTALCPortEntry 32 }

        alcPStatsX25DiscardedMesgsTooLong OBJECT-TYPE
            SYNTAX Counter
            ACCESS read-only
            STATUS mandatory
            DESCRIPTION
                "The number of messages received from X.25 that were discarded
                 because they were longer than the allowable ALC maximum
                 configured."
        ::= { cdx6500PPSTALCPortEntry 33 }

        alcPStatsALCDiscardedMesgsQFull OBJECT-TYPE
            SYNTAX Counter
            ACCESS read-only
            STATUS mandatory
            DESCRIPTION
                "The number of messages discarded because the ALC outbound
                 message queue was full."
        ::= { cdx6500PPSTALCPortEntry 34 }

        alcPStatsX25DiscardedMesgsQFull OBJECT-TYPE
            SYNTAX Counter
            ACCESS read-only
            STATUS mandatory
            DESCRIPTION
                "The number of messages discarded because the X.25 outbound
                 message queue was full."
        ::= { cdx6500PPSTALCPortEntry 35 }

        alcPStatsCurrTxALCQSize OBJECT-TYPE
            SYNTAX INTEGER
            ACCESS read-only
            STATUS mandatory
            DESCRIPTION
                "The number of messages currently queued in the ALC
                 outbound message queue for transmission."
        ::= { cdx6500PPSTALCPortEntry 36 }

        alcPStatsCurrTxX25QSize OBJECT-TYPE
            SYNTAX INTEGER
            ACCESS read-only
            STATUS mandatory
            DESCRIPTION
                "The number of messages currently queued in the X.25
                 outbound message queue for transmission."
        ::= { cdx6500PPSTALCPortEntry 37 }

        alcPStatsMaxTxALCQSize OBJECT-TYPE
            SYNTAX INTEGER
            ACCESS read-only
            STATUS mandatory
            DESCRIPTION
                "The maximum (highwater mark) size of the ALC outbound
                 queue so far."
        ::= { cdx6500PPSTALCPortEntry 38 }

        alcPStatsMaxTxX25QSize OBJECT-TYPE
            SYNTAX INTEGER
            ACCESS read-only
            STATUS mandatory
            DESCRIPTION
                "The maximum (highwater mark) size of the X.25 outbound
                 queue so far."
        ::= { cdx6500PPSTALCPortEntry 39 }

        -- ALC Interchange Statistics

        cdx6500PPSTALCInterchangeTable OBJECT-TYPE
            SYNTAX SEQUENCE OF Cdx6500PPSTALCInterchangeEntry
            ACCESS not-accessible
            STATUS mandatory
            DESCRIPTION
                "This table contains ALC Interchange Statistics parameters."
          ::= { cdx6500PPSTALCStatsTable 2 }
          
        cdx6500PPSTALCInterchangeEntry OBJECT-TYPE
            SYNTAX Cdx6500PPSTALCInterchangeEntry
            ACCESS not-accessible
            STATUS mandatory
            DESCRIPTION
                "Entries in the ALC Interchange Statistics Table."
            INDEX { alcIStatsPortNumber,
                    alcIStatsInterchangeAddress }
        ::= { cdx6500PPSTALCInterchangeTable 1 }
          
        Cdx6500PPSTALCInterchangeEntry ::=
            SEQUENCE {
                alcIStatsPortNumber
                    INTEGER,
                alcIStatsInterchangeAddress
                    OCTET STRING,
                alcIStatsInterchangeState
                    INTEGER,
                alcIStatsFramesIn
                    Counter,
                alcIStatsFramesOut
                    Counter,
                alcIStatsDataMesgsIn
                    Counter,
                alcIStatsDataMesgsOut
                    Counter,
                alcIStatsCharsIn
                    Counter,
                alcIStatsCharsOut
                    Counter,
                alcIStatsPolls
                    Counter,
                alcIStatsGAs
                    Counter,
                alcIStatsResets
                    Counter,
                alcIStatsDiscardBadTAIn
                    Counter,
                alcIStatsDiscardBadTAOut
                    Counter,
                alcIStatsDisabledIAIn
                    Counter,
                alcIStatsDisabledIAOut
                    Counter,
                alcIStatsMaxQSizeOut
                    INTEGER,
                alcIStatsCCCErrors
                    Counter,
                alcIStatsT1Timeouts
                    Counter,
                alcIStatsT2Timeouts
                    Counter,
                alcIStatsConnState
                    INTEGER,
                alcIStatsALCMesgsIn
                    Counter,
                alcIStatsALCMesgsOut
                    Counter,
                alcIStatsX25MesgsIn
                    Counter,
                alcIStatsX25MesgsOut
                    Counter,
                alcIStatsALCCharsIn
                    Counter,
                alcIStatsALCCharsOut
                    Counter,
                alcIStatsX25CharsIn
                    Counter,
                alcIStatsX25CharsOut
                    Counter,
                alcIStatsALCDiscardedMesgsEntityDown
                    Counter,
                alcIStatsX25DiscardedMesgsEntityDown
                    Counter,
                alcIStatsX25DiscardedMesgsBadALCAddr
                    Counter,
                alcIStatsX25DiscardedMesgsBadHeader
                    Counter,
                alcIStatsX25DiscardedMesgsTooLong
                    Counter,
                alcIStatsALCDiscardedMesgsQFull
                    Counter,
                alcIStatsX25DiscardedMesgsQFull
                    Counter,
                alcIStatsCurrTxALCQSize
                    INTEGER,
                alcIStatsCurrTxX25QSize
                    INTEGER,
                alcIStatsMaxTxALCQSize
                    INTEGER,
                alcIStatsMaxTxX25QSize
                    INTEGER
            }

        alcIStatsPortNumber OBJECT-TYPE
            SYNTAX INTEGER (1..54)
            ACCESS read-only
            STATUS mandatory
            DESCRIPTION
                "Port number of this port."
        ::= { cdx6500PPSTALCInterchangeEntry 1 }

        alcIStatsInterchangeAddress OBJECT-TYPE
            SYNTAX OCTET STRING (SIZE(1))
            ACCESS read-only
            STATUS mandatory
            DESCRIPTION
                "The address of the interchange.
                 Addresses 0D,0F,1D,2D,3D and 3F are illegal as they are used 
                 as line control characters."
        ::= { cdx6500PPSTALCInterchangeEntry 2 }

        alcIStatsInterchangeState OBJECT-TYPE
            SYNTAX INTEGER {
                    offline   (1),
                    online    (2),
                    fastPoll (3),
                    slowPoll (4),
                    stopped   (6),
                    timedOut (7),
                    pending   (8),
                    failed    (10),
                    flowCtrl (11),
                    na        (100)
                    }
            ACCESS read-only
            STATUS mandatory
            DESCRIPTION
                "Current State of this Interchange.
                 online   :The interchange is active. This is displayed for 
                           HPAD interchanges, and TPAD interchanges configured
                           as NOPOLL, only.
                 offline  :The interchange has been disabled by the operator.
                 pending  :The interchange is inactive because of conditions
                           detected by the application (ALP PAD).
                 failed   :The line with which this interchange is associated
                           is down.
                 timedOut:The interchange is not being polled. This is 
                           displayed for HPAD interchanges on non poll-coerced
                           lines only.
                 flowCtrl:The application (ALP PAD) has imposed flow control
                           on the interchange.
                 stopped  :The line with which this interchange is associated
                           is in the FLOW CONTROL state. This is valid for 
                           TPAD interchanges only.
                 slowPoll:The interchange is in slow poll.
                 fastPoll:The interchange is in fast poll.
                 na       :Value not Available"
        ::= { cdx6500PPSTALCInterchangeEntry 3 }

        alcIStatsFramesIn OBJECT-TYPE
            SYNTAX Counter
            ACCESS read-only
            STATUS mandatory
            DESCRIPTION
                "Number of ALC frames received."
        ::= { cdx6500PPSTALCInterchangeEntry 4 }

        alcIStatsFramesOut OBJECT-TYPE
            SYNTAX Counter
            ACCESS read-only
            STATUS mandatory
            DESCRIPTION
                "Number of ALC frames transmitted."
        ::= { cdx6500PPSTALCInterchangeEntry 5 }

        alcIStatsDataMesgsIn OBJECT-TYPE
            SYNTAX Counter
            ACCESS read-only
            STATUS mandatory
            DESCRIPTION
                "Number of ALC data messages received."
        ::= { cdx6500PPSTALCInterchangeEntry 6 }

        alcIStatsDataMesgsOut OBJECT-TYPE
            SYNTAX Counter
            ACCESS read-only
            STATUS mandatory
            DESCRIPTION
                "Number of ALC data messages transmitted."
        ::= { cdx6500PPSTALCInterchangeEntry 7 }

        alcIStatsCharsIn OBJECT-TYPE
            SYNTAX Counter
            ACCESS read-only
            STATUS mandatory
            DESCRIPTION
                "Total number of characters received, excluding
                 synchronization characters."
        ::= { cdx6500PPSTALCInterchangeEntry 8 }

        alcIStatsCharsOut OBJECT-TYPE
            SYNTAX Counter
            ACCESS read-only
            STATUS mandatory
            DESCRIPTION
                "Total number of characters transmitted, excluding
                 synchronization characters."
        ::= { cdx6500PPSTALCInterchangeEntry 9 }

        alcIStatsPolls OBJECT-TYPE
            SYNTAX Counter
            ACCESS read-only
            STATUS mandatory
            DESCRIPTION
                "The number of poll messages transmitted for a line
                 defined as a TPAD. The number received for one 
                 defined as HPAD."
        ::= { cdx6500PPSTALCInterchangeEntry 10 }

        alcIStatsGAs OBJECT-TYPE
            SYNTAX Counter
            ACCESS read-only
            STATUS mandatory
            DESCRIPTION
                "The number of Go Ahead messages transmitted for a line 
                 defined as HPAD. The number received for one defined
                 as TPAD."
        ::= { cdx6500PPSTALCInterchangeEntry 11 }

        alcIStatsResets OBJECT-TYPE
            SYNTAX Counter
            ACCESS read-only
            STATUS mandatory
            DESCRIPTION
                "The number of Reset messages transmitted for a line defined
                 as TPAD. The number received for one defined as HPAD."
        ::= { cdx6500PPSTALCInterchangeEntry 12 }

        alcIStatsDiscardBadTAIn OBJECT-TYPE
            SYNTAX Counter
            ACCESS read-only
            STATUS mandatory
            DESCRIPTION
                "The number of received messages discarded because the Terminal
                 Address was not defined."
        ::= { cdx6500PPSTALCInterchangeEntry 13 }

        alcIStatsDiscardBadTAOut OBJECT-TYPE
            SYNTAX Counter
            ACCESS read-only
            STATUS mandatory
            DESCRIPTION
                "The number of transmitted messages discarded because the
                 Terminal Address was not defined."
        ::= { cdx6500PPSTALCInterchangeEntry 14 }

        alcIStatsDisabledIAIn OBJECT-TYPE
            SYNTAX Counter
            ACCESS read-only
            STATUS mandatory
            DESCRIPTION
                "The number of received messages discarded because the 
                 Interchange was disabled."
        ::= { cdx6500PPSTALCInterchangeEntry 15 }

        alcIStatsDisabledIAOut OBJECT-TYPE
            SYNTAX Counter
            ACCESS read-only
            STATUS mandatory
            DESCRIPTION
                "The number of transmitted messages discarded because the 
                 Interchange was disabled."
        ::= { cdx6500PPSTALCInterchangeEntry 16 }

        alcIStatsMaxQSizeOut OBJECT-TYPE
            SYNTAX INTEGER
            ACCESS read-only
            STATUS mandatory
            DESCRIPTION
                "Maximum number of frames queued for transmission."
        ::= { cdx6500PPSTALCInterchangeEntry 17 }

        alcIStatsCCCErrors OBJECT-TYPE
            SYNTAX Counter
            ACCESS read-only
            STATUS mandatory
            DESCRIPTION
                "Number of messages received with an invalid checksum."
        ::= { cdx6500PPSTALCInterchangeEntry 18 }

        alcIStatsT1Timeouts OBJECT-TYPE
            SYNTAX Counter
            ACCESS read-only
            STATUS mandatory
            DESCRIPTION
                "Number of T1 timer expirations. This is defined for TPAD
                 only."
        ::= { cdx6500PPSTALCInterchangeEntry 19 }

        alcIStatsT2Timeouts OBJECT-TYPE
            SYNTAX Counter
            ACCESS read-only
            STATUS mandatory
            DESCRIPTION
                "Number of T2 timer expirations. This is defined for TPAD
                 only."
        ::= { cdx6500PPSTALCInterchangeEntry 20 }

        alcIStatsConnState OBJECT-TYPE
            SYNTAX INTEGER {
                    online     (1),
                    offline    (2),
                    connecting (3),
                    inactive   (4),
                    pending    (5),
                    na         (100)
                    }
            ACCESS read-only
            STATUS mandatory
            DESCRIPTION
                "Current state of the connection.
                 online    :The connection is available for data transfer.
                 offline   :The connection has been disabled by an operator.
                 connecting:The ALP PAD is attempting to make the X.25
                            virtual circuit available for use.
                 inactive  :The inactivity timer has expired, so the virtual
                            circuit has been dropped. Data received from ALC
                            will cause the connection to be re-established.
                 pending   :The CSD option has been configured and the ALC
                            entity is currently down; hence the ALP PAD has
                            disabled the virtual circuit.
                 na        :Value not Available"
        ::= { cdx6500PPSTALCInterchangeEntry 21 }

        alcIStatsALCMesgsIn OBJECT-TYPE
            SYNTAX Counter
            ACCESS read-only
            STATUS mandatory
            DESCRIPTION
                "The number of messages received from ALC."
        ::= { cdx6500PPSTALCInterchangeEntry 22 }

        alcIStatsALCMesgsOut OBJECT-TYPE
            SYNTAX Counter
            ACCESS read-only
            STATUS mandatory
            DESCRIPTION
                "The number of messages transmitted to ALC."
        ::= { cdx6500PPSTALCInterchangeEntry 23 }

        alcIStatsX25MesgsIn OBJECT-TYPE
            SYNTAX Counter
            ACCESS read-only
            STATUS mandatory
            DESCRIPTION
                "The number of messages received from X.25."
        ::= { cdx6500PPSTALCInterchangeEntry 24 }

        alcIStatsX25MesgsOut OBJECT-TYPE
            SYNTAX Counter
            ACCESS read-only
            STATUS mandatory
            DESCRIPTION
                "The number of messages transmitted to X.25."
        ::= { cdx6500PPSTALCInterchangeEntry 25 }

        alcIStatsALCCharsIn OBJECT-TYPE
            SYNTAX Counter
            ACCESS read-only
            STATUS mandatory
            DESCRIPTION
                "The number of characters received from ALC."
        ::= { cdx6500PPSTALCInterchangeEntry 26 }

        alcIStatsALCCharsOut OBJECT-TYPE
            SYNTAX Counter
            ACCESS read-only
            STATUS mandatory
            DESCRIPTION
                "The number of characters transmitted to ALC."
        ::= { cdx6500PPSTALCInterchangeEntry 27 }

        alcIStatsX25CharsIn OBJECT-TYPE
            SYNTAX Counter
            ACCESS read-only
            STATUS mandatory
            DESCRIPTION
                "The number of characters received from X.25."
        ::= { cdx6500PPSTALCInterchangeEntry 28 }

        alcIStatsX25CharsOut OBJECT-TYPE
            SYNTAX Counter
            ACCESS read-only
            STATUS mandatory
            DESCRIPTION
                "The number of characters transmitted to X.25."
        ::= { cdx6500PPSTALCInterchangeEntry 29 }

        alcIStatsALCDiscardedMesgsEntityDown OBJECT-TYPE
            SYNTAX Counter
            ACCESS read-only
            STATUS mandatory
            DESCRIPTION
                "The number of messages received by ALC for which the 
                 destination entity is unable to process the data."
        ::= { cdx6500PPSTALCInterchangeEntry 30 }

        alcIStatsX25DiscardedMesgsEntityDown OBJECT-TYPE
            SYNTAX Counter
            ACCESS read-only
            STATUS mandatory
            DESCRIPTION
                "The number of messages received by X.25 for which the 
                 destination entity is unable to process the data."
        ::= { cdx6500PPSTALCInterchangeEntry 31 }

        alcIStatsX25DiscardedMesgsBadALCAddr OBJECT-TYPE
            SYNTAX Counter
            ACCESS read-only
            STATUS mandatory
            DESCRIPTION
                "The number of messages received from X.25 for which the
                 addresses specified do not match those associated with 
                 the connection."
        ::= { cdx6500PPSTALCInterchangeEntry 32 }

        alcIStatsX25DiscardedMesgsBadHeader OBJECT-TYPE
            SYNTAX Counter
            ACCESS read-only
            STATUS mandatory
            DESCRIPTION
                "The number of messages received by X.25 of which the IN
                 header configured does not match the header present in the
                 message."
        ::= { cdx6500PPSTALCInterchangeEntry 33 }

        alcIStatsX25DiscardedMesgsTooLong OBJECT-TYPE
            SYNTAX Counter
            ACCESS read-only
            STATUS mandatory
            DESCRIPTION
                "The number of messages received from X.25 that were discarded
                 because they were longer than the allowable ALC maximum
                 configured."
        ::= { cdx6500PPSTALCInterchangeEntry 34 }

        alcIStatsALCDiscardedMesgsQFull OBJECT-TYPE
            SYNTAX Counter
            ACCESS read-only
            STATUS mandatory
            DESCRIPTION
                "The number of messages discarded because the ALC outbound
                 message queue was full."
        ::= { cdx6500PPSTALCInterchangeEntry 35 }

        alcIStatsX25DiscardedMesgsQFull OBJECT-TYPE
            SYNTAX Counter
            ACCESS read-only
            STATUS mandatory
            DESCRIPTION
                "The number of messages discarded because the X.25 outbound
                 message queue was full."
        ::= { cdx6500PPSTALCInterchangeEntry 36 }

        alcIStatsCurrTxALCQSize OBJECT-TYPE
            SYNTAX INTEGER
            ACCESS read-only
            STATUS mandatory
            DESCRIPTION
                "The number of messages currently queued in the ALC
                 outbound message queue for transmission."
        ::= { cdx6500PPSTALCInterchangeEntry 37 }

        alcIStatsCurrTxX25QSize OBJECT-TYPE
            SYNTAX INTEGER
            ACCESS read-only
            STATUS mandatory
            DESCRIPTION
                "The number of messages currently queued in the X.25
                 outbound message queue for transmission."
        ::= { cdx6500PPSTALCInterchangeEntry 38 }

        alcIStatsMaxTxALCQSize OBJECT-TYPE
            SYNTAX INTEGER
            ACCESS read-only
            STATUS mandatory
            DESCRIPTION
                "The maximum (highwater mark) size of the ALC outbound
                 queue so far."
        ::= { cdx6500PPSTALCInterchangeEntry 39 }

        alcIStatsMaxTxX25QSize OBJECT-TYPE
            SYNTAX INTEGER
            ACCESS read-only
            STATUS mandatory
            DESCRIPTION
                "The maximum (highwater mark) size of the X.25 outbound
                 queue so far."
        ::= { cdx6500PPSTALCInterchangeEntry 40 }

        -- ALC Terminal Statistics

        cdx6500PPSTALCTerminalTable OBJECT-TYPE
            SYNTAX SEQUENCE OF Cdx6500PPSTALCTerminalEntry
            ACCESS not-accessible
            STATUS mandatory
            DESCRIPTION
                "This table contains ALC Terminalinal Statistics parameters."
          ::= { cdx6500PPSTALCStatsTable 3 }
          
        cdx6500PPSTALCTerminalEntry OBJECT-TYPE
            SYNTAX Cdx6500PPSTALCTerminalEntry
            ACCESS not-accessible
            STATUS mandatory
            DESCRIPTION
                "Entries in the ALC Terminalinal Statistics Table."
            INDEX { alcTStatsPortNumber,
                    alcTStatsInterchangeAddress,
                    alcTStatsTerminalAddress }
        ::= { cdx6500PPSTALCTerminalTable 1 }
          
        Cdx6500PPSTALCTerminalEntry ::=
            SEQUENCE {
                alcTStatsPortNumber
                    INTEGER,
                alcTStatsInterchangeAddress
                    OCTET STRING,
                alcTStatsTerminalAddress
                    OCTET STRING,
                alcTStatsConnState
                    INTEGER,
                alcTStatsALCMesgsIn
                    Counter,
                alcTStatsALCMesgsOut
                    Counter,
                alcTStatsX25MesgsIn
                    Counter,
                alcTStatsX25MesgsOut
                    Counter,
                alcTStatsALCCharsIn
                    Counter,
                alcTStatsALCCharsOut
                    Counter,
                alcTStatsX25CharsIn
                    Counter,
                alcTStatsX25CharsOut
                    Counter,
                alcTStatsALCDiscardedMesgsEntityDown
                    Counter,
                alcTStatsX25DiscardedMesgsEntityDown
                    Counter,
                alcTStatsX25DiscardedMesgsBadALCAddr
                    Counter,
                alcTStatsX25DiscardedMesgsBadHeader
                    Counter,
                alcTStatsX25DiscardedMesgsTooLong
                    Counter,
                alcTStatsALCDiscardedMesgsQFull
                    Counter,
                alcTStatsX25DiscardedMesgsQFull
                    Counter,
                alcTStatsCurrTxALCQSize
                    INTEGER,
                alcTStatsCurrTxX25QSize
                    INTEGER,
                alcTStatsMaxTxALCQSize
                    INTEGER,
                alcTStatsMaxTxX25QSize
                    INTEGER
            }

        alcTStatsPortNumber OBJECT-TYPE
            SYNTAX INTEGER (1..54)
            ACCESS read-only
            STATUS mandatory
            DESCRIPTION
                "Port number of this port."
        ::= { cdx6500PPSTALCTerminalEntry 1 }

        alcTStatsInterchangeAddress OBJECT-TYPE
            SYNTAX OCTET STRING (SIZE(1))
            ACCESS read-only
            STATUS mandatory
            DESCRIPTION
                "The address of the interchange.
                 Addresses 0D,0F,1D,2D,3D and 3F are illegal as they are used 
                 as line control characters."
        ::= { cdx6500PPSTALCTerminalEntry 2 }

        alcTStatsTerminalAddress OBJECT-TYPE
            SYNTAX OCTET STRING (SIZE(1))
            ACCESS read-only
            STATUS mandatory
            DESCRIPTION
                "Address identifying this terminal."
        ::= { cdx6500PPSTALCTerminalEntry 3 }

        alcTStatsConnState OBJECT-TYPE
            SYNTAX INTEGER {
                    online     (1),
                    offline    (2),
                    connecting (3),
                    inactive   (4),
                    pending    (5),
                    na         (100)
                    }
            ACCESS read-only
            STATUS mandatory
            DESCRIPTION
                "Current state of the connection.
                 online    :The connection is available for data transfer.
                 offline   :The connection has been disabled by an operator.
                 connecting:The ALP PAD is attempting to make the X.25
                            virtual circuit available for use.
                 inactive  :The inactivity timer has expired, so the virtual
                            circuit has been dropped. Data received from ALC
                            will cause the connection to be re-established.
                 pending   :The CSD option has been configured and the ALC
                            entity is currently down; hence the ALP PAD has
                            disabled the virtual circuit.
                 na        :Value not Available"
        ::= { cdx6500PPSTALCTerminalEntry 4 }

        alcTStatsALCMesgsIn OBJECT-TYPE
            SYNTAX Counter
            ACCESS read-only
            STATUS mandatory
            DESCRIPTION
                "The number of messages received from ALC."
        ::= { cdx6500PPSTALCTerminalEntry 5 }

        alcTStatsALCMesgsOut OBJECT-TYPE
            SYNTAX Counter
            ACCESS read-only
            STATUS mandatory
            DESCRIPTION
                "The number of messages transmitted to ALC."
        ::= { cdx6500PPSTALCTerminalEntry 6 }

        alcTStatsX25MesgsIn OBJECT-TYPE
            SYNTAX Counter
            ACCESS read-only
            STATUS mandatory
            DESCRIPTION
                "The number of messages received from X.25."
        ::= { cdx6500PPSTALCTerminalEntry 7 }

        alcTStatsX25MesgsOut OBJECT-TYPE
            SYNTAX Counter
            ACCESS read-only
            STATUS mandatory
            DESCRIPTION
                "The number of messages transmitted to X.25."
        ::= { cdx6500PPSTALCTerminalEntry 8 }

        alcTStatsALCCharsIn OBJECT-TYPE
            SYNTAX Counter
            ACCESS read-only
            STATUS mandatory
            DESCRIPTION
                "The number of characters received from ALC."
        ::= { cdx6500PPSTALCTerminalEntry 9 }

        alcTStatsALCCharsOut OBJECT-TYPE
            SYNTAX Counter
            ACCESS read-only
            STATUS mandatory
            DESCRIPTION
                "The number of characters transmitted to ALC."
        ::= { cdx6500PPSTALCTerminalEntry 10 }

        alcTStatsX25CharsIn OBJECT-TYPE
            SYNTAX Counter
            ACCESS read-only
            STATUS mandatory
            DESCRIPTION
                "The number of characters received from X.25."
        ::= { cdx6500PPSTALCTerminalEntry 11 }

        alcTStatsX25CharsOut OBJECT-TYPE
            SYNTAX Counter
            ACCESS read-only
            STATUS mandatory
            DESCRIPTION
                "The number of characters transmitted to X.25."
        ::= { cdx6500PPSTALCTerminalEntry 12 }

        alcTStatsALCDiscardedMesgsEntityDown OBJECT-TYPE
            SYNTAX Counter
            ACCESS read-only
            STATUS mandatory
            DESCRIPTION
                "The number of messages received by ALC for which the 
                 destination entity is unable to process the data."
        ::= { cdx6500PPSTALCTerminalEntry 13 }

        alcTStatsX25DiscardedMesgsEntityDown OBJECT-TYPE
            SYNTAX Counter
            ACCESS read-only
            STATUS mandatory
            DESCRIPTION
                "The number of messages received by X.25 for which the 
                 destination entity is unable to process the data."
        ::= { cdx6500PPSTALCTerminalEntry 14 }

        alcTStatsX25DiscardedMesgsBadALCAddr OBJECT-TYPE
            SYNTAX Counter
            ACCESS read-only
            STATUS mandatory
            DESCRIPTION
                "The number of messages received from X.25 for which the
                 addresses specified do not match those associated with 
                 the connection."
        ::= { cdx6500PPSTALCTerminalEntry 15 }

        alcTStatsX25DiscardedMesgsBadHeader OBJECT-TYPE
            SYNTAX Counter
            ACCESS read-only
            STATUS mandatory
            DESCRIPTION
                "The number of messages received by X.25 of which the IN
                 header configured does not match the header present in the
                 message."
        ::= { cdx6500PPSTALCTerminalEntry 16 }

        alcTStatsX25DiscardedMesgsTooLong OBJECT-TYPE
            SYNTAX Counter
            ACCESS read-only
            STATUS mandatory
            DESCRIPTION
                "The number of messages received from X.25 that were discarded
                 because they were longer than the allowable ALC maximum
                 configured."
        ::= { cdx6500PPSTALCTerminalEntry 17 }

        alcTStatsALCDiscardedMesgsQFull OBJECT-TYPE
            SYNTAX Counter
            ACCESS read-only
            STATUS mandatory
            DESCRIPTION
                "The number of messages discarded because the ALC outbound
                 message queue was full."
        ::= { cdx6500PPSTALCTerminalEntry 18 }

        alcTStatsX25DiscardedMesgsQFull OBJECT-TYPE
            SYNTAX Counter
            ACCESS read-only
            STATUS mandatory
            DESCRIPTION
                "The number of messages discarded because the X.25 outbound
                 message queue was full."
        ::= { cdx6500PPSTALCTerminalEntry 19 }

        alcTStatsCurrTxALCQSize OBJECT-TYPE
            SYNTAX INTEGER
            ACCESS read-only
            STATUS mandatory
            DESCRIPTION
                "The number of messages currently queued in the ALC
                 outbound message queue for transmission."
        ::= { cdx6500PPSTALCTerminalEntry 20 }

        alcTStatsCurrTxX25QSize OBJECT-TYPE
            SYNTAX INTEGER
            ACCESS read-only
            STATUS mandatory
            DESCRIPTION
                "The number of messages currently queued in the X.25
                 outbound message queue for transmission."
        ::= { cdx6500PPSTALCTerminalEntry 21 }

        alcTStatsMaxTxALCQSize OBJECT-TYPE
            SYNTAX INTEGER
            ACCESS read-only
            STATUS mandatory
            DESCRIPTION
                "The maximum (highwater mark) size of the ALC outbound
                 queue so far."
        ::= { cdx6500PPSTALCTerminalEntry 22 }

        alcTStatsMaxTxX25QSize OBJECT-TYPE
            SYNTAX INTEGER
            ACCESS read-only
            STATUS mandatory
            DESCRIPTION
                "The maximum (highwater mark) size of the X.25 outbound
                 queue so far."
        ::= { cdx6500PPSTALCTerminalEntry 23 }

        -- ALC Port Controls

        cdx6500ContALC OBJECT IDENTIFIER ::= { cdx6500Controls 10 }

        cdx6500ContALCPortTable OBJECT-TYPE
            SYNTAX SEQUENCE OF Cdx6500ContALCPortEntry
            ACCESS not-accessible
            STATUS mandatory
            DESCRIPTION
                "This table contains ALC Port Control parameters."
          ::= { cdx6500ContALC 1 }
          
        cdx6500ContALCPortEntry OBJECT-TYPE
            SYNTAX Cdx6500ContALCPortEntry
            ACCESS not-accessible
            STATUS mandatory
            DESCRIPTION
                "Entries in the ALC Port Control Table."
            INDEX { alcPContPortNumber }
        ::= { cdx6500ContALCPortTable 1 }
          
        Cdx6500ContALCPortEntry ::=
            SEQUENCE {
                alcPContPortNumber
                    INTEGER,
                alcPContPortBoot
                    INTEGER,
                alcPContPortEnable
                    INTEGER,
                alcPContPortDisable
                    INTEGER
            }

        alcPContPortNumber OBJECT-TYPE
            SYNTAX INTEGER (1..54)
            ACCESS not-accessible
            STATUS mandatory
            DESCRIPTION
                "ALC Port Number."
        ::= { cdx6500ContALCPortEntry 1 }

        alcPContPortBoot OBJECT-TYPE
            SYNTAX INTEGER {
                    boot   (1),
                    noBoot (2)
                   }
            ACCESS write-only
            STATUS mandatory
            DESCRIPTION
                "Boots the specified ALC Port.
                 boot   - Boot the port.
                 noBoot - Do not boot the port."
        ::= { cdx6500ContALCPortEntry 2 }

        alcPContPortEnable OBJECT-TYPE
            SYNTAX INTEGER {
                    enable   (1),
                    noEnable (2)
                   }
            ACCESS write-only
            STATUS mandatory
            DESCRIPTION
                "Enables the specified ALC Port.
                 enable   - Enable the port.
                 noEnable - Do not enable the port."
        ::= { cdx6500ContALCPortEntry 3 }

        alcPContPortDisable OBJECT-TYPE
            SYNTAX INTEGER {
                    disable   (1),
                    noDisable (2)
                   }
            ACCESS write-only
            STATUS mandatory
            DESCRIPTION
                "Disables the specified ALC Port.
                 disable   - Disable the port.
                 noDisable - Do not disable the port."
        ::= { cdx6500ContALCPortEntry 4 }

        cdx6500ContALCInterchangeTable OBJECT-TYPE
            SYNTAX SEQUENCE OF Cdx6500ContALCInterchangeEntry
            ACCESS not-accessible
            STATUS mandatory
            DESCRIPTION
                "This table contains ALC Interchange Control parameters."
          ::= { cdx6500ContALC 2 }

        cdx6500ContALCInterchangeEntry OBJECT-TYPE
            SYNTAX Cdx6500ContALCInterchangeEntry
            ACCESS not-accessible
            STATUS mandatory
            DESCRIPTION
                "Entries in the ALC Interchange Control Table."
            INDEX { alcIContPortNumber,
                    alcIContInterchangeAddress }
        ::= { cdx6500ContALCInterchangeTable 1 }

        Cdx6500ContALCInterchangeEntry ::=
            SEQUENCE {
                alcIContPortNumber
                    INTEGER,
                alcIContInterchangeAddress
                    OCTET STRING,
                alcIContInterchangeBoot
                    INTEGER,
                alcIContInterchangeEnable
                    INTEGER,
                alcIContInterchangeDisable
                    INTEGER
            }

        alcIContPortNumber OBJECT-TYPE
            SYNTAX INTEGER (1..54)
            ACCESS not-accessible
            STATUS mandatory
            DESCRIPTION
                "ALC Port Number."
        ::= { cdx6500ContALCInterchangeEntry 1 }

        alcIContInterchangeAddress OBJECT-TYPE
            SYNTAX OCTET STRING (SIZE(1))
            ACCESS not-accessible
            STATUS mandatory
            DESCRIPTION
                "ALC Interchange address."
        ::= { cdx6500ContALCInterchangeEntry 2 }

        alcIContInterchangeBoot OBJECT-TYPE
            SYNTAX INTEGER {
                    boot   (1),
                    noBoot (2)
                   }
            ACCESS write-only
            STATUS mandatory
            DESCRIPTION
                "Boots the specified ALC Interchange.
                 boot   - Boot the interchange.
                 noBoot - Do not boot the interchange."
        ::= { cdx6500ContALCInterchangeEntry 3 }

        alcIContInterchangeEnable OBJECT-TYPE
            SYNTAX INTEGER {
                    enable   (1),
                    noEnable (2)
                   }
            ACCESS write-only
            STATUS mandatory
            DESCRIPTION
                "Enables the specified ALC Interchange.
                 enable   - Enable the interchange.
                 noEnable - Do not enable the interchange."
        ::= { cdx6500ContALCInterchangeEntry 4 }

        alcIContInterchangeDisable OBJECT-TYPE
            SYNTAX INTEGER {
                    disable   (1),
                    noDisable (2)
                   }
            ACCESS write-only
            STATUS mandatory
            DESCRIPTION
                "Disables the specified ALC Interchange.
                 disable   - Disable the interchange.
                 noDisable - Do not disable the interchange."
        ::= { cdx6500ContALCInterchangeEntry 5 }

        cdx6500ContALCTerminalTable OBJECT-TYPE
            SYNTAX SEQUENCE OF Cdx6500ContALCTerminalEntry
            ACCESS not-accessible
            STATUS mandatory
            DESCRIPTION
                "This table contains ALC Terminal Control parameters."
          ::= { cdx6500ContALC 3 }

        cdx6500ContALCTerminalEntry OBJECT-TYPE
            SYNTAX Cdx6500ContALCTerminalEntry
            ACCESS not-accessible
            STATUS mandatory
            DESCRIPTION
                "Entries in the ALC Terminal Control Table."
            INDEX { alcTContPortNumber,
                    alcTContInterchangeAddress,
                    alcTContTerminalAddress }
        ::= { cdx6500ContALCTerminalTable 1 }

        Cdx6500ContALCTerminalEntry ::=
            SEQUENCE {
                alcTContPortNumber
                    INTEGER,
                alcTContInterchangeAddress
                    OCTET STRING,
                alcTContTerminalAddress
                    OCTET STRING,
                alcTContTerminalBoot
                    INTEGER,
                alcTContTerminalEnable
                    INTEGER,
                alcTContTerminalDisable
                    INTEGER
            }

        alcTContPortNumber OBJECT-TYPE
            SYNTAX INTEGER (1..54)
            ACCESS not-accessible
            STATUS mandatory
            DESCRIPTION
                "ALC Port Number."
        ::= { cdx6500ContALCTerminalEntry 1 }

        alcTContInterchangeAddress OBJECT-TYPE
            SYNTAX OCTET STRING (SIZE(1))
            ACCESS not-accessible
            STATUS mandatory
            DESCRIPTION
                "ALC Interchange address."
        ::= { cdx6500ContALCTerminalEntry 2 }

        alcTContTerminalAddress OBJECT-TYPE
            SYNTAX OCTET STRING (SIZE(1))
            ACCESS not-accessible
            STATUS mandatory
            DESCRIPTION
                "Address identifying this terminal."
        ::= { cdx6500ContALCTerminalEntry 3 }

        alcTContTerminalBoot OBJECT-TYPE
            SYNTAX INTEGER {
                    boot   (1),
                    noBoot (2)
                   }
            ACCESS write-only
            STATUS mandatory
            DESCRIPTION
                "Boots the specified ALC terminal.
                 boot   - Boot the terminal.
                 noBoot - Do not boot the terminal."
        ::= { cdx6500ContALCTerminalEntry 4 }

        alcTContTerminalEnable OBJECT-TYPE
            SYNTAX INTEGER {
                    enable   (1),
                    noEnable (2)
                   }
            ACCESS write-only
            STATUS mandatory
            DESCRIPTION
                "Enables the specified ALC Terminal.
                 enable   - Enable the terminal.
                 noEnable - Do not enable the terminal."
        ::= { cdx6500ContALCTerminalEntry 5 }

        alcTContTerminalDisable OBJECT-TYPE
            SYNTAX INTEGER {
                    disable   (1),
                    noDisable (2)
                   }
            ACCESS write-only
            STATUS mandatory
            DESCRIPTION
                "Disables the specified ALC terminal.
                 disable   - Disable the terminal.
                 noDisable - Do not disable the terminal."
        ::= { cdx6500ContALCTerminalEntry 6 }

        END
