-- Nortel Networks CES Management MIB.
-- Based on: Management CES-IS V2.0 af-vtoa-0078.000

Wellfleet-CES-MIB DEFINITIONS ::= BEGIN

IMPORTS

Counter
    FROM RFC1155-SMI
OBJECT-TYPE
    FROM RFC-1212
wfAtmInterfaceGroup
    FROM Wellfleet-COMMON-MIB;


wfAtmCESGroup OBJECT IDENTIFIER ::= { wfAtmInterfaceGroup 4 }


-- This is the MIB module based on the ATM Forum Circuit Emulation
-- Service Interoperability Specification Version 2.0.
--

--    CES Configuration Table

wfAtmCESObjects     OBJECT IDENTIFIER ::= { wfAtmCESGroup 1 }

wfAtmCESConfTable OBJECT-TYPE
    SYNTAX  SEQUENCE OF WfAtmCESConfEntry
    ACCESS  not-accessible
    STATUS  mandatory
    DESCRIPTION
        "The CES configuration table used to manage interworking
         between CBR interfaces or channels and ATM Virtual Channel
         Links (VCLs)."
    ::= { wfAtmCESObjects 1 }

wfAtmCESConfEntry OBJECT-TYPE
    SYNTAX  WfAtmCESConfEntry
    ACCESS  not-accessible
    STATUS  mandatory
    DESCRIPTION
        "An entry in the CES configuration table. There is one
         entry in the table per CES entity, mapping one CBR
         interface, channel, or bundle to an ATM VCL."
    INDEX { wfAtmCESConfAtmIndex,
	    wfAtmCESConfCbrIndex }
    ::= { wfAtmCESConfTable 1 }

WfAtmCESConfEntry ::= SEQUENCE {
    wfAtmCESConfDelete                    INTEGER,
    wfAtmCESConfDisable                   INTEGER,
    wfAtmCESConfAtmIndex                  INTEGER,
    wfAtmCESConfCbrIndex                  INTEGER,
    wfAtmCESConfAtmVpi                    INTEGER,
    wfAtmCESConfAtmVci                    INTEGER,
    wfAtmCESConfCfgAtmVpi                 INTEGER,
    wfAtmCESConfCfgAtmVci                 INTEGER,
    wfAtmCESConfVclCct                    INTEGER,
    wfAtmCESConfCbrService                INTEGER,
    wfAtmCESConfCbrClockMode              INTEGER,
    wfAtmCESConfCas                       INTEGER,
    wfAtmCESConfPartialFill               INTEGER,
    wfAtmCESConfBufMaxSize                INTEGER,
    wfAtmCESConfCdvRxT                    INTEGER,
    wfAtmCESConfCellLossIntegrationPeriod INTEGER,
    wfAtmCESConfConnType                  INTEGER,
    wfAtmCESConfLocalAddr                 OCTET STRING,
    wfAtmCESConfAdminStatus               INTEGER,
    wfAtmCESConfOperStatus                INTEGER
}

wfAtmCESConfDelete OBJECT-TYPE
    SYNTAX INTEGER {
    	       created(1),
    	       deleted(2)
    	   }
    ACCESS read-write
    STATUS mandatory
    DESCRIPTION
        "Create/delete MIB instance parameter."
    DEFVAL { created }
    ::= { wfAtmCESConfEntry 1 }

wfAtmCESConfDisable OBJECT-TYPE
    SYNTAX INTEGER {
               enabled(1),
               disabled(2)
           }
    ACCESS read-write
    STATUS mandatory
    DESCRIPTION
        "Enable/Disable MIB instance parameter."
    DEFVAL { enabled }
    ::= { wfAtmCESConfEntry 2 }

wfAtmCESConfAtmIndex OBJECT-TYPE
    SYNTAX        INTEGER
    ACCESS        read-only
    STATUS        mandatory
    DESCRIPTION
        "The value of this object is equal to the line number
         value of the ATM Port interface mapped through this CES IWF 
         to a CBR interface."
    ::= { wfAtmCESConfEntry 3 }

wfAtmCESConfCbrIndex OBJECT-TYPE
    SYNTAX        INTEGER
    ACCESS        read-only
    STATUS        mandatory
    DESCRIPTION
        "The value of this object is equal to the line number value
         of the CBR interface, channel, or bundle that is being
         cross-connected to this ATM VCL."
    ::= { wfAtmCESConfEntry 4 }

wfAtmCESConfAtmVpi OBJECT-TYPE
    SYNTAX        INTEGER
    ACCESS        read-only
    STATUS        mandatory
    DESCRIPTION
        "The value of this object is equal to the VPI used
         by the ATM VCL mapped through this CES IWF to a CBR
         interface."
    ::= { wfAtmCESConfEntry 5 }

wfAtmCESConfAtmVci OBJECT-TYPE
    SYNTAX        INTEGER
    ACCESS        read-only
    STATUS        mandatory
    DESCRIPTION
        "The value of this object is equal to the VCI used
         by the ATM VCL mapped through this CES IWF to a CBR
         interface."
    ::= { wfAtmCESConfEntry 6 }

wfAtmCESConfCfgAtmVpi OBJECT-TYPE
    SYNTAX        INTEGER
    ACCESS        read-write
    STATUS        mandatory
    DESCRIPTION
        "The value of this object is equal to the VPI used
         by the ATM VCL mapped through this CES IWF to a CBR
         interface.  Setting this attribute when wfAtmCESConfConnType
         is set to activeSvc or passiveSvc has no effect."
    ::= { wfAtmCESConfEntry 7 }

wfAtmCESConfCfgAtmVci OBJECT-TYPE
    SYNTAX        INTEGER
    ACCESS        read-write
    STATUS        mandatory
    DESCRIPTION
        "The value of this object is equal to the VCI used
         by the ATM VCL mapped through this CES IWF to a CBR
         interface.  Setting this attribute when wfAtmCESConfConnType
         is set to activeSvc or passiveSvc has no effect."
    ::= { wfAtmCESConfEntry 8 }

wfAtmCESConfVclCct OBJECT-TYPE
    SYNTAX        INTEGER
    ACCESS        read-write
    STATUS        mandatory
    DESCRIPTION
        "Identifies the object which corresponds to the Wellfleet circuit
         number."
    ::= { wfAtmCESConfEntry 9 }

wfAtmCESConfCbrService OBJECT-TYPE
    SYNTAX        INTEGER {
                      unstructured(1),
                      structured(2)
                  }
    ACCESS        read-write
    STATUS        mandatory
    DESCRIPTION
        "Define if DSx/Ex service is structured or unstructured. A
         structured(2) interface is some nx64kbKbps. An unstructured
         (1) interface is 1.544Mbps, 2.048Mbps, 6.312Mbps, 44.736 Mbps,
         or 34.368 Mbps. unstructured(1) passes all bits through the
         ATM network. strucutured(2) passes data bits through the
         ATM network, and may also pass signalling bits.
         At this time, only unstructured mode is defined for the
         44.736 Mbps and 34.368 Mbps services."
    DEFVAL        { structured }
    ::= { wfAtmCESConfEntry 10 }

wfAtmCESConfCbrClockMode OBJECT-TYPE
    SYNTAX        INTEGER {
                    synchronous(1),
                    srts(2),
                    adaptive(3)
                  }
    ACCESS        read-write 
    STATUS        mandatory
    DESCRIPTION
        "Define if DSx/Ex service clocking mode. This maps into
         transmit clock source of CBR interface.
         For structured modes this value, if present, must be set to
         synchronous(1)."
    DEFVAL { synchronous }
    ::= { wfAtmCESConfEntry 11 }

wfAtmCESConfCas OBJECT-TYPE
    SYNTAX        INTEGER {
                    basic(1),
                    e1Cas(2),
                    ds1SfCas(3),
                    ds1EsfCas(4),
                    j2Cas(5)
                  }
    ACCESS        read-write
    STATUS        mandatory
    DESCRIPTION
        "This parameter selects which AAL1 Format should be used:
         Basic does not carry CAS bits, and uses a single 125 usec frame.
         e1Cas, ds1SfCas, dS1EsfCas and j2Cas carry CAS bits in a
         multiframe structure for E1, DS1 SF, DS1 ESF and J2
         respectively.
         This applies to structured interfaces only. Default is
         basic (1). For unstructured interfaces this value, if present,
         must be set to the default of basic (1)."
    DEFVAL { basic }
    ::= { wfAtmCESConfEntry 12 }

wfAtmCESConfPartialFill OBJECT-TYPE
    SYNTAX        INTEGER (0 .. 47)
    ACCESS        read-write
    STATUS        mandatory
    DESCRIPTION
        "If partial cell fill is used, the number of user octets per
         cell must be set with this parameter. Setting this parameter
         to zero disables partial cell fill, and causes all cells to
         be completely filled before they are sent."
    DEFVAL { 0 } -- Partial Cell Fill not used
    ::= { wfAtmCESConfEntry 13 }

wfAtmCESConfBufMaxSize OBJECT-TYPE
    SYNTAX        INTEGER (1..65536)
    ACCESS        read-write
    STATUS        mandatory
    DESCRIPTION
        "Define maximum size in 10 microsecond increments of the
         reassembly buffer. Some implementations may want allow the
         maximum buffer size to be programmed to a size less than the
         physical limit to reduce the maximum delay through a circuit."
    DEFVAL { 128 }
    ::= { wfAtmCESConfEntry 14 }

wfAtmCESConfCdvRxT OBJECT-TYPE
    SYNTAX        INTEGER (1..65535)
    ACCESS        read-write
    STATUS        mandatory
    DESCRIPTION
        "The maximum cell arrival jitter in 10 usec increments that
         the reassembly process will tolerate in the cell stream
         without producing errors on the CBR service interface."
    DEFVAL { 100 }
    ::= { wfAtmCESConfEntry 15 }

wfAtmCESConfCellLossIntegrationPeriod OBJECT-TYPE
    SYNTAX        INTEGER (1000 .. 65535)
    ACCESS        read-write
    STATUS        mandatory
    DESCRIPTION
        "The time in milliseconds for the cell loss integration period.
         If cells are continuously lost for this period of time,
         wfAtmCESCellLossStatus is set to loss (2). The
         default definition is 2500."
    DEFVAL { 2500 }
    ::= { wfAtmCESConfEntry 16 }

wfAtmCESConfConnType OBJECT-TYPE
    SYNTAX       INTEGER {
                   other(1),
                   pvc(2),
                   activeSvc(3),
                   passiveSvc(4)
                 }
    ACCESS       read-write
    STATUS       mandatory
    DESCRIPTION
        "The type of ATM connectivity between associated CES IWF's.
         Valid values are:
            other      - none of the types specified below
            pvc        - supporting connectivity is a permanent
                         virtual connection
            activeSvc  - attempt calls whenever none established
            passiveSvc - accept calls"
    DEFVAL { pvc }
    ::= { wfAtmCESConfEntry 17 }

wfAtmCESConfLocalAddr OBJECT-TYPE
    SYNTAX        OCTET STRING
    ACCESS        read-write
    STATUS        mandatory
    DESCRIPTION
        "The ATM address of the local CES IWF process. This address
         may be used by the automatic SVC establishment procedures to
         identify the intended recipient CES IWF of an incoming automatic
         SVC call request. Optionally, the MAX-ACCESS of this object
         may be read-only, for those implementations where it is
         not desired to manually configure this address."
    ::= { wfAtmCESConfEntry 18 }

wfAtmCESConfAdminStatus OBJECT-TYPE
    SYNTAX        INTEGER {
                    up(1),
                    down(2)
                  }
    ACCESS        read-write
    STATUS        mandatory
    DESCRIPTION
        "The desired administrative status of the CES interworking
         function. The up and down states indicate that the traffic
         flow is enabled or disabled respectively across the CES
         interworking function."
    DEFVAL { up }
    ::= { wfAtmCESConfEntry 19 }

wfAtmCESConfOperStatus OBJECT-TYPE
    SYNTAX        INTEGER {
                    up(1),
                    down(2),
                    unknown(3)
                  }
    ACCESS        read-only
    STATUS        mandatory
    DESCRIPTION
        "The operational status of the CES interworking function.
         The up and down states indicate that the traffic flow is
         enabled or disabled respectively across the CES interworking
         function. The unknown state indicates that the state of the
         CES interworking function cannot be determined. The state
         will be down or unknown if the supporting CBR or ATM
         interfaces are down or unknown, respectively."
    ::= { wfAtmCESConfEntry 20 }


-- CES Statistics Table

wfAtmCESStatsTable OBJECT-TYPE
    SYNTAX        SEQUENCE OF WfAtmCESStatsEntry
    ACCESS        not-accessible
    STATUS        mandatory
    DESCRIPTION
        "The CES AAL1 statistical data table."
    ::= { wfAtmCESObjects 2 }

wfAtmCESStatsEntry OBJECT-TYPE
    SYNTAX        WfAtmCESStatsEntry
    ACCESS        not-accessible
    STATUS        mandatory
    DESCRIPTION
        "An entry in the CES AAL1 Stats table. There is one
         entry in this table corresponding to each entry in the
         wfAtmCESConfTable."
    INDEX {  wfAtmCESStatsAtmIndex,
	     wfAtmCESStatsAtmVpi,
             wfAtmCESStatsAtmVci }
    ::= { wfAtmCESStatsTable 1 }

WfAtmCESStatsEntry ::= SEQUENCE {
    wfAtmCESStatsAtmIndex                  INTEGER,
    wfAtmCESStatsAtmVpi                    INTEGER,
    wfAtmCESStatsAtmVci                    INTEGER,
    wfAtmCESStatsCbrIndex                  INTEGER,
    wfAtmCESStatsVclCct                    INTEGER,
    wfAtmCESStatsReassCells                Counter,
    wfAtmCESStatsHdrErrors                 Counter,
    wfAtmCESStatsPointerReframes           Counter,
    wfAtmCESStatsPointerParityErrors       Counter,
    wfAtmCESStatsAal1SeqErrors             Counter,
    wfAtmCESStatsLostCells                 Counter,
    wfAtmCESStatsMisinsertedCells          Counter,
    wfAtmCESStatsBufUnderflows             Counter, 
    wfAtmCESStatsBufOverflows              Counter,
    wfAtmCESStatsCellLossStatus            INTEGER
}

wfAtmCESStatsAtmIndex OBJECT-TYPE
    SYNTAX        INTEGER
    ACCESS        read-only
    STATUS        mandatory
    DESCRIPTION
        "The value of this object is equal to the line number
         value of the ATM Port interface mapped through this CES IWF 
         to a CBR interface."
    ::= { wfAtmCESStatsEntry 1 }

wfAtmCESStatsAtmVpi OBJECT-TYPE
    SYNTAX        INTEGER
    ACCESS        read-only
    STATUS        mandatory
    DESCRIPTION
        "The value of this object is equal to the VPI used
         by the ATM VCL mapped through this CES IWF to a CBR
         interface."
    ::= { wfAtmCESStatsEntry 2 }

wfAtmCESStatsAtmVci OBJECT-TYPE
    SYNTAX        INTEGER
    ACCESS        read-only
    STATUS        mandatory
    DESCRIPTION
        "The value of this object is equal to the VCI used
         by the ATM VCL mapped through this CES IWF to a CBR
         interface."
    ::= { wfAtmCESStatsEntry 3 }

wfAtmCESStatsCbrIndex OBJECT-TYPE
    SYNTAX        INTEGER
    ACCESS        read-only
    STATUS        mandatory
    DESCRIPTION
        "The value of this object is equal to the line number value
         of the CBR interface, channel, or bundle that is being
         cross-connected to this ATM VCL."
    ::= { wfAtmCESStatsEntry 4 }

wfAtmCESStatsVclCct OBJECT-TYPE
    SYNTAX        INTEGER
    ACCESS        read-only
    STATUS        mandatory
    DESCRIPTION
        "Identifies the object which corresponds to the Wellfleet circuit
         number."
    ::= { wfAtmCESStatsEntry 5 }

wfAtmCESStatsReassCells OBJECT-TYPE
    SYNTAX        Counter
    ACCESS        read-only
    STATUS        mandatory
    DESCRIPTION
        "This count gives the number of cells played out to the
         CES Service Interface. It excludes cells that were
         discarded for any reason, including cells that were not used
         due to being declared misinserted, or discarded while the
         reassembler was waiting to achieve synchronization."
    ::= { wfAtmCESStatsEntry 6 }

wfAtmCESStatsHdrErrors OBJECT-TYPE
    SYNTAX        Counter
    ACCESS        read-only
    STATUS        mandatory
    DESCRIPTION
        "The count of the number of AAL1 header errors detected,
         including those corrected. Header errors include correctable
         and uncorrectable CRC, plus bad parity."
    ::= { wfAtmCESStatsEntry 7 }

wfAtmCESStatsPointerReframes OBJECT-TYPE
    SYNTAX        Counter
    ACCESS        read-only
    STATUS        mandatory
    DESCRIPTION
        "This records the count of the number of events in which the
         AAL1 reassembler found that an SDT pointer is not where it is
         expected, and the pointer must be reacquired. This count is
         only meaningful for structured CES modes, as unstructured CES
         modes do not use pointers. For unstructured CES modes, this
         count, if present, should indicate zero."
    ::= { wfAtmCESStatsEntry 8 }

wfAtmCESStatsPointerParityErrors OBJECT-TYPE
    SYNTAX        Counter
    ACCESS        read-only
    STATUS        mandatory
    DESCRIPTION
        "This records the count of the number of events in which the
         AAL1 reassembler detects a parity check failure at the point
         where a structured data pointer is expected. This count is only
         meaningful for structured CES modes, as unstructured CES modes
         do not use pointers. For unstructured CES modes, this count, if
         present, should indicate zero."
    ::= { wfAtmCESStatsEntry 9 }

wfAtmCESStatsAal1SeqErrors OBJECT-TYPE
    SYNTAX        Counter
    ACCESS        read-only
    STATUS        mandatory
    DESCRIPTION
        "Number of times that the sequence number of an incoming AAL1
         Type 1 SAR-PDU causes a transition from the 'sync' state to
         the 'out of sequence' state, as defined by ITU-T I.363.1."
    ::= { wfAtmCESStatsEntry 10 }

wfAtmCESStatsLostCells OBJECT-TYPE
    SYNTAX        Counter
    ACCESS        read-only
    STATUS        mandatory
    DESCRIPTION
        "Number of lost cells, as detected by the AAL1 sequence number
         processing, for example. This records the count of the number
         of cells detected as lost in the network prior to the
         destination CES IWF AAL1 layer processing."
    ::= { wfAtmCESStatsEntry 11 }

wfAtmCESStatsMisinsertedCells OBJECT-TYPE
    SYNTAX        Counter
    ACCESS        read-only
    STATUS        mandatory
    DESCRIPTION
        "Number of AAL1 sequence violations which the AAL Convergence
         sublayer interprets as a misinserted cell, as defined by
         ITU-T I.363.1."
    ::= { wfAtmCESStatsEntry 12 }

wfAtmCESStatsBufUnderflows OBJECT-TYPE
    SYNTAX        Counter
    ACCESS        read-only
    STATUS        mandatory
    DESCRIPTION
        "Number of buffer underflows. This records the count of the
         number of times the CES reassembly buffer underflows. In the
         case of a continuous underflow caused by a loss of ATM cell
         flow, a single buffer underflow should be counted. If the CES
         IWF is implemented with multiple buffers (such as a cell level
         buffer and a bit level buffer), then either buffer underflow
         will cause this count to be incremented."
    ::= { wfAtmCESStatsEntry 13 }

wfAtmCESStatsBufOverflows OBJECT-TYPE
    SYNTAX        Counter
    ACCESS        read-only
    STATUS        mandatory
    DESCRIPTION
        "Number of buffer overflows. This records the count of the
         number of times the CES reassembly buffer overflows. If the CES
         IWF is implemented with multiple buffers (such as a cell level
         buffer and a bit level buffer, then either buffer overflow will
         cause this count to be incremented "
    ::= { wfAtmCESStatsEntry 14 }

wfAtmCESStatsCellLossStatus OBJECT-TYPE
    SYNTAX        INTEGER {
                    noLoss(1),
                    loss(2)
                  }
    ACCESS        read-only
    STATUS        mandatory
    DESCRIPTION
        "When cells are continuously lost for the number of milliseconds
         specified by wfAtmCESConfCellLossIntegrationPeriod, the value is set
         to loss (2). When cells are no longer lost, the value is set
         to noLoss (1)."
    ::= { wfAtmCESStatsEntry 15 }

END
