Wellfleet-QOS-MIB DEFINITIONS ::= BEGIN

-- Creation date: 1998


    IMPORTS

      Counter
        FROM RFC1155-SMI
      OBJECT-TYPE
        FROM RFC-1212
      DisplayString
        FROM RFC1213-MIB
      wfServicePkgGroup
        FROM Wellfleet-COMMON-MIB;


    wfQosServPkgTable OBJECT-TYPE
        SYNTAX	SEQUENCE OF WfQosServPkgEntry
        ACCESS	not-accessible
        STATUS	mandatory
        DESCRIPTION
                "This file describes the MIBS for managing Qos Templates"
        ::= { wfServicePkgGroup 1 }

    wfQosServPkgEntry OBJECT-TYPE
        SYNTAX	WfQosServPkgEntry
        ACCESS	not-accessible
        STATUS	mandatory
        DESCRIPTION
                "An entry in the Qos Base table"
        INDEX	{ wfQosServPkgIndex }
        ::= { wfQosServPkgTable 1 }

    WfQosServPkgEntry ::= SEQUENCE {
    	    wfQosServPkgDelete
    		INTEGER,
    	    wfQosServPkgIndex
    		INTEGER,
    	    wfQosServPkgServiceName
    		DisplayString,
    	    wfQosServPkgScheduling
    		INTEGER,
    	    wfQosServPkgNumQueues
    		INTEGER,
    	    wfQosServPkgNumLines
    		INTEGER
        }

    wfQosServPkgDelete OBJECT-TYPE
        SYNTAX	INTEGER {
    		    created(1),
    		    deleted(2)
    		}
        ACCESS	read-write
        STATUS	mandatory
        DESCRIPTION
                "Create/Delete parameter"
        DEFVAL	{ created }
        ::= { wfQosServPkgEntry 1 }

    wfQosServPkgIndex OBJECT-TYPE
        SYNTAX	INTEGER
        ACCESS	read-only
        STATUS	mandatory
        DESCRIPTION
                "Instance ID, filled in by driver"
        ::= { wfQosServPkgEntry 2 }

    wfQosServPkgServiceName OBJECT-TYPE
        SYNTAX  DisplayString
        ACCESS  read-write
        STATUS  mandatory
        DESCRIPTION
                "Service Name given to this template"
        ::= { wfQosServPkgEntry 3 }

    wfQosServPkgScheduling OBJECT-TYPE
        SYNTAX	INTEGER {
    		    round-robin(1),
    		    strict-priority(2)
    		}
        ACCESS	read-write
        STATUS	mandatory
        DESCRIPTION
                "Selects the scheduling method, Round Robbin or Strict Priority,
		to service the Tx Queues.  In Round Robbin, each Queue is
		serviced according to the weights applied in the Queue Mib.
		In Strict Priority, the highest priority Queue with data
		is serviced."
        DEFVAL	{ round-robin }
        ::= { wfQosServPkgEntry 4 }

    wfQosServPkgNumQueues OBJECT-TYPE
        SYNTAX	INTEGER
        ACCESS	read-only
        STATUS	mandatory
        DESCRIPTION
                "Number of queues configured for this queue package"
        ::= { wfQosServPkgEntry 5 }

    wfQosServPkgNumLines OBJECT-TYPE
        SYNTAX	INTEGER
        ACCESS	read-only
        STATUS	mandatory
        DESCRIPTION
                "Number of lines using this queue package"
        ::= { wfQosServPkgEntry 6 }





    wfQosServPkgQueCfgTable OBJECT-TYPE
        SYNTAX	SEQUENCE OF WfQosServPkgQueCfgEntry
        ACCESS	not-accessible
        STATUS	mandatory
        DESCRIPTION
                "This file describes the MIBS for managing Qos Templates"
        ::= { wfServicePkgGroup 2 }

    wfQosServPkgQueCfgEntry OBJECT-TYPE
        SYNTAX	WfQosServPkgQueCfgEntry
        ACCESS	not-accessible
        STATUS	mandatory
        DESCRIPTION
                "An entry in the Qos Base table"
        INDEX	{ wfQosServPkgQueCfgServiceIndex,
		  wfQosServPkgQueCfgQueueIndex }
        ::= { wfQosServPkgQueCfgTable 1 }

    WfQosServPkgQueCfgEntry ::= SEQUENCE {
    	    wfQosServPkgQueCfgDelete
    		INTEGER,
    	    wfQosServPkgQueCfgServiceIndex
    		INTEGER,
    	    wfQosServPkgQueCfgQueueIndex
    		INTEGER,
    	    wfQosServPkgQueCfgQueueName
    		DisplayString,
    	    wfQosServPkgQueCfgState
    		INTEGER,
    	    wfQosServPkgQueCfgClass
    		INTEGER,
    	    wfQosServPkgQueCfgAcctRule
    		INTEGER,
    	    wfQosServPkgQueCfgRxCommitInfoRate
    		INTEGER,
    	    wfQosServPkgQueCfgRxBurstRate
    		INTEGER,
    	    wfQosServPkgQueCfgRxBurstSize
    		INTEGER,
    	    wfQosServPkgQueCfgRxBurstAction
    		INTEGER,
    	    wfQosServPkgQueCfgTxDropThresh
    		INTEGER,
    	    wfQosServPkgQueCfgTxWeight
    		INTEGER,
    	    wfQosServPkgQueCfgTxActualWeight
    		DisplayString
        }

    wfQosServPkgQueCfgDelete OBJECT-TYPE
        SYNTAX	INTEGER {
    		    created(1),
    		    deleted(2)
    		}
        ACCESS	read-write
        STATUS	mandatory
        DESCRIPTION
                "Create/Delete parameter"
        DEFVAL	{ created }
        ::= { wfQosServPkgQueCfgEntry 1 }

    wfQosServPkgQueCfgServiceIndex OBJECT-TYPE
        SYNTAX	INTEGER
        ACCESS	read-only
        STATUS	mandatory
        DESCRIPTION
                "Instance Service ID, filled in by driver"
        ::= { wfQosServPkgQueCfgEntry 2 }

    wfQosServPkgQueCfgQueueIndex OBJECT-TYPE
        SYNTAX	INTEGER
        ACCESS	read-only
        STATUS	mandatory
        DESCRIPTION
                "Instance Queue ID, filled in by driver"
        ::= { wfQosServPkgQueCfgEntry 3 }

    wfQosServPkgQueCfgQueueName OBJECT-TYPE
        SYNTAX  DisplayString
        ACCESS  read-write
        STATUS  mandatory
        DESCRIPTION
                "Queue Name given to this template"
        ::= { wfQosServPkgQueCfgEntry 4 }

    wfQosServPkgQueCfgState OBJECT-TYPE
        SYNTAX	INTEGER {
		    up(1),
		    waitPkg(2),
		    misCfg(3)
		}
        ACCESS	read-only
        STATUS	mandatory
        DESCRIPTION
                "State of this Queue, either Up, Waiting for a Service
		Package, or Misconfigured."
        DEFVAL	{ waitPkg }
        ::= { wfQosServPkgQueCfgEntry 5 }

    wfQosServPkgQueCfgClass OBJECT-TYPE
        SYNTAX	INTEGER(0..7)
        ACCESS	read-write
        STATUS	mandatory
        DESCRIPTION
               "Class level for this queue, 0=highest, 7=lowest"
	DEFVAL  { 7 }
        ::= { wfQosServPkgQueCfgEntry 6 }

    wfQosServPkgQueCfgAcctRule OBJECT-TYPE
        SYNTAX	INTEGER
        ACCESS	read-write
        STATUS	mandatory
        DESCRIPTION
               "Accounting Rule Template Index."
	DEFVAL  { 0 }
        ::= { wfQosServPkgQueCfgEntry 7 }

    wfQosServPkgQueCfgRxCommitInfoRate OBJECT-TYPE
        SYNTAX	INTEGER(0..1536)
        ACCESS	read-write
        STATUS	mandatory
        DESCRIPTION
               "Commit Info Rate (CIR), in Kbits per second, configured
		for this template"
	DEFVAL  { 0 }
        ::= { wfQosServPkgQueCfgEntry 8 }

    wfQosServPkgQueCfgRxBurstRate OBJECT-TYPE
        SYNTAX	INTEGER(0..1536)
        ACCESS	read-write
        STATUS	mandatory
        DESCRIPTION
               "Burst Rate (BR), in Kbits per second,  configured for this
		template"
	DEFVAL  { 0 }
        ::= { wfQosServPkgQueCfgEntry 9 }

    wfQosServPkgQueCfgRxBurstSize OBJECT-TYPE
        SYNTAX	INTEGER
        ACCESS	read-write
        STATUS	mandatory
        DESCRIPTION
               "Burst Size, in bytes, configured for this template"
	DEFVAL  { 8000 }
        ::= { wfQosServPkgQueCfgEntry 10 }

    wfQosServPkgQueCfgRxBurstAction OBJECT-TYPE
        SYNTAX	INTEGER {
			none(1),
			downgrade(2),
			mark(3),
			mark-downgrade(4)
		}
        ACCESS	read-write
        STATUS	mandatory
        DESCRIPTION
               "Action when Burst Rate is exceeded"
	DEFVAL  { none }
        ::= { wfQosServPkgQueCfgEntry 11 }

    wfQosServPkgQueCfgTxDropThresh OBJECT-TYPE
        SYNTAX	INTEGER {
			none(1),
			percent-83(2),
			percent-66(3),
			percent-50(4)
		}
        ACCESS	read-write
        STATUS	mandatory
        DESCRIPTION
               "Hardware Threshold in percent to start dropping
		Output Packets for this queue.  When set to none,
		all packets are accepted until the Queue Fills
		100 percent."
	DEFVAL  { none }
        ::= { wfQosServPkgQueCfgEntry 12 }

    wfQosServPkgQueCfgTxWeight OBJECT-TYPE
        SYNTAX	INTEGER
        ACCESS	read-write
        STATUS	mandatory
        DESCRIPTION
               "Weight in percentage for the Tx Queue when set
		to Round Robbin Priority Type."
	DEFVAL  { 100 }
        ::= { wfQosServPkgQueCfgEntry 13 }

    wfQosServPkgQueCfgTxActualWeight OBJECT-TYPE
        SYNTAX  DisplayString
        ACCESS	read-only
        STATUS	mandatory
        DESCRIPTION
               "Actual Weight, in percentage, given to this Tx Queue
		within its Service Package when set to Round Robbin
		Scheduling."
        ::= { wfQosServPkgQueCfgEntry 14 }







    wfQueueStatTable OBJECT-TYPE
        SYNTAX	SEQUENCE OF WfQueueStatEntry
        ACCESS	not-accessible
        STATUS	mandatory
        DESCRIPTION
                "This file describes the MIBS for getting Queues Stats"
        ::= { wfServicePkgGroup 3 }

    wfQueueStatEntry OBJECT-TYPE
        SYNTAX	WfQueueStatEntry
        ACCESS	not-accessible
        STATUS	mandatory
        DESCRIPTION
                "An entry in the Queue Base table"
        INDEX	{ wfQueueStatPortLineNumber,
        	  wfQueueStatLineIndex,
        	  wfQueueStatQueueIndex }
        ::= { wfQueueStatTable 1 }

    WfQueueStatEntry ::= SEQUENCE {
    	    wfQueueStatPortLineNumber
    		INTEGER,
    	    wfQueueStatLineIndex
    		INTEGER,
    	    wfQueueStatQueueIndex
    		INTEGER,
    	    wfQueueStatTxOctets
    		Counter,
    	    wfQueueStatTxPackets
    		Counter,
    	    wfQueueStatTxDrops
    		Counter,
    	    wfQueueStatRxBelowCirOctets
    		Counter,
    	    wfQueueStatRxBelowCirPackets
    		Counter,
    	    wfQueueStatRxAboveCirOctets
    		Counter,
    	    wfQueueStatRxAboveCirPackets
    		Counter,
    	    wfQueueStatRxAboveBrOctets
    		Counter,
    	    wfQueueStatRxAboveBrPackets
    		Counter
        }


    wfQueueStatPortLineNumber OBJECT-TYPE
        SYNTAX  INTEGER
        ACCESS  read-only
        STATUS  mandatory
        DESCRIPTION
                "Instance ID PortLineNumber"
        ::= { wfQueueStatEntry 1 }

    wfQueueStatLineIndex OBJECT-TYPE
        SYNTAX  INTEGER
        ACCESS  read-only
        STATUS  mandatory
        DESCRIPTION
                "Instance Line Number"
        ::= { wfQueueStatEntry 2 }

    wfQueueStatQueueIndex OBJECT-TYPE
        SYNTAX  INTEGER
        ACCESS  read-only
        STATUS  mandatory
        DESCRIPTION
                "Queue Index, matches that of wfQosServPkgQueCfgQueueIndex"
        ::= { wfQueueStatEntry 3 }

    wfQueueStatTxOctets OBJECT-TYPE
        SYNTAX  Counter
        ACCESS  read-only
        STATUS  mandatory
        DESCRIPTION
                "Number of Transmit Octets received without error"
        ::= { wfQueueStatEntry 4 }

    wfQueueStatTxPackets OBJECT-TYPE
        SYNTAX  Counter
        ACCESS  read-only
        STATUS  mandatory
        DESCRIPTION
                "Number of Transmit Packets received without error"
        ::= { wfQueueStatEntry 5 }

    wfQueueStatTxDrops OBJECT-TYPE
        SYNTAX  Counter
        ACCESS  read-only
        STATUS  mandatory
        DESCRIPTION
                "Number of Transmit Packets Dropped"
        ::= { wfQueueStatEntry 6 }

    wfQueueStatRxBelowCirOctets OBJECT-TYPE
	SYNTAX  Counter
	ACCESS  read-only
	STATUS  mandatory
	DESCRIPTION
		"The number of octets received which were below the
		 committed information rate (CIR)."
	::= { wfQueueStatEntry 7 }

    wfQueueStatRxBelowCirPackets OBJECT-TYPE
	SYNTAX  Counter
	ACCESS  read-only
	STATUS  mandatory
	DESCRIPTION
		"The number of packets received which were below the
		 committed information rate (CIR)."
	::= { wfQueueStatEntry 8 }

    wfQueueStatRxAboveCirOctets OBJECT-TYPE
	SYNTAX  Counter
	ACCESS  read-only
	STATUS  mandatory
	DESCRIPTION
		"The number of octets received which exceeded the
		 committed information rate, but which were within
		 the allocated burst rate (BR)."
	::= { wfQueueStatEntry 9 }

    wfQueueStatRxAboveCirPackets OBJECT-TYPE
	SYNTAX  Counter
	ACCESS  read-only
	STATUS  mandatory
	DESCRIPTION
		"The number of packets received which exceeded the
		 committed information rate, but which were within
		 the allocated burst rate (BR)."
	::= { wfQueueStatEntry 10 }

    wfQueueStatRxAboveBrOctets OBJECT-TYPE
	SYNTAX  Counter
	ACCESS  read-only
	STATUS  mandatory
	DESCRIPTION
		"The number of octets received which exceeded the
		 allocated burst rate (BR)."
	::= { wfQueueStatEntry 11 }

    wfQueueStatRxAboveBrPackets OBJECT-TYPE
	SYNTAX  Counter
	ACCESS  read-only
	STATUS  mandatory
	DESCRIPTION
		"The number of packets received which exceeded the
		 allocated burst rate (BR)."
	::= { wfQueueStatEntry 12 }



    END  -- Wellfleet-QOS-MIB
