-- Revision 1.0.0
-- Copyright 1999 D-Link, Inc.
-- All rights reserved.

SW-TRUNK-MIB    DEFINITIONS ::= BEGIN
    IMPORTS
        OBJECT-TYPE     FROM RFC-1212
        DisplayString   FROM RFC1213-MIB
        enterprises     FROM RFC1155-SMI;
        
-- updated by Jemy 1/21/2000 for ES2000        
-- PortList    ::= OCTET STRING(SIZE(16))
-- added by Jemy 1/21/2000
    TrunkSetList ::= OCTET STRING(SIZE(1))
-- end    

    marconi     OBJECT IDENTIFIER ::= { enterprises 326 }
    systems     OBJECT IDENTIFIER ::= { marconi 2 }
    external    OBJECT IDENTIFIER ::= { systems 20 }
    dlink       OBJECT IDENTIFIER ::= { external 1 }

    dlinkcommon OBJECT IDENTIFIER ::= { dlink 1 }

    golf        OBJECT IDENTIFIER ::= { dlink 2 }
    golfproducts        OBJECT IDENTIFIER ::= { golf 1 }
    es2000              OBJECT IDENTIFIER ::= { golfproducts 3 }

    golfcommon          OBJECT IDENTIFIER ::= { golf 2 }                
    
    marconi-mgmt    OBJECT IDENTIFIER ::= { golfcommon 2 }

    es2000Mgmt      OBJECT IDENTIFIER ::= { marconi-mgmt 28 }

    swL2Mgmt        OBJECT IDENTIFIER ::= { es2000Mgmt 2 }

    swPortTrunk     OBJECT IDENTIFIER ::= { swL2Mgmt 6 }

-- *****************************************************************************
--  swPortTrunkCtrlTable
-- *****************************************************************************
    swPortTrunkCtrlTable OBJECT-TYPE
        SYNTAX  SEQUENCE OF SwPortTrunkCtrlEntry
        ACCESS  not-accessible
        STATUS  mandatory
        DESCRIPTION
            "This table specifies which port trunking configuration.
             Trunking ID is as following :
             trunk 1, 3, 5, 7, 9, 11, 13, 15 - unit1, tx_module, port1~8;
             trunk 2, 4, 6, 8, 10, 12, 14, 16 - unit1, tx_module, port9~16"
        ::= { swPortTrunk 1 }

    swPortTrunkCtrlEntry OBJECT-TYPE
        SYNTAX  SwPortTrunkCtrlEntry
        ACCESS  not-accessible
        STATUS  mandatory
        DESCRIPTION
            "Each entry specifies which ports are grouped as a single logical link."
        INDEX  { swPortTrunkCtrlIndex }
        ::= { swPortTrunkCtrlTable 1 }

    SwPortTrunkCtrlEntry ::=
        SEQUENCE {
            swPortTrunkCtrlIndex
                INTEGER,
            swPortTrunkCtrlAnchorPort
                INTEGER,
            swPortTrunkCtrlMasterPort
                INTEGER,
            swPortTrunkCtrlName
                DisplayString (SIZE (0..16)),
            swPortTrunkCtrlMember
                TrunkSetList,
            swPortTrunkCtrlState
                INTEGER
        }

    swPortTrunkCtrlIndex OBJECT-TYPE
        SYNTAX  INTEGER
        ACCESS  read-only
        STATUS  mandatory
        DESCRIPTION
            "The index of logical trunk of ports."
        ::= { swPortTrunkCtrlEntry 1 }

    swPortTrunkCtrlAnchorPort OBJECT-TYPE
        SYNTAX  INTEGER
        ACCESS  read-write
        STATUS  mandatory
        DESCRIPTION
            "Get anchor port number between trunk ports."
        ::= { swPortTrunkCtrlEntry 2 }

    swPortTrunkCtrlMasterPort OBJECT-TYPE
        SYNTAX  INTEGER
        ACCESS  read-only
        STATUS  mandatory
        DESCRIPTION
            "Get master port number between trunk ports."
        ::= { swPortTrunkCtrlEntry 3 }

    swPortTrunkCtrlName OBJECT-TYPE
        SYNTAX  DisplayString (SIZE (0..16))
        ACCESS  read-write
        STATUS  mandatory
        DESCRIPTION
            "The name of logical trunk of ports."
        ::= { swPortTrunkCtrlEntry 4 }

    swPortTrunkCtrlMember OBJECT-TYPE
        SYNTAX  TrunkSetList
        ACCESS  read-write
        STATUS  mandatory
        DESCRIPTION
            "Specifies the member ports which are grouped as a trunk."
        ::= { swPortTrunkCtrlEntry 5 }


    swPortTrunkCtrlState OBJECT-TYPE
        SYNTAX  INTEGER {
            other(1),
            disabled(2),
            enabled(3)
        }
        ACCESS  read-write
        STATUS  mandatory
        DESCRIPTION
            "This object determines whether the trunk setting is in enable/disable state."
        ::= { swPortTrunkCtrlEntry 6 }

-- *****************************************************************************
--  swPortTrunkMemberTable
-- *****************************************************************************
    swPortTrunkMemberTable OBJECT-TYPE
        SYNTAX  SEQUENCE OF SwPortTrunkMemberEntry
        ACCESS  not-accessible
        STATUS  mandatory
        DESCRIPTION
            "A list of information provide a different view for member ports grouped as a trunk."
        ::= { swPortTrunk 2 }

    swPortTrunkMemberEntry OBJECT-TYPE
        SYNTAX  SwPortTrunkMemberEntry
        ACCESS  not-accessible
        STATUS  mandatory
        DESCRIPTION
            "Each entry corresponds to a member port."
        INDEX   { swPortTrunkMemberIndex,
                  swPortTrunkMemberUnitIndex,
                  swPortTrunkMemberModuleIndex,
                  swPortTrunkMemberPortIndex }
        ::= { swPortTrunkMemberTable 1 }

    SwPortTrunkMemberEntry ::=
        SEQUENCE {
            swPortTrunkMemberIndex
                INTEGER,
            swPortTrunkMemberUnitIndex
                INTEGER,
            swPortTrunkMemberModuleIndex
                INTEGER,
            swPortTrunkMemberPortIndex
                INTEGER
        }

    swPortTrunkMemberIndex OBJECT-TYPE
        SYNTAX  INTEGER
        ACCESS  read-only
        STATUS  mandatory
        DESCRIPTION
            "Indicates the trunk ID where the port is located."
        ::= { swPortTrunkMemberEntry 1 }

    swPortTrunkMemberUnitIndex OBJECT-TYPE
        SYNTAX  INTEGER
        ACCESS  read-only
        STATUS  mandatory
        DESCRIPTION
            "Indicates the unit ID where the port is located."
        ::= { swPortTrunkMemberEntry 2 }

    swPortTrunkMemberModuleIndex OBJECT-TYPE
        SYNTAX  INTEGER
        ACCESS  read-only
        STATUS  mandatory
        DESCRIPTION
            "Indicates the module ID where the port is located."
        ::= { swPortTrunkMemberEntry 3 }

    swPortTrunkMemberPortIndex OBJECT-TYPE
        SYNTAX  INTEGER
        ACCESS  read-only
        STATUS  mandatory
        DESCRIPTION
            "Indicates the port index relative to the module."
        ::= { swPortTrunkMemberEntry 4 }

END
