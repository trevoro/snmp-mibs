-- This file is corresponding to Release 6.1.2.100 from 2001/09/26 00:00:00
-- (C)opyright 1991-1999 BinTec Communications AG, All Rights Reserved
--  $RCSfile: mibpabx,v $ 
-- $Revision: 1.25 $ 

BIANCA-BOX-PABX-MIB DEFINITIONS ::= BEGIN

IMPORTS
		DisplayString FROM SNMPv2-TC
	OBJECT-TYPE, IpAddress FROM RFC1155-SMI
	BitValue FROM BIANCA-BRICK-PPP-MIB;

    org		OBJECT IDENTIFIER ::= { iso 3 }
    dod		OBJECT IDENTIFIER ::= { org 6 }
    internet	OBJECT IDENTIFIER ::= { dod 1 }
    private	OBJECT IDENTIFIER ::= { internet 4 }
    enterprises	OBJECT IDENTIFIER ::= { private 1 }
    bintec 	OBJECT IDENTIFIER ::= { enterprises 272 }
    bibo	OBJECT IDENTIFIER ::= { bintec 4 }
    pabx	OBJECT IDENTIFIER 
	::= { bibo 20 }


    -- PABX Group

    -- Management Information for the PABX Subsystem of the BIANCA/BOX

	Date ::= INTEGER
	HexValue ::= INTEGER


        pabxUserTable OBJECT-TYPE
            SYNTAX  SEQUENCE OF PabxUserEntry
            ACCESS  not-accessible
            STATUS  mandatory
            DESCRIPTION
		"The pabxUserTable contains information about the pabx users.
		 CAPI and TAPI users must authenticate to the system by means
		 of user name and password, before active or passive
		 connections may be established. The default configuration
		 defines a user named <default> with all permissions. This
		 user will also be used by old CAPI applications which are
		 not able to select a user. Please note, that the password 
		 for the user <default> must be empty in this case.

		 Entries in this table can be deleted by setting
		 the object pabxUserTapiMon to the value <delete>."
	::= { pabx 1 }

	pabxUserEntry OBJECT-TYPE
            SYNTAX  PabxUserEntry
            ACCESS  not-accessible
            STATUS  mandatory
            DESCRIPTION
		""
	    INDEX   { pabxUserName }
              ::= { pabxUserTable 1 }

	PabxUserEntry ::=
            SEQUENCE {
		pabxUserName			DisplayString,
		pabxUserPassword		DisplayString,
		pabxUserTapiMon			INTEGER,
		pabxUserTapiCtrl		INTEGER,
		pabxUserTapiMedia		INTEGER,
		pabxUserCapi			INTEGER,
		pabxUserId			INTEGER,
		pabxUserPIN			INTEGER,
		pabxUserPrimGroupId		INTEGER
            }

	pabxUserName OBJECT-TYPE
	    SYNTAX  DisplayString (SIZE (0..15))
	    ACCESS  read-write
	    STATUS  mandatory
	    DESCRIPTION
		"The name of the user."
	::= { pabxUserEntry 1 }

	pabxUserPassword OBJECT-TYPE
            SYNTAX  DisplayString (SIZE (0..15))
            ACCESS  read-write
	    STATUS  mandatory
            DESCRIPTION
		"The password for the user."
	::= { pabxUserEntry 2 }

	pabxUserTapiMon OBJECT-TYPE
            SYNTAX  INTEGER { 
		enable(1), 
		disable(2),
		delete(3)
	    }
            ACCESS  read-write
            STATUS  mandatory
            DESCRIPTION
                "Allow or deny monitoring of call activity with TAPI
		 or delete entry."
	::= { pabxUserEntry 3 }

	pabxUserTapiCtrl OBJECT-TYPE
            SYNTAX  INTEGER { 
		enable(1), 
		disable(2)
	    }
            ACCESS  read-write
            STATUS  mandatory
            DESCRIPTION
                "Allow or deny controlling of calls for the terminal belonging
		 to the user with TAPI."
	::= { pabxUserEntry 4 }

	pabxUserTapiMedia OBJECT-TYPE
            SYNTAX  INTEGER {
		enable(1),
		disable(2)
	    }
            ACCESS  read-write
            STATUS  mandatory
            DESCRIPTION
                "Allow or deny the usage of TAPI media streams."
	::= { pabxUserEntry 5 }

	pabxUserCapi OBJECT-TYPE
            SYNTAX  INTEGER {
		enable(1),
		disable(2)
	    }
            ACCESS  read-write
            STATUS  mandatory
            DESCRIPTION
                "Allow or deny the usage of CAPI."
	::= { pabxUserEntry 6 }

	pabxUserId OBJECT-TYPE
	    SYNTAX  INTEGER (0..2147483647)
	    ACCESS  read-write
	    STATUS  mandatory
	    DESCRIPTION
		"The user id uniquely identifies a user and is now used as
		 reference to that user in other tables instead of her name.
		 The id 0 has the meaning 'no special user'."
	::= { pabxUserEntry 7 }

	pabxUserPIN OBJECT-TYPE
	    SYNTAX  DisplayString (SIZE (4..9))
	    ACCESS  read-write
	    STATUS  mandatory
	    DESCRIPTION
		"The PIN is the personal identification number that is needed
		 for authorisation during telephone based configurations.
		 It consists solely of digits and must be between 4 and 9
		 characters long.

		 Default Value is '0000'."
	::= { pabxUserEntry 8 }

	pabxUserPrimGroupId OBJECT-TYPE
	    SYNTAX  INTEGER (0..2147483647)
	    ACCESS  read-write
	    STATUS  mandatory
	    DESCRIPTION
		"PrimGroupId is the primary group identification number for
		 that user. It serves only for configuration purposes so that
		 all newly created extensions for a terminal that user is
		 primary user of, will automatically become member in that
		 group. The default value is 0."
	::= { pabxUserEntry 9 }



	pabxTrunkTable OBJECT-TYPE
	    SYNTAX  SEQUENCE OF PabxTrunkEntry
	    ACCESS  not-accessible
	    STATUS  mandatory
	    DESCRIPTION
		"This table contains an entry for each trunk-line (or
		 central office line) connecting the system to an outside
		 network.

		 Entries are deleted from this table by setting the object
		 pabxTrunkProtocol to the value <delete>."
	::= { pabx 2 }

	pabxTrunkEntry OBJECT-TYPE
	    SYNTAX  PabxTrunkEntry
	    ACCESS  not-accessible
	    STATUS  mandatory
	    DESCRIPTION
		""
	    INDEX    { pabxTrunkNumber }
	::= { pabxTrunkTable 1 }

	PabxTrunkEntry ::=
	    SEQUENCE {
		pabxTrunkNumber				INTEGER,
		pabxTrunkDescr				DisplayString,
		pabxTrunkSlot				INTEGER,
		pabxTrunkUnit				INTEGER,
		pabxTrunkProtocol			INTEGER,
		pabxTrunkConfig				INTEGER,
		pabxTrunkTeiProc			INTEGER,
		pabxTrunkTeiValue			INTEGER,
		pabxTrunkCountryCode			DisplayString,
		pabxTrunkAreaCode			DisplayString,
		pabxTrunkSubscriberNo			DisplayString,
		pabxTrunkExtension			DisplayString,
		pabxTrunkType				INTEGER,
		pabxTrunkL2Mode                         INTEGER
	    }

	pabxTrunkNumber OBJECT-TYPE
	    SYNTAX  INTEGER (0..31) 
	    ACCESS  read-write
	    STATUS  mandatory

	    DESCRIPTION
		"The object pabxTrunkNumber ranges from 0..31 and specifies
		 a unique identification for the trunk line."
	::= { pabxTrunkEntry 1 }

	pabxTrunkDescr OBJECT-TYPE
	    SYNTAX  DisplayString 
	    ACCESS  read-write
	    STATUS  mandatory

	    DESCRIPTION
		"Description text for the trunk-line. This object
		 is for information only and not otherwise being
		 used by the system."
	::= { pabxTrunkEntry 2 }

	pabxTrunkSlot OBJECT-TYPE
	    SYNTAX  INTEGER (1..31) 
	    ACCESS  read-write
	    STATUS  mandatory

	    DESCRIPTION
		"This object specifies the number of the physical slot
		 the trunk-line is leading to."
	::= { pabxTrunkEntry 3 }

	pabxTrunkUnit OBJECT-TYPE
	    SYNTAX  INTEGER (0..9) 
	    ACCESS  read-write
	    STATUS  mandatory

	    DESCRIPTION
		"This object specifies the physical unit in the slot
		 specified by pabxTrunkSlot. When there is only one
		 unit in the slot, the unitnumber has to be set to 0."
	::= { pabxTrunkEntry 4 }

	pabxTrunkProtocol OBJECT-TYPE
	    SYNTAX  INTEGER { delete(1), dss1(2) } 
	    ACCESS  read-write
	    STATUS  mandatory

	    DESCRIPTION
		"This object specifies the protocol to be used on the
		 trunk-line. Currently only dss1 is available."
	::= { pabxTrunkEntry 5 }

	pabxTrunkConfig OBJECT-TYPE
	    SYNTAX  INTEGER { point-to-multipoint(1), point-to-point(2), unknown(3) } 
	    ACCESS  read-write
	    STATUS  mandatory

	    DESCRIPTION
		"This object specifies, whether the trunk line is running
		 in point-to-point or point-to-multipoint configuration."
	::= { pabxTrunkEntry 6 }

	pabxTrunkTeiProc OBJECT-TYPE
	    SYNTAX  INTEGER { automatic(1), fixed(2) } 
	    ACCESS  read-write
	    STATUS  mandatory

	    DESCRIPTION
		"This object specifies the TEI procedure to be used with the
		 trunk-line. The procedure may be either <automatic> or 
		 <fixed>. In the latter case, the TEI value has to be
		 specified in the object pabxTrunkTeiValue"
	::= { pabxTrunkEntry 7 }

	pabxTrunkTeiValue OBJECT-TYPE
	    SYNTAX  INTEGER (0..63) 
	    ACCESS  read-write
	    STATUS  mandatory

	    DESCRIPTION
		"This object specifies the TEI value to be used for
		 fixed TEI configurations and is ignored in automatic
		 TEI configurations."
	::= { pabxTrunkEntry 8 }

	pabxTrunkCountryCode OBJECT-TYPE
	    SYNTAX  DisplayString 
	    ACCESS  read-write
	    STATUS  mandatory

	    DESCRIPTION
		"This object specifies the country code of the trunk-line.
		 This information has to be specified in point-to-point
		 configurations, because the country code has to be skipped
		 in the destination address of incoming calls in order to
		 isolate the local extension part."
	::= { pabxTrunkEntry 9 }

	pabxTrunkAreaCode OBJECT-TYPE
	    SYNTAX  DisplayString 
	    ACCESS  read-write
	    STATUS  mandatory

	    DESCRIPTION
		"This object specifies the area code of the trunk-line.
		 This information has to be specified in point-to-point
		 configurations, because the area code has to be skipped
		 in the destination address of incoming calls in order to
		 isolate the local extension part."
	::= { pabxTrunkEntry 10 }

	pabxTrunkSubscriberNo OBJECT-TYPE
	    SYNTAX  DisplayString 
	    ACCESS  read-write
	    STATUS  mandatory

	    DESCRIPTION
		"This object specifies the subscriber number of the trunk-line.
		 This information has to be specified in point-to-point
		 configurations, because the subscriber number has to be skipped
		 in the destination address of incoming calls in order to
		 isolate the local extension part."
	::= { pabxTrunkEntry 11 }

	pabxTrunkExtension OBJECT-TYPE
	    SYNTAX  DisplayString 
	    ACCESS  read-write
	    STATUS  mandatory

	    DESCRIPTION
		"This object specifies the extension number of the trunk-line.
		 This information has to be specified in point-to-point
		 configurations, because the extension number has to be skipped
		 in the destination address of incoming calls in order to
		 isolate the local extension part.

		 Please note, that this object shall be empty, when connected
		 to a normal central office line."
	::= { pabxTrunkEntry 12 }

	pabxTrunkType OBJECT-TYPE
	    SYNTAX  INTEGER {
		external(1),
		internal(2)
	    } 
	    ACCESS  read-write
	    STATUS  mandatory

	    DESCRIPTION
		"The trunk type identifies the purpose of an ISDN interface.
		 Normal external trunks are identified with type 'external'.
		 When cascading trunks one side must behave as network side
		 and, hence, a trunk entry must be created for it, despite
		 of operating in NT (actually NT or LTS) mode.
		 This is achieved by creating a trunk of type 'internal'.
		 Internal trunks are always point to point type interfaces.
		 Type 'external' is assumed by default."
	::= { pabxTrunkEntry 13 }

	pabxTrunkL2Mode OBJECT-TYPE
	    SYNTAX  INTEGER {
		auto(1),
		te(2),
		nt(3)
	    } 
	    ACCESS  read-write
	    STATUS  mandatory

	    DESCRIPTION
		"The TrunkL2Mode specifies the mode layer 2 is to operate
		 in. To be able to use leased lines as well as back to back
		 connections to link two machines, layer 2 mode must be
		 configurable independently from layer 1 mode.
		 If mode is set to auto(1), layer 2 mode is derived from
		 physical configuration of interface (NT/TE). Settings te(2)
		 and nt(3) force the respective configuration.
		 By default mode is set to 'auto'."
	::= { pabxTrunkEntry 14 }




	pabxTrunkPrefixTable OBJECT-TYPE
	    SYNTAX  SEQUENCE OF PabxTrunkPrefixEntry
	    ACCESS  not-accessible
	    STATUS  mandatory
	    DESCRIPTION
		"This table specifies escape codes, that may be used to
		 access the available trunk-lines. Initially, the prefix
		 <0> will be defined to use any trunk line in the
		 system.

		 Please note, that this table is only used, when
		 The global object pabxLocalPrefix is set to an
		 empty string.

		 Entries in this table are deleted by setting the object
		 pabxTrunkPrefixStatus to the value <delete>"
	::= { pabx 3 }

	pabxTrunkPrefixEntry OBJECT-TYPE
	    SYNTAX  PabxTrunkPrefixEntry
	    ACCESS  not-accessible
	    STATUS  mandatory
	    DESCRIPTION
		""
	    INDEX   { pabxTrunkPrefixPrefix }
	::= { pabxTrunkPrefixTable 1 }

	PabxTrunkPrefixEntry ::=
	    SEQUENCE {
		pabxTrunkPrefixPrefix			DisplayString,
		pabxTrunkPrefixTrunkMask		BitValue,
		pabxTrunkPrefixStatus			INTEGER,
		pabxTrunkPrefixStripOnOutgoing		INTEGER,
		pabxTrunkPrefixPrependOnIncoming	INTEGER
	    }

	pabxTrunkPrefixPrefix OBJECT-TYPE
	    SYNTAX  DisplayString (SIZE(1..8))
	    ACCESS  read-write
	    STATUS  mandatory

	    DESCRIPTION
		"This object specifies a prefix used to access (a subset of)
		 the available trunk-lines. It's value is a string consisting
		 of the dialable digits 0..9, * and #."
	::= { pabxTrunkPrefixEntry 1 }

	pabxTrunkPrefixTrunkMask OBJECT-TYPE
	    SYNTAX  BitValue 
	    ACCESS  read-write
	    STATUS  mandatory

	    DESCRIPTION
		"This object is a bit mask consisting of bit 0 to bit 31.
		 Each bit corresponds to the trunk-line index with the
		 same number (Bit 0 <-> Number 0 ...). The whole mask
		 specifies the set of trunk lines to be used with the
		 trunk-prefix."
	::= { pabxTrunkPrefixEntry 2 }

	pabxTrunkPrefixStatus OBJECT-TYPE
	    SYNTAX  INTEGER { valid(1), invalid(2), delete(3) }
	    ACCESS  read-write
	    STATUS  mandatory

	    DESCRIPTION
		"This object specifies the status of the trunk-prefix.
		 When set to valid, the trunk prefix will be used normally,
		 when set to invalid, the prefix will not be used and
		 when set to delete, the table-entry will be deleted."
	::= { pabxTrunkPrefixEntry 3 }

	pabxTrunkPrefixStripOnOutgoing OBJECT-TYPE
	    SYNTAX  INTEGER {
		 enable(1),
		 disable(2)
	    }
	    ACCESS  read-write
	    STATUS  mandatory

	    DESCRIPTION
		"This object specifies handling of trunk-prefix on outgoing
		 calls:
		 When set to enable (by default) the trunk prefix will be
		 stripped on outgoing calls, what must be set for external
		 trunks (otherwise a wrong called party number would be
		 passed on).
		 When set to disable, the prefix will remain in the called
		 party number, allowing a distributed PABX via internal
		 trunks."
	::= { pabxTrunkPrefixEntry 4 }

	pabxTrunkPrefixPrependOnIncoming OBJECT-TYPE
	    SYNTAX  INTEGER {
		 enable(1),
		 disable(2)
	    }
	    ACCESS  read-write
	    STATUS  mandatory

	    DESCRIPTION
		"This object specifies handling of trunk-prefix on incoming
		 calls:
		 When set to enable (by default) the trunk prefix will be
		 appended to the calling party number on incoming calls,
		 what must be set for external trunks (otherwise a wrong
		 calling party number would be provided, hence leading to the
		 calling party number being unusable for a call back).
		 When set to disable, no prefix will be prepended to the
		 calling party number, nedded for a distributed PABX via
		 internal trunks."
	::= { pabxTrunkPrefixEntry 5 }



        pabxExtensionTable OBJECT-TYPE
            SYNTAX  SEQUENCE OF PabxExtensionEntry
            ACCESS  not-accessible
            STATUS  mandatory
            DESCRIPTION
		"This table defines the local numbers (extensions), that
		 shall be used within PABX and assigns an identifier to it.
		 Besides the extension is assigned to a terminal and user
		 via apropriate identifiers and to either a physical or
		 a logical destination. The items pabxExtSlot and pabxExtUnit
		 moved to the terminal table as every extension must be
		 associated with a terminal and, moreover, a terminal is
		 always as a whole physically attached to a slot and unit.
		 Also pabxExtUser is no longer valid, because the associated
		 user is now refered to via the pabxExtUserId, avoiding some
		 possible configuration faults.

		 Rows are deleted from the table by setting the object
		 pabxExtDestination to the value <delete>."
	::= { pabx 4 }

	pabxExtensionEntry OBJECT-TYPE
            SYNTAX  PabxExtensionEntry
            ACCESS  not-accessible
            STATUS  mandatory
            DESCRIPTION
		""
	    INDEX   { pabxExtExtension }
              ::= { pabxExtensionTable 1 }

	PabxExtensionEntry ::=
            SEQUENCE {
                pabxExtExtension	DisplayString,
		pabxExtType		INTEGER,
--		pabxExtDestination	INTEGER,
--		pabxExtSlot		INTEGER,
--		pabxExtUnit		INTEGER,
		pabxExtIpAddr		IpAddress,
--		pabxExtUser		DisplayString,
		pabxExtEAZ		DisplayString,
		pabxExtLayer1Prot	INTEGER,
		pabxExtIfIndex		INTEGER,
		pabxExtId		INTEGER,
		pabxExtUserId           INTEGER,
		pabxExtTermId		INTEGER,
		pabxExtDefaultExtFlag   INTEGER,
		pabxExtPresentationNr   DisplayString,
		pabxExtOutsideCallSeq   INTEGER,
		pabxExtInsideCallSeq    INTEGER,
		pabxExtPresentationFlag INTEGER,
		pabxExtProfileId	INTEGER,
		pabxExtCtrlByCapiApp	INTEGER,
		pabxExtCtrlByCapiAppNo	INTEGER
            }

	pabxExtExtension OBJECT-TYPE
	    SYNTAX  DisplayString (SIZE (0..15))
            ACCESS  read-write
            STATUS  mandatory
            DESCRIPTION
                "This object contains the extension, which is a dialable
		 string consisting of the digits 0..9, * and #."
	::= { pabxExtensionEntry 1 }

	pabxExtType OBJECT-TYPE
            SYNTAX  INTEGER {
                voice(1),
                data(2),
                voice-and-data(3),
		delete(4)
            }
            ACCESS  read-write
            STATUS  mandatory
            DESCRIPTION
		"Specifies the call types, for which the entry shall be valid."
        ::= { pabxExtensionEntry 2 }

--	pabxExtDestination OBJECT-TYPE
--            SYNTAX  INTEGER {
--		delete(1),
--                physical(2),
--                application(3),
--                internet-telephony(4),
--		multiprotocol-routing(5),
--		isdn-login(6),
--		msg-box(7)
--            }
--            ACCESS  read-write
--            STATUS  mandatory
--            DESCRIPTION
--		"This object specifies the type of the destination. When
--		 set to physical, the destination is the physical device
--		 selected by pabxExtSlot and pabxExtUnit. When set to
--		 application, the extension may be used by CAPI or TAPI
--		 software applications. When set to internet-telephony,
--		 the destination is the computer on the network with
--		 the ip-address pabxExtIpAddr. When this object ist set to
--		 multiprotocol-routing, the destination is the builtin
--		 multiprotocol-router. In this case the object
--		 pabxExtLayer1Prot may be used to specify the layer1 protocol
--		 and pabxExtIfIndex may be used to assign the extension to
--		 a specific multiprotocol-interface. Finally isdn-login may
--		 be used to assign the extension to the isdn-login facility
--		 of the system."
--        ::= { pabxExtensionEntry 3 }

--        pabxExtSlot OBJECT-TYPE
--            SYNTAX  INTEGER (0..31)
--            ACCESS  read-write
--            STATUS  mandatory
--
--            DESCRIPTION
--                "Specifies the systems slot, to which the call shall be
--		 routed if pabxExtDestination is set to physical."
--        ::= { pabxExtensionEntry 4 }

--        pabxExtUnit OBJECT-TYPE
--            SYNTAX  INTEGER (0..31)
--            ACCESS  read-write
--            STATUS  mandatory
--
--            DESCRIPTION
--		"Specifies the unit, to which the call shall be routed if
--		 pabxExtDestination is set to physical."
--        ::= { pabxExtensionEntry 5 }

	pabxExtIpAddr OBJECT-TYPE
	    SYNTAX  IpAddress
	    ACCESS  read-write
	    STATUS  mandatory
	    DESCRIPTION
	      "Specifies the ip-address, to which the call shall be routed
	       if pabxExtDestination is set to internet-telephony."
	::= { pabxExtensionEntry 6 }

--	pabxExtUser OBJECT-TYPE
--	    SYNTAX  DisplayString (SIZE (0..15))
--	    ACCESS  read-write
--	    STATUS  mandatory
--	    DESCRIPTION
--		"The owner of the extension."
--	::= { pabxExtensionEntry 7 }

	pabxExtEAZ OBJECT-TYPE
	    SYNTAX  DisplayString (SIZE (0..1))
	    ACCESS  read-write
	    STATUS  mandatory
	    DESCRIPTION
		"The EAZ is to be used by 1TR6-based applications such as
		 CAPI 1.1. and is only valid if the object
		 pabxExtDestination is set to application."
	::= { pabxExtensionEntry 8 }

	pabxExtLayer1Prot OBJECT-TYPE
            SYNTAX  INTEGER {
		auto(1),
		sync-64k(11),
		sync-56k(12),
		modem(13),
		v110-1200(15),
		v110-2400(16),
		v110-4800(17),
		v110-9600(18),
		v110-14400(19),
		v110-19200(20),
		v110-38400(21),
                modem-profile-1(26), modem-profile-2(27),
		modem-profile-3(28), modem-profile-4(29),
		modem-profile-5(30), modem-profile-6(31),
                modem-profile-7(32), modem-profile-8(33)
	    }
	    ACCESS  read-write
	    STATUS  mandatory
	    DESCRIPTION
		"The layer1 protocol to be used for multiprotocol-routing
		 (incoming calls only)."
	::= { pabxExtensionEntry 9 }

	pabxExtIfIndex OBJECT-TYPE
	    SYNTAX  INTEGER
	    ACCESS  read-write
	    STATUS  mandatory
	    DESCRIPTION
		"The interface index of the MPR interface to be used for the
		 call. This object is valid for routing only."
	::= { pabxExtensionEntry 10 }

	pabxExtId OBJECT-TYPE
	    SYNTAX  INTEGER (0..2147483647)
	    ACCESS  read-write
	    STATUS  mandatory
	    DESCRIPTION
		"The id uniquely identifies an extension may be within the
		 range from 0 to 2147483647. This id is used to refer to that
		 extension from other tables. Id 0 has the special meaning,
		 that the PABX shall choose a valid one."
	::= { pabxExtensionEntry 11 }
	
	pabxExtUserId OBJECT-TYPE
	    SYNTAX  INTEGER (0..2147483647)
	    ACCESS  read-write
	    STATUS  mandatory
	    DESCRIPTION
		"This identificator refers to the user the extension is
		 associated with. Its default value is 0 meaning no particular
		 user."
	::= { pabxExtensionEntry 12 }

	pabxExtTermId OBJECT-TYPE
	    SYNTAX  INTEGER
	    ACCESS  read-write
	    STATUS  mandatory
	    DESCRIPTION
		"This identificator refers to the terminal the extension is
		 associated with. Its value must be a valid identificator,
		 i.e. there must be a terminal with the given id. The special
		 number -1 is used for specifying that the extension is a
		 group extension."
	::= { pabxExtensionEntry 13 }

	pabxExtDefaultExtFlag OBJECT-TYPE
	    SYNTAX  INTEGER {
		no(1),
		yes(2)
	    }
	    ACCESS  read-write
	    STATUS  mandatory
	    DESCRIPTION
		"This value specifies whether the extension should be used as a default
		 extension (for outgoing calls) for the associated terminal. The flag to
		 be set currently only makes sense for physical analog terminals.
		 The case that this flag is yes(1) for more than one extension per terminal
		 is considered a configuration error. Which extension will be used in that
		 case depends on the order in which extensions are configured
		 (automatically at system start-up) and, hence, is undefined."
	::= { pabxExtensionEntry 14 }

	pabxExtPresentationNr OBJECT-TYPE
	    SYNTAX  DisplayString (SIZE (0..15))
	    ACCESS  read-write
	    STATUS  mandatory
	    DESCRIPTION
		"This field allows for specifying an extension that will be presented to
		 externally called partners instead of the actual calling number. Hence
		 it allows to use a group extension so that the called partner does only
		 see the extension she should use for call back if necessary, rather than
		 the extension within the group.
		 Default value is the empty string meaning that no mapping shall take
		 place."
	::= { pabxExtensionEntry 15 }

	pabxExtOutsideCallSeq OBJECT-TYPE
            SYNTAX  INTEGER {
                type1(1),
                type2(2),
                type3(3),
		type4(4),
		type5(5),
		type6(6),
		systeltype7(7),
		systeltype8(8),
		systeltype9(9),
		systeltype10(10)
            }
	    ACCESS  read-write
	    STATUS  mandatory
	    DESCRIPTION
		"Set the ringing sequence for incoming calls from outside"
	::= { pabxExtensionEntry 16 }

	pabxExtInsideCallSeq OBJECT-TYPE
            SYNTAX  INTEGER {
                type1(1),
                type2(2),
                type3(3),
		type4(4),
		type5(5),
		type6(6),
		systeltype7(7),
		systeltype8(8),
		systeltype9(9),
		systeltype10(10)
            }
	    ACCESS  read-write
	    STATUS  mandatory
	    DESCRIPTION
		"Set the ringing sequence for incoming calls inside the PABX."
	::= { pabxExtensionEntry 17 }
	
	pabxExtPresentationFlag OBJECT-TYPE
            SYNTAX  INTEGER {
                off(1),
                internal(2),
		external(3),
		on(4)
            }
	    ACCESS  read-write
	    STATUS  mandatory
	    DESCRIPTION
		"Specify when the presentation number should take effect.
		 By default its value is 'off' defining the actual extension
		 is to be used.
		 If presentation number shall be used only on internal calls
		 ExtPresentation must be set to 'internal'.
		 Analogous to the last, value 'external' is for use on
		 external calls.
		 The last value 'on' specifies that the presentation number
		 is to be used in any case."
	::= { pabxExtensionEntry 18 }

	pabxExtProfileId OBJECT-TYPE
            SYNTAX  INTEGER (0..2147483647)
            ACCESS  read-write
            STATUS  mandatory
            DESCRIPTION
		"ProfileId holds an id specifying an applying profile entry in
		 pabx profile table.
		 If set to 0 no profile applies as 0 is not a valid id for
		 profiles. In that case terminal profile applies, or if also 0,
		 system default settings apply for the extension."
        ::= { pabxExtensionEntry 19 }

	pabxExtCtrlByCapiApp OBJECT-TYPE
            SYNTAX  INTEGER {
		off(1),
		on(2)
	    }
            ACCESS  read-write
            STATUS  mandatory
            DESCRIPTION
		"CtrlByCapiAppl indicates whether a capi application controls
		 this extension. If set to on a special CAPI application
		 registered for handling incoming calls, causing PABX to only
		 signal that incoming call towards CAPI application, hence
		 avoiding a spurious short alerting of Phone until call is
		 answered by application.
		 A CAPI application can request this feature by a LISTEN request
		 with special contents.
		 The default value is off."
        ::= { pabxExtensionEntry 20 }

	pabxExtCtrlByCapiAppNo OBJECT-TYPE
            SYNTAX  INTEGER
            ACCESS  read-only
            STATUS  mandatory
            DESCRIPTION
		"CtrlByCapiAppl indicates capi application number that controls
		 extension in case pabxExtCtrlByCapiApp is set to on."
        ::= { pabxExtensionEntry 21 }



	
	pabxExtFeatureTable OBJECT-TYPE
	    SYNTAX SEQUENCE OF PabxExtFeatureEntry
	    ACCESS  not-accessible
	    STATUS  mandatory
	    DESCRIPTION
		"This table stores all extension related feature settings that
		 would have overloaded the extension table. The extension for
		 which the settings apply is identified by its id. Currently
		 found features are only the different call forwarding modes.
		 For every mode (unconditional, busy and no reply) a separate
		 telephone number can be stored. The active call forwarding
		 mode is stored in an extra mode field.
		 The pabxExtUsrConfigTable is replaced by that one.

		 To delete a row set pabxExtFeatureCFMode to value delete.
		 CAUTION:
		    deleting a row will result in also deleting the related
		    extension table entry!"
	::= { pabx 5 }

	pabxExtFeatureEntry OBJECT-TYPE
	    SYNTAX  PabxExtFeatureEntry
	    ACCESS  not-accessible
	    STATUS  mandatory
	    DESCRIPTION
		""
	    INDEX { pabxExtFeatureExtId }
	::= { pabxExtFeatureTable 1 }

	PabxExtFeatureEntry ::=
	    SEQUENCE {
		pabxExtFeatureExtId		INTEGER,
		pabxExtFeatureCFUncond		DisplayString,
		pabxExtFeatureCFBusy		DisplayString,
		pabxExtFeatureCFNoReply		DisplayString,
		pabxExtFeatureCFNoReplyTimer	INTEGER,
		pabxExtFeatureCFMode		INTEGER,
	        pabxExtFeatureEMailAddr         DisplayString,
		pabxExtFeatureSystelMSNSlot	INTEGER,
		pabxExtFeatureSystelVolume	INTEGER,
		pabxExtFeatureSystelText	DisplayString
-- next one's not currently supported by system phones
--		pabxExtFeatureSystelAWS		DisplayString
	    }

	pabxExtFeatureExtId OBJECT-TYPE
	    SYNTAX  INTEGER (0..2147483647)
	    ACCESS  read-only
	    STATUS  mandatory
	    DESCRIPTION
		"This parameter identifies the extension for which all feature
		 settings stored here apply. It must be a valid one, i.e. one
		 that is also found in the pabxExtensionTable."
	::= { pabxExtFeatureEntry 1 }

	pabxExtFeatureCFUncond OBJECT-TYPE
	    SYNTAX  DisplayString (SIZE (0..31))
	    ACCESS  read-write
	    STATUS  mandatory
	    DESCRIPTION
		"This field contains the phone number to be used for
		 unconditional call forwarding."
	::= { pabxExtFeatureEntry 2 }

	pabxExtFeatureCFBusy OBJECT-TYPE
	    SYNTAX  DisplayString (SIZE (0..31))
	    ACCESS  read-write
	    STATUS  mandatory
	    DESCRIPTION
		"This field contains the phone number to be used for
		 call forwarding in case of busy subscriber."
	::= { pabxExtFeatureEntry 3 }

	pabxExtFeatureCFNoReply OBJECT-TYPE
	    SYNTAX  DisplayString (SIZE (0..31))
	    ACCESS  read-write
	    STATUS  mandatory
	    DESCRIPTION
		"This field contains the phone number to be used for
		 call forwarding in case user does not respond."
	::= { pabxExtFeatureEntry 4 }

	pabxExtFeatureCFNoReplyTimer OBJECT-TYPE
	    SYNTAX  INTEGER (1..120)
	    ACCESS  read-write
	    STATUS  mandatory
	    DESCRIPTION
		"This field defines the time in seconds a call must be in state
		 alerting until call forwarding will be activated. Reasonable
		 values are 3 up to maybe 30, nevertheless all values between
		 1 and 120 are allowed."
	::= { pabxExtFeatureEntry 5 }

	pabxExtFeatureCFMode OBJECT-TYPE
	    SYNTAX  INTEGER {
-- Commented out:		delete(1),
		none(2),
		busy(3),
		noreply(4),
		busy-noreply(5),
		uncond(6)
	    }
	    ACCESS  read-write
	    STATUS  mandatory
	    DESCRIPTION
		"In this field the active call forwarding mode for the
		 extension is stored. It can have the values none, busy,
		 noreply and uncond for the different modes. Besides it makes
		 sense to allow both noreply and busy to be active at a time,
		 so there's the additional value busy-noreply.
		 Apart from that, if mode is set to delete the entry will be
		 deleted."
	::= { pabxExtFeatureEntry 6 }

        pabxExtFeatureEMailAddr OBJECT-TYPE
	    SYNTAX  DisplayString (SIZE (0..31))
	    ACCESS  read-write
	    STATUS  mandatory
	    DESCRIPTION
		"This field contains the E-Mail address for the extension"
	::= { pabxExtFeatureEntry 7 }

	pabxExtFeatureSystelMSNSlot OBJECT-TYPE
            SYNTAX  INTEGER (0..10)
            ACCESS  read-write
            STATUS  mandatory
            DESCRIPTION
		"SystelMSNSlot is only valid for extensions associated with
		 system terminals. It identifies the MSN configuration slot
		 within the system phone (1 through 10) where it is to be stored
		 when configuring system phone from brick.
		 Value 0 has the special meaning that the configuration slot is
		 undefined; the configuration position is chosen randomly then.
		 Default value is 0."
        ::= { pabxExtFeatureEntry 8 }

	pabxExtFeatureSystelVolume OBJECT-TYPE
            SYNTAX  INTEGER
            ACCESS  read-write
            STATUS  mandatory
            DESCRIPTION
		"SystelVolume specifies ringing volume setting within system
		 phone for externally (to brick) initiated incoming calls.
		 Default value is 4."
        ::= { pabxExtFeatureEntry 9 }

	pabxExtFeatureSystelText OBJECT-TYPE
            SYNTAX  DisplayString
            ACCESS  read-write
            STATUS  mandatory
            DESCRIPTION
		"SystelText contains info text shown in system phone display
		 on incoming and outgoing calls indicating the used/directed-to
		 MSN."
        ::= { pabxExtFeatureEntry 10 }

-- next one's not currently supported by system phones
--	pabxExtFeatureSystelAWS OBJECT-TYPE
--            SYNTAX  DisplayString
--            ACCESS  read-write
--            STATUS  mandatory
--            DESCRIPTION
--		"SystelAWS holds call forward."
--        ::= { pabxExtFeatureEntry 11 }




-- removed:
-- pabxExtUserConfigTable { pabx 7 }
-- Don't reuse!!!


	pabxGroupTable OBJECT-TYPE
	    SYNTAX SEQUENCE OF PabxGroupEntry
	    ACCESS  not-accessible
	    STATUS  mandatory
	    DESCRIPTION
		"The group table contains all defined groups. It contains the
		 group id and the associated name and one more field that is
		 currently only needed for deleting groups.

		 To delete a row set pabxGroupCalladdInhibit to value delete."
	::= { pabx 8 }

	pabxGroupEntry OBJECT-TYPE
	    SYNTAX  PabxGroupEntry
	    ACCESS  not-accessible
	    STATUS  mandatory
	    DESCRIPTION
		""
	    INDEX   { pabxGroupId }
	::= { pabxGroupTable 1 }

	PabxGroupEntry ::=
	    SEQUENCE {
		pabxGroupId		INTEGER,
		pabxGroupName		DisplayString,
		pabxGroupCalladdInhibit INTEGER
	    }

	pabxGroupId OBJECT-TYPE
	    SYNTAX  INTEGER (0..2147483647)
	    ACCESS  read-write
	    STATUS  mandatory
	    DESCRIPTION
		"The group id is a non-negative identificator that is unique.
		 The maximum value for it is 2147483647. Id 0 treated
		 specially meaning 'auto group id' when creating new groups."
	::= { pabxGroupEntry 1 }

	pabxGroupName OBJECT-TYPE
	    SYNTAX  DisplayString (SIZE(0..15))
	    ACCESS  read-write
	    STATUS  mandatory
	    DESCRIPTION
		"The group name is just a human readable description for the
		 group and serves for ease of configuration."
	::= { pabxGroupEntry 2 }

	pabxGroupCalladdInhibit OBJECT-TYPE
	    SYNTAX  INTEGER {
		delete(1),
		enable(2),
		disable(3)
	    }
	    ACCESS  read-write
	    STATUS mandatory
	    DESCRIPTION
		"As of the necessity to be able of removing groups, another
		 integer variable had to be added. Therefore only the value
		 delete has consequences. The other values are for future use
		 and normal entries so far may have either value."
	::= { pabxGroupEntry 3 }



	pabxTerminalTable OBJECT-TYPE
	    SYNTAX  SEQUENCE OF PabxTerminalEntry
	    ACCESS  not-accessible
	    STATUS  mandatory
	    DESCRIPTION
		"The terminal table contains all terminals with specification
		 of their corresponding hardware interface, hence invalidating
		 the respective entries in the extension table. Besides a
		 primary user may be given that will be assumed for newly
		 created extensions for that terminal.

		 Deleting a row is done by setting pabxTermDestination to value
		 delete."
	::= { pabx 9 }

	pabxTerminalEntry OBJECT-TYPE
	    SYNTAX  PabxTerminalEntry
	    ACCESS  not-accessible
	    STATUS  mandatory
	    DESCRIPTION
		""
	    INDEX   { pabxTermId }
	::= { pabxTerminalTable 1 }

	PabxTerminalEntry ::=
	    SEQUENCE {
		pabxTermId		INTEGER,
		pabxTermName		DisplayString,
		pabxTermSlot		INTEGER,
		pabxTermUnit		INTEGER,
		pabxTermDestination	INTEGER,
		pabxTermPrimUserId	INTEGER,
		pabxTermType		INTEGER,
		pabxTermProfileId       INTEGER,
		pabxTermSystelSerialNo  DisplayString
	    }

	pabxTermId OBJECT-TYPE
	    SYNTAX  INTEGER (0..2147483647)
	    ACCESS  read-write
	    STATUS  mandatory
	    DESCRIPTION
                "The id uniquely identifies a terminal and can have the values
		 0 up to 2147483647, where number 0 has the special meaning
		 'auto id' when creating new terminals."
	::= { pabxTerminalEntry 1 }

	pabxTermName OBJECT-TYPE
	    SYNTAX  DisplayString (SIZE (0..15))
	    ACCESS  read-write
	    STATUS  mandatory
	    DESCRIPTION
                "This optional field contains just a (preferably unique)
		 descriptive name for the terminal."
	::= { pabxTerminalEntry 2 }

	pabxTermSlot OBJECT-TYPE
	    SYNTAX  INTEGER (0..31)
	    ACCESS  read-write
	    STATUS  mandatory
	    DESCRIPTION
                "Designates the slot of the physical interface the terminal
		 is attached to."
	::= { pabxTerminalEntry 3 }

	pabxTermUnit OBJECT-TYPE
	    SYNTAX  INTEGER (0..31)
	    ACCESS  read-write
	    STATUS  mandatory
	    DESCRIPTION
                "Designates the unit of the physical interface the terminal
		 is attached to."
	::= { pabxTerminalEntry 4 }

	pabxTermDestination OBJECT-TYPE
            SYNTAX  INTEGER {
		delete(1),
                physical(2),
                application(3),
                internet-telephony(4),
		multiprotocol-routing(5),
		isdn-login(6),
		msg-box(7)
            }
            ACCESS  read-write
            STATUS  mandatory
            DESCRIPTION
		"This object specifies the type of the destination. When
		 set to physical, the destination is the physical device
		 selected by pabxExtSlot and pabxExtUnit. When set to
		 application, the extension may be used by CAPI or TAPI
		 software applications. When set to internet-telephony,
		 the destination is the computer on the network with
		 the ip-address pabxExtIpAddr. When this object ist set to
		 multiprotocol-routing, the destination is the builtin
		 multiprotocol-router. In this case the object
		 pabxExtLayer1Prot may be used to specify the layer1 protocol
		 and pabxExtIfIndex may be used to assign the extension to
		 a specific multiprotocol-interface. Finally isdn-login may
		 be used to assign the extension to the isdn-login facility
		 of the system."
        ::= { pabxTerminalEntry 5 }

	pabxTermPrimUserId OBJECT-TYPE
	    SYNTAX  INTEGER (0..2147483647)
	    ACCESS  read-write
	    STATUS  mandatory
	    DESCRIPTION
                "The primary user id allows for automatically setting the user
		 for newly created extensions for that terminal. The default
		 value is 0 meaning no particular user."
	::= { pabxTerminalEntry 6 }

	pabxTermType OBJECT-TYPE
            SYNTAX  INTEGER {
		phone(1),
                modem(2),
                fax(3),
                headset(4),
                answeringmachine(5),
		system-phone(6)
            }
            ACCESS  read-write
            STATUS  mandatory
            DESCRIPTION
		"The terminal type identifies which kind of terminal it is.
		 By default type is set to phone; other possibilities are
		 modem, fax and headset.
		 When set to modem or fax the normal dial tone is provided
		 instead of a pulsed one normally (without automatic dialout
		 on trunks)."
        ::= { pabxTerminalEntry 7 }

	pabxTermProfileId OBJECT-TYPE
            SYNTAX  INTEGER (0..2147483647)
            ACCESS  read-write
            STATUS  mandatory
            DESCRIPTION
		"ProfileId holds an id specifying an applying profile entry in
		 pabx profile table.
		 If set to 0 no profile applies as 0 is not a valid id for
		 profiles. In that case system default settings apply for
		 the terminal (-> pabxSTATICTable)."
        ::= { pabxTerminalEntry 8 }

	pabxTermSystelSerialNo OBJECT-TYPE
	    SYNTAX  DisplayString (SIZE (0..15))
	    ACCESS  read-write
	    STATUS  mandatory
	    DESCRIPTION
                "This field is only for terminals of type system-phone and
		 specifies its serial number.
		 For terminals set to terminal type 'system phone' the next
		 system terminal found will automatically be associated with
		 a terminal in case serial number is left blank.

		 Default value is the empty string."
	::= { pabxTerminalEntry 9 }





	pabxExtToGroupTable OBJECT-TYPE
	    SYNTAX  SEQUENCE OF PabxExtToGroupEntry
	    ACCESS  not-accessible
	    STATUS  mandatory
	    DESCRIPTION
		"The exttogroup table contains all associations of extensions
		 to groups. To allow for extensions being in arbitrary groups
		 as well as groups containing any number of extensions it is
		 necessary to implement an extra table holding that
	         informations and is done right here. Currently the table has
		 only 3 columns (beside the index) where two of them hold an
		 id either, one an extension id the other a group id, and the
		 last column currently serves solely for the purpose of
		 deleting rows.

		 Deleting a row is done by setting pabxTerminalLock to value
		 delete."
	::= { pabx 10 }

	pabxExtToGroupEntry OBJECT-TYPE
	    SYNTAX  PabxExtToGroupEntry
	    ACCESS  not-accessible
	    STATUS  mandatory
	    DESCRIPTION
		""
	    INDEX   { pabxExtToGroupExtId }
	::= { pabxExtToGroupTable 1 }

	PabxExtToGroupEntry ::=
	    SEQUENCE {
		pabxExtToGroupExtId		INTEGER,
		pabxExtToGroupGroupId		INTEGER,
		pabxExtToGroupCallPickupActive	INTEGER
	    }

	pabxExtToGroupExtId OBJECT-TYPE
	    SYNTAX  INTEGER (1..2147483647)
	    ACCESS  read-write
	    STATUS  mandatory
	    DESCRIPTION
		"This field identifies the extension that should become member
		 in a group."
	::= { pabxExtToGroupEntry 1 }

	pabxExtToGroupGroupId OBJECT-TYPE
	    SYNTAX  INTEGER (1..2147483647)
	    ACCESS  read-write
	    STATUS  mandatory
	    DESCRIPTION
		"This field identifies the group the extension will become
		 member of"
	::= { pabxExtToGroupEntry 2 }

	pabxExtToGroupCallPickupActive OBJECT-TYPE
	    SYNTAX  INTEGER {
		delete(1),
		enable(2)
	    }
	    ACCESS  read-write
	    STATUS  mandatory
	    DESCRIPTION
		"Currently the only purpose of that field is to supply the user
		 with a possibility to delete such association entries."
	::= { pabxExtToGroupEntry 3 }



	pabxTrunkMsnTable OBJECT-TYPE
	    SYNTAX  SEQUENCE OF PabxTrunkMsnEntry
	    ACCESS  not-accessible
	    STATUS  mandatory
	    DESCRIPTION
		"The pabxTrunkMsnTable contains all MSNs that were detected
		 during auto-configuration process on point-to-multipoint
		 trunk lines.
		 The table is handled solely by pabxautocf, hence there's
		 no chance for alteration or deletion of rows."
	::= { pabx 11 }

	pabxTrunkMsnEntry OBJECT-TYPE
	    SYNTAX  PabxTrunkMsnEntry
	    ACCESS  not-accessible
	    STATUS  mandatory
	    DESCRIPTION
		""
	    INDEX   { pabxTrunkMsnSlot }
	::= { pabxTrunkMsnTable 1 }

	PabxTrunkMsnEntry ::=
	    SEQUENCE {
		pabxTrunkMsnSlot		INTEGER,
		pabxTrunkMsnUnit		INTEGER,
		pabxTrunkMsnNumber			DisplayString
	    }

	pabxTrunkMsnSlot OBJECT-TYPE
	    SYNTAX  INTEGER (0..31)
	    ACCESS  read-only
	    STATUS  mandatory

	    DESCRIPTION
		"Specifies slot of interface for which an MSN is found."
	::= { pabxTrunkMsnEntry 1 }

	pabxTrunkMsnUnit OBJECT-TYPE
	    SYNTAX  INTEGER (0..31)
	    ACCESS  read-only
	    STATUS  mandatory

	    DESCRIPTION
		"Specifies unit of interface for which an MSN is found."
	::= { pabxTrunkMsnEntry 2 }

	pabxTrunkMsnNumber OBJECT-TYPE
	    SYNTAX  DisplayString (SIZE (0..31))
	    ACCESS  read-only
	    STATUS  mandatory

	    DESCRIPTION
		"Holds the found MSN."
	::= { pabxTrunkMsnEntry 3 }

	pabxTrunkMsnNumberType OBJECT-TYPE
	    SYNTAX  INTEGER {
		unknown(1),
		private(2),
		public-international(3),
		public-national(4),
		public-subscriber(5),
		public-other(6)
	    }
	    ACCESS  read-only
	    STATUS  mandatory

	    DESCRIPTION
		"Tells the type of number stored in pabxTrunkMsnNumber field."
	::= { pabxTrunkMsnEntry 4 }



	pabxProfileTable OBJECT-TYPE
	    SYNTAX  SEQUENCE OF PabxProfileEntry
	    ACCESS  not-accessible
	    STATUS  mandatory
	    DESCRIPTION
		"The pabxProfileTable."
	::= { pabx 12 }

	pabxProfileEntry OBJECT-TYPE
	    SYNTAX  PabxProfileEntry
	    ACCESS  not-accessible
	    STATUS  mandatory
	    DESCRIPTION
		""
	    INDEX   { pabxProfileId }
	::= { pabxProfileTable 1 }

	PabxProfileEntry ::=
	    SEQUENCE {
		pabxProfileId			INTEGER,
		pabxProfileName                 DisplayString,
		pabxProfileAutoDialOutNo        DisplayString,
		pabxProfileDialPerm		INTEGER,
		pabxProfileAvailability		INTEGER
	    }

	pabxProfileId OBJECT-TYPE
	    SYNTAX  INTEGER (0..2147483647)
	    ACCESS  read-write
	    STATUS  mandatory

	    DESCRIPTION
		"Identifies a profile entry for association to extension,
		 terminal or user. Must be within range 0-2147483647 where value
		 '0' has special meaning 'automatic id' when creating a new
		 entry. Hence, value '0' cannot be used and may only show up in
		 MIB table for ignored entries."
	::= { pabxProfileEntry 1 }

	pabxProfileName OBJECT-TYPE
	    SYNTAX  DisplayString (SIZE (0..31))
	    ACCESS  read-write
	    STATUS  mandatory

	    DESCRIPTION
		"Descriptive - preferably unique - name for profile."
	::= { pabxProfileEntry 2 }

	pabxProfileAutoDialOutNo OBJECT-TYPE
	    SYNTAX  DisplayString (SIZE (0..15))
	    ACCESS  read-write
	    STATUS  mandatory

	    DESCRIPTION
		"Number string to be dialled automatically when just starting a
		 call. Allows for automatical dialout via trunk.
		 Default is the empty string '' meaning the system default
		 shall be used (see pabxSTATICTable).
		 If not empty it takes precedence over system default."
	::= { pabxProfileEntry 3 }

	pabxProfileDialPerm OBJECT-TYPE
            SYNTAX  INTEGER {
                internal(1),
		local(2),
		national(3),
		national-special(4),
		full(5)
            }
	    ACCESS  read-write
	    STATUS  mandatory
	    DESCRIPTION
		"Define dial permissions of extension.
		 When set to 'internal' dialling out over (external) trunks is
		 prevented.
		 Value 'local' allows dialling external numbers without an area
		 prefix.
		 With setting 'national' any national number but special numbers
		 (like mobile numbers) may be dialled.
		 The only restriction applying to value 'national_special' is
		 dialling of internaltional numbers.
		 The default setting 'full' grants access to any number."
	::= { pabxProfileEntry 4 }

	pabxProfileAvailability OBJECT-TYPE
            SYNTAX  INTEGER {
                internal(1),
                external(2),
                full(3),
		delete(15)
            }
	    ACCESS  read-write
	    STATUS  mandatory
	    DESCRIPTION
		"Define availability of an extension/terminal.
		 By default extensions are fully available (full), i.e. internal
		 and external bound calls can reach the extension depending on
		 the trunk constellation.
		 Setting availability to internal restricts the extension to be
		 called only by internal callers."
	::= { pabxProfileEntry 5 }



	pabxExtNoPermTable OBJECT-TYPE
	    SYNTAX  SEQUENCE OF PabxExtNoPermEntry
	    ACCESS  not-accessible
	    STATUS  mandatory
	    DESCRIPTION
		"The pabxExtNoPermTable."
	::= { pabx 13 }

	pabxExtNoPermEntry OBJECT-TYPE
	    SYNTAX  PabxExtNoPermEntry
	    ACCESS  not-accessible
	    STATUS  mandatory
	    DESCRIPTION
		""
	    INDEX   { pabxExtNoPermNumber }
	::= { pabxExtNoPermTable 1 }

	PabxExtNoPermEntry ::=
	    SEQUENCE {
		pabxExtNoPermNumber		DisplayString,
		pabxExtNoPermPermission		INTEGER,
		pabxExtNoPermStatus             INTEGER,
		pabxExtNoPermDescription        DisplayString
	    }

	pabxExtNoPermNumber OBJECT-TYPE
	    SYNTAX  DisplayString (SIZE (0..31))
	    ACCESS  read-write
	    STATUS  mandatory

	    DESCRIPTION
		""
	::= { pabxExtNoPermEntry 1 }

	pabxExtNoPermPermission OBJECT-TYPE
	    SYNTAX  INTEGER {
                internal(1),
		local(2),
		national(3),
		national-special(4),
		full(5),
		deny(6),
		provider(7),
		delete(255)
	    }
	    ACCESS  read-write
	    STATUS  mandatory

	    DESCRIPTION
		""
	::= { pabxExtNoPermEntry 2 }

	pabxExtNoPermStatus OBJECT-TYPE
	    SYNTAX  INTEGER {
                ok(1),
		format-error(2),
		exists-error(3)
	    }
	    ACCESS  read-only
	    STATUS  mandatory

	    DESCRIPTION
		""
	::= { pabxExtNoPermEntry 3 }

	pabxExtNoPermDescription OBJECT-TYPE
	    SYNTAX  DisplayString (SIZE (0..39))
	    ACCESS  read-write
	    STATUS  mandatory

	    DESCRIPTION
		""
	::= { pabxExtNoPermEntry 4 }







	systelTerminalTable OBJECT-TYPE
	    SYNTAX  SEQUENCE OF SystelTerminalEntry
	    ACCESS  not-accessible
	    STATUS  mandatory
	    DESCRIPTION
		"The systelTerminalTable stores all information about system
		 phones attached to the brick. This covers serial number,
		 software version, release date and other information provided
		 by system phone.

		 Deleting a row is done by setting systelTermAutoMove to value
		 delete."
	::= { pabx 14 }

	systelTerminalEntry OBJECT-TYPE
	    SYNTAX  SystelTerminalEntry
	    ACCESS  not-accessible
	    STATUS  mandatory
	    DESCRIPTION
		""
	    INDEX   { systelTermSerialNo }
	::= { systelTerminalTable 1 }

	SystelTerminalEntry ::=
	    SEQUENCE {
		systelTermSerialNo      	DisplayString,
		systelTermAutoMove      	INTEGER,
		systelTermSWVersion     	DisplayString,
		systelTermRelDate       	DisplayString,
		systelTermCountry       	DisplayString,
		systelTermOEMString     	DisplayString,
		systelTermDBVersion     	DisplayString,
		systelTermSlot          	INTEGER,
		systelTermUnit          	INTEGER,
		systelTermTei           	INTEGER,
		systelTermAutoConf		INTEGER,
		systelTermTriggerConf   	INTEGER,
		systelTermLastConfAction	INTEGER
	    }

	systelTermSerialNo OBJECT-TYPE
	    SYNTAX  DisplayString (SIZE (0..15))
	    ACCESS  read-write
	    STATUS  mandatory
	    DESCRIPTION
                "This field is only for terminals of type system-phone and
		 specifies its serial number."
	::= { systelTerminalEntry 1 }

	systelTermAutoMove OBJECT-TYPE
            SYNTAX  INTEGER {
		disable(1),
                enable(2),
		delete(3)
            }
            ACCESS  read-write
            STATUS  mandatory
            DESCRIPTION
		"This field specifies whether a terminal shall be automatically
		 reconfigured in case terminal logs in on another port than the
		 one defined in current configuration.
		 By default automatic reconfiguration is disabled."
        ::= { systelTerminalEntry 2 }

	systelTermSWVersion OBJECT-TYPE
	    SYNTAX  DisplayString
	    ACCESS  read-only
	    STATUS  mandatory

	    DESCRIPTION
                "SystelSWVersion shows the version of the attached system phone
		 and is only valid for terminals of type system-phone."
	::= { systelTerminalEntry 3 }

	systelTermRelDate OBJECT-TYPE
	    SYNTAX  DisplayString
	    ACCESS  read-only
	    STATUS  mandatory

	    DESCRIPTION
                "SystelRelDate shows the system phone software's release date
		 and is only valid for terminals of type system-phone."
	::= { systelTerminalEntry 4 }

	systelTermCountry OBJECT-TYPE
	    SYNTAX  DisplayString
	    ACCESS  read-only
	    STATUS  mandatory

	    DESCRIPTION
                "SystelCountry shows the active country profile in the attached
		 system phone and is only valid for terminals of type
		 system-phone."
	::= { systelTerminalEntry 5 }

	systelTermOEMString OBJECT-TYPE
	    SYNTAX  DisplayString
	    ACCESS  read-only
	    STATUS  mandatory

	    DESCRIPTION
                "SystelOEMString shows OEM string found in system phone and is
 		 only valid for terminals of type system-phone."
	::= { systelTerminalEntry 6 }

	systelTermDBVersion OBJECT-TYPE
	    SYNTAX  DisplayString
	    ACCESS  read-only
	    STATUS  mandatory

	    DESCRIPTION
                "SystelDBVersion shows data base version found in system phone
 		 and is only valid for terminals of type system-phone."
	::= { systelTerminalEntry 7 }

	systelTermSlot OBJECT-TYPE
            SYNTAX  INTEGER
            ACCESS  read-only
            STATUS  mandatory

            DESCRIPTION
		"The field systelTermSlot serves as a hint to which port the
		 system phone is attached to and is only needed for automatical
		 configuration purposes."
        ::= { systelTerminalEntry 8 }

	systelTermUnit OBJECT-TYPE
            SYNTAX  INTEGER
            ACCESS  read-only
            STATUS  mandatory

            DESCRIPTION
		"The field systelTermUnit serves as a hint to which port the
		 system phone is attached to and is only needed for automatical
		 configuration purposes."
        ::= { systelTerminalEntry 9 }

	systelTermTei OBJECT-TYPE
            SYNTAX  INTEGER (0..127)
            ACCESS  read-only
            STATUS  mandatory

            DESCRIPTION
		"The field systelTermTei only shows the TEI of an active system
		 terminal."
        ::= { systelTerminalEntry 10 }

	systelTermAutoConf OBJECT-TYPE
            SYNTAX  INTEGER {
		off(1),
		on-registration(2)
	    }
            ACCESS  read-write
            STATUS  mandatory

            DESCRIPTION
		"AutoConf controls whether the brick tries setting system phone
                 configuration automatically. Value off means no automatic
		 setting is performed, value on-registration causes the brick to
		 invoke automatic configuration upon system phone registration.
		 Default value is off."
        ::= { systelTerminalEntry 11 }

	systelTermTriggerConf OBJECT-TYPE
            SYNTAX  INTEGER {
		done(1),
		check(2),
		set(3),
		get(4),
		get-and-create(5),
		error(255)
	    }
            ACCESS  read-write
            STATUS  mandatory

            DESCRIPTION
		"TriggerConf allows for initiation of configuration process
		 by setting variable to start anytime when system phone is
		 registered with brick. Beyond termination status of last
		 configuration process is reflected: either done upon success or
		 error upon failure.
		 Default value is done."
        ::= { systelTerminalEntry 12 }

	systelTermLastConfAction OBJECT-TYPE
            SYNTAX  INTEGER {
		unknown(1),
		check(2),
		set(3),
		get(4),
		get-and-create(5)
	    }
            ACCESS  read-only
            STATUS  mandatory

            DESCRIPTION
		"LastConfAction remembers the most recently performed action
		 initiated via TriggerConf helping users interpreting return
		 value of either done or error there.
		 Default value is unknown."
        ::= { systelTerminalEntry 13 }



	pabxSpeedDialTable OBJECT-TYPE
	    SYNTAX  SEQUENCE OF PabxSpeedDialEntry
	    ACCESS  not-accessible
	    STATUS  mandatory
	    DESCRIPTION
		"The pabxSpeedDialTable contains shortcuts for dialling
		 arbitrary numbers.
		 and is in fact part of the dial plan like extensions and trunk
		 prefixes.

		 Deleting a row is done by setting pabxSpeedDialCtrl to value
		 delete."
	::= { pabx 15 }

	pabxSpeedDialEntry OBJECT-TYPE
	    SYNTAX  PabxSpeedDialEntry
	    ACCESS  not-accessible
	    STATUS  mandatory
	    DESCRIPTION
		""
	    INDEX   { pabxSpeedDialShortcut }
	::= { pabxSpeedDialTable 1 }

	PabxSpeedDialEntry ::=
	    SEQUENCE {
		pabxSpeedDialShortcut	DisplayString,
		pabxSpeedDialNumber	DisplayString,
		pabxSpeedDialCtrl	INTEGER
	    }

	pabxSpeedDialShortcut OBJECT-TYPE
	    SYNTAX  DisplayString (SIZE (0..7))
	    ACCESS  read-write
	    STATUS  mandatory
	    DESCRIPTION
                "This field contains the shortcut number for an arbitrary number
		 by which it is replaced."
	::= { pabxSpeedDialEntry 1 }

	pabxSpeedDialNumber OBJECT-TYPE
	    SYNTAX  DisplayString (SIZE (0..31))
	    ACCESS  read-write
	    STATUS  mandatory
	    DESCRIPTION
                "This field contains actual number that replaces shortcut."
	::= { pabxSpeedDialEntry 2 }

	pabxSpeedDialCtrl OBJECT-TYPE
            SYNTAX  INTEGER {
		on(1),
                off(2),
		delete(3)
            }
            ACCESS  read-write
            STATUS  mandatory
            DESCRIPTION
		"This field specifies whether a speed dial entry is active at
		 all. Besides entries in speed dial table can be deleted by
		 setting this field to delete.
		 Default value is on"
        ::= { pabxSpeedDialEntry 3 }






	pabxLocalPrefix OBJECT-TYPE
	    SYNTAX  DisplayString (SIZE(0..8))
	    ACCESS  read-write
	    STATUS  mandatory
	    DESCRIPTION
		"When this object is not empty, internal numbers are dialed by
		 using the contents of this object as a prefix. External
		 numbers are dialled as usual, without using a prefix.

		 When this object is empty, internal numbers are dialled
		 without a prefix, while external numbers need a prefix
		 specified in the pabxTrunkPrefixTable."
	::= { pabx  20 }

	pabxTrunkMask OBJECT-TYPE
	    SYNTAX  BitValue
	    ACCESS  read-write
	    STATUS  mandatory
	    DESCRIPTION
		"This object is a bitmask specifying the set of trunk-lines
		 to be used for external calls, when pabxLocalPrefix is
		 not empty and external numbers are dialled without
		 trunk-prefix."
	::= { pabx  21 }

	pabxPriorityVoice OBJECT-TYPE
	    SYNTAX  INTEGER {
		disable(1),
		enable(2)
	    }
            ACCESS  read-write
            STATUS  mandatory

	    DESCRIPTION
		"Enable of Disable Priority Voice Feature"
	::= { pabx 22 }

	pabxMusicOnHold OBJECT-TYPE
	    SYNTAX  INTEGER {
		internal(1),
		external(2)
	    }
            ACCESS  read-write
            STATUS  mandatory

	    DESCRIPTION
		"Select the source while call in hold state"
	::= { pabx 23 }

	pabxDoorIntercomCallExtension OBJECT-TYPE
	    SYNTAX  DisplayString (SIZE (0..31))
            ACCESS  read-write
            STATUS  mandatory

	    DESCRIPTION
		"Specify extension to be called by door intercom."
	::= { pabx 24 }

	pabxDoorIntercomExternalOpen OBJECT-TYPE
	    SYNTAX  INTEGER {
		allow(1),
		deny(2)
	    }
            ACCESS  read-write
            STATUS  mandatory

	    DESCRIPTION
		"Specifies whether opening the door (i.e. calling a door
		 intercom extension) is possible via a trunk call ('allow')
		 or not ('deny').
		 The default is 'denied'."
	::= { pabx 25 }

	pabxTapiAdmPassword OBJECT-TYPE
            SYNTAX  DisplayString (SIZE (0..15))
            ACCESS  read-write
	    STATUS  mandatory
            DESCRIPTION
		"Password for TAPI super-user named 'TAPIadmin'. Default is
		 'bintec'."
	::= { pabx 26 }

	pabxDefaultAutoDialOutNo OBJECT-TYPE
	    SYNTAX  DisplayString (SIZE (0..15))
	    ACCESS  read-write
	    STATUS  mandatory
	    DESCRIPTION
		"String to be used by default if auto dialout is selected for a
		 user/terminal/extension that has no profile associated with.
		 Default value at system initialisation (no boot configuration)
		 is '0'.
		 If it's set to an empty string autodialout is disabled by
		 system default."
	::= { pabx 27 }

	pabxDefaultAvailability OBJECT-TYPE
            SYNTAX  INTEGER {
                internal(1),
                external(2),
                full(3)
            }
	    ACCESS  read-write
	    STATUS  mandatory
	    DESCRIPTION
		"Define default availability of extension w/o associated
		 profile.
		 By default extensions are fully available (full), i.e. internal
		 and external bound calls can reach the extension depending on
		 the trunk constellation.
		 Setting availability to internal restricts referred to
		 extensions to be available only by internal callers."
	::= { pabx 28 }

	pabxDefaultDialPerm OBJECT-TYPE
            SYNTAX  INTEGER {
                internal(1),
		local(2),
		national(3),
		national-special(4),
		full(5)
            }
	    ACCESS  read-write
	    STATUS  mandatory
	    DESCRIPTION
		"Define dial permissions of extensions w/o associated profile.
		 When set to 'internal' dialling out over (external) trunks is
		 prevented.
		 Value 'local' allows dialling external numbers without an area
		 prefix.
		 With setting 'national' any national number but special numbers
		 (like mobile numbers) may be dialled.
		 The only restriction applying to value 'national_special' is
		 dialling of internaltional numbers.
		 The default setting 'full' grants access to any number."
	::= { pabx 29 }

	pabxExternalCallDialPerm OBJECT-TYPE
            SYNTAX  INTEGER {
                internal(1),
		local(2),
		national(3),
		national-special(4),
		full(5)
            }
	    ACCESS  read-write
	    STATUS  mandatory
	    DESCRIPTION
		"Define dial permissions for external calls.
		 When set to 'internal' dialling out over (external) trunks is
		 prevented.
		 Value 'local' allows dialling external numbers without an area
		 prefix.
		 With setting 'national' any national number but special numbers
		 (like mobile numbers) may be dialled.
		 The only restriction applying to value 'national_special' is
		 dialling of internaltional numbers.
		 The default setting is 'internal'."
	::= { pabx 30 }

	pabxCapiAdmPassword OBJECT-TYPE
            SYNTAX  DisplayString (SIZE (0..15))
            ACCESS  read-write
	    STATUS  mandatory
            DESCRIPTION
		"Password for CAPI super-user named 'CAPIadmin'. Default is
		 an empty password meaning CAPIadmin registration is blocked."
	::= { pabx 31 }

	pabxCountry OBJECT-TYPE
            SYNTAX  INTEGER {
		germany(1),
		uk(2),
		france(3)
	    }
            ACCESS  read-write
	    STATUS  mandatory
            DESCRIPTION
		"Specifies country where machine resides for country specific
		 settings."
	::= { pabx 32 }

END		-- of BIANCA-BOX-PABX-MIB definitions
