-- *****************************************************************
-- Unisphere-Data-FILE-XFER-MIB
--
-- Unisphere Networks Inc. Enterprise MIB
--
-- Copyright (c) 1999 Redstone Communications, Incorporated.
-- Copyright (c) 1999, 2002 Unisphere Networks, Incorporated.
-- All Rights Reserved.
-- *****************************************************************

Unisphere-Data-FILE-XFER-MIB DEFINITIONS ::= BEGIN

IMPORTS
    MODULE-IDENTITY,
    OBJECT-TYPE,
    NOTIFICATION-TYPE,
    TimeTicks
        FROM SNMPv2-SMI
    RowStatus,
    DisplayString
        FROM SNMPv2-TC
    MODULE-COMPLIANCE,
    OBJECT-GROUP,
    NOTIFICATION-GROUP
        FROM SNMPv2-CONF
    UsdName
        FROM Unisphere-Data-TC
    usDataMibs
        FROM Unisphere-Data-MIBs;


usdFileXferMIB  MODULE-IDENTITY
    LAST-UPDATED "200103281346Z"  -- 28-Mar-01 08:46 AM EST
    ORGANIZATION "Unisphere Networks, Inc."
    CONTACT-INFO
        "       Unisphere Networks, Inc.
        Postal: 10 Technology Park Drive
                Westford, MA  01886
                USA
        Tel:    +1 978 589 5800
        E-mail: mib@UnisphereNetworks.com"
    DESCRIPTION
        "The File Transfer MIB for Unisphere Networks Inc. enterprise."
    --  Revision history
    REVISION    "200103281346Z"  -- 28-Mar-01 08:46 AM EST  - RX 3.0
    DESCRIPTION
        "Make it SMIv2 conformant."
    REVISION    "200005010000Z"  --  1-May-00               - RX 2.0
    DESCRIPTION
        "Key revisions include:
          o  Obsoleted usdFileXferRemoteUserName.
          o  Obsoleted usdFileXferRemoteUserPassword.
          o  Added usdFileXferRouterName.
          o  Added usdFileXferCopyRunningCfgFailed(9) to usdFileXferStatus."
    REVISION      "9908180000Z"  -- 18-Aug-99               - RX 1.1
    DESCRIPTION
        "Initial version of this MIB module."
    ::= { usDataMibs 23 }

-- ++++++++++++++++++++++++++++++++++++++++++++++++++++++++++++++++++++++
-- Textual conventions
-- ++++++++++++++++++++++++++++++++++++++++++++++++++++++++++++++++++++++

-- No textual conventions are defined in this MIB module.

-- ++++++++++++++++++++++++++++++++++++++++++++++++++++++++++++++++++++++
-- Managed objects
-- ++++++++++++++++++++++++++++++++++++++++++++++++++++++++++++++++++++++

usdFileXferObjects    OBJECT IDENTIFIER ::= { usdFileXferMIB 1 }


usdFileXferTable OBJECT-TYPE
    SYNTAX SEQUENCE OF UsdFileXferTableEntry
    MAX-ACCESS not-accessible
    STATUS current
    DESCRIPTION
        "A list of entries which describe file transfers."
    ::= { usdFileXferObjects 1 }

usdFileXferTableEntry OBJECT-TYPE
    SYNTAX UsdFileXferTableEntry
    MAX-ACCESS not-accessible
    STATUS current
    DESCRIPTION
        "A description of a particular file transfer entry."
    INDEX { usdFileXferIndex }
    ::= { usdFileXferTable 1 }

UsdFileXferTableEntry ::= SEQUENCE {
        usdFileXferIndex               INTEGER,
        usdFileXferDirection           INTEGER,
        usdFileXferFileType            INTEGER,
        usdFileXferRemoteFileName      DisplayString,
        usdFileXferRemoteUserName      DisplayString,
        usdFileXferRemoteUserPassword  OCTET STRING,
        usdFileXferLocalFileName       DisplayString,
        usdFileXferProtocol            INTEGER,
        usdFileXferStatus              INTEGER, 
        usdFileXferRowStatus           RowStatus,
        usdFileXferTimeStamp           TimeTicks,
        usdFileXferRouterName          UsdName
    }

usdFileXferIndex OBJECT-TYPE
    SYNTAX INTEGER (1..65535)
    MAX-ACCESS read-only
    STATUS current
    DESCRIPTION
        "A unique index used to identify this entry."
    ::= { usdFileXferTableEntry 1 }

usdFileXferDirection OBJECT-TYPE
    SYNTAX INTEGER {
        usdFileXferLocalToRemote(1),
        usdFileXferRemoteToLocal(2) }
    MAX-ACCESS read-write
    STATUS current
    DESCRIPTION
        "Specifies the direction of the file transfer."
    DEFVAL { usdFileXferRemoteToLocal }    
    ::= { usdFileXferTableEntry 2 }

usdFileXferFileType OBJECT-TYPE
    SYNTAX INTEGER {
        usdFileXferSoftwareRelease(1),
        usdFileXferSystemConfig(2),
        usdFileXferRunningConfig(3),
        usdFileXferSystemLog(4),
        usdFileXferScript(5),
        usdFileXferRebootHistory(6),
        usdFileXferBulkStatistics(7) }
    MAX-ACCESS read-write
    STATUS current
    DESCRIPTION
        "Specifies the file type of the file transfer."
    DEFVAL { usdFileXferBulkStatistics }    
    ::= { usdFileXferTableEntry 3 }

usdFileXferRemoteFileName OBJECT-TYPE
    SYNTAX DisplayString (SIZE (0..128))
    MAX-ACCESS read-write
    STATUS current
    DESCRIPTION
        "The full path name of the source/destination file on the remote
         system."
    DEFVAL {""}
    ::= { usdFileXferTableEntry 4 }

usdFileXferRemoteUserName OBJECT-TYPE
    SYNTAX DisplayString (SIZE (0..64))
    MAX-ACCESS read-write
    STATUS obsolete
    DESCRIPTION
        "The user name to use when requesting the file transfer to/from the
         remote system.

         This object has been obsoleted.  Use the enterprise host mib in order
         to configure the username."
    DEFVAL {"anonymous"}
    ::= { usdFileXferTableEntry 5 }

usdFileXferRemoteUserPassword OBJECT-TYPE
    SYNTAX OCTET STRING (SIZE (0..64))
    MAX-ACCESS read-write
    STATUS obsolete
    DESCRIPTION
        "The password to use when requesting the file transfer to/from
         the remote system. When read, this object returns a zero
         string. Note that, for security reasons, some ftp servers may
         insist on a non-zero length user password.

         This object has been obsoleted. Use the enterprise host mib
         in order to configure the password."
    DEFVAL {"anonymous"}
    ::= { usdFileXferTableEntry 6 }

usdFileXferLocalFileName OBJECT-TYPE
    SYNTAX DisplayString (SIZE (0..128))
    MAX-ACCESS read-write
    STATUS current
    DESCRIPTION
        "The local file name to transfer or to create as a result of 
         an incoming transfer."
    DEFVAL {""}
    ::= { usdFileXferTableEntry 7 }

usdFileXferProtocol OBJECT-TYPE
    SYNTAX INTEGER {
        usdFileXferFtp(1),
        usdFileXferTftp(2) }
    MAX-ACCESS read-write
    STATUS current
    DESCRIPTION
        "Specifies the file transfer protocol type."
    DEFVAL { usdFileXferFtp }
    ::= { usdFileXferTableEntry 8 }

usdFileXferStatus OBJECT-TYPE
    SYNTAX INTEGER {
        usdFileXferSuccessfulCompletion(1),
        usdFileXferInProgress(2),
        usdFileXferRemoteUnreachable(3),
        usdFileXferUserAuthFailed(4),
        usdFileXferFileNotFound(5),
        usdFileXferFileTooBig(6),
        usdFileXferFileIncompatible(7),
        usdFileXferPended(8),
        usdFileXferCopyRunningCfgFailed(9) }
    MAX-ACCESS read-only
    STATUS current
    DESCRIPTION
        "The status of the file transfer."
    ::= { usdFileXferTableEntry 9 }

usdFileXferRowStatus OBJECT-TYPE
    SYNTAX RowStatus
    MAX-ACCESS read-write
    STATUS current
    DESCRIPTION
        "The row status object controls the creation/deletion of rows
         in this table. Its semantics are the same as those for the
         RowStatus textual convention specified for SNMPv2. 

         Setting this object to createAndGo(4) is allowed.  If required
         objects are missing, the agent will create the row and set its
         status to notReady(3).  If all of the required objects are
         present and valid, the agent will create the row, set it to
         active and commence the file xfer.  Upon completion of the
         file xfer, the agent will set the rowStatus to notInService(2),
         indicating that the row is valid and useable by a management
         client.  To commence another transfer, a management client should
         set the rowStatus to active(1).

         Setting this object to createAndWait(5) causes an entry
         to be created with usdFileXferRowStatus value of notInService(2) if
         all of the required objects are present and valid.  Or, if some
         of the required objects are missing or invalid, the agent will
         create the row and sets its status to notReady(3).
    
         Setting this object to active(1) causes the transfer to
         start for the given row. Objects within the row cannot 
         be modified once a row has been set to active(1),

         Setting this object to destroy(6) causes the corresponding
         row to be deleted.
        
         Note that only a single instance of a row can be active at 
         at any given moment, although several rows can exist in the
         table."
    ::= { usdFileXferTableEntry 10 }

usdFileXferTimeStamp OBJECT-TYPE
    SYNTAX TimeTicks
    MAX-ACCESS read-only
    STATUS current
    DESCRIPTION
        "The value of sysUpTime at the last status change for this
         entry."
    ::= { usdFileXferTableEntry 11 }

usdFileXferRouterName OBJECT-TYPE
    SYNTAX UsdName 
    MAX-ACCESS read-write
    STATUS current
    DESCRIPTION
        "The name of the router to be used when resolving the hostname
        portion of the usdFileXferRemoteFileName object. If this object
        contains an invalid or empty value, the default router will be
        used."
    ::= { usdFileXferTableEntry 12 }

usdFileXferTrapEnabled OBJECT-TYPE
    SYNTAX     INTEGER { true(1), false(2) }
    MAX-ACCESS read-write
    STATUS     current
    DESCRIPTION
        "An indication of whether the usdFileXferTrap trap is enabled."
    ::= { usdFileXferObjects 2 }


-- +++++++++++++++++++++++++++++++++++++++++++++++++++++++++++++++++++++++++++++
-- Notifications
-- +++++++++++++++++++++++++++++++++++++++++++++++++++++++++++++++++++++++++++++

usdFileXferNotifications OBJECT IDENTIFIER ::= { usdFileXferMIB 2 }

usdFileXferNotifyPrefix OBJECT IDENTIFIER ::= { usdFileXferNotifications 0 }


usdFileXferTrap NOTIFICATION-TYPE
    OBJECTS {
        usdFileXferStatus,
        usdFileXferTimeStamp }
    STATUS      current
    DESCRIPTION
        "An indication that the status associated with a particular file
        transfer entry has changed."
    ::= { usdFileXferNotifyPrefix 1 }

-- ++++++++++++++++++++++++++++++++++++++++++++++++++++++++++++++++++++++
-- Conformance information
-- ++++++++++++++++++++++++++++++++++++++++++++++++++++++++++++++++++++++

usdFileXferConformance OBJECT IDENTIFIER ::= { usdFileXferMIB 4 }
usdFileXferCompliances OBJECT IDENTIFIER ::= { usdFileXferConformance 1 }
usdFileXferGroups      OBJECT IDENTIFIER ::= { usdFileXferConformance 2 }

-- compliance statements

usdFileXferCompliance1 MODULE-COMPLIANCE
    STATUS  obsolete
    DESCRIPTION
        "Obsolete compliance statement for entities that implement the Unisphere
        file transfer MIB.  This compliance statement became obsolete when
        remote user information was removed and router name was added."
    MODULE  -- this module
        MANDATORY-GROUPS {
            usdFileXferGroup1,
            usdFileXferTrapGroup }
    ::= { usdFileXferCompliances 2 }                                   -- RX 1.1

usdFileXferCompliance2 MODULE-COMPLIANCE
    STATUS  current
    DESCRIPTION
        "The compliance statement for entities that implement the Unisphere file
        transfer MIB."
    MODULE  -- this module
        MANDATORY-GROUPS {
            usdFileXferGroup2,
            usdFileXferTrapGroup }
    ::= { usdFileXferCompliances 3 }                                   -- RX 2.0

-- units of conformance

usdFileXferGroup1 OBJECT-GROUP
    OBJECTS {
        usdFileXferIndex,
        usdFileXferDirection,
        usdFileXferFileType,
        usdFileXferRemoteFileName,
        usdFileXferRemoteUserName,
        usdFileXferRemoteUserPassword,
        usdFileXferLocalFileName,
        usdFileXferProtocol,
        usdFileXferStatus, 
        usdFileXferRowStatus,
        usdFileXferTimeStamp,
        usdFileXferTrapEnabled }
    STATUS  obsolete
    DESCRIPTION
        "Obsolete collection of objects providing management of file transfers
        in a Unisphere product.  This group became obsolete when remote user
        information was removed and usdFileXferRouterName was added."
    ::= { usdFileXferGroups 2 }

usdFileXferGroup2 OBJECT-GROUP
    OBJECTS {
        usdFileXferIndex,
        usdFileXferDirection,
        usdFileXferFileType,
        usdFileXferRemoteFileName,
        usdFileXferLocalFileName,
        usdFileXferProtocol,
        usdFileXferStatus, 
        usdFileXferRowStatus,
        usdFileXferTimeStamp,
        usdFileXferRouterName,
        usdFileXferTrapEnabled }
    STATUS  current
    DESCRIPTION
        "A collection of objects providing management of file transfers in a
        Unisphere product."
    ::= { usdFileXferGroups 3 }

usdFileXferTrapGroup NOTIFICATION-GROUP
    NOTIFICATIONS { usdFileXferTrap }
    STATUS  current
    DESCRIPTION
        "A management notification pertaining to file transfers."
    ::= { usdFileXferGroups 4 }

END
