NETGEAR-REF-MIB DEFINITIONS ::= BEGIN

-- Copyright LVL7 Systems (2001-2005) All rights reserved.
-- This SNMP Management Information Specification
-- embodies LVL7 System's confidential and proprietary
-- intellectual property.  LVL7 Systems retains all title
-- and ownership in the Specification including any revisions.

-- This Specification is supplied "AS IS", LVL7 Systems
-- makes no warranty, either expressed or implied,
-- as to the use, operation, condition, or performance of the
-- Specification.
    
    IMPORTS
      MODULE-IDENTITY FROM SNMPv2-SMI
		TEXTUAL-CONVENTION FROM SNMPv2-TC
		enterprises                                       FROM RFC1155-SMI;
    

    netgear MODULE-IDENTITY
    LAST-UPDATED "200502231200Z" -- 23 Feb 2005 12:00:00 GMT
    ORGANIZATION "Netgear"
    CONTACT-INFO
       ""
        
    DESCRIPTION
       ""
        
    -- revision history
    REVISION
       "200502231200Z" -- 23 Feb 2005 12:00:00 GMT
   	DESCRIPTION
       "Initial revision."
       
    ::= { enterprises 4526 }  -- 1.3.6.1.4.1.4526
    
--
-- below are products that defined prior to NMS100 release that they have product code
-- defined directly above the functions objects
--
managedSwitch           OBJECT IDENTIFIER ::= { netgear 1 } 

--
-- 700 series L2 managed switch
--
fsm726s                 OBJECT IDENTIFIER ::= { managedSwitch 1 }
fsm750s                 OBJECT IDENTIFIER ::= { managedSwitch 2 }
gsm712                  OBJECT IDENTIFIER ::= { managedSwitch 3 }
fsm726                  OBJECT IDENTIFIER ::= { managedSwitch 4 }  
gsm712f                 OBJECT IDENTIFIER ::= { managedSwitch 5 }
fsm726v3		            OBJECT IDENTIFIER ::= { managedSwitch 10 }

--
-- 7000 series L2/L3 managed switch
--
gsm7312                 OBJECT IDENTIFIER ::= { managedSwitch 6 }
gsm7324                 OBJECT IDENTIFIER ::= { managedSwitch 7 }
gsm7224                 OBJECT IDENTIFIER ::= { managedSwitch 8 }
fsm7326p                OBJECT IDENTIFIER ::= { managedSwitch 9 }

--********************************************************************
-- new post-NMS100 SNMP products 
--

--
-- new post-NMS100 SNMP-enabled products. These products will have their 
-- functions defined under each generic product category
--
ng7000Switch   	        OBJECT IDENTIFIER ::= { netgear 10 }
ng700Switch             OBJECT IDENTIFIER ::= { netgear 11 }
ngrouter		            OBJECT IDENTIFIER ::= { netgear 12 }
ngfirewall		          OBJECT IDENTIFIER ::= { netgear 13 }
ngap			              OBJECT IDENTIFIER ::= { netgear 14 }
ngwlan			            OBJECT IDENTIFIER ::= { netgear 15 }
ng9000chassisswitch     OBJECT IDENTIFIER ::= { netgear 16 }

--
-- and their sysObjectID will be under a branch on their own
--
productID               OBJECT IDENTIFIER ::= { netgear 100 }

stackswitch             OBJECT IDENTIFIER ::= { productID 1 }
l2switch                OBJECT IDENTIFIER ::= { productID 2 }
l3switch		            OBJECT IDENTIFIER ::= { productID 3 }
smartswitch             OBJECT IDENTIFIER ::= { productID 4 }

router			            OBJECT IDENTIFIER ::= { productID 5 }
firewall		            OBJECT IDENTIFIER ::= { productID 6 }
accesspoint		          OBJECT IDENTIFIER ::= { productID 7 }
wirelessLAN		          OBJECT IDENTIFIER ::= { productID 8 }
chassisswitch		        OBJECT IDENTIFIER ::= { productID 9 }

--
-- managed switches
--

fsm7328s                OBJECT IDENTIFIER ::= { stackswitch 1 }
fsm7352s                OBJECT IDENTIFIER ::= { stackswitch 2 }
gsm7328s		            OBJECT IDENTIFIER ::= { stackswitch 3 }
gsm7352s                OBJECT IDENTIFIER ::= { stackswitch 4 }
fsm7352sp		            OBJECT IDENTIFIER ::= { stackswitch 5 }
fsm7328sp		            OBJECT IDENTIFIER ::= { stackswitch 6 }

gsm7312v2		            OBJECT IDENTIFIER ::= { l3switch 1 }
gsm7324v2		            OBJECT IDENTIFIER ::= { l3switch 2 }
xsm7312			            OBJECT IDENTIFIER ::= { l3switch 3 }
gsm7324p		            OBJECT IDENTIFIER ::= { l3switch 4 }

gsm7248                 OBJECT IDENTIFIER ::= { l2switch 1 }
gsm7212                 OBJECT IDENTIFIER ::= { l2switch 2 }

gcm9600			            OBJECT IDENTIFIER ::= { chassisswitch 1 }

--
-- new SNMP-enabled Smartswitch
--
gs748t                  OBJECT IDENTIFIER ::= { smartswitch 1 }
fs726t			            OBJECT IDENTIFIER ::= { smartswitch 2 }
gs716t			            OBJECT IDENTIFIER ::= { smartswitch 3 }
fs750t			            OBJECT IDENTIFIER ::= { smartswitch 4 }
gs724t			            OBJECT IDENTIFIER ::= { smartswitch 5 }

--
-- new SNMP-enabled business router/firewall
--
fvx538			            OBJECT IDENTIFIER ::= { router 1 }
fvs338			            OBJECT IDENTIFIER ::= { router 2 }

--
-- new SNMP-enabled firewall
--
fwag114			            OBJECT IDENTIFIER ::= { firewall 3 }

--
-- new SNMP-enabled AP
--
wag302			            OBJECT IDENTIFIER ::= { accesspoint 1 }

--
-- new WLAN
--
wapc538			            OBJECT IDENTIFIER ::= { wirelessLAN 1 }

    
-- New Textual Conventions
AgentPortMask ::= TEXTUAL-CONVENTION
   STATUS  current
   DESCRIPTION
       "Each octet within this value specifies a set of eight
        ports, with the first octet specifying ports 1 through
        8, the second octet specifying ports 9 through 16, etc.
        Within each octet, the most significant bit represents
        the lowest numbered port, and the least significant bit
        represents the highest numbered port.  Thus, each port
        of the bridge is represented by a single bit within the
        value of this object.  If that bit has a value of '1'
        then that port is included in the set of ports; the port
        is not included if its bit has a value of '0'
             
        When setting this value, the system will ignore 
        configuration for ports not between the first and last 
        valid ports.  Configuration of any port numbers between 
        this range that are not valid ports return a failure 
        message, but will still apply configuration for valid 
        ports."
   SYNTAX  OCTET STRING


END
