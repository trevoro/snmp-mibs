--			Ascend mibbrilt MIB
--
--			Ascend Communications, Inc
--			1275 Harbor Bay Pkwy
--			Alameda, CA 94502
--			+1 510 769 6001
--			info@ascend.com
--
-- Copyright (c) 1993-1999 Ascend Communications, Inc.
-- All rights reserved.
--
-- Do not edit this file directly.
-- It is generated automatically by mibgen for use with
-- TAOS version 10.0.1 or newer.
--

ASCEND-MIBBRILT-MIB DEFINITIONS ::= BEGIN

    IMPORTS

        configuration
            FROM ASCEND-MIB
	IpAddress
	    FROM RFC1155-SMI
	OBJECT-TYPE
	    FROM RFC-1212;

	-- If any of the MIB compilers have problems with the DisplayString
	-- or PhysAddress, uncomment the next two lines.

    DisplayString	::=	OCTET STRING
    -- PhysAddress	::=	OCTET STRING

    mibbRILtProfile  OBJECT IDENTIFIER ::= { configuration 27}

	-- The mibbRILtProfile table
	--
	-- This table contains parameters for the mibbRILtProfile profile
	--

    mibbRILtProfileTable	OBJECT-TYPE
	SYNTAX		SEQUENCE OF MibbRILtProfileEntry
	ACCESS		not-accessible
	STATUS		mandatory
	DESCRIPTION	"A list of mibbRILtProfile profile entries."
	::= { mibbRILtProfile 1 }

    mibbRILtProfileEntry	OBJECT-TYPE
	SYNTAX		MibbRILtProfileEntry
	ACCESS		not-accessible
	STATUS		mandatory
	DESCRIPTION	"A mibbRILtProfile entry containing objects that
			 maps to the parameters of mibbRILtProfile profile."
	INDEX		{ bRILtProfile-Shelf-o, bRILtProfile-Slot-o, bRILtProfile-Item-o }
	::= { mibbRILtProfileTable 1 }

    MibbRILtProfileEntry ::=
	SEQUENCE {
	    bRILtProfile-Shelf-o
		INTEGER,
	    bRILtProfile-Slot-o
		INTEGER,
	    bRILtProfile-Item-o
		INTEGER,
	    bRILtProfile-ProfileNumber
		INTEGER,
	    bRILtProfile-Name
		DisplayString,
	    bRILtProfile-LineInterface-Enabled
		INTEGER,
	    bRILtProfile-LineInterface-AnswerNumber1
		DisplayString,
	    bRILtProfile-LineInterface-AnswerNumber2
		DisplayString,
	    bRILtProfile-LineInterface-ClockSource
		INTEGER,
	    bRILtProfile-LineInterface-IdslBandwidth
		INTEGER,
	    bRILtProfile-LineInterface-Gr303Crv
		INTEGER,
	    bRILtProfile-LineInterface-Gr303InterfaceGroup
		INTEGER,
	    bRILtProfile-LineInterface-IgnoreLineup
		INTEGER,
	    bRILtProfile-PhysicalAddress-Shelf
		INTEGER,
	    bRILtProfile-PhysicalAddress-Slot
		INTEGER,
	    bRILtProfile-PhysicalAddress-ItemNumber
		INTEGER,
	    bRILtProfile-SwitchType
		INTEGER,
	    bRILtProfile-SparingMode
		INTEGER,
	    bRILtProfile-Action-o
		INTEGER
	}

    bRILtProfile-Shelf-o	OBJECT-TYPE
	SYNTAX	INTEGER
	ACCESS	read-only
	STATUS	mandatory
	DESCRIPTION	""
	::= { mibbRILtProfileEntry 1 }

    bRILtProfile-Slot-o	OBJECT-TYPE
	SYNTAX	INTEGER
	ACCESS	read-only
	STATUS	mandatory
	DESCRIPTION	""
	::= { mibbRILtProfileEntry 2 }

    bRILtProfile-Item-o	OBJECT-TYPE
	SYNTAX	INTEGER
	ACCESS	read-only
	STATUS	mandatory
	DESCRIPTION	""
	::= { mibbRILtProfileEntry 3 }

    bRILtProfile-ProfileNumber	OBJECT-TYPE
	SYNTAX	INTEGER
	ACCESS	read-write
	STATUS	mandatory
	DESCRIPTION	"If it is a stored profile, the number of the profile (1..MAX_NETWORK_PROFILES). If it is the current profile, the number of the stored profile from which it was loaded, or zero if it has never been loaded."
	::= { mibbRILtProfileEntry 4 }

    bRILtProfile-Name	OBJECT-TYPE
	SYNTAX	DisplayString
	ACCESS	read-write
	STATUS	mandatory
	DESCRIPTION	"The null terminated ascii string that the user gave to this particular profile."
	::= { mibbRILtProfileEntry 5 }

    bRILtProfile-LineInterface-Enabled	OBJECT-TYPE
	SYNTAX	INTEGER {
		    no (1),
		    yes (2)
		}
	ACCESS	read-write
	STATUS	mandatory
	DESCRIPTION	"Boolean that is TRUE if this interface is part of the set used for this network set, or FALSE otherwise."
	::= { mibbRILtProfileEntry 6 }

    bRILtProfile-LineInterface-AnswerNumber1	OBJECT-TYPE
	SYNTAX	DisplayString
	ACCESS	read-write
	STATUS	mandatory
	DESCRIPTION	"Phone numbers to match when routing by incoming phone number."
	::= { mibbRILtProfileEntry 7 }

    bRILtProfile-LineInterface-AnswerNumber2	OBJECT-TYPE
	SYNTAX	DisplayString
	ACCESS	read-write
	STATUS	mandatory
	DESCRIPTION	"Phone numbers to match when routing by incoming phone number."
	::= { mibbRILtProfileEntry 8 }

    bRILtProfile-LineInterface-ClockSource	OBJECT-TYPE
	SYNTAX	INTEGER {
		    eligible (1),
		    notEligible (2)
		}
	ACCESS	read-write
	STATUS	mandatory
	DESCRIPTION	"Boolean that is TRUE if this interface can be used as the netclock source."
	::= { mibbRILtProfileEntry 9 }

    bRILtProfile-LineInterface-IdslBandwidth	OBJECT-TYPE
	SYNTAX	INTEGER {
		    idsl128 (1),
		    idsl144 (2)
		}
	ACCESS	read-write
	STATUS	mandatory
	DESCRIPTION	"Configure IDSL subscriber bandwidth available."
	::= { mibbRILtProfileEntry 10 }

    bRILtProfile-LineInterface-Gr303Crv	OBJECT-TYPE
	SYNTAX	INTEGER
	ACCESS	read-write
	STATUS	mandatory
	DESCRIPTION	"GR-303 CRV associated with this line"
	::= { mibbRILtProfileEntry 11 }

    bRILtProfile-LineInterface-Gr303InterfaceGroup	OBJECT-TYPE
	SYNTAX	INTEGER
	ACCESS	read-write
	STATUS	mandatory
	DESCRIPTION	"GR-303 interface group associated with this line"
	::= { mibbRILtProfileEntry 12 }

    bRILtProfile-LineInterface-IgnoreLineup	OBJECT-TYPE
	SYNTAX	INTEGER {
		    systemDefined (1),
		    no (2),
		    yes (3)
		}
	ACCESS	read-write
	STATUS	mandatory
	DESCRIPTION	"Ignore line up value for this port."
	::= { mibbRILtProfileEntry 18 }

    bRILtProfile-PhysicalAddress-Shelf	OBJECT-TYPE
	SYNTAX	INTEGER {
		    anyShelf (1),
		    shelf1 (2),
		    shelf2 (3),
		    shelf3 (4),
		    shelf4 (5),
		    shelf5 (6),
		    shelf6 (7),
		    shelf7 (8),
		    shelf8 (9),
		    shelf9 (10)
		}
	ACCESS	read-write
	STATUS	mandatory
	DESCRIPTION	"The number of the shelf that the addressed physical device resides on."
	::= { mibbRILtProfileEntry 13 }

    bRILtProfile-PhysicalAddress-Slot	OBJECT-TYPE
	SYNTAX	INTEGER {
		    anySlot (1),
		    slot1 (2),
		    slot2 (3),
		    slot3 (4),
		    slot4 (5),
		    slot5 (6),
		    slot6 (7),
		    slot7 (8),
		    slot8 (9),
		    slot9 (10),
		    slot10 (11),
		    slot11 (12),
		    slot12 (13),
		    slot13 (14),
		    slot14 (15),
		    slot15 (16),
		    slot16 (17),
		    slot17 (18),
		    slot18 (19),
		    slot19 (20),
		    slot20 (21),
		    slot21 (22),
		    slot22 (23),
		    slot23 (24),
		    slot24 (25),
		    slot25 (26),
		    slot26 (27),
		    slot27 (28),
		    slot28 (29),
		    slot29 (30),
		    slot30 (31),
		    slot31 (32),
		    slot32 (33),
		    slot33 (34),
		    slot34 (35),
		    slot35 (36),
		    slot36 (37),
		    slot37 (38),
		    slot38 (39),
		    slot39 (40),
		    slot40 (41),
		    aLim (55),
		    bLim (56),
		    cLim (57),
		    dLim (58),
		    leftController (49),
		    rightController (50),
		    controller (42),
		    firstControlModule (53),
		    secondControlModule (54),
		    trunkModule1 (45),
		    trunkModule2 (46),
		    controlModule (51),
		    slotPrimary (59)
		}
	ACCESS	read-write
	STATUS	mandatory
	DESCRIPTION	"The number of the slot that the addressed physical device resides on."
	::= { mibbRILtProfileEntry 14 }

    bRILtProfile-PhysicalAddress-ItemNumber	OBJECT-TYPE
	SYNTAX	INTEGER
	ACCESS	read-write
	STATUS	mandatory
	DESCRIPTION	"A number that specifies an addressable entity within the context of shelf and slot."
	::= { mibbRILtProfileEntry 15 }

    bRILtProfile-SwitchType	OBJECT-TYPE
	SYNTAX	INTEGER {
		    attPri (1),
		    ntiPri (2),
		    globandPri (3),
		    japanPri (4),
		    vn3Pri (5),
		    onetr6Pri (6),
		    net5Pri (7),
		    danishPri (8),
		    australPri (9),
		    natIsdn2Pri (10),
		    taiwanPri (31),
		    isdxDpnss (11),
		    islxDpnss (12),
		    mercuryDpnss (13),
		    dass2 (14),
		    btSs7 (32),
		    unknownBri (15),
		    att5essBri (16),
		    dms100Nt1Bri (17),
		    nisdn1Bri (18),
		    vn2Bri (19),
		    btnr191Bri (20),
		    net3Bri (21),
		    ptpNet3Bri (22),
		    kddBri (23),
		    belgianBri (24),
		    australBri (25),
		    swissBri (26),
		    german1tr6Bri (27),
		    dutch1tr6Bri (28),
		    switchCas (29),
		    idslPtpBri (30)
		}
	ACCESS	read-write
	STATUS	mandatory
	DESCRIPTION	"Switch type to be emulated."
	::= { mibbRILtProfileEntry 16 }

    bRILtProfile-SparingMode	OBJECT-TYPE
	SYNTAX	INTEGER {
		    inactive (1),
		    manual (2),
		    automatic (3)
		}
	ACCESS	read-write
	STATUS	mandatory
	DESCRIPTION	"Port sparing operational mode for this port."
	::= { mibbRILtProfileEntry 19 }

    bRILtProfile-Action-o	OBJECT-TYPE
	SYNTAX	INTEGER {
		    noAction (1),
		    createProfile (2),
		    deleteProfile (3)
		}
	ACCESS	read-write
	STATUS	mandatory
	DESCRIPTION	""
	::= { mibbRILtProfileEntry 17 }


	-- The mibbRILtProfile__line_interface__channel_config table
	--
	-- This table contains parameters for the mibbRILtProfile__line_interface__channel_config profile
	--

    mibbRILtProfile-LineInterface-ChannelConfigTable	OBJECT-TYPE
	SYNTAX		SEQUENCE OF MibbRILtProfile-LineInterface-ChannelConfigEntry
	ACCESS		not-accessible
	STATUS		mandatory
	DESCRIPTION	"A list of mibbRILtProfile__line_interface__channel_config profile entries."
	::= { mibbRILtProfile 2 }

    mibbRILtProfile-LineInterface-ChannelConfigEntry	OBJECT-TYPE
	SYNTAX		MibbRILtProfile-LineInterface-ChannelConfigEntry
	ACCESS		not-accessible
	STATUS		mandatory
	DESCRIPTION	"A mibbRILtProfile__line_interface__channel_config entry containing objects that
			 maps to the parameters of mibbRILtProfile__line_interface__channel_config profile."
	INDEX		{ bRILtProfile-LineInterface-ChannelConfig-Shelf-o, bRILtProfile-LineInterface-ChannelConfig-Slot-o, bRILtProfile-LineInterface-ChannelConfig-Item-o, bRILtProfile-LineInterface-ChannelConfig-Index-o }
	::= { mibbRILtProfile-LineInterface-ChannelConfigTable 1 }

    MibbRILtProfile-LineInterface-ChannelConfigEntry ::=
	SEQUENCE {
	    bRILtProfile-LineInterface-ChannelConfig-Shelf-o
		INTEGER,
	    bRILtProfile-LineInterface-ChannelConfig-Slot-o
		INTEGER,
	    bRILtProfile-LineInterface-ChannelConfig-Item-o
		INTEGER,
	    bRILtProfile-LineInterface-ChannelConfig-Index-o
		INTEGER,
	    bRILtProfile-LineInterface-ChannelConfig-ChannelUsage
		INTEGER,
	    bRILtProfile-LineInterface-ChannelConfig-NailedGroup
		INTEGER
	}

    bRILtProfile-LineInterface-ChannelConfig-Shelf-o	OBJECT-TYPE
	SYNTAX	INTEGER
	ACCESS	read-only
	STATUS	mandatory
	DESCRIPTION	""
	::= { mibbRILtProfile-LineInterface-ChannelConfigEntry 1 }

    bRILtProfile-LineInterface-ChannelConfig-Slot-o	OBJECT-TYPE
	SYNTAX	INTEGER
	ACCESS	read-only
	STATUS	mandatory
	DESCRIPTION	""
	::= { mibbRILtProfile-LineInterface-ChannelConfigEntry 2 }

    bRILtProfile-LineInterface-ChannelConfig-Item-o	OBJECT-TYPE
	SYNTAX	INTEGER
	ACCESS	read-only
	STATUS	mandatory
	DESCRIPTION	""
	::= { mibbRILtProfile-LineInterface-ChannelConfigEntry 3 }

    bRILtProfile-LineInterface-ChannelConfig-Index-o	OBJECT-TYPE
	SYNTAX	INTEGER
	ACCESS	read-only
	STATUS	mandatory
	DESCRIPTION	""
	::= { mibbRILtProfile-LineInterface-ChannelConfigEntry 4 }

    bRILtProfile-LineInterface-ChannelConfig-ChannelUsage	OBJECT-TYPE
	SYNTAX	INTEGER {
		    unusedChannel (1),
		    switchedChannel (2),
		    nailed64Channel (3),
		    dChannel (4),
		    nfasPrimaryDChannel (5),
		    nfasSecondaryDChannel (6),
		    semiPermChannel (7),
		    ss7SignalingChannel (8)
		}
	ACCESS	read-write
	STATUS	mandatory
	DESCRIPTION	"Usage of the b-channel."
	::= { mibbRILtProfile-LineInterface-ChannelConfigEntry 5 }

    bRILtProfile-LineInterface-ChannelConfig-NailedGroup	OBJECT-TYPE
	SYNTAX	INTEGER
	ACCESS	read-write
	STATUS	mandatory
	DESCRIPTION	"A number that identifies the set of channels that makes up a nailed group."
	::= { mibbRILtProfile-LineInterface-ChannelConfigEntry 6 }

END
