ECLAPBEXT-MIB DEFINITIONS ::= BEGIN

	  IMPORTS
		  Counter, enterprises
			  FROM RFC1155-SMI
		  OBJECT-TYPE
			  FROM RFC-1212
		  TRAP-TYPE
			  FROM RFC-1215;

	  -- add transmission definition for mibcomp. ( novell )
   
	  --  LAPB MIB

	  PositiveInteger ::= INTEGER (0..2147483647)

	  IfIndexType     ::= INTEGER (1..2147483647)
	  -- IfIndexType specifies an index object for a table
	  -- with entries that match entries in the MIB-II ifTable.
	  -- The value of the index for the table will match the
	  -- ifIndex entry for same interface in the ifTable.
	  -- The values of this object range from 1 to ifNumber
	  -- inclusive.


eicon           OBJECT IDENTIFIER  ::= { enterprises 434 }
management      OBJECT IDENTIFIER  ::= { eicon 2 }
mibv2           OBJECT IDENTIFIER  ::= { management 2 }
module          OBJECT IDENTIFIER  ::= { mibv2 4 }


			  --  LAPBEXT MIB

	  lapbext    OBJECT IDENTIFIER ::= { module 1 }

--
-- This type is used to define the possible bandwidth status of a particular line:
--
--	normal			nothing of concern, bandwith is below threshold in both
--				directions
--	tx-usage-high			bandwidth in use for transmission is above threshold
--	rx-usage-high			bandwidth in use for reception is above threshold
--	tx-and-rxusage-high	bandwidth in use is above threshold in both directions
--	undefined			bandwidth state is undefined (e.g. because the line is down)
--

BandwidthStatus ::= INTEGER {
		normal(1),
		tx-usage-high(2),
		rx-usage-high(3),
		tx-and-rx-usage-high(4),
		undefined(5)
		}


--      #################################################################
--                      Lapb Counters Table
--      The Hdlc data flow statistics counters table. 
--      It is Eicon specific extension to Internet lapb MIB  
--      #################################################################           

lapbCountersTable       OBJECT-TYPE
	SYNTAX  SEQUENCE OF LapbCountEntry 
	ACCESS  not-accessible
	STATUS  mandatory
	DESCRIPTION     
		"Runtime counters table, one row per port"
	::= { lapbext 1 }
 
lapbCountEntry          OBJECT-TYPE
	SYNTAX  LapbCountEntry
	ACCESS  not-accessible
	STATUS  mandatory
	DESCRIPTION     
		"The set of counters for one port. Can be reset to 0."
	INDEX           { lapbCountPortRef }
	::= { lapbCountersTable 1 }

LapbCountEntry ::= SEQUENCE {
	lapbCountPortRef
		INTEGER,
	lapbCountRetransmis
		Counter,
	lapbCountSABMTxs
		Counter,
	lapbCountSABMRxs
		Counter,
	lapbCountDISCTxs
		Counter,
	lapbCountDISCRxs
		Counter,
	lapbCountDMsTxs
		Counter,
	lapbCountDMsRxs
		Counter,
	lapbCountRNRsTxs
		Counter,
	lapbCountRNRsRxs
		Counter,
	lapbCountUATxs
		Counter,
	lapbCountUARxs
		Counter,
	lapbCountRRTxs
		Counter,
	lapbCountRRRxs
		Counter,
	lapbCountFRMRTxs
		Counter,
	lapbCountFRMRRxs
		Counter,
	lapbCountBadCRCTxs
		Counter,
	lapbCountBadCRCRxs
		Counter,
	lapbCountAbortTxs
		Counter,
	lapbCountAbortRxs
		Counter,
	lapbCountBadTypeTxs
		Counter,
	lapbCountBadTypeRxs
		Counter,
	lapbCountInfoFrameTxs
		Counter,
	lapbCountInfoFrameRxs
		Counter,
	lapbCountUnderrun
		Counter,
	lapbCountOverrun
		Counter,
	lapbCountXIDTxs
		Counter,
	lapbCountXIDRxs
		Counter
	}

lapbCountPortRef        OBJECT-TYPE
	SYNTAX  INTEGER
	ACCESS  read-only 
	STATUS  mandatory
	DESCRIPTION     
		"The port number, the same as lapbParmPortRef from the 
		lapbParmTable."
	::= { lapbCountEntry 1 }

lapbCountRetransmis     OBJECT-TYPE
	SYNTAX  Counter
	ACCESS  read-only 
	STATUS  mandatory
	DESCRIPTION     
		"The number of times a frame has been retransmitted"
	::= { lapbCountEntry 2 }

lapbCountSABMTxs        OBJECT-TYPE
	SYNTAX  Counter
	ACCESS  read-only 
	STATUS  mandatory
	DESCRIPTION     
		"The number of Set Asynchronous Balanced Mode frames sent"
	::= { lapbCountEntry 3 }

lapbCountSABMRxs        OBJECT-TYPE
	SYNTAX  Counter
	ACCESS  read-only       
	STATUS  mandatory
	DESCRIPTION     
		"The number of Set Asynchronous Balanced Mode frames received"
	::= { lapbCountEntry 4 }

lapbCountDISCTxs        OBJECT-TYPE
	SYNTAX  Counter
	ACCESS  read-only       
	STATUS  mandatory
	DESCRIPTION     
		"The number of Disconnect frames sent"
	::= { lapbCountEntry 5 }

lapbCountDISCRxs        OBJECT-TYPE
	SYNTAX  Counter
	ACCESS  read-only       
	STATUS  mandatory
	DESCRIPTION     
		"The number of Disconnect frames received"
	::= { lapbCountEntry 6 }

lapbCountDMsTxs OBJECT-TYPE
	SYNTAX  Counter
	ACCESS  read-only       
	STATUS  mandatory
	DESCRIPTION     
		"The number of Disconnected Mode frames sent"
	::= { lapbCountEntry 7 }

lapbCountDMsRxs OBJECT-TYPE
	SYNTAX  Counter
	ACCESS  read-only       
	STATUS  mandatory
	DESCRIPTION     
		"The number of Disconnected Mode frames received"
	::= { lapbCountEntry 8 }

lapbCountRNRsTxs        OBJECT-TYPE
	SYNTAX  Counter
	ACCESS  read-only       
	STATUS  mandatory
	DESCRIPTION     
		"The number of Receiver Not Ready frames sent"
	::= { lapbCountEntry 9 }

lapbCountRNRsRxs        OBJECT-TYPE
	SYNTAX  Counter
	ACCESS  read-only       
	STATUS  mandatory
	DESCRIPTION     
		"The number of Receiver Not Ready frames received"
	::= { lapbCountEntry 10 }

lapbCountUATxs  OBJECT-TYPE
	SYNTAX  Counter
	ACCESS  read-only       
	STATUS  mandatory
	DESCRIPTION     
		"The number of Unnumbered Acknowledgement frames transmitted."
	::= { lapbCountEntry 11 }

lapbCountUARxs  OBJECT-TYPE
	SYNTAX  Counter
	ACCESS  read-only       
	STATUS  mandatory
	DESCRIPTION     
		"The number of Unnumbered Acknowledgement frames received."
	::= { lapbCountEntry 12 }

lapbCountRRTxs  OBJECT-TYPE
	SYNTAX  Counter
	ACCESS  read-only       
	STATUS  mandatory
	DESCRIPTION     
		"The number of Receiver Ready frames transmitted. "
	::= { lapbCountEntry 13 }

lapbCountRRRxs  OBJECT-TYPE
	SYNTAX  Counter
	ACCESS  read-only       
	STATUS  mandatory
	DESCRIPTION     
		"The number of Receiver Ready frames received."
	::= { lapbCountEntry 14 }

lapbCountFRMRTxs        OBJECT-TYPE
	SYNTAX  Counter
	ACCESS  read-only       
	STATUS  mandatory
	DESCRIPTION     
		"The number of Frame Reject frames sent."
	::= { lapbCountEntry 15 }

lapbCountFRMRRxs        OBJECT-TYPE
	SYNTAX  Counter
	ACCESS  read-only       
	STATUS  mandatory
	DESCRIPTION     
		"The number of Frame Reject frames received."
	::= { lapbCountEntry 16 }

lapbCountBadCRCTxs      OBJECT-TYPE
	SYNTAX  Counter
	ACCESS  read-only       
	STATUS  mandatory
	DESCRIPTION     
		"The number of frames sent with bad CRC."
	::= { lapbCountEntry 17 }

lapbCountBadCRCRxs      OBJECT-TYPE
	SYNTAX  Counter
	ACCESS  read-only       
	STATUS  mandatory
	DESCRIPTION     
		"The number of frames received with bad CRC."
	::= { lapbCountEntry 18 }

lapbCountAbortTxs       OBJECT-TYPE
	SYNTAX  Counter
	ACCESS  read-only       
	STATUS  mandatory
	DESCRIPTION     
		"The number of frames sent with Abort indication."
	::= { lapbCountEntry 19 }

lapbCountAbortRxs       OBJECT-TYPE
	SYNTAX  Counter
	ACCESS  read-only       
	STATUS  mandatory
	DESCRIPTION     
		"The number of frames received with Abort indication."
	::= { lapbCountEntry 20 }

lapbCountBadTypeTxs     OBJECT-TYPE
	SYNTAX  Counter
	ACCESS  read-only       
	STATUS  mandatory
	DESCRIPTION     
		"The number of Unknown frames sent."
	::= { lapbCountEntry 21 }

lapbCountBadTypeRxs     OBJECT-TYPE
	SYNTAX  Counter
	ACCESS  read-only       
	STATUS  mandatory
	DESCRIPTION     
		"The number of Unknown frames received."
	::= { lapbCountEntry 22 }

lapbCountInfoFrameTxs   OBJECT-TYPE
	SYNTAX  Counter
	ACCESS  read-only       
	STATUS  mandatory
	DESCRIPTION     
		"The number of Information frames sent."
	::= { lapbCountEntry 23 }

lapbCountInfoFrameRxs   OBJECT-TYPE
	SYNTAX  Counter
	ACCESS  read-only       
	STATUS  mandatory
	DESCRIPTION     
		"The number of Information frames received."
	::= { lapbCountEntry 24 }

lapbCountUnderrun       OBJECT-TYPE
	SYNTAX  Counter
	ACCESS  read-only       
	STATUS  mandatory
	DESCRIPTION     
		"The number of times that more frames have been 
		transmitted than the receiver can handle."
	::= { lapbCountEntry 25 }

lapbCountOverrun        OBJECT-TYPE
	SYNTAX  Counter
	ACCESS  read-only       
	STATUS  mandatory
	DESCRIPTION     
		"The number of times that the EiconCard could not
		handle incoming frames."
	::= { lapbCountEntry 26 }

lapbCountXIDTxs         OBJECT-TYPE
	SYNTAX  Counter
	ACCESS  read-only       
	STATUS  mandatory
	DESCRIPTION     
		"The number of Exchange Station Identification
		frames sent."
	::= { lapbCountEntry 27 }

lapbCountXIDRxs         OBJECT-TYPE
	SYNTAX  Counter
	ACCESS  read-only       
	STATUS  mandatory
	DESCRIPTION     
		"The number of Exchange Station Identification
		frames received."
	::= { lapbCountEntry 28 }


lapbBandwidthTable	OBJECT-TYPE
	SYNTAX	SEQUENCE OF LapbBandwidthEntry
	ACCESS	not-accessible
	STATUS	mandatory
	DESCRIPTION	
	"The table of configurable and informational parameters with
		respect to the bandwidth traps for lapb interfaces"
	::= { lapbext 2 }

lapbBandwidthEntry	OBJECT-TYPE
	SYNTAX	LapbBandwidthEntry
	ACCESS	not-accessible
	STATUS	mandatory
	DESCRIPTION	"The set of configurable and informational parameters to support
		the bandwidth traps for each lapb interface"
	INDEX	{ lapbBandwidthIndex }
	::= { lapbBandwidthTable 1 }

LapbBandwidthEntry ::= SEQUENCE {
		lapbBandwidthIndex
			INTEGER,
		lapbBandwidthHigh
			INTEGER, 	
		lapbBandwidthLow
			INTEGER,
		lapbBandwidthSecs
			INTEGER,
		lapbBandwidthNumPeriods
			INTEGER, 
		lapbBandwidthTrapState
			INTEGER, 
		lapbBandwidthTrapStatus
			BandwidthStatus,
		lapbBandwidthRxInUse 
			INTEGER, 
		lapbBandwidthTxInUse
			INTEGER
			}

lapbBandwidthIndex	OBJECT-TYPE
	SYNTAX	INTEGER (1..48)
	ACCESS	read-only
	STATUS	mandatory
	DESCRIPTION	
		"The identifier of the EiconPort assigned by the agent."
	::= { lapbBandwidthEntry 1 }

lapbBandwidthHigh OBJECT-TYPE
	SYNTAX	INTEGER (1..100)
	ACCESS	read-write
	STATUS	mandatory
	DESCRIPTION
		"The higher configurable threshold for the
		lapbTrapBandwidthShortage. If the percentage of bandwidth being
		used exceeds this amount over a configurable number of seconds
		(lapbBandwidthSecs) for a configurable number of consecutive
		periods, (lapbBandwidthNumPeriods), then the trap is sent and the
		lapbBandwidthTrapsStatus is changed accordingly"
	DEFVAL	{ 80 }
	::= { lapbBandwidthEntry 2 }
		
lapbBandwidthLow 	OBJECT-TYPE
	SYNTAX	INTEGER (1..100)
	ACCESS	read-write
	STATUS	mandatory
	DESCRIPTION	
		"The lower configurable threshold for the lapbTrapBandwidthClear.
		If the percentage of bandwidth being used drops below this amount,
		subsequent to a lapbTrapBandwidthShortage, then the trap is sent
		and the lapbBadwidthTrapsStatus is changed accordingly. Note that
		this value MUST be below that for labpBandwidthHigh"
	DEFVAL	{ 60 }
	::= { lapbBandwidthEntry 3 }

lapbBandwidthSecs	OBJECT-TYPE
	SYNTAX	INTEGER (10..600)
	ACCESS	read-write
	STATUS	mandatory
	DESCRIPTION	
		"The number of seconds over which the bandwidth is calculated."
	DEFVAL	{ 60 }
	::= { lapbBandwidthEntry 4 }

lapbBandwidthNumPeriods	OBJECT-TYPE
	SYNTAX	INTEGER (1 .. 100)
	ACCESS	read-write
	STATUS	mandatory
	DESCRIPTION	
		"The number of consecutive periods, each of length
		lapbBandwidthSecs seconds, that the condition must be present for
		before the lapbBandwidthShortage trap is sent."
	DEFVAL	{ 3 }
	::= { lapbBandwidthEntry 5 }

lapbBandwidthTrapState OBJECT-TYPE
	SYNTAX	INTEGER { disabled(1), enabled(2) }
	ACCESS	read-write
	STATUS	mandatory
	DESCRIPTION	
		"This variable indicates whether the agent should
		generate the lapbTrapBandwidthShortage and lapbTrapBandwidthClear
		traps if the relevant conditions arise. Set this value to disabled
		to stop these traps being generated"
	DEFVAL	{ enabled }
	::= { lapbBandwidthEntry 6 }

lapbBandwidthTrapStatus OBJECT-TYPE
	SYNTAX	BandwidthStatus
	ACCESS	read-only
	STATUS	mandatory
	DESCRIPTION	
		"The status of the bandwidth traps. This value should be polled to
		determine whether or not the bandwidth shortage condition is
		present and a trap has been sent."
::= { lapbBandwidthEntry 7 }

lapbBandwidthRxInUse OBJECT-TYPE
	SYNTAX	INTEGER (0..100)
	ACCESS	read-only
	STATUS	mandatory
	DESCRIPTION	
		"The percentage of bandwidth that is currently in use receiving
		incoming traffic."
	::= { lapbBandwidthEntry 8 }

lapbBandwidthTxInUse OBJECT-TYPE
	SYNTAX	INTEGER (0..100)
	ACCESS	read-only
	STATUS	mandatory
	DESCRIPTION	
		"The percentage of bandwidth that is currently in use transmitting
		outgoing traffic."
	::= { lapbBandwidthEntry 9 }



	  -- ###########################################################
	  --                      LAPB operating parameters.
	  -- ###########################################################

	  -- Support of the lapbOperTable is mandatory for all
	  -- agents of systems that implement LAPB.

	  lapbOperTable   OBJECT-TYPE
		  SYNTAX  SEQUENCE OF LapbOperEntry
		  ACCESS  not-accessible
		  STATUS  mandatory
		  DESCRIPTION
			  "This table contains configuration
			  information about interface parameters
			  currently set in the interface.  Many of
			  these objects have corresponding objects in
		  the lapbAdmnTable."
		  ::= { lapbext 3  }

	  lapbOperEntry   OBJECT-TYPE
		  SYNTAX  LapbOperEntry
		  ACCESS  not-accessible
		  STATUS  mandatory
		  DESCRIPTION
			  "Currently set parameter values for a
			  specific LAPB."
		  INDEX { lapbOperIndex }
		  ::= { lapbOperTable 1 }

	  LapbOperEntry ::= SEQUENCE {
		  lapbOperIndex
			  IfIndexType,
		  lapbOperStationType
			  INTEGER,
		  lapbOperControlField
			  INTEGER,
		  lapbOperTransmitN1FrameSize
			  PositiveInteger,
		  lapbOperReceiveN1FrameSize
			  PositiveInteger,
		  lapbOperTransmitKWindowSize
			  INTEGER,
		  lapbOperReceiveKWindowSize
			  INTEGER,
		  lapbOperN2RxmitCount
			  INTEGER,
		  lapbOperT1AckTimer
			  PositiveInteger,
		  lapbOperT2AckDelayTimer
			  PositiveInteger,
		  lapbOperT3DisconnectTimer
			  PositiveInteger,
		  lapbOperT4IdleTimer
			  PositiveInteger,
		  lapbOperPortId
			  OBJECT IDENTIFIER,
		  lapbOperProtocolVersionId
			  OBJECT IDENTIFIER
		  }

	  lapbOperIndex   OBJECT-TYPE
	     SYNTAX       IfIndexType
		  ACCESS  read-only
		  STATUS  mandatory
		  DESCRIPTION
			  "The ifIndex value for the LAPB interface."
		  ::= { lapbOperEntry 1 }

	  lapbOperStationType     OBJECT-TYPE
		  SYNTAX  INTEGER {
			  dte (1),
			  dce (2),
			  dxe (3)
			  }
		  ACCESS  read-only
		  STATUS  mandatory
		  DESCRIPTION
			  "Identifies the current operating station
			  type of this interface.  A value of dxe (3)
			  indicates XID negotiation has not yet taken
			  place."


		  REFERENCE "ISO 7776 section 3.1"
		  ::= { lapbOperEntry 2 }

	  lapbOperControlField OBJECT-TYPE
		  SYNTAX  INTEGER {
			  modulo8 (1),
			  modulo128 (2)
			  }
		  ACCESS  read-only
		  STATUS  mandatory
		  DESCRIPTION
			  "The current operating size of the sequence
			  numbers used to number frames."
		  REFERENCE "ISO 7776 section 3.3"
		  ::= { lapbOperEntry 3 }

	  lapbOperTransmitN1FrameSize OBJECT-TYPE
		  SYNTAX  PositiveInteger
		  ACCESS  read-only
		  STATUS  mandatory
		  DESCRIPTION
			  "The current operating N1 frame size used
			  for the maximum number of bits in a frame
			  this DTE can transmit.  This excludes flags
			  and 0 bits inserted for transparency."
		  REFERENCE "ISO 7776 section 5.7.3"
		  ::= { lapbOperEntry 4 }

	  lapbOperReceiveN1FrameSize OBJECT-TYPE
		  SYNTAX  PositiveInteger
		  ACCESS  read-only
		  STATUS  mandatory
		  -- See lapbOperTransmitN1FrameSize above
		  DESCRIPTION
			  "The current operating N1 frame size used
			  for the maximum number of bits in a frame
			  the DCE/remote DTE can transmit.  This
			  excludes flags and 0 bits inserted for
			  transparency."
		  ::= { lapbOperEntry 5 }

	  lapbOperTransmitKWindowSize OBJECT-TYPE
		  SYNTAX  INTEGER (1..127)
		  ACCESS  read-only
		  STATUS  mandatory
		  DESCRIPTION
			  "The current PDU window size this Interface
			  uses to transmit.  This is the maximum


			  number of unacknowledged sequenced PDUs that
			  may be outstanding from this DTE at any one
			  time."
		  REFERENCE "ISO 7776 section 5.7.4"
		  ::= { lapbOperEntry 6 }

	  lapbOperReceiveKWindowSize OBJECT-TYPE
		  SYNTAX  INTEGER (1..127)
		  ACCESS  read-only
		  STATUS  mandatory
		  DESCRIPTION
			  "The current receive PDU window size for
			  this Interface.  This is the maximum number
			  of unacknowledged sequenced PDUs that may be
			  outstanding from the DCE/remote DTE at any
			  one time."
		  REFERENCE "ISO 7776 section 5.7.4"
		  ::= { lapbOperEntry 7 }

	  lapbOperN2RxmitCount    OBJECT-TYPE
		  SYNTAX  INTEGER (0..65535)
		  ACCESS  read-only
		  STATUS  mandatory
		  DESCRIPTION
			  "The current N2 retry counter used for this
			  interface.  This specifies the number of
			  times a PDU will be resent after the T1
			  timer expires without an acknowledgement for
			  the PDU."
		  REFERENCE "ISO 7776 section 5.7.2"
		  ::= { lapbOperEntry 8 }

	  lapbOperT1AckTimer      OBJECT-TYPE
		  SYNTAX  PositiveInteger
		  ACCESS  read-only
		  STATUS  mandatory
		  DESCRIPTION
			  "The current T1 timer for this interface.
			  This specifies the maximum time in
			  Milliseconds to wait for acknowledgment of a
			  PDU."
		  REFERENCE "ISO 7776 section 5.7.1.1"
		  ::= { lapbOperEntry 9 }

	  lapbOperT2AckDelayTimer         OBJECT-TYPE
		  SYNTAX  PositiveInteger
		  ACCESS  read-only
		  STATUS  mandatory


		  DESCRIPTION
			  "The current T2 timer for this interface.
			  This specifies the maximum time in
			  Milliseconds to wait before sending an
			  acknowledgment for a sequenced PDU.  A value
			  of zero means there will be no delay in
			  acknowledgement generation."
		  REFERENCE "ISO 7776 section 5.7.1.2"
		  ::= { lapbOperEntry 10 }

	  lapbOperT3DisconnectTimer OBJECT-TYPE
		  SYNTAX  PositiveInteger
		  ACCESS  read-only
		  STATUS  mandatory
		  DESCRIPTION
			  "The current T3 timer for this interface.
			  This specifies the time in Milliseconds to
			  wait before considering the link
			  disconnected.  A value of zero indicates the
			  link will be considered disconnected upon
			  completion of the frame exchange to
			  disconnect the link."
		  REFERENCE "ISO 7776 section 5.7.1.3"
		  ::= { lapbOperEntry 11 }

	  lapbOperT4IdleTimer OBJECT-TYPE
		  SYNTAX  PositiveInteger
		  ACCESS  read-write
		  STATUS  mandatory
		  DESCRIPTION
			  "The current T4 timer for this interface.
			  This specifies the maximum time in
			  Milliseconds to allow without frames being
			  exchanged on the data link.  A value of
			  2147483647 indicates no idle timer is being
			  kept."
		  REFERENCE "ISO 7776 section 5.7.1.4"
		  ::= { lapbOperEntry 12 }

	  lapbOperPortId OBJECT-TYPE
		  SYNTAX  OBJECT IDENTIFIER
		  ACCESS  read-only
		  STATUS  mandatory
		  DESCRIPTION
			  "This object identifies an instance of the
			  index object in the first group of objects
			  in the MIB specific to the physical device
			  or interface used to send and receive


			  frames.  If an agent does not support any
			  such objects, it should return nullSpec
			  OBJECT IDENTIFIER {0 0}."
		  ::= { lapbOperEntry 13 }

	  lapbOperProtocolVersionId       OBJECT-TYPE
		  SYNTAX  OBJECT IDENTIFIER
		  ACCESS  read-only
		  STATUS  mandatory
		  DESCRIPTION
			  "This object identifies the version of the
			  lapb protocol implemented by this
			  interface."
		  ::= { lapbOperEntry 14 }

	  -- ###########################################################
	  --                      LAPB    Flow Table
	  -- ###########################################################

	  -- Support of the lapbFlowTable is mandatory for all
	  -- agents of systems that implement LAPB.

	  lapbFlowTable OBJECT-TYPE
		  SYNTAX  SEQUENCE OF LapbFlowEntry
		  ACCESS  not-accessible
		  STATUS  mandatory
		  DESCRIPTION
			  "This table defines the objects recorded by
			  LAPB to provide information about the
			  traffic flow through the interface."
		  ::= { lapbext 4  }

	  lapbFlowEntry OBJECT-TYPE
		  SYNTAX  LapbFlowEntry
		  ACCESS  not-accessible
		  STATUS  mandatory
		  DESCRIPTION
			  "The information regarding the effects of
			  flow controls in LAPB."
		   INDEX { lapbFlowIfIndex }
		  ::= { lapbFlowTable 1 }

	  LapbFlowEntry ::= SEQUENCE {
		  lapbFlowIfIndex
			  IfIndexType,
		  lapbFlowStateChanges
			  Counter,


		  lapbFlowChangeReason
			  INTEGER,
		  lapbFlowCurrentMode
			  INTEGER,
		  lapbFlowBusyDefers
			  Counter,
		  lapbFlowRejOutPkts
			  Counter,
		  lapbFlowRejInPkts
			  Counter,
		  lapbFlowT1Timeouts
			  Counter,
		  lapbFlowFrmrSent
		  OCTET STRING,
		  lapbFlowFrmrReceived
			  OCTET STRING,
		  lapbFlowXidReceived
			  OCTET STRING
		  }

	  lapbFlowIfIndex OBJECT-TYPE
		  SYNTAX  IfIndexType
		  ACCESS  read-only
		  STATUS  mandatory
		  DESCRIPTION
			  "The ifIndex value for the LAPB Interface."
		  ::= { lapbFlowEntry 1 }

	  lapbFlowStateChanges OBJECT-TYPE
		  SYNTAX  Counter
		  ACCESS  read-only
		  STATUS  mandatory
		  DESCRIPTION
			  "The number of LAPB State Changes, including
			  resets."
		  ::= { lapbFlowEntry 2 }

	  lapbFlowChangeReason OBJECT-TYPE
		  SYNTAX  INTEGER {
			  notStarted (1),    -- Initial state
			  abmEntered (2),    -- SABM or UA
			  abmeEntered (3),   -- SABME or UA
			  abmReset (4),      -- SABM in ABM
			  abmeReset (5),     -- SABME in ABME
			  dmReceived (6),    -- DM Response
			  dmSent (7),        -- DM sent
			  discReceived (8),  -- DISC Response
			  discSent (9),      -- DISC Sent


			  frmrReceived (10), -- FRMR Received
			  frmrSent (11),     -- FRMR Sent
			  n2Timeout (12),    -- N2 Timer Expired
			  other (13)
			    }
		  ACCESS  read-only
		  STATUS  mandatory
		  DESCRIPTION
			  "The reason for the most recent incrementing
			  of lapbFlowStateChanges.  A DM or DISC frame
			  generated to initiate link set-up does not
			  alter this object.  When the MIB-II object
			  ifOperStatus does not have a value of
			  testing, there exists a correlation between
			  this object and ifOperStatus.  IfOperStatus
			  will have a value of up when this object
			  contains:  abmEntered, abmeEntered,
			  abmReset, or abmeReset.  IfOperStatus will
			  have a value of down when this object has a
			  value of notStarted, or dmReceived through
			  n2Timeout.  There is no correlation when
			  this object has the value other."
		  ::= { lapbFlowEntry 3 }

	  lapbFlowCurrentMode OBJECT-TYPE
		  SYNTAX  INTEGER {
			  disconnected (1),
				  -- initial state or DISC received

			  linkSetup (2),
				  -- SABM sent

			  frameReject (3),
				  -- Invalid frame received and
				  -- FRMR sent

			  disconnectRequest (4),
				  -- DISC sent

			  informationTransfer (5),
				  -- normal information transfer state
				  -- SABM(E) sent and UA received, or
				  -- SABM(E) received and UA sent

			  rejFrameSent (6),
				  -- invalid NS received and REJ sent

			  waitingAcknowledgement (7),


				  -- T1 expired and RR sent

			  stationBusy (8),
				  -- RNR sent

			  remoteStationBusy (9),
				  -- RNR received

			  bothStationsBusy (10),
				  -- RNR received and RNR sent

			  waitingAckStationBusy (11),
				  -- T1 expired, RNR sent

			  waitingAckRemoteBusy (12),
				  -- T1 expired, RNR received

			  waitingAckBothBusy (13),
				  -- T1 expired, RNR sent,
				  -- and RNR received

			  rejFrameSentRemoteBusy (14),
				  -- REJ sent and RNR received

			  xidFrameSent (15),
				  -- XID frame sent

			  error (16),
				  -- An error state other than
				  -- a one defined above

			  other (17)
				  --  A state not listed above
			    }
		  ACCESS  read-only
		  STATUS  mandatory
		  DESCRIPTION
			  "The current condition of the conversation."
		  ::= { lapbFlowEntry 4 }

	  lapbFlowBusyDefers OBJECT-TYPE
		  SYNTAX  Counter
		  ACCESS  read-only
		  STATUS  mandatory
		  DESCRIPTION
			  "The number of times this device was unable
			  to transmit a frame due to a perceived
			  remote busy condition.  Busy conditions can


			  result from the receipt of an RNR from the
			  remote device, the lack of valid sequence
			  number space (window saturation), or other
			  conditions."
		  ::= { lapbFlowEntry 5 }

	  lapbFlowRejOutPkts OBJECT-TYPE
		  SYNTAX  Counter
		  ACCESS  read-only
		  STATUS  mandatory
		  DESCRIPTION
			  "The number of REJ or SREJ frames sent by
			  this station."
		  ::= { lapbFlowEntry 6 }

	  lapbFlowRejInPkts OBJECT-TYPE
		  SYNTAX  Counter
		  ACCESS  read-only
		  STATUS  mandatory
		  DESCRIPTION
			  "The number of REJ or SREJ frames received
			  by this station."
		  ::= { lapbFlowEntry 7 }

	  lapbFlowT1Timeouts OBJECT-TYPE
		  SYNTAX  Counter
		  ACCESS  read-only
		  STATUS  mandatory
		  DESCRIPTION
			  "The number of times a re-transmission was
			  effected by the T1 Timer expiring."
		  ::= { lapbFlowEntry 8 }

	  lapbFlowFrmrSent OBJECT-TYPE
		  SYNTAX  OCTET STRING (SIZE (0..7))
		  ACCESS  read-only
		  STATUS  mandatory
		  DESCRIPTION
			  "The Information Field of the FRMR most
			  recently sent.  If no FRMR has been sent
			  (the normal case) or the information isn't
			  available, this will be an OCTET STRING of
			  zero length."
		  REFERENCE "ISO 7776 Section 4.3.9, tables 7 and 8"
		  ::= { lapbFlowEntry 9 }

	  lapbFlowFrmrReceived OBJECT-TYPE
		  SYNTAX  OCTET STRING (SIZE (0..7))


		  ACCESS  read-only
		  STATUS  mandatory
		  DESCRIPTION
			  "The Information Field of the FRMR most
			  recently received.  If no FRMR has been
			  received (the normal case) or the
			  information isn't available, this will be an
			  OCTET STRING of zero length."
		  REFERENCE "ISO 7776 Section 4.3.9, tables 7 and 8"
		  ::= { lapbFlowEntry 10 }

	  lapbFlowXidReceived OBJECT-TYPE
		  SYNTAX  OCTET STRING (SIZE (0..8206))
		  ACCESS  read-only
		  STATUS  mandatory
		  DESCRIPTION
			  "The Information Field of the XID frame most
			  recently received.  If no XID frame has been
			  received, this will be an OCTET STRING of
			  zero length."
		  REFERENCE "ISO 8885"
		  ::= { lapbFlowEntry 11 }


	  -- The following describes some of the MIB-II interface
	  -- objects and their relationship with the objects in this
	  -- MIB extension.

	  -- ifDescr:  describes the interface.   It should include
	  -- identification information for the physical line and a
	  -- description of the network.  For connections to PDNs,
	  -- it should name the PDN.

	  -- ifMtu: the maximum number of octets an upper layer can
	  -- pass to this interface as a single frame.

	  -- ifSpeed:


	  -- ifAdminStatus:

	  -- ifOperStatus:

	  -- ifLastChange: the last time the state of the interface
	  -- changed.  A reset is considered an instantaneous change to
	  -- the ndm state and back to abm or abme.  This will be the
	  -- last time that lapbFlowChangeReason and lapbFlowChanges
	  -- changed.

	  -- ifInOctets: contains the number of octets
	  -- received from the peer LAPB including FCS.

	  -- ifInUcastPkts: contains the number of I-frames delivered
	  -- by this interface to a higher layer interface.

	  -- ifInDiscards: contains the number of received
	  -- frames discarded because of internal conditions
	  -- (such as lack of buffering).

	  -- ifInErrors: contains the number of Invalid frames received.
	  -- This does not have any relationship with the number REJ,
	  -- or RNR frames sent or received.

	  -- ifInUnknownProtos: contains the number of frames
	  -- that were correct but were dropped because they
	  -- were inappropriate for the current state.  This
	  -- includes an invalid Poll bit, an unknown address,
	  -- or other condition such as an RNR when connection
	  -- not established.  This also includes the number of
	  -- DISC or other frames that were ignored because the
	  -- link was not established and this interface was not
	  -- configured to perform link setup on that type frame.

	  -- ifOutOctets: number of octets sent to peer including
	  -- FCS octets.

	  -- ifOutUcastPkts: number of I-frames received from
	  -- a higher layer for transmission to peer.

	  -- ifOutDiscards: number of frames to be sent that were
	  -- dropped due to internal conditions such as buffering etc.

	  -- ifOutErrors: number of transmissions that failed
	  -- due to errors or were considered invalid by the receiver.
	  -- This does not have any relationship with the number REJ,
	  -- or RNR frames sent or received.


	  -- ifOutQLen: number of frames waiting to be transmitted.

	  -- This MIB does not provide any support for:
	  --      Multilink procedure (MLP) in ISO 7776 section 6
	  --      LLC Pbit timer
	  --      LLC REJ timer
	  --      LLC Busy State Timer 7.8.1.4

	  -- ###########################################################



lapbTrapBandwidthShortage	TRAP-TYPE
	ENTERPRISE	eicon
	VARIABLES	{ lapbBandwidthIndex , lapbBandwidthRxInUse,
			lapbBandwidthTxInUse, lapbBandwidthTrapStatus }
	DESCRIPTION
		"This trap indicates that the amount of bandwidth used on the
		specified port has risen above lapbBandwidthHigh percent over
		lapbBandwidthNumPeriods of lapbBandwidthSecs. The next two
		parameters indicate the percentage of the total bandwidth used in
		each direction (Transmitting or Receiving) over the last
		lapbBandwidthSecs number of seconds. The final parameter indicates
		the direction(s) in which the bandwidth threshold has been
		exceeded"
	::= 411

lapbTrapBandwidthClear	TRAP-TYPE
	ENTERPRISE	eicon 
	VARIABLES	{ lapbBandwidthIndex , lapbBandwidthRxInUse,
			lapbBandwidthTxInUse, lapbBandwidthTrapStatus }
	DESCRIPTION	
		"This trap indicates that the condition causing a previous
		lapbTrapBandwidthShortage no longer applies; in particular that
		the bandwidth being used on the specified port has dropped to below
		lapbBandwidthLow percent over the last lapbBandwidthSecs number of
		seconds The final parameter indicates the direction(s) in which the
		bandwidth exceeded condition has been cleared"
	::= 412



END
