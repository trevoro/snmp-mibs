NTNTECH-SYSTEM-OBJECTS-IDENTIFIER-MIB DEFINITIONS ::= BEGIN    

--	**************************************************************   
--  Enterprise:
--   	Paradyne Corporation. 
--
--  ContactInfo:
--    	Paradyne Corporation
--     	8545 126th Avenue North
--     	Largo, FL 33773
--     	phone: +1 (727) 530-2000
--     	email: support@paradyne.com 
--		www:   http://www.nettonet.com/support/
--
--  Description:
--    	ntntech-sytem-objects-identifier-MIB.my
--    	Revision: 1.02.02
--    	Part Number: xx-xxxx-xx
--    	Date: November 17, 2004
--    
--    	This module provides explicit definitions for the Net to
--		Net Technologies naming	tree below:
--    
--    	nettonettech { enterprises 8059 }
--    
--    	This module will be extended, as additional sub-sections
--    	of this naming tree are defined.
--
--  Disclaimer:
--	   	This is an extremely preliminary MIB module and is subject
--		to change at any time therefore, use at your own risk.
--    
-- 	Copyright (c) 2000 - 2004 by Paradyne Corporation.
-- 	All rights reserved.          

-- **************************************************************
IMPORTS  
	ntntechSystemObjects						FROM NTNTECH-ROOT-MIB 	        
   	OBJECT-TYPE, MODULE-IDENTITY				FROM SNMPv2-SMI;
-- **************************************************************        

ntntechSystemObjectsIdentifierMIB MODULE-IDENTITY  
    LAST-UPDATED "0411170200Z"  -- November 17, 2004
    ORGANIZATION "Paradyne Corporation"
    CONTACT-INFO
        "Paradyne Corporation
        8545 126th Avenue North
        Largo, FL 33773   
     	
        phone: +1 (727) 530-2000
        email: support@paradyne.com 
        www:   http://www.nettonet.com/support/"

    DESCRIPTION
          "As per MIB-2, the system group- this MIB describes the vendor's
          authoritative identification of the network management subsystem
          contained in this entity." 
          
    REVISION   "0208281200Z"
    DESCRIPTION
          "New Release - v1.01.00"    
          
    REVISION   "0209200753Z"
    DESCRIPTION
          "Add ADSL uDSLAM OID [AuD8000-12]" 
          
    REVISION   "0210220200Z"
    DESCRIPTION
          "New Release - v1.01.01"               
          
    REVISION   "0310230804Z"
    DESCRIPTION
          "Add new branch- sysObjIdNetworkExtender
          and associated leaves- ane8420,sne2040p,sne2040s"    
          
   	REVISION     "0311140842Z"
    DESCRIPTION
      	"Added iPD12000E, and iPD4000E to the sysObjIdiPDSLAM OID."  
     
    REVISION  "0404271026Z"
    DESCRIPTION
    	"Changed and subsequently added to the network extender table.
    	Added sne2040p and sne2040s" 
    	
    REVISION "0410110945Z"
    DESCRIPTION
    	"Updated the copyright and reference to Paradyne."

    REVISION "0411171101Z"
    DESCRIPTION
    	" New Release -- version 1.02.01"
          
::= { ntntechSystemObjects 1 }   

sysObjIdentifierMIBObjects OBJECT IDENTIFIER ::= { ntntechSystemObjectsIdentifierMIB 1 }   

sysObjIdiPDSLAM OBJECT IDENTIFIER ::= { sysObjIdentifierMIBObjects 1 }

ipd12000 OBJECT-TYPE
   	SYNTAX      OBJECT IDENTIFIER
   	MAX-ACCESS  read-only
   	STATUS      current
   	DESCRIPTION
           "The Paradyne Corporation authoritative identification for the
           IPD12000 DSLAM."
   	::= { sysObjIdiPDSLAM 1 }    
   	
ipd4000 OBJECT-TYPE
   	SYNTAX      OBJECT IDENTIFIER
   	MAX-ACCESS  read-only
   	STATUS      current
   	DESCRIPTION
           "The Paradyne Corporation authoritative identification for the
           IPD4000 DSLAM."
   	::= { sysObjIdiPDSLAM 2 }    
   	
ipd12000E OBJECT-TYPE
   	SYNTAX      OBJECT IDENTIFIER
   	MAX-ACCESS  read-only
   	STATUS      current
   	DESCRIPTION
           "The Paradyne Corporation authoritative identification for the
           IPD12000E DSLAM."
   	::= { sysObjIdiPDSLAM 3 }    
   	
ipd4000E OBJECT-TYPE
   	SYNTAX      OBJECT IDENTIFIER
   	MAX-ACCESS  read-only
   	STATUS      current
   	DESCRIPTION
           "The Paradyne Corporation authoritative identification for the
           IPD4000E DSLAM."
   	::= { sysObjIdiPDSLAM 4 }    
   	
sysObjIdMiniDSLAM OBJECT IDENTIFIER ::= { sysObjIdentifierMIBObjects 2 } 

smd2000p12 OBJECT-TYPE
   	SYNTAX      OBJECT IDENTIFIER
   	MAX-ACCESS  read-only
   	STATUS      current
   	DESCRIPTION
           "The Paradyne Corporation authoritative identification for the
           SMD2000 12-port SDSL Mini DSLAM running CAP line encoding."
   	::= { sysObjIdMiniDSLAM 1 }    
   	
amd8000p12 OBJECT-TYPE
   	SYNTAX      OBJECT IDENTIFIER
   	MAX-ACCESS  read-only
   	STATUS      current
   	DESCRIPTION
           "The Paradyne Corporation authoritative identification for the
           AMD8000 12-port ADSL Mini DSLAM."
   	::= { sysObjIdMiniDSLAM 2 }  
   	
smd2000p24 OBJECT-TYPE
   	SYNTAX      OBJECT IDENTIFIER
   	MAX-ACCESS  read-only
   	STATUS      current
   	DESCRIPTION
           "The Paradyne Corporation authoritative identification for the
           SMD2000 24-port SDSL Mini DSLAM."
   	::= { sysObjIdMiniDSLAM 3 } 
   	
smd2000Qp12 OBJECT-TYPE
   	SYNTAX      OBJECT IDENTIFIER
   	MAX-ACCESS  read-only
   	STATUS      current
   	DESCRIPTION
           "The Paradyne Corporation authoritative identification for the
           SMD2000 12-port SDSL Mini DSLAM running 2B1Q line encoding."
   	::= { sysObjIdMiniDSLAM 4 }   
   	
smd2000Gp12 OBJECT-TYPE
   	SYNTAX      OBJECT IDENTIFIER
   	MAX-ACCESS  read-only
   	STATUS      current
   	DESCRIPTION
           "The Paradyne Corporation authoritative identification for the
           SMD2000 12-port SDSL Mini DSLAM running G.SHDSL line encoding."
   	::= { sysObjIdMiniDSLAM 5 }  

sysObjIdMicroDSLAM OBJECT IDENTIFIER ::= { sysObjIdentifierMIBObjects 3 } 

sud2011p12T OBJECT-TYPE
   	SYNTAX      OBJECT IDENTIFIER
   	MAX-ACCESS  read-only
   	STATUS      current
   	DESCRIPTION
           "The Paradyne Corporation authoritative identification for the
           SuD2011 12-port [10/100,T1] Micro DSLAM."
   	::= { sysObjIdMicroDSLAM 1 }    
   	
sud2011p12E OBJECT-TYPE
   	SYNTAX      OBJECT IDENTIFIER
   	MAX-ACCESS  read-only
   	STATUS      current
   	DESCRIPTION
           "The Paradyne Corporation authoritative identification for the
           SuD2011 12-port [10/100,E1] Micro DSLAM."
   	::= { sysObjIdMicroDSLAM 2 }  
   	
sud2003p12T OBJECT-TYPE
   	SYNTAX      OBJECT IDENTIFIER
   	MAX-ACCESS  read-only
   	STATUS      current
   	DESCRIPTION
           "The Paradyne Corporation authoritative identification for the
           SuD2003 12-port [T1,T1,T1] Micro DSLAM."
   	::= { sysObjIdMicroDSLAM 3 }
   	
sud2003p12E OBJECT-TYPE
   	SYNTAX      OBJECT IDENTIFIER
   	MAX-ACCESS  read-only
   	STATUS      current
   	DESCRIPTION
           "The Paradyne Corporation authoritative identification for the
           SuD2003 12-port [E1,E1,E1] Micro DSLAM."
   	::= { sysObjIdMicroDSLAM 4 }   
   	
sud2011p6T OBJECT-TYPE
   	SYNTAX      OBJECT IDENTIFIER
   	MAX-ACCESS  read-only
   	STATUS      current
   	DESCRIPTION
           "The Paradyne Corporation authoritative identification for the
           SuD2011 6-port [10/100,T1] Micro DSLAM."
   	::= { sysObjIdMicroDSLAM 5 }    
   	
sud2011p6E OBJECT-TYPE
   	SYNTAX      OBJECT IDENTIFIER
   	MAX-ACCESS  read-only
   	STATUS      current
   	DESCRIPTION
           "The Paradyne Corporation authoritative identification for the
           SuD2011 6-port [10/100,E1] Micro DSLAM."
   	::= { sysObjIdMicroDSLAM 6 } 
   	
sud2002p6T OBJECT-TYPE
   	SYNTAX      OBJECT IDENTIFIER
   	MAX-ACCESS  read-only
   	STATUS      current
   	DESCRIPTION
           "The Paradyne Corporation authoritative identification for the
           SuD2011 6-port [T1,T1] Micro DSLAM."
   	::= { sysObjIdMicroDSLAM 7 }    
   	
sud2002p6E OBJECT-TYPE
   	SYNTAX      OBJECT IDENTIFIER
   	MAX-ACCESS  read-only
   	STATUS      current
   	DESCRIPTION
           "The Paradyne Corporation authoritative identification for the
           SuD2011 6-port [E1,E1] Micro DSLAM."
   	::= { sysObjIdMicroDSLAM 8 }  
   	        
sud2000p12 OBJECT-TYPE
   	SYNTAX      OBJECT IDENTIFIER
   	MAX-ACCESS  read-only
   	STATUS      current
   	DESCRIPTION
           "The Paradyne Corporation authoritative identification for the
           SuD2000 12-port Micro DSLAM."
   	::= { sysObjIdMicroDSLAM 9 }     
   	
aud8000p12 OBJECT-TYPE
   	SYNTAX      OBJECT IDENTIFIER
   	MAX-ACCESS  read-only
   	STATUS      current
   	DESCRIPTION
           "The Paradyne Corporation authoritative identification for the
           AuD8000 12-port Micro DSLAM."
   	::= { sysObjIdMicroDSLAM 10 }            

pdyn4929 OBJECT-TYPE
   	SYNTAX      OBJECT IDENTIFIER
   	MAX-ACCESS  read-only
   	STATUS      current
   	DESCRIPTION
           "The Paradyne Corporation authoritative identification for the
           4929 24-port ADSL2+ Micro DSLAM."
   	::= { sysObjIdMicroDSLAM 11 }            
   	
sysObjIdNetworkExtender OBJECT IDENTIFIER ::= { sysObjIdentifierMIBObjects 4 }   

ane8420 OBJECT-TYPE
   	SYNTAX      OBJECT IDENTIFIER
   	MAX-ACCESS  read-only
   	STATUS      current
   	DESCRIPTION
           "The Paradyne Corporation authoritative identification for the
           ANE8420 Network Extender."
   	::= { sysObjIdNetworkExtender 1 }    
   	
sne2000-2020p OBJECT-TYPE
   	SYNTAX      OBJECT IDENTIFIER
   	MAX-ACCESS  read-only
   	STATUS      current
   	DESCRIPTION
           "The Paradyne Corporation authoritative identification for the
           SNE2000p and SNE2020p (provider) Network Extender."
   	::= { sysObjIdNetworkExtender 2 }  
   	
sne2000-2020s OBJECT-TYPE
   	SYNTAX      OBJECT IDENTIFIER
   	MAX-ACCESS  read-only
   	STATUS      current
   	DESCRIPTION
           "The Paradyne Corporation authoritative identification for the
           SNE2000s and SNE2020s(subscriber) Network Extender."
   	::= { sysObjIdNetworkExtender 3 }               
   	
sne2040p OBJECT-TYPE
   	SYNTAX      OBJECT IDENTIFIER
   	MAX-ACCESS  read-only
   	STATUS      current
   	DESCRIPTION
           "The Paradyne Corporation authoritative identification for the
           SNE2040p (provider) Network Extender."
   	::= { sysObjIdNetworkExtender 4 }

sne2040s OBJECT-TYPE
   	SYNTAX      OBJECT IDENTIFIER
   	MAX-ACCESS  read-only
   	STATUS      current
   	DESCRIPTION
           "The Paradyne Corporation authoritative identification for the
           SNE2040s (subscriber) Network Extender."
   	::= { sysObjIdNetworkExtender 5 }

   	
    
END
