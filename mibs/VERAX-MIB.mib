--    Verax Network Management System Enterprise MIB
--    Revision 18 Feb 2010

--    Copyright 2009-2010 Verax Systems
--    All rights reserved

VERAX-MIB DEFINITIONS ::= BEGIN

    IMPORTS
	enterprises, MODULE-IDENTITY
		FROM RFC1155-SMI;

    veraxMIB MODULE-IDENTITY
       LAST-UPDATED "201211051200Z"
       ORGANIZATION "Verax Systems"
       CONTACT-INFO
           "Verax Systems Corp.
            E-mail: office@veraxsystems.com"
       DESCRIPTION
           "This MIB is the base Verax System MIB."
		::= { enterprises 21340 }   
		   
      products      	 OBJECT IDENTIFIER ::= { veraxMIB 1 }
	  veraxnms			 OBJECT IDENTIFIER ::= { products 2 }
	  
END
