DNSHOTEXT-MIB 

   --FORCE-INCLUDE <mib.h>
   --FORCE-INCLUDE <snmpdefs.h>
   --FORCE-INCLUDE <snmpstat.h>
   --FORCE-INCLUDE "mibproto.h"
 
	DEFINITIONS ::= BEGIN

	IMPORTS
		MODULE-IDENTITY, OBJECT-TYPE, Integer32, Counter32
			FROM SNMPv2-SMI
		DisplayString
			FROM SNMPv2-TC
		dnshotExt
			FROM APENT-MIB;

--DNSHOTEXT MIB

    apDnshotExtMib MODULE-IDENTITY
	   LAST-UPDATED "9710092000Z" -- Thu October 9 20:00:00 EST 1997
	   ORGANIZATION "ArrowPoint Communications Inc."
	   CONTACT-INFO
	   "                      
	   Postal:               ArrowPoint Communications Inc.
				                 50 Nagog Park
				                 Acton, Massachusetts 01720
	   Tel:                   +1 978-206-3000  option 1
	   E-Mail:                support@arrowpoint.com"
       DESCRIPTION
	  "The MIB module used to describe the ArrowPoint Domain Hotlist table"
      ::= { dnshotExt 1}


apDnshotExtEnable OBJECT-TYPE
	  SYNTAX          INTEGER {
							  enable(1),
							  disable(0)
					  		  }
  	  MAX-ACCESS      read-write
      STATUS          current
      DESCRIPTION
      "Enable or Disable the Domain Name hotlist"
	  ::= { dnshotExt 2}

apDnshotExtSize OBJECT-TYPE
	SYNTAX          Integer32 (1..100)
	MAX-ACCESS      read-create
    STATUS          current
    DESCRIPTION
      "Total number of domain hotlist entries which will be maintained."
	DEFVAL { 10 }
	::= { dnshotExt 3}

apDnshotExtInterval OBJECT-TYPE
	SYNTAX          Integer32 (1..60)
	MAX-ACCESS      read-write
    STATUS          current
    DESCRIPTION
      "The interval in units of minutes used to refreshing the domain hotlist."
	DEFVAL { 1 }
	::= { dnshotExt 4}

apDnshotExtThreshold OBJECT-TYPE
	SYNTAX          Integer32 (0..65535)
	MAX-ACCESS      read-create
	STATUS  		current
	DESCRIPTION     
		"The threshold under which an item is not considered hot."
	DEFVAL { 0 }
	::= { dnshotExt 5}

apDnshotExtTable OBJECT-TYPE
	SYNTAX          SEQUENCE OF APDnshotEntry
	MAX-ACCESS      not-accessible
	STATUS          current
	DESCRIPTION
		"A list of ACLs."
	::= { dnshotExt 6 }

apDnshotEntry OBJECT-TYPE
	SYNTAX          APDnshotEntry
	MAX-ACCESS      not-accessible
	STATUS          current	
	DESCRIPTION	
		"A set of parameters which describe a hot domain name."
	INDEX   { apDnshotIndex }
	::= { apDnshotExtTable 1 }

APDnshotEntry ::= SEQUENCE {
		apDnshotIndex             Integer32,
		apDnshotName              DisplayString,
		apDnshotHits			  Counter32
}

apDnshotIndex    OBJECT-TYPE
	SYNTAX			Integer32 (0..100)
	MAX-ACCESS      read-only
	STATUS  		current
	DESCRIPTION     
		"The Dns Hotlist Table Record Index"
	::= {apDnshotEntry 1}

apDnshotName OBJECT-TYPE
	SYNTAX          DisplayString (SIZE(1..31))
	MAX-ACCESS      read-only
	STATUS          current
	DESCRIPTION     
			"The hot domain name."
	::= {apDnshotEntry 2}

apDnshotHits OBJECT-TYPE
	SYNTAX          Counter32
	MAX-ACCESS      read-only
	STATUS  		current
	DESCRIPTION     
		"Total number of frames moved by this service for this content rule."
	::= {apDnshotEntry 3}

END
