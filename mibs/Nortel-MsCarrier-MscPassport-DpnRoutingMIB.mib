Nortel-MsCarrier-MscPassport-DpnRoutingMIB
DEFINITIONS ::= BEGIN



IMPORTS

      OBJECT-TYPE
   FROM RFC-1212

      mscPassportMIBs
   FROM Nortel-MsCarrier-MscPassport-UsefulDefinitionsMIB

      RowPointer,
      DisplayString,
      StorageType,
      RowStatus,
      Integer32,
      Unsigned32
   FROM Nortel-MsCarrier-MscPassport-StandardTextualConventionsMIB

      AsciiString,
      NonReplicated,
      PassportCounter64,
      AsciiStringIndex
   FROM Nortel-MsCarrier-MscPassport-TextualConventionsMIB

      mscRtgIndex,
      mscRtg
   FROM Nortel-MsCarrier-MscPassport-BaseRoutingMIB;




-- LAST-UPDATED   "9909010000Z"
-- ORGANIZATION   "Nortel Networks"
-- CONTACT-INFO   "
--         Nortel Carrier Data Network Management
--         
--         Postal:       P.O. Box 3511, Station C 
--                       Ottawa, Ontario 
--                       Canada  K1Y 4H7
--         
--         via the WEB:  http://www.nortelnetworks.com  
--                       select 'Contact Us' from the menu
--          
--         via phone:    1-800-4NORTEL"
-- DESCRIPTION
--    "The module describing the Nortel MsCarrier MscPassport
--     DpnRouting Enterprise MIB."

dpnRoutingMIB OBJECT IDENTIFIER ::= { mscPassportMIBs 21 }










-- Routing DpnAddressPlan 
-- This component is a subcomponent of Routing. It resides on all 
-- Passport nodes that carry DPN traffic and is responsible for 
-- maintaining the routing information required to route this traffic.
-- 
-- It is required on nodes that (i) support gateways to RMs and/or 
-- AMs, (ii) nodes that source and/or sink DPN traffic (for example, 
-- nodes which support VC end points), and (iii) intermediary nodes 
-- that simply carry DPN traffic.

mscRtgDpn OBJECT IDENTIFIER ::= { mscRtg 4 }



mscRtgDpnRowStatusTable OBJECT-TYPE
   SYNTAX     SEQUENCE OF MscRtgDpnRowStatusEntry
   ACCESS     not-accessible
   STATUS     mandatory
   DESCRIPTION
     "This entry controls the addition and deletion of 
      mscRtgDpn components."
::= { mscRtgDpn 1 }

mscRtgDpnRowStatusEntry OBJECT-TYPE
   SYNTAX     MscRtgDpnRowStatusEntry
   ACCESS     not-accessible
   STATUS     mandatory
   DESCRIPTION
     "A single entry in the table represents a single 
      mscRtgDpn component."
   INDEX {
      mscRtgIndex,
      mscRtgDpnIndex }
::= { mscRtgDpnRowStatusTable 1 }

MscRtgDpnRowStatusEntry ::= SEQUENCE {
   mscRtgDpnRowStatus
      RowStatus,
   mscRtgDpnComponentName
      DisplayString,
   mscRtgDpnStorageType
      StorageType,
   mscRtgDpnIndex
      NonReplicated }

mscRtgDpnRowStatus OBJECT-TYPE
   SYNTAX     RowStatus 
   ACCESS     read-only
   STATUS     mandatory
   DESCRIPTION
     "This variable is used as the basis for SNMP naming of
      mscRtgDpn components.
      These components cannot be added nor deleted."
::= { mscRtgDpnRowStatusEntry 1 }

mscRtgDpnComponentName OBJECT-TYPE
   SYNTAX     DisplayString 
   ACCESS     read-only
   STATUS     mandatory
   DESCRIPTION
     "This variable provides the component's string name for
      use with the ASCII Console Interface"
::= { mscRtgDpnRowStatusEntry 2 }

mscRtgDpnStorageType OBJECT-TYPE
   SYNTAX     StorageType 
   ACCESS     read-only
   STATUS     mandatory
   DESCRIPTION
     "This variable represents the storage type value for the
      mscRtgDpn tables."
::= { mscRtgDpnRowStatusEntry 4 }

mscRtgDpnIndex OBJECT-TYPE
   SYNTAX     NonReplicated 
   ACCESS     not-accessible
   STATUS     mandatory
   DESCRIPTION
     "This variable represents the index for the mscRtgDpn tables."
::= { mscRtgDpnRowStatusEntry 10 }

mscRtgDpnProvTable OBJECT-TYPE
   SYNTAX     SEQUENCE OF MscRtgDpnProvEntry
   ACCESS     not-accessible
   STATUS     mandatory
   DESCRIPTION
     "This group contains the provisioning data for the DpnAddressPlan. 
      Attributes in this group must be set to allow the DpnAddressPlan 
      component to function properly."
::= { mscRtgDpn 11 }

mscRtgDpnProvEntry OBJECT-TYPE
   SYNTAX     MscRtgDpnProvEntry
   ACCESS     not-accessible
   STATUS     mandatory
   DESCRIPTION
     "An entry in the mscRtgDpnProvTable."
   INDEX {
      mscRtgIndex,
      mscRtgDpnIndex }
::= { mscRtgDpnProvTable 1 }

MscRtgDpnProvEntry ::= SEQUENCE {
   mscRtgDpnLogicalNetworkNumber
      Unsigned32,
   mscRtgDpnRoutingId
      Unsigned32,
   mscRtgDpnModuleId
      Unsigned32,
   mscRtgDpnDelayMetricCutOff
      Unsigned32,
   mscRtgDpnThroughputMetricCutOff
      Unsigned32,
   mscRtgDpnForwardingPolicy
      INTEGER,
   mscRtgDpnDelayMetricRangeBoundary
      Unsigned32,
   mscRtgDpnTputMetricRangeBoundary
      Unsigned32 }

mscRtgDpnLogicalNetworkNumber OBJECT-TYPE
   SYNTAX     Unsigned32 (1..1)
   ACCESS     read-only
   STATUS     mandatory
   DESCRIPTION
     "This attribute specifies the Logical Network Number for the 
      DpnAddressPlan. Since only one instance of this component can 
      exist, this value is always set to one. It is provided here to be 
      consistent with other address plans and so that it can be queried."
   DEFVAL     { 1 }
::= { mscRtgDpnProvEntry 1 }

mscRtgDpnRoutingId OBJECT-TYPE
   SYNTAX     Unsigned32 (1..126)
   ACCESS     read-write
   STATUS     mandatory
   DESCRIPTION
     "This attribute specifies the Routing Identifier (RID) associated with 
      the Passport node.
      
      The RID is used to identify a group of one or more interconnected 
      Passport nodes (called a subnet) supporting the transport of DPN 
      traffic. Its value must be the same as that of the other Passport nodes 
      in this subnet and different from that of all RMs and other Passport 
      subnets in the network.
      
      The routingId must be set when a DpnAddressPlan component is 
      configured on an Passport node.
      
      Changing the value of the routingId will cause the node to restart."
::= { mscRtgDpnProvEntry 2 }

mscRtgDpnModuleId OBJECT-TYPE
   SYNTAX     Unsigned32 (1..1909)
   ACCESS     read-write
   STATUS     mandatory
   DESCRIPTION
     "This attribute specifies the Module Identifier (MID) associated with 
      the Passport node.
      
      The MID is used to identify an Passport node supporting the 
      transport of DPN traffic. Its value must be different from that of all 
      MIDs assigned to Passport nodes in this RID subnet (interconnected 
      Passport nodes sharing a RID) and AMs in clusters supported by 
      this subnet. If routing zones are used, it must also be unique from 
      all other MIDs in this zone.
      
      The moduleId must be set when a DpnAddressPlan component is 
      configured on an Passport node.
      
      Changing the value of the moduleId will cause the node to restart."
::= { mscRtgDpnProvEntry 3 }

mscRtgDpnDelayMetricCutOff OBJECT-TYPE
   SYNTAX     Unsigned32 (64..250)
   ACCESS     read-write
   STATUS     mandatory
   DESCRIPTION
     "This attribute specifies the delay metric value beyond which a 
      destination RID should be considered unreachable. That is, if a 
      delay metric to a RID is equal to or greater than this value then the 
      RID is considered to be unreachable in the delay class of service.
      
      Lowering this value has the effect of speeding up the detection of 
      the loss of reachability to a RID. It also reduces the amount of 
      Routing Table Update (RTU) traffic generated in this scenario. Care 
      must be taken to ensure that the value chosen is big enough for the 
      longest delay path in the network. 
      
      This attribute is optional; a default of 128 is used when it is not set. 
      It is recommended that all nodes in the network be provisioned with 
      the same cut off value."
   DEFVAL     { 128 }
::= { mscRtgDpnProvEntry 4 }

mscRtgDpnThroughputMetricCutOff OBJECT-TYPE
   SYNTAX     Unsigned32 (128..245)
   ACCESS     read-write
   STATUS     mandatory
   DESCRIPTION
     "This attribute specifies the throughput metric value beyond which a 
      destination RID should be considered unreachable. That is, if a 
      throughput metric to a RID is equal to or greater than this value 
      then the RID will be considered to be unreachable in the throughput 
      class of service.
      
      Lowering this value has the effect of speeding up the detection of 
      the loss of reachability to a RID. It also reduces the amount of 
      Routing Table Update (RTU) traffic generated in this scenario.Care 
      must be taken to ensure that the value chosen is big enough for the 
      longest throughput path in the network.
      
      This attribute is optional; a default of 245 is used when it is not set. 
      It is recommended that all nodes in the network be provisioned with 
      the same cut off value."
   DEFVAL     { 245 }
::= { mscRtgDpnProvEntry 5 }

mscRtgDpnForwardingPolicy OBJECT-TYPE
   SYNTAX     INTEGER  {
                 loadspread(0),
                 loadshare(1),
                 loadspreadFast(2) }
   ACCESS     read-write
   STATUS     mandatory
   DESCRIPTION
     "This attribute specifies the forwarding policy used by packet 
      forwarding to handle DPN traffic on a Passport module. 
      
      When this attribute is set to loadshare, DPN traffic is shared among 
      preferred links in a link group in proportion to the available 
      bandwidth on each link; the traffic is not forwarded in an order-
      preserved manner and needs resequencing at the destination, but the 
      available bandwidth in a link group is utilized efficiently.
      
      When this attribute is set to loadspread, DPN traffic is forwarded in 
      an order-preserved manner along a randomly selected route; the 
      traffic sticks to a particular link in a link group, and will not spill 
      over to other links in the link group unless there is congestion on 
      the selected link. 
      
      When this attribute is set to loadspreadFast, DPN traffic is 
      forwarded in an order-preserved manner along a randomly selected 
      route; the traffic sticks to a particular link in a link group, and will 
      not spill over to other links in the link group. Choosing this value 
      may improve throughput but traffic may be discarded in the 
      presence of congestion.
      
      It is recommended that all nodes in the network be provisioned with 
      the same forwarding policy."
   DEFVAL     { loadspread }
::= { mscRtgDpnProvEntry 6 }

mscRtgDpnDelayMetricRangeBoundary OBJECT-TYPE
   SYNTAX     Unsigned32 (0..2147483647)
   ACCESS     read-write
   STATUS     mandatory
   DESCRIPTION
     "This attribute specifies the total path delay metric below which the 
      variance value specified for delay COS and a low metric range is 
      used, and at or above which the variance value specified for delay 
      COS and a high metric range is used. 
      
      This attribute defaults to 0, so that the variance value specified for 
      delay COS and a high metric range is used for all delay paths. If this 
      attribute is set to 2147483647, the variance value specified for 
      delay COS and a low metric range is used for all delay paths."
   DEFVAL     { 0 }
::= { mscRtgDpnProvEntry 7 }

mscRtgDpnTputMetricRangeBoundary OBJECT-TYPE
   SYNTAX     Unsigned32 (0..2147483647)
   ACCESS     read-write
   STATUS     mandatory
   DESCRIPTION
     "This attribute specifies the total path throughput metric below which 
      the variance value specified for throughput COS and a low metric 
      range is used, and at or above which the variance value specified for 
      throughput COS and a high metric range is used. 
      
      This attribute defaults to 0, so that the variance value specified for 
      throughput COS and a high metric range is used for all delay paths. 
      If this attribute is set to 2147483647, the variance value specified 
      for throughput COS and a low metric range is used for all 
      throughput paths."
   DEFVAL     { 0 }
::= { mscRtgDpnProvEntry 8 }

mscRtgDpnConStatsTable OBJECT-TYPE
   SYNTAX     SEQUENCE OF MscRtgDpnConStatsEntry
   ACCESS     not-accessible
   STATUS     mandatory
   DESCRIPTION
     "This group of attributes provides statistics about the behavior of the 
      DpnAddressPlan component. The statistics concern the distribution 
      of routing information, required to support the routing of DPN 
      traffic, to all Passport nodes in the RID subnet."
::= { mscRtgDpn 13 }

mscRtgDpnConStatsEntry OBJECT-TYPE
   SYNTAX     MscRtgDpnConStatsEntry
   ACCESS     not-accessible
   STATUS     mandatory
   DESCRIPTION
     "An entry in the mscRtgDpnConStatsTable."
   INDEX {
      mscRtgIndex,
      mscRtgDpnIndex }
::= { mscRtgDpnConStatsTable 1 }

MscRtgDpnConStatsEntry ::= SEQUENCE {
   mscRtgDpnControlPktTx
      Unsigned32,
   mscRtgDpnControlPktRx
      Unsigned32,
   mscRtgDpnControlBytesTx
      Unsigned32,
   mscRtgDpnControlBytesRx
      Unsigned32,
   mscRtgDpnOutOfSequencePkt
      Unsigned32 }

mscRtgDpnControlPktTx OBJECT-TYPE
   SYNTAX     Unsigned32 (0..4294967295)
   ACCESS     read-only
   STATUS     mandatory
   DESCRIPTION
     "This attribute counts the total number of internal Passport DPN 
      control packets, originating from this node, sent to other Passport 
      nodes in the RID subnet. The packets contain DPN routing 
      information required by the DpnAddressPlan component to support 
      the transport of DPN traffic. The Packets received from a neighbor 
      node and forwarded to other neighbors are not counted. The counter 
      wraps around to zero when the maximum value is reached."
::= { mscRtgDpnConStatsEntry 1 }

mscRtgDpnControlPktRx OBJECT-TYPE
   SYNTAX     Unsigned32 (0..4294967295)
   ACCESS     read-only
   STATUS     mandatory
   DESCRIPTION
     "This attribute counts the total number of internal Passport DPN 
      control packets received from other Passport nodes in the RID 
      subnet. The packets contain DPN routing information required by 
      the DpnAddressPlan component to support the transport of DPN 
      traffic. The counter wraps around to zero when the maximum value 
      is reached."
::= { mscRtgDpnConStatsEntry 2 }

mscRtgDpnControlBytesTx OBJECT-TYPE
   SYNTAX     Unsigned32 (0..4294967295)
   ACCESS     read-only
   STATUS     mandatory
   DESCRIPTION
     "This attribute counts the total number of internal Passport DPN 
      control packet bytes, originating from the node, sent to other 
      Passport nodes in the RID subnet. The packets contain DPN routing 
      information required by the DpnAddressPlan component to support 
      the transport of DPN traffic. Packet bytes received from a neighbor 
      node and forwarded to other neighbors are not counted. The counter 
      wraps around to zero when the maximum value is reached."
::= { mscRtgDpnConStatsEntry 3 }

mscRtgDpnControlBytesRx OBJECT-TYPE
   SYNTAX     Unsigned32 (0..4294967295)
   ACCESS     read-only
   STATUS     mandatory
   DESCRIPTION
     "This attribute counts the total number of internal Passport DPN 
      control packet bytes received from other Passport nodes in the RID 
      subnet. The packets contain DPN routing information required by 
      the DpnAddressPlan component to support the transport of DPN 
      traffic. The counter wraps around to zero when the maximum value 
      is reached."
::= { mscRtgDpnConStatsEntry 4 }

mscRtgDpnOutOfSequencePkt OBJECT-TYPE
   SYNTAX     Unsigned32 (0..4294967295)
   ACCESS     read-only
   STATUS     mandatory
   DESCRIPTION
     "This attribute counts the total number of internal Passport DPN 
      control packets received and rejected. These packets contained old 
      sequence numbers. The packets contain DPN routing information 
      required by the DpnAddressPlan component to support the 
      transport of DPN traffic. The counter wraps around to zero when the 
      maximum value is reached."
::= { mscRtgDpnConStatsEntry 5 }

mscRtgDpnFwdStatsTable OBJECT-TYPE
   SYNTAX     SEQUENCE OF MscRtgDpnFwdStatsEntry
   ACCESS     not-accessible
   STATUS     mandatory
   DESCRIPTION
     "This group of attributes provides statistics for the traffic handled by 
      DPN packet forwarding on this module. The statistics can be used 
      to monitor the connectionless traffic profile on this module."
::= { mscRtgDpn 14 }

mscRtgDpnFwdStatsEntry OBJECT-TYPE
   SYNTAX     MscRtgDpnFwdStatsEntry
   ACCESS     not-accessible
   STATUS     mandatory
   DESCRIPTION
     "An entry in the mscRtgDpnFwdStatsTable."
   INDEX {
      mscRtgIndex,
      mscRtgDpnIndex }
::= { mscRtgDpnFwdStatsTable 1 }

MscRtgDpnFwdStatsEntry ::= SEQUENCE {
   mscRtgDpnTotalPackets
      PassportCounter64,
   mscRtgDpnThroughputPackets
      PassportCounter64,
   mscRtgDpnDelayPackets
      PassportCounter64,
   mscRtgDpnNormalReliabilityPackets
      PassportCounter64,
   mscRtgDpnHighReliabilityPackets
      PassportCounter64,
   mscRtgDpnDiscardNoRoute
      PassportCounter64,
   mscRtgDpnInterruptingPackets
      PassportCounter64,
   mscRtgDpnDiscardLpCongested
      PassportCounter64 }

mscRtgDpnTotalPackets OBJECT-TYPE
   SYNTAX     PassportCounter64 
   ACCESS     read-only
   STATUS     mandatory
   DESCRIPTION
     "This attribute counts the total number of delay and throughput 
      packets handled by DPN packet forwarding on this module. Note 
      that DPRS packets leaving the network at this module are not 
      counted. The counter wraps to zero when the maximum value is 
      exceeded."
::= { mscRtgDpnFwdStatsEntry 1 }

mscRtgDpnThroughputPackets OBJECT-TYPE
   SYNTAX     PassportCounter64 
   ACCESS     read-only
   STATUS     mandatory
   DESCRIPTION
     "This attribute counts the throughput packets handled by DPN packet 
      forwarding on this module. Note that DPRS packets leaving the 
      network at this module are not counted. The counter wraps to zero 
      when the maximum value is exceeded."
::= { mscRtgDpnFwdStatsEntry 2 }

mscRtgDpnDelayPackets OBJECT-TYPE
   SYNTAX     PassportCounter64 
   ACCESS     read-only
   STATUS     mandatory
   DESCRIPTION
     "This attribute counts the delay packets handled by DPN packet 
      forwarding on this module. Note that DPRS packets leaving the 
      network at this module are not counted. The counter wraps to zero 
      when the maximum value is exceeded."
::= { mscRtgDpnFwdStatsEntry 3 }

mscRtgDpnNormalReliabilityPackets OBJECT-TYPE
   SYNTAX     PassportCounter64 
   ACCESS     read-only
   STATUS     mandatory
   DESCRIPTION
     "This attribute counts the normal reliability packets handled by DPN 
      packet forwarding on this module when the forwardingPolicy 
      attribute of Routing DpnAddressPlan is set to loadshare or 
      loadspread. Note that DPRS packets leaving the network at this 
      module are not counted. The counter wraps to zero when the 
      maximum value is exceeded."
::= { mscRtgDpnFwdStatsEntry 4 }

mscRtgDpnHighReliabilityPackets OBJECT-TYPE
   SYNTAX     PassportCounter64 
   ACCESS     read-only
   STATUS     mandatory
   DESCRIPTION
     "This attribute counts the high reliability packets handled by DPN 
      packet forwarding on this module when the forwardingPolicy 
      attribute of Routing DpnAddressPlan is set to loadshare or 
      loadspread. Note that DPRS packets leaving the network at this 
      module are not counted. The counter wraps to zero when the 
      maximum value is exceeded."
::= { mscRtgDpnFwdStatsEntry 5 }

mscRtgDpnDiscardNoRoute OBJECT-TYPE
   SYNTAX     PassportCounter64 
   ACCESS     read-only
   STATUS     mandatory
   DESCRIPTION
     "This attribute counts the packets discarded when DPN packet 
      forwarding has failed to find a route to forward the packets on this 
      module. Note that DPRS packets leaving the network at this module 
      are not counted. The counter wraps to zero when the maximum 
      value is exceeded."
::= { mscRtgDpnFwdStatsEntry 6 }

mscRtgDpnInterruptingPackets OBJECT-TYPE
   SYNTAX     PassportCounter64 
   ACCESS     read-only
   STATUS     mandatory
   DESCRIPTION
     "This attribute counts the total number of multimedia packets 
      handled by DPN packet forwarding on this module. Note that DPRS 
      packets leaving the network at this module are not counted. The 
      counter wraps to zero when the maximum value is exceeded."
::= { mscRtgDpnFwdStatsEntry 7 }

mscRtgDpnDiscardLpCongested OBJECT-TYPE
   SYNTAX     PassportCounter64 
   ACCESS     read-only
   STATUS     mandatory
   DESCRIPTION
     "This attribute counts the packets that have been discarded by 
      packet forwarding due to LP congestion on this module. A packet 
      encounters LP congestion when there is insufficient shared 
      memory. Note that DPRS packets leaving the network at this 
      module are not counted. The counter wraps to zero when the 
      maximum value is exceeded."
::= { mscRtgDpnFwdStatsEntry 8 }

mscRtgDpnCallServerModuleRidsTable OBJECT-TYPE
   SYNTAX     SEQUENCE OF MscRtgDpnCallServerModuleRidsEntry
   ACCESS     not-accessible
   STATUS     mandatory
   DESCRIPTION
     "This attribute indicates the RIDs of the Call Server Resource 
      Modules (CSRMs) currently in use to support Call Server functions, 
      such as SCR and DCR, for the Passport subnet. Up to two CSRMs 
      can be in use to support such Call Server functions.
      
      Note that packets destined to Call Server functions are routed to the 
      closest CSRM supporting the required server functionality."
::= { mscRtgDpn 232 }

mscRtgDpnCallServerModuleRidsEntry OBJECT-TYPE
   SYNTAX     MscRtgDpnCallServerModuleRidsEntry
   ACCESS     not-accessible
   STATUS     mandatory
   DESCRIPTION
     "An entry in the mscRtgDpnCallServerModuleRidsTable."
   INDEX {
      mscRtgIndex,
      mscRtgDpnIndex,
      mscRtgDpnCallServerModuleRidsValue }
::= { mscRtgDpnCallServerModuleRidsTable 1 }

MscRtgDpnCallServerModuleRidsEntry ::= SEQUENCE {
   mscRtgDpnCallServerModuleRidsValue
      Integer32 }

mscRtgDpnCallServerModuleRidsValue OBJECT-TYPE
   SYNTAX     Integer32 (1..126)
   ACCESS     read-only
   STATUS     mandatory
   DESCRIPTION
     "This variable represents both the value and the index for the
      mscRtgDpnCallServerModuleRidsTable."
::= { mscRtgDpnCallServerModuleRidsEntry 1 }

mscRtgDpnSubnetMidsTable OBJECT-TYPE
   SYNTAX     SEQUENCE OF MscRtgDpnSubnetMidsEntry
   ACCESS     not-accessible
   STATUS     mandatory
   DESCRIPTION
     "This attribute indicates which of the ReachableMidInfo (Mid) 
      components refer to MIDs which are members of the Passport 
      subnet. This list does not include AMs connected to the subnet."
::= { mscRtgDpn 233 }

mscRtgDpnSubnetMidsEntry OBJECT-TYPE
   SYNTAX     MscRtgDpnSubnetMidsEntry
   ACCESS     not-accessible
   STATUS     mandatory
   DESCRIPTION
     "An entry in the mscRtgDpnSubnetMidsTable."
   INDEX {
      mscRtgIndex,
      mscRtgDpnIndex,
      mscRtgDpnSubnetMidsValue }
::= { mscRtgDpnSubnetMidsTable 1 }

MscRtgDpnSubnetMidsEntry ::= SEQUENCE {
   mscRtgDpnSubnetMidsValue
      RowPointer }

mscRtgDpnSubnetMidsValue OBJECT-TYPE
   SYNTAX     RowPointer 
   ACCESS     read-only
   STATUS     mandatory
   DESCRIPTION
     "This variable represents both the value and the index for the
      mscRtgDpnSubnetMidsTable."
::= { mscRtgDpnSubnetMidsEntry 1 }

mscRtgDpnVarianceTable OBJECT-TYPE
   SYNTAX     SEQUENCE OF MscRtgDpnVarianceEntry
   ACCESS     not-accessible
   STATUS     mandatory
   DESCRIPTION
     "This attribute specifies the variance values for high and low metric 
      ranges, for each class of service (COS). A variance value is the 
      maximum allowed difference in metric between the best path and 
      the second path, as a percentage of the best path metric. High and 
      low metric ranges are defined for each COS by the 
      delayMetricRangeBoundary and tputMetricRangeBoundary 
      attributes, and refer to total path metrics.
      
      When a variance value for a certain COS and metric range is set to 
      the default value of 0, only equal metric paths can be used under 
      that COS when the best path metric is in that range. When it is set 
      to a value greater than 0, an alternate path which is safe (that is, 
      non-looping) and which has a metric within this percentage of the 
      best path metric can be used as a multipath.
      
      The special value of 9999 signifies an infinite variance, so that any 
      safe alternate path may be used in addition to the single best path, 
      regardless of its metric."
::= { mscRtgDpn 343 }

mscRtgDpnVarianceEntry OBJECT-TYPE
   SYNTAX     MscRtgDpnVarianceEntry
   ACCESS     not-accessible
   STATUS     mandatory
   DESCRIPTION
     "An entry in the mscRtgDpnVarianceTable."
   INDEX {
      mscRtgIndex,
      mscRtgDpnIndex,
      mscRtgDpnVarianceCosIndex,
      mscRtgDpnVarianceMetricRangeIndex }
::= { mscRtgDpnVarianceTable 1 }

MscRtgDpnVarianceEntry ::= SEQUENCE {
   mscRtgDpnVarianceCosIndex
      INTEGER,
   mscRtgDpnVarianceMetricRangeIndex
      INTEGER,
   mscRtgDpnVarianceValue
      Unsigned32 }

mscRtgDpnVarianceCosIndex OBJECT-TYPE
   SYNTAX     INTEGER  {
                 delay(0),
                 throughput(1) }
   ACCESS     not-accessible
   STATUS     mandatory
   DESCRIPTION
     "This variable represents the next to last index for the 
      mscRtgDpnVarianceTable."
::= { mscRtgDpnVarianceEntry 1 }

mscRtgDpnVarianceMetricRangeIndex OBJECT-TYPE
   SYNTAX     INTEGER  {
                 low(0),
                 high(1) }
   ACCESS     not-accessible
   STATUS     mandatory
   DESCRIPTION
     "This variable represents the final index for the 
      mscRtgDpnVarianceTable."
::= { mscRtgDpnVarianceEntry 2 }

mscRtgDpnVarianceValue OBJECT-TYPE
   SYNTAX     Unsigned32 (0..500 | 9999)
   ACCESS     read-write
   STATUS     mandatory
   DESCRIPTION
     "This variable represents an individual value for the
      mscRtgDpnVarianceTable."
::= { mscRtgDpnVarianceEntry 3 }

-- 
-- *** THIS SUBTREE CURRENTLY NOT IMPLEMENTED ***
-- 

-- Routing Dpn ReachableRidInfo/<rid>
-- This component is a dynamic subcomponent of the 
-- DpnAddressPlan. It provides information about the paths to RIDs in 
-- the network that are reachable.
-- 
-- There is one instance per reachable RID.

mscRtgDpnRid OBJECT IDENTIFIER ::= { mscRtgDpn 2 }



mscRtgDpnRidRowStatusTable OBJECT-TYPE
   SYNTAX     SEQUENCE OF MscRtgDpnRidRowStatusEntry
   ACCESS     not-accessible
   STATUS     mandatory
   DESCRIPTION
     "*** THIS TABLE CURRENTLY NOT IMPLEMENTED ***

      This entry controls the addition and deletion of 
      mscRtgDpnRid components."
::= { mscRtgDpnRid 1 }

mscRtgDpnRidRowStatusEntry OBJECT-TYPE
   SYNTAX     MscRtgDpnRidRowStatusEntry
   ACCESS     not-accessible
   STATUS     mandatory
   DESCRIPTION
     "A single entry in the table represents a single 
      mscRtgDpnRid component."
   INDEX {
      mscRtgIndex,
      mscRtgDpnIndex,
      mscRtgDpnRidIndex }
::= { mscRtgDpnRidRowStatusTable 1 }

MscRtgDpnRidRowStatusEntry ::= SEQUENCE {
   mscRtgDpnRidRowStatus
      RowStatus,
   mscRtgDpnRidComponentName
      DisplayString,
   mscRtgDpnRidStorageType
      StorageType,
   mscRtgDpnRidIndex
      Integer32 }

mscRtgDpnRidRowStatus OBJECT-TYPE
   SYNTAX     RowStatus 
   ACCESS     read-only
   STATUS     mandatory
   DESCRIPTION
     "This variable is used as the basis for SNMP naming of
      mscRtgDpnRid components.
      These components cannot be added nor deleted."
::= { mscRtgDpnRidRowStatusEntry 1 }

mscRtgDpnRidComponentName OBJECT-TYPE
   SYNTAX     DisplayString 
   ACCESS     read-only
   STATUS     mandatory
   DESCRIPTION
     "This variable provides the component's string name for
      use with the ASCII Console Interface"
::= { mscRtgDpnRidRowStatusEntry 2 }

mscRtgDpnRidStorageType OBJECT-TYPE
   SYNTAX     StorageType 
   ACCESS     read-only
   STATUS     mandatory
   DESCRIPTION
     "This variable represents the storage type value for the
      mscRtgDpnRid tables."
::= { mscRtgDpnRidRowStatusEntry 4 }

mscRtgDpnRidIndex OBJECT-TYPE
   SYNTAX     Integer32 (0..127)
   ACCESS     not-accessible
   STATUS     mandatory
   DESCRIPTION
     "This variable represents the index for the mscRtgDpnRid tables."
::= { mscRtgDpnRidRowStatusEntry 10 }

mscRtgDpnRidOperTable OBJECT-TYPE
   SYNTAX     SEQUENCE OF MscRtgDpnRidOperEntry
   ACCESS     not-accessible
   STATUS     mandatory
   DESCRIPTION
     "*** THIS TABLE CURRENTLY NOT IMPLEMENTED ***

      This group of attributes is maintained by the DpnAddressPlan 
      component to provide information about the RIDs reachable in the 
      network."
::= { mscRtgDpnRid 10 }

mscRtgDpnRidOperEntry OBJECT-TYPE
   SYNTAX     MscRtgDpnRidOperEntry
   ACCESS     not-accessible
   STATUS     mandatory
   DESCRIPTION
     "An entry in the mscRtgDpnRidOperTable."
   INDEX {
      mscRtgIndex,
      mscRtgDpnIndex,
      mscRtgDpnRidIndex }
::= { mscRtgDpnRidOperTable 1 }

MscRtgDpnRidOperEntry ::= SEQUENCE {
   mscRtgDpnRidDpnDelayMetric
      Unsigned32,
   mscRtgDpnRidDpnTputMetric
      Unsigned32 }

mscRtgDpnRidDpnDelayMetric OBJECT-TYPE
   SYNTAX     Unsigned32 (0..255)
   ACCESS     read-only
   STATUS     mandatory
   DESCRIPTION
     "This attribute indicates the minimum DPN delay metric to the 
      destination RID. The delay metric associated with a path is 
      computed by the routing system by translating the smallest 
      delayMetric calculated for the destination. A path with a lower 
      metric value is preferable to one with a higher value as it is 
      associated with lower delay facilities. The metric displayed is that 
      of the best path to the destination. This metric is advertised to 
      neighbor RMs and Passports in a different RID subnet.
      
      A metric value of 255 means the RID is unreachable in the delay 
      class of service. A value of 0 indicates that no cost is associated 
      with the path to the destination. This would be the case for the local 
      node's RID. A metric value of 252 indicates that the destination 
      RID is that of a Network Module (NM)."
::= { mscRtgDpnRidOperEntry 1 }

mscRtgDpnRidDpnTputMetric OBJECT-TYPE
   SYNTAX     Unsigned32 (0..255)
   ACCESS     read-only
   STATUS     mandatory
   DESCRIPTION
     "This attribute indicates the minimum DPN throughput metric to the 
      destination RID. The throughput metric associated with a path is 
      computed by the routing system by translating the smallest 
      tputMetric calculated for the destination. A path with a lower metric 
      value is preferable to one with a higher value as it is associated with 
      higher bandwidth facilities. The metric displayed is that of the best 
      path to the destination. This metric is advertised to neighbor RMs 
      and Passports in a different RID subnet.
      
      A metric value of 255 means the RID is unreachable in the 
      throughput class of service. A value of 0 indicates that no cost is 
      associated with the path to the destination. This would be the case 
      for the local node's RID."
::= { mscRtgDpnRidOperEntry 2 }

mscRtgDpnRidDelayNextHopLinkGroupsTable OBJECT-TYPE
   SYNTAX     SEQUENCE OF MscRtgDpnRidDelayNextHopLinkGroupsEntry
   ACCESS     not-accessible
   STATUS     mandatory
   DESCRIPTION
     "*** THIS TABLE CURRENTLY NOT IMPLEMENTED ***

      This attribute indicates the delay link group, or groups, that are 
      being used to reach a neighbor which is the next hop in the path to 
      the destination RID. DPN traffic will be spread across the links, in 
      up to two link groups, when available. The link groups selected are 
      those associated with the two loop-free paths with the lowest delay 
      metrics to the destination.
      
      The link group can be that of either a Passport node interconnection 
      or a gateway to an RM.
      
      If no link groups are listed then the destination is not reachable in 
      the delay class of service (except in the case of the local node's 
      RID).
      
      Link group instances are managed by the TransportResource 
      component. Further information about the links in the group can be 
      obtained from it."
::= { mscRtgDpnRid 226 }

mscRtgDpnRidDelayNextHopLinkGroupsEntry OBJECT-TYPE
   SYNTAX     MscRtgDpnRidDelayNextHopLinkGroupsEntry
   ACCESS     not-accessible
   STATUS     mandatory
   DESCRIPTION
     "An entry in the mscRtgDpnRidDelayNextHopLinkGroupsTable."
   INDEX {
      mscRtgIndex,
      mscRtgDpnIndex,
      mscRtgDpnRidIndex,
      mscRtgDpnRidDelayNextHopLinkGroupsIndex }
::= { mscRtgDpnRidDelayNextHopLinkGroupsTable 1 }

MscRtgDpnRidDelayNextHopLinkGroupsEntry ::= SEQUENCE {
   mscRtgDpnRidDelayNextHopLinkGroupsIndex
      Integer32,
   mscRtgDpnRidDelayNextHopLinkGroupsValue
      RowPointer }

mscRtgDpnRidDelayNextHopLinkGroupsIndex OBJECT-TYPE
   SYNTAX     Integer32 (0..1)
   ACCESS     not-accessible
   STATUS     mandatory
   DESCRIPTION
     "This variable represents the index for the mscRtgDpnRidDelayNextHopLinkGroupsTable."
::= { mscRtgDpnRidDelayNextHopLinkGroupsEntry 1 }

mscRtgDpnRidDelayNextHopLinkGroupsValue OBJECT-TYPE
   SYNTAX     RowPointer 
   ACCESS     read-only
   STATUS     mandatory
   DESCRIPTION
     "This variable represents an individual value for the
      mscRtgDpnRidDelayNextHopLinkGroupsTable."
::= { mscRtgDpnRidDelayNextHopLinkGroupsEntry 2 }

mscRtgDpnRidTputNextHopLinkGroupsTable OBJECT-TYPE
   SYNTAX     SEQUENCE OF MscRtgDpnRidTputNextHopLinkGroupsEntry
   ACCESS     not-accessible
   STATUS     mandatory
   DESCRIPTION
     "*** THIS TABLE CURRENTLY NOT IMPLEMENTED ***

      This attribute indicates the throughput link group, or groups, that 
      are being used to reach a neighbor which is the next hop in the path 
      to the destination RID. DPN traffic will be spread across the links, 
      in up to two link groups, when available. The link groups selected 
      are those associated with the two loop-free paths with the lowest 
      throughput metrics to the destination.
      
      The link group can be that of either a Passport node interconnection 
      or a gateway to an RM.
      
      If no link groups are listed then the destination is not reachable in 
      the throughput class of service (except in the case of the local 
      node's RID).
      
      Link group instances are managed by the TransportResource 
      component. Further information about the links in the group can be 
      obtained from it."
::= { mscRtgDpnRid 227 }

mscRtgDpnRidTputNextHopLinkGroupsEntry OBJECT-TYPE
   SYNTAX     MscRtgDpnRidTputNextHopLinkGroupsEntry
   ACCESS     not-accessible
   STATUS     mandatory
   DESCRIPTION
     "An entry in the mscRtgDpnRidTputNextHopLinkGroupsTable."
   INDEX {
      mscRtgIndex,
      mscRtgDpnIndex,
      mscRtgDpnRidIndex,
      mscRtgDpnRidTputNextHopLinkGroupsIndex }
::= { mscRtgDpnRidTputNextHopLinkGroupsTable 1 }

MscRtgDpnRidTputNextHopLinkGroupsEntry ::= SEQUENCE {
   mscRtgDpnRidTputNextHopLinkGroupsIndex
      Integer32,
   mscRtgDpnRidTputNextHopLinkGroupsValue
      RowPointer }

mscRtgDpnRidTputNextHopLinkGroupsIndex OBJECT-TYPE
   SYNTAX     Integer32 (0..1)
   ACCESS     not-accessible
   STATUS     mandatory
   DESCRIPTION
     "This variable represents the index for the mscRtgDpnRidTputNextHopLinkGroupsTable."
::= { mscRtgDpnRidTputNextHopLinkGroupsEntry 1 }

mscRtgDpnRidTputNextHopLinkGroupsValue OBJECT-TYPE
   SYNTAX     RowPointer 
   ACCESS     read-only
   STATUS     mandatory
   DESCRIPTION
     "This variable represents an individual value for the
      mscRtgDpnRidTputNextHopLinkGroupsTable."
::= { mscRtgDpnRidTputNextHopLinkGroupsEntry 2 }

mscRtgDpnRidDelayPathTrafficProportionsTable OBJECT-TYPE
   SYNTAX     SEQUENCE OF MscRtgDpnRidDelayPathTrafficProportionsEntry
   ACCESS     not-accessible
   STATUS     mandatory
   DESCRIPTION
     "*** THIS TABLE CURRENTLY NOT IMPLEMENTED ***

      This attribute indicates the target percentages of the total delay 
      traffic flows to the destination which are sent over each delay path. 
      These percentages are achieved when there is a large number of 
      virtual circuits (VCs)."
::= { mscRtgDpnRid 328 }

mscRtgDpnRidDelayPathTrafficProportionsEntry OBJECT-TYPE
   SYNTAX     MscRtgDpnRidDelayPathTrafficProportionsEntry
   ACCESS     not-accessible
   STATUS     mandatory
   DESCRIPTION
     "An entry in the mscRtgDpnRidDelayPathTrafficProportionsTable."
   INDEX {
      mscRtgIndex,
      mscRtgDpnIndex,
      mscRtgDpnRidIndex,
      mscRtgDpnRidDelayPathTrafficProportionsIndex }
::= { mscRtgDpnRidDelayPathTrafficProportionsTable 1 }

MscRtgDpnRidDelayPathTrafficProportionsEntry ::= SEQUENCE {
   mscRtgDpnRidDelayPathTrafficProportionsIndex
      Integer32,
   mscRtgDpnRidDelayPathTrafficProportionsValue
      Unsigned32 }

mscRtgDpnRidDelayPathTrafficProportionsIndex OBJECT-TYPE
   SYNTAX     Integer32 (0..1)
   ACCESS     not-accessible
   STATUS     mandatory
   DESCRIPTION
     "This variable represents the index for the mscRtgDpnRidDelayPathTrafficProportionsTable."
::= { mscRtgDpnRidDelayPathTrafficProportionsEntry 1 }

mscRtgDpnRidDelayPathTrafficProportionsValue OBJECT-TYPE
   SYNTAX     Unsigned32 (0..100)
   ACCESS     read-only
   STATUS     mandatory
   DESCRIPTION
     "This variable represents an individual value for the
      mscRtgDpnRidDelayPathTrafficProportionsTable."
::= { mscRtgDpnRidDelayPathTrafficProportionsEntry 2 }

mscRtgDpnRidTputPathTrafficProportionsTable OBJECT-TYPE
   SYNTAX     SEQUENCE OF MscRtgDpnRidTputPathTrafficProportionsEntry
   ACCESS     not-accessible
   STATUS     mandatory
   DESCRIPTION
     "*** THIS TABLE CURRENTLY NOT IMPLEMENTED ***

      This attribute indicates the target percentages of the total throughput 
      traffic flows to the destination which are sent over each throughput 
      path. These percentages are achieved when there is a large number 
      of virtual circuits (VCs)."
::= { mscRtgDpnRid 329 }

mscRtgDpnRidTputPathTrafficProportionsEntry OBJECT-TYPE
   SYNTAX     MscRtgDpnRidTputPathTrafficProportionsEntry
   ACCESS     not-accessible
   STATUS     mandatory
   DESCRIPTION
     "An entry in the mscRtgDpnRidTputPathTrafficProportionsTable."
   INDEX {
      mscRtgIndex,
      mscRtgDpnIndex,
      mscRtgDpnRidIndex,
      mscRtgDpnRidTputPathTrafficProportionsIndex }
::= { mscRtgDpnRidTputPathTrafficProportionsTable 1 }

MscRtgDpnRidTputPathTrafficProportionsEntry ::= SEQUENCE {
   mscRtgDpnRidTputPathTrafficProportionsIndex
      Integer32,
   mscRtgDpnRidTputPathTrafficProportionsValue
      Unsigned32 }

mscRtgDpnRidTputPathTrafficProportionsIndex OBJECT-TYPE
   SYNTAX     Integer32 (0..1)
   ACCESS     not-accessible
   STATUS     mandatory
   DESCRIPTION
     "This variable represents the index for the mscRtgDpnRidTputPathTrafficProportionsTable."
::= { mscRtgDpnRidTputPathTrafficProportionsEntry 1 }

mscRtgDpnRidTputPathTrafficProportionsValue OBJECT-TYPE
   SYNTAX     Unsigned32 (0..100)
   ACCESS     read-only
   STATUS     mandatory
   DESCRIPTION
     "This variable represents an individual value for the
      mscRtgDpnRidTputPathTrafficProportionsTable."
::= { mscRtgDpnRidTputPathTrafficProportionsEntry 2 }

mscRtgDpnRidDelayMetricTable OBJECT-TYPE
   SYNTAX     SEQUENCE OF MscRtgDpnRidDelayMetricEntry
   ACCESS     not-accessible
   STATUS     mandatory
   DESCRIPTION
     "*** THIS TABLE CURRENTLY NOT IMPLEMENTED ***

      This attribute indicates the delay metrics of up to two paths to the 
      destination RID. The delay metric associated with a path is 
      computed by the routing system based on the sum of the delays 
      associated with the links in the path to the destination. A path with a 
      lower metric value is preferable to one with a higher value as it is 
      associated with lower delay facilities. The metrics displayed are 
      those of the paths being used to reach the destination.
      
      Metric values of 2147483647 for both paths means the RID is 
      unreachable in the delay class of service. A metric value of 
      2147483647 for the second path only means that there is only one 
      viable delay path to the destination. A value of 0 indicates that no 
      cost is associated with the path to the destination. This would be the 
      case for the local node's RID. Metric values of 2147483646 indicate 
      that the destination RID is that of a Network Module (NM)."
::= { mscRtgDpnRid 339 }

mscRtgDpnRidDelayMetricEntry OBJECT-TYPE
   SYNTAX     MscRtgDpnRidDelayMetricEntry
   ACCESS     not-accessible
   STATUS     mandatory
   DESCRIPTION
     "An entry in the mscRtgDpnRidDelayMetricTable."
   INDEX {
      mscRtgIndex,
      mscRtgDpnIndex,
      mscRtgDpnRidIndex,
      mscRtgDpnRidDelayMetricIndex }
::= { mscRtgDpnRidDelayMetricTable 1 }

MscRtgDpnRidDelayMetricEntry ::= SEQUENCE {
   mscRtgDpnRidDelayMetricIndex
      Integer32,
   mscRtgDpnRidDelayMetricValue
      Unsigned32 }

mscRtgDpnRidDelayMetricIndex OBJECT-TYPE
   SYNTAX     Integer32 (0..1)
   ACCESS     not-accessible
   STATUS     mandatory
   DESCRIPTION
     "This variable represents the index for the mscRtgDpnRidDelayMetricTable."
::= { mscRtgDpnRidDelayMetricEntry 1 }

mscRtgDpnRidDelayMetricValue OBJECT-TYPE
   SYNTAX     Unsigned32 (0..2147483647)
   ACCESS     read-only
   STATUS     mandatory
   DESCRIPTION
     "This variable represents an individual value for the
      mscRtgDpnRidDelayMetricTable."
::= { mscRtgDpnRidDelayMetricEntry 2 }

mscRtgDpnRidTputMetricTable OBJECT-TYPE
   SYNTAX     SEQUENCE OF MscRtgDpnRidTputMetricEntry
   ACCESS     not-accessible
   STATUS     mandatory
   DESCRIPTION
     "*** THIS TABLE CURRENTLY NOT IMPLEMENTED ***

      This attribute indicates the throughput metrics of up to two paths to 
      the destination RID. The throughput metric associated with a path is 
      computed by the routing system based on the sum of the bandwidth 
      associated with the links in the path to the destination. A path with a 
      lower metric value is preferable to one with a higher value as it is 
      associated with higher bandwidth facilities. The metrics displayed 
      are those of the paths being used to reach the destination.
      
      Metric values of 2147483647 for both paths means the RID is 
      unreachable in the throughput class of service. A metric value of 
      2147483647 for the second path only means that there is only one 
      viable throughput path to the destination. A value of 0 indicates that 
      no cost is associated with the path to the destination. This would be 
      the case for the local node's RID."
::= { mscRtgDpnRid 340 }

mscRtgDpnRidTputMetricEntry OBJECT-TYPE
   SYNTAX     MscRtgDpnRidTputMetricEntry
   ACCESS     not-accessible
   STATUS     mandatory
   DESCRIPTION
     "An entry in the mscRtgDpnRidTputMetricTable."
   INDEX {
      mscRtgIndex,
      mscRtgDpnIndex,
      mscRtgDpnRidIndex,
      mscRtgDpnRidTputMetricIndex }
::= { mscRtgDpnRidTputMetricTable 1 }

MscRtgDpnRidTputMetricEntry ::= SEQUENCE {
   mscRtgDpnRidTputMetricIndex
      Integer32,
   mscRtgDpnRidTputMetricValue
      Unsigned32 }

mscRtgDpnRidTputMetricIndex OBJECT-TYPE
   SYNTAX     Integer32 (0..1)
   ACCESS     not-accessible
   STATUS     mandatory
   DESCRIPTION
     "This variable represents the index for the mscRtgDpnRidTputMetricTable."
::= { mscRtgDpnRidTputMetricEntry 1 }

mscRtgDpnRidTputMetricValue OBJECT-TYPE
   SYNTAX     Unsigned32 (0..2147483647)
   ACCESS     read-only
   STATUS     mandatory
   DESCRIPTION
     "This variable represents an individual value for the
      mscRtgDpnRidTputMetricTable."
::= { mscRtgDpnRidTputMetricEntry 2 }

-- 
-- *** THIS SUBTREE CURRENTLY NOT IMPLEMENTED ***
-- 

-- Routing Dpn Rid/<rid> Mid/<mid>
-- This component is a subcomponent of ReachableRidInfo. It 
-- supports the ping verb by providing the ability to ping a MID under 
-- a RID that is known to be reachable. The state (reachable/
-- unreachable) of MIDs, other than those supported by the local RID 
-- subnet (see the ReachableMidInfo subcomponent), is not 
-- maintained by the DpnAddressPlan component.

mscRtgDpnRidMid OBJECT IDENTIFIER ::= { mscRtgDpnRid 2 }



mscRtgDpnRidMidRowStatusTable OBJECT-TYPE
   SYNTAX     SEQUENCE OF MscRtgDpnRidMidRowStatusEntry
   ACCESS     not-accessible
   STATUS     mandatory
   DESCRIPTION
     "*** THIS TABLE CURRENTLY NOT IMPLEMENTED ***

      This entry controls the addition and deletion of 
      mscRtgDpnRidMid components."
::= { mscRtgDpnRidMid 1 }

mscRtgDpnRidMidRowStatusEntry OBJECT-TYPE
   SYNTAX     MscRtgDpnRidMidRowStatusEntry
   ACCESS     not-accessible
   STATUS     mandatory
   DESCRIPTION
     "A single entry in the table represents a single 
      mscRtgDpnRidMid component."
   INDEX {
      mscRtgIndex,
      mscRtgDpnIndex,
      mscRtgDpnRidIndex,
      mscRtgDpnRidMidIndex }
::= { mscRtgDpnRidMidRowStatusTable 1 }

MscRtgDpnRidMidRowStatusEntry ::= SEQUENCE {
   mscRtgDpnRidMidRowStatus
      RowStatus,
   mscRtgDpnRidMidComponentName
      DisplayString,
   mscRtgDpnRidMidStorageType
      StorageType,
   mscRtgDpnRidMidIndex
      Integer32 }

mscRtgDpnRidMidRowStatus OBJECT-TYPE
   SYNTAX     RowStatus 
   ACCESS     read-only
   STATUS     mandatory
   DESCRIPTION
     "This variable is used as the basis for SNMP naming of
      mscRtgDpnRidMid components.
      These components cannot be added nor deleted."
::= { mscRtgDpnRidMidRowStatusEntry 1 }

mscRtgDpnRidMidComponentName OBJECT-TYPE
   SYNTAX     DisplayString 
   ACCESS     read-only
   STATUS     mandatory
   DESCRIPTION
     "This variable provides the component's string name for
      use with the ASCII Console Interface"
::= { mscRtgDpnRidMidRowStatusEntry 2 }

mscRtgDpnRidMidStorageType OBJECT-TYPE
   SYNTAX     StorageType 
   ACCESS     read-only
   STATUS     mandatory
   DESCRIPTION
     "This variable represents the storage type value for the
      mscRtgDpnRidMid tables."
::= { mscRtgDpnRidMidRowStatusEntry 4 }

mscRtgDpnRidMidIndex OBJECT-TYPE
   SYNTAX     Integer32 (0..2046)
   ACCESS     not-accessible
   STATUS     mandatory
   DESCRIPTION
     "This variable represents the index for the mscRtgDpnRidMid tables."
::= { mscRtgDpnRidMidRowStatusEntry 10 }

-- 
-- *** THIS SUBTREE CURRENTLY NOT IMPLEMENTED ***
-- 

-- Routing Dpn ReachableMidInfo/<mid>
-- This component is a dynamic subcomponent of the 
-- DpnAddressPlan. It provides information about the MIDs, 
-- supported by the local RID subnet, that are, or were once, 
-- reachable. This includes the MIDs of the Passport nodes in the 
-- subnet and the AM clusters supported by the subnet.
-- 
-- The information is accessed by specifying a MID.

mscRtgDpnMid OBJECT IDENTIFIER ::= { mscRtgDpn 3 }



mscRtgDpnMidRowStatusTable OBJECT-TYPE
   SYNTAX     SEQUENCE OF MscRtgDpnMidRowStatusEntry
   ACCESS     not-accessible
   STATUS     mandatory
   DESCRIPTION
     "*** THIS TABLE CURRENTLY NOT IMPLEMENTED ***

      This entry controls the addition and deletion of 
      mscRtgDpnMid components."
::= { mscRtgDpnMid 1 }

mscRtgDpnMidRowStatusEntry OBJECT-TYPE
   SYNTAX     MscRtgDpnMidRowStatusEntry
   ACCESS     not-accessible
   STATUS     mandatory
   DESCRIPTION
     "A single entry in the table represents a single 
      mscRtgDpnMid component."
   INDEX {
      mscRtgIndex,
      mscRtgDpnIndex,
      mscRtgDpnMidIndex }
::= { mscRtgDpnMidRowStatusTable 1 }

MscRtgDpnMidRowStatusEntry ::= SEQUENCE {
   mscRtgDpnMidRowStatus
      RowStatus,
   mscRtgDpnMidComponentName
      DisplayString,
   mscRtgDpnMidStorageType
      StorageType,
   mscRtgDpnMidIndex
      Integer32 }

mscRtgDpnMidRowStatus OBJECT-TYPE
   SYNTAX     RowStatus 
   ACCESS     read-only
   STATUS     mandatory
   DESCRIPTION
     "This variable is used as the basis for SNMP naming of
      mscRtgDpnMid components.
      These components cannot be added nor deleted."
::= { mscRtgDpnMidRowStatusEntry 1 }

mscRtgDpnMidComponentName OBJECT-TYPE
   SYNTAX     DisplayString 
   ACCESS     read-only
   STATUS     mandatory
   DESCRIPTION
     "This variable provides the component's string name for
      use with the ASCII Console Interface"
::= { mscRtgDpnMidRowStatusEntry 2 }

mscRtgDpnMidStorageType OBJECT-TYPE
   SYNTAX     StorageType 
   ACCESS     read-only
   STATUS     mandatory
   DESCRIPTION
     "This variable represents the storage type value for the
      mscRtgDpnMid tables."
::= { mscRtgDpnMidRowStatusEntry 4 }

mscRtgDpnMidIndex OBJECT-TYPE
   SYNTAX     Integer32 (0..2046)
   ACCESS     not-accessible
   STATUS     mandatory
   DESCRIPTION
     "This variable represents the index for the mscRtgDpnMid tables."
::= { mscRtgDpnMidRowStatusEntry 10 }

mscRtgDpnMidOperTable OBJECT-TYPE
   SYNTAX     SEQUENCE OF MscRtgDpnMidOperEntry
   ACCESS     not-accessible
   STATUS     mandatory
   DESCRIPTION
     "*** THIS TABLE CURRENTLY NOT IMPLEMENTED ***

      This group of attributes is maintained by DpnAddressPlan 
      component to provide information about the MIDs reachable, or 
      once reachable, through the local RID subnet."
::= { mscRtgDpnMid 10 }

mscRtgDpnMidOperEntry OBJECT-TYPE
   SYNTAX     MscRtgDpnMidOperEntry
   ACCESS     not-accessible
   STATUS     mandatory
   DESCRIPTION
     "An entry in the mscRtgDpnMidOperTable."
   INDEX {
      mscRtgIndex,
      mscRtgDpnIndex,
      mscRtgDpnMidIndex }
::= { mscRtgDpnMidOperTable 1 }

MscRtgDpnMidOperEntry ::= SEQUENCE {
   mscRtgDpnMidSubstituteRid
      Unsigned32 }

mscRtgDpnMidSubstituteRid OBJECT-TYPE
   SYNTAX     Unsigned32 (1..128)
   ACCESS     read-only
   STATUS     mandatory
   DESCRIPTION
     "This attribute indicates the substitute RID in use for the MID. This 
      RID will be substituted for the RID in DPN packets destined to the 
      local node's RID and the MID in question when the MID is 
      unreachable (when, for example, all links to an AM from the 
      Passport subnet are down). It will also be used in the case where the 
      path through the substitute RID is better than that available through 
      the subnet's connection to the cluster containing the AM MID.
      
      Substitute RIDs are learned from AM clusters that are supported by 
      two RIDs (the Passport subnet's RID and another one). The 
      operator can check this value to determine if a possible back up 
      route to an AM exists. When there are no delayNextHopLinkGroups 
      or tputNextHopLinkGroups shown to reach the MID, the substitute 
      RID will be used.
      
      A value of 128 indicates that no substitute RID is known."
   DEFVAL     { 128 }
::= { mscRtgDpnMidOperEntry 3 }

mscRtgDpnMidDelayNextHopLinkGroupsTable OBJECT-TYPE
   SYNTAX     SEQUENCE OF MscRtgDpnMidDelayNextHopLinkGroupsEntry
   ACCESS     not-accessible
   STATUS     mandatory
   DESCRIPTION
     "*** THIS TABLE CURRENTLY NOT IMPLEMENTED ***

      This attribute indicates the delay link group, or groups, that are 
      being used to reach a neighbor which is the next hop in the path to 
      the destination MID. DPN traffic will be spread across the links, in 
      up to two link groups, when available. The link groups selected are 
      those associated with the two loop-free paths with the lowest delay 
      metrics to the destination.
      
      The link group can be that of either a Passport node interconnection 
      or a gateway to an AM.
      
      If no link groups are listed then the destination is not reachable in 
      the delay class of service (except in the case of the local node's 
      MID, or when a substitute RID path is available).
      
      Link group instances are managed by the TransportResource 
      component. Further information about the links in the group can be 
      obtained from it."
::= { mscRtgDpnMid 228 }

mscRtgDpnMidDelayNextHopLinkGroupsEntry OBJECT-TYPE
   SYNTAX     MscRtgDpnMidDelayNextHopLinkGroupsEntry
   ACCESS     not-accessible
   STATUS     mandatory
   DESCRIPTION
     "An entry in the mscRtgDpnMidDelayNextHopLinkGroupsTable."
   INDEX {
      mscRtgIndex,
      mscRtgDpnIndex,
      mscRtgDpnMidIndex,
      mscRtgDpnMidDelayNextHopLinkGroupsIndex }
::= { mscRtgDpnMidDelayNextHopLinkGroupsTable 1 }

MscRtgDpnMidDelayNextHopLinkGroupsEntry ::= SEQUENCE {
   mscRtgDpnMidDelayNextHopLinkGroupsIndex
      Integer32,
   mscRtgDpnMidDelayNextHopLinkGroupsValue
      RowPointer }

mscRtgDpnMidDelayNextHopLinkGroupsIndex OBJECT-TYPE
   SYNTAX     Integer32 (0..1)
   ACCESS     not-accessible
   STATUS     mandatory
   DESCRIPTION
     "This variable represents the index for the mscRtgDpnMidDelayNextHopLinkGroupsTable."
::= { mscRtgDpnMidDelayNextHopLinkGroupsEntry 1 }

mscRtgDpnMidDelayNextHopLinkGroupsValue OBJECT-TYPE
   SYNTAX     RowPointer 
   ACCESS     read-only
   STATUS     mandatory
   DESCRIPTION
     "This variable represents an individual value for the
      mscRtgDpnMidDelayNextHopLinkGroupsTable."
::= { mscRtgDpnMidDelayNextHopLinkGroupsEntry 2 }

mscRtgDpnMidTputNextHopLinkGroupsTable OBJECT-TYPE
   SYNTAX     SEQUENCE OF MscRtgDpnMidTputNextHopLinkGroupsEntry
   ACCESS     not-accessible
   STATUS     mandatory
   DESCRIPTION
     "*** THIS TABLE CURRENTLY NOT IMPLEMENTED ***

      This attribute indicates the throughput link group, or groups, that 
      are being used to reach a neighbor which is the next hop in the path 
      to the destination MID. DPN traffic will be spread across the links, 
      in up to two link groups, when available. The link groups selected 
      are those associated with the two loop-free paths with the lowest 
      throughput metrics to the destination.
      
      The link group can be that of either a Passport node interconnection 
      or a gateway to an AM.
      
      If no link groups are listed then the destination is not reachable in 
      the throughput class of service (except in the case of the local 
      node's MID, or when a substitute RID path is available).
      
      Link group instances are managed by the TransportResource 
      component. Further information about the links in the group can be 
      obtained from it."
::= { mscRtgDpnMid 229 }

mscRtgDpnMidTputNextHopLinkGroupsEntry OBJECT-TYPE
   SYNTAX     MscRtgDpnMidTputNextHopLinkGroupsEntry
   ACCESS     not-accessible
   STATUS     mandatory
   DESCRIPTION
     "An entry in the mscRtgDpnMidTputNextHopLinkGroupsTable."
   INDEX {
      mscRtgIndex,
      mscRtgDpnIndex,
      mscRtgDpnMidIndex,
      mscRtgDpnMidTputNextHopLinkGroupsIndex }
::= { mscRtgDpnMidTputNextHopLinkGroupsTable 1 }

MscRtgDpnMidTputNextHopLinkGroupsEntry ::= SEQUENCE {
   mscRtgDpnMidTputNextHopLinkGroupsIndex
      Integer32,
   mscRtgDpnMidTputNextHopLinkGroupsValue
      RowPointer }

mscRtgDpnMidTputNextHopLinkGroupsIndex OBJECT-TYPE
   SYNTAX     Integer32 (0..1)
   ACCESS     not-accessible
   STATUS     mandatory
   DESCRIPTION
     "This variable represents the index for the mscRtgDpnMidTputNextHopLinkGroupsTable."
::= { mscRtgDpnMidTputNextHopLinkGroupsEntry 1 }

mscRtgDpnMidTputNextHopLinkGroupsValue OBJECT-TYPE
   SYNTAX     RowPointer 
   ACCESS     read-only
   STATUS     mandatory
   DESCRIPTION
     "This variable represents an individual value for the
      mscRtgDpnMidTputNextHopLinkGroupsTable."
::= { mscRtgDpnMidTputNextHopLinkGroupsEntry 2 }

mscRtgDpnMidDelayMetricTable OBJECT-TYPE
   SYNTAX     SEQUENCE OF MscRtgDpnMidDelayMetricEntry
   ACCESS     not-accessible
   STATUS     mandatory
   DESCRIPTION
     "*** THIS TABLE CURRENTLY NOT IMPLEMENTED ***

      This attribute indicates the delay metrics of up to two paths to the 
      destination MID. The delay metric associated with a path is 
      computed by the routing system based on the sum of the delays 
      associated with the links (or estimated delays for links to AMs) in 
      the path to the destination. It is computed for every possible path to 
      the destination and is used by the DpnAddressPlan component for 
      path comparison purposes. A path with a lower metric value is 
      preferable to one with a higher value as it is associated with lower 
      delay facilities. The metrics displayed are those of the paths being 
      used to reach the destination.
      
      Metric values of 2147483647 for both paths means the MID is 
      unreachable in the delay class of service (though it might still be 
      reachable via its substitute RID). A metric value of 2147483647 for 
      the second path only means that there is only one viable delay path 
      to the destination.A value of 0 indicates that no cost is associated 
      with the path to the destination. This would be the case for the local 
      node's MID."
::= { mscRtgDpnMid 330 }

mscRtgDpnMidDelayMetricEntry OBJECT-TYPE
   SYNTAX     MscRtgDpnMidDelayMetricEntry
   ACCESS     not-accessible
   STATUS     mandatory
   DESCRIPTION
     "An entry in the mscRtgDpnMidDelayMetricTable."
   INDEX {
      mscRtgIndex,
      mscRtgDpnIndex,
      mscRtgDpnMidIndex,
      mscRtgDpnMidDelayMetricIndex }
::= { mscRtgDpnMidDelayMetricTable 1 }

MscRtgDpnMidDelayMetricEntry ::= SEQUENCE {
   mscRtgDpnMidDelayMetricIndex
      Integer32,
   mscRtgDpnMidDelayMetricValue
      Unsigned32 }

mscRtgDpnMidDelayMetricIndex OBJECT-TYPE
   SYNTAX     Integer32 (0..1)
   ACCESS     not-accessible
   STATUS     mandatory
   DESCRIPTION
     "This variable represents the index for the mscRtgDpnMidDelayMetricTable."
::= { mscRtgDpnMidDelayMetricEntry 1 }

mscRtgDpnMidDelayMetricValue OBJECT-TYPE
   SYNTAX     Unsigned32 (0..2147483647)
   ACCESS     read-only
   STATUS     mandatory
   DESCRIPTION
     "This variable represents an individual value for the
      mscRtgDpnMidDelayMetricTable."
::= { mscRtgDpnMidDelayMetricEntry 2 }

mscRtgDpnMidTputMetricTable OBJECT-TYPE
   SYNTAX     SEQUENCE OF MscRtgDpnMidTputMetricEntry
   ACCESS     not-accessible
   STATUS     mandatory
   DESCRIPTION
     "*** THIS TABLE CURRENTLY NOT IMPLEMENTED ***

      This attribute indicates the throughput metrics to the destination 
      MID. The throughput metric associated with a path is computed by 
      the routing system based on the sum of the bandwidth associated 
      with the links (or estimated bandwidth for links to AMs) in the path 
      to the destination. It is computed for every possible path to the 
      destination and is used by the DpnAddressPlan component for path 
      comparison purposes. A path with a lower metric value is preferable 
      to one with a higher value as it is associated with higher bandwidth 
      facilities. The metrics displayed are those of the paths being used to 
      reach the destination.
      
      Metric values of 2147483647 for both paths means the MID is 
      unreachable in the throughput class of service (though it might still 
      be reachable via its substitute RID). A metric value of 2147483647 
      for the second path only means that there is only one viable 
      throughput path to the destination. A value of 0 indicates that no 
      cost is associated with the path to the destination. This would be the 
      case for the local node's RID."
::= { mscRtgDpnMid 331 }

mscRtgDpnMidTputMetricEntry OBJECT-TYPE
   SYNTAX     MscRtgDpnMidTputMetricEntry
   ACCESS     not-accessible
   STATUS     mandatory
   DESCRIPTION
     "An entry in the mscRtgDpnMidTputMetricTable."
   INDEX {
      mscRtgIndex,
      mscRtgDpnIndex,
      mscRtgDpnMidIndex,
      mscRtgDpnMidTputMetricIndex }
::= { mscRtgDpnMidTputMetricTable 1 }

MscRtgDpnMidTputMetricEntry ::= SEQUENCE {
   mscRtgDpnMidTputMetricIndex
      Integer32,
   mscRtgDpnMidTputMetricValue
      Unsigned32 }

mscRtgDpnMidTputMetricIndex OBJECT-TYPE
   SYNTAX     Integer32 (0..1)
   ACCESS     not-accessible
   STATUS     mandatory
   DESCRIPTION
     "This variable represents the index for the mscRtgDpnMidTputMetricTable."
::= { mscRtgDpnMidTputMetricEntry 1 }

mscRtgDpnMidTputMetricValue OBJECT-TYPE
   SYNTAX     Unsigned32 (0..2147483647)
   ACCESS     read-only
   STATUS     mandatory
   DESCRIPTION
     "This variable represents an individual value for the
      mscRtgDpnMidTputMetricTable."
::= { mscRtgDpnMidTputMetricEntry 2 }

mscRtgDpnMidDelayPathTrafficProportionsTable OBJECT-TYPE
   SYNTAX     SEQUENCE OF MscRtgDpnMidDelayPathTrafficProportionsEntry
   ACCESS     not-accessible
   STATUS     mandatory
   DESCRIPTION
     "*** THIS TABLE CURRENTLY NOT IMPLEMENTED ***

      This attribute indicates the target percentages of the total delay 
      traffic flows to the destination which are sent over each delay path. 
      These percentages are achieved when there is a large number of 
      virtual circuits (VCs)."
::= { mscRtgDpnMid 332 }

mscRtgDpnMidDelayPathTrafficProportionsEntry OBJECT-TYPE
   SYNTAX     MscRtgDpnMidDelayPathTrafficProportionsEntry
   ACCESS     not-accessible
   STATUS     mandatory
   DESCRIPTION
     "An entry in the mscRtgDpnMidDelayPathTrafficProportionsTable."
   INDEX {
      mscRtgIndex,
      mscRtgDpnIndex,
      mscRtgDpnMidIndex,
      mscRtgDpnMidDelayPathTrafficProportionsIndex }
::= { mscRtgDpnMidDelayPathTrafficProportionsTable 1 }

MscRtgDpnMidDelayPathTrafficProportionsEntry ::= SEQUENCE {
   mscRtgDpnMidDelayPathTrafficProportionsIndex
      Integer32,
   mscRtgDpnMidDelayPathTrafficProportionsValue
      Unsigned32 }

mscRtgDpnMidDelayPathTrafficProportionsIndex OBJECT-TYPE
   SYNTAX     Integer32 (0..1)
   ACCESS     not-accessible
   STATUS     mandatory
   DESCRIPTION
     "This variable represents the index for the mscRtgDpnMidDelayPathTrafficProportionsTable."
::= { mscRtgDpnMidDelayPathTrafficProportionsEntry 1 }

mscRtgDpnMidDelayPathTrafficProportionsValue OBJECT-TYPE
   SYNTAX     Unsigned32 (0..100)
   ACCESS     read-only
   STATUS     mandatory
   DESCRIPTION
     "This variable represents an individual value for the
      mscRtgDpnMidDelayPathTrafficProportionsTable."
::= { mscRtgDpnMidDelayPathTrafficProportionsEntry 2 }

mscRtgDpnMidTputPathTrafficProportionsTable OBJECT-TYPE
   SYNTAX     SEQUENCE OF MscRtgDpnMidTputPathTrafficProportionsEntry
   ACCESS     not-accessible
   STATUS     mandatory
   DESCRIPTION
     "*** THIS TABLE CURRENTLY NOT IMPLEMENTED ***

      This attribute indicates the target percentages of the total throughput 
      traffic flows to the destination which are sent over each throughput 
      path. These percentages are achieved when there is a large number 
      of virtual circuits (VCs)."
::= { mscRtgDpnMid 333 }

mscRtgDpnMidTputPathTrafficProportionsEntry OBJECT-TYPE
   SYNTAX     MscRtgDpnMidTputPathTrafficProportionsEntry
   ACCESS     not-accessible
   STATUS     mandatory
   DESCRIPTION
     "An entry in the mscRtgDpnMidTputPathTrafficProportionsTable."
   INDEX {
      mscRtgIndex,
      mscRtgDpnIndex,
      mscRtgDpnMidIndex,
      mscRtgDpnMidTputPathTrafficProportionsIndex }
::= { mscRtgDpnMidTputPathTrafficProportionsTable 1 }

MscRtgDpnMidTputPathTrafficProportionsEntry ::= SEQUENCE {
   mscRtgDpnMidTputPathTrafficProportionsIndex
      Integer32,
   mscRtgDpnMidTputPathTrafficProportionsValue
      Unsigned32 }

mscRtgDpnMidTputPathTrafficProportionsIndex OBJECT-TYPE
   SYNTAX     Integer32 (0..1)
   ACCESS     not-accessible
   STATUS     mandatory
   DESCRIPTION
     "This variable represents the index for the mscRtgDpnMidTputPathTrafficProportionsTable."
::= { mscRtgDpnMidTputPathTrafficProportionsEntry 1 }

mscRtgDpnMidTputPathTrafficProportionsValue OBJECT-TYPE
   SYNTAX     Unsigned32 (0..100)
   ACCESS     read-only
   STATUS     mandatory
   DESCRIPTION
     "This variable represents an individual value for the
      mscRtgDpnMidTputPathTrafficProportionsTable."
::= { mscRtgDpnMidTputPathTrafficProportionsEntry 2 }

-- 
-- *** THIS SUBTREE CURRENTLY NOT IMPLEMENTED ***
-- 

-- Routing Dpn ReachableCallServerInfo/<server>
-- This component is a dynamic subcomponent of the 
-- DpnAddressPlan. It provides information about the Call Server 
-- functions, supported by one of the up to two Call Server Resource 
-- Modules, that are reachable.
-- 
-- The information is accessed by specifying one of the following 
-- abbreviated names:
-- scr - Source Call Routing Agent
-- dcr - Destination Call Routing Agent
-- gscr - Gateway Source Call Router Server
-- gdcr - Gateway Destination Call Router Server
-- grman - Gateway Call Routing Manager
-- crd - Call Redirection Remote Server Interface
-- lcr - (Limping) Call Redirection Server
-- nui - Network User Identifier Remote Server Interface
-- lnui - (Limping) Network User Identifier
-- npm - Network Process Monitor System

mscRtgDpnCs OBJECT IDENTIFIER ::= { mscRtgDpn 4 }



mscRtgDpnCsRowStatusTable OBJECT-TYPE
   SYNTAX     SEQUENCE OF MscRtgDpnCsRowStatusEntry
   ACCESS     not-accessible
   STATUS     mandatory
   DESCRIPTION
     "*** THIS TABLE CURRENTLY NOT IMPLEMENTED ***

      This entry controls the addition and deletion of 
      mscRtgDpnCs components."
::= { mscRtgDpnCs 1 }

mscRtgDpnCsRowStatusEntry OBJECT-TYPE
   SYNTAX     MscRtgDpnCsRowStatusEntry
   ACCESS     not-accessible
   STATUS     mandatory
   DESCRIPTION
     "A single entry in the table represents a single 
      mscRtgDpnCs component."
   INDEX {
      mscRtgIndex,
      mscRtgDpnIndex,
      mscRtgDpnCsIndex }
::= { mscRtgDpnCsRowStatusTable 1 }

MscRtgDpnCsRowStatusEntry ::= SEQUENCE {
   mscRtgDpnCsRowStatus
      RowStatus,
   mscRtgDpnCsComponentName
      DisplayString,
   mscRtgDpnCsStorageType
      StorageType,
   mscRtgDpnCsIndex
      INTEGER }

mscRtgDpnCsRowStatus OBJECT-TYPE
   SYNTAX     RowStatus 
   ACCESS     read-only
   STATUS     mandatory
   DESCRIPTION
     "This variable is used as the basis for SNMP naming of
      mscRtgDpnCs components.
      These components cannot be added nor deleted."
::= { mscRtgDpnCsRowStatusEntry 1 }

mscRtgDpnCsComponentName OBJECT-TYPE
   SYNTAX     DisplayString 
   ACCESS     read-only
   STATUS     mandatory
   DESCRIPTION
     "This variable provides the component's string name for
      use with the ASCII Console Interface"
::= { mscRtgDpnCsRowStatusEntry 2 }

mscRtgDpnCsStorageType OBJECT-TYPE
   SYNTAX     StorageType 
   ACCESS     read-only
   STATUS     mandatory
   DESCRIPTION
     "This variable represents the storage type value for the
      mscRtgDpnCs tables."
::= { mscRtgDpnCsRowStatusEntry 4 }

mscRtgDpnCsIndex OBJECT-TYPE
   SYNTAX     INTEGER  {
                 dcr(1),
                 nui(4),
                 crd(5),
                 lnui(6),
                 scr(7),
                 npm(8),
                 grman(10),
                 gscr(11),
                 gdcr(12),
                 lcr(14) }
   ACCESS     not-accessible
   STATUS     mandatory
   DESCRIPTION
     "This variable represents the index for the mscRtgDpnCs tables."
::= { mscRtgDpnCsRowStatusEntry 10 }

mscRtgDpnCsDelayNextHopLinkGroupsTable OBJECT-TYPE
   SYNTAX     SEQUENCE OF MscRtgDpnCsDelayNextHopLinkGroupsEntry
   ACCESS     not-accessible
   STATUS     mandatory
   DESCRIPTION
     "*** THIS TABLE CURRENTLY NOT IMPLEMENTED ***

      This attribute indicates the delay link group, or groups, that are 
      being used to reach a neighbor which is the next hop in the path to 
      the Call Server Resource Module (CSRM) supporting the server. 
      DPN server traffic will be load shared across the links, in up to two 
      link groups, when available. The link groups selected are those 
      associated with the two loop-free paths with the lowest delay 
      metrics to the destination.
      
      The link group can be that of either a Passport node interconnection 
      or a gateway to a CSRM.
      
      If no link groups are listed then the server is not reachable in the 
      delay class of service.
      
      Link group instances are managed by the TransportResource 
      component. Further information about the links in the group can be 
      obtained from it."
::= { mscRtgDpnCs 230 }

mscRtgDpnCsDelayNextHopLinkGroupsEntry OBJECT-TYPE
   SYNTAX     MscRtgDpnCsDelayNextHopLinkGroupsEntry
   ACCESS     not-accessible
   STATUS     mandatory
   DESCRIPTION
     "An entry in the mscRtgDpnCsDelayNextHopLinkGroupsTable."
   INDEX {
      mscRtgIndex,
      mscRtgDpnIndex,
      mscRtgDpnCsIndex,
      mscRtgDpnCsDelayNextHopLinkGroupsIndex }
::= { mscRtgDpnCsDelayNextHopLinkGroupsTable 1 }

MscRtgDpnCsDelayNextHopLinkGroupsEntry ::= SEQUENCE {
   mscRtgDpnCsDelayNextHopLinkGroupsIndex
      Integer32,
   mscRtgDpnCsDelayNextHopLinkGroupsValue
      RowPointer }

mscRtgDpnCsDelayNextHopLinkGroupsIndex OBJECT-TYPE
   SYNTAX     Integer32 (0..1)
   ACCESS     not-accessible
   STATUS     mandatory
   DESCRIPTION
     "This variable represents the index for the mscRtgDpnCsDelayNextHopLinkGroupsTable."
::= { mscRtgDpnCsDelayNextHopLinkGroupsEntry 1 }

mscRtgDpnCsDelayNextHopLinkGroupsValue OBJECT-TYPE
   SYNTAX     RowPointer 
   ACCESS     read-only
   STATUS     mandatory
   DESCRIPTION
     "This variable represents an individual value for the
      mscRtgDpnCsDelayNextHopLinkGroupsTable."
::= { mscRtgDpnCsDelayNextHopLinkGroupsEntry 2 }

mscRtgDpnCsTputNextHopLinkGroupsTable OBJECT-TYPE
   SYNTAX     SEQUENCE OF MscRtgDpnCsTputNextHopLinkGroupsEntry
   ACCESS     not-accessible
   STATUS     mandatory
   DESCRIPTION
     "*** THIS TABLE CURRENTLY NOT IMPLEMENTED ***

      This attribute indicates the throughput link group, or groups, that 
      are being used to reach a neighbor which is either the next hop in 
      the path to the Call Server Resource Module (CSRM) supporting 
      the server. DPN server traffic will be load shared across the links, in 
      up to two link groups, when available. The link groups selected are 
      those associated with the two loop-free paths with the lowest 
      throughput metrics to the destination.
      
      The link group can be that of either a Passport node interconnection 
      or a gateway to the CSRM.
      
      If no link groups are listed then the server is not reachable in the 
      throughput class of service.
      
      Link group instances are managed by the TransportResource 
      component. Further information about the links in the group can be 
      obtained from it."
::= { mscRtgDpnCs 231 }

mscRtgDpnCsTputNextHopLinkGroupsEntry OBJECT-TYPE
   SYNTAX     MscRtgDpnCsTputNextHopLinkGroupsEntry
   ACCESS     not-accessible
   STATUS     mandatory
   DESCRIPTION
     "An entry in the mscRtgDpnCsTputNextHopLinkGroupsTable."
   INDEX {
      mscRtgIndex,
      mscRtgDpnIndex,
      mscRtgDpnCsIndex,
      mscRtgDpnCsTputNextHopLinkGroupsIndex }
::= { mscRtgDpnCsTputNextHopLinkGroupsTable 1 }

MscRtgDpnCsTputNextHopLinkGroupsEntry ::= SEQUENCE {
   mscRtgDpnCsTputNextHopLinkGroupsIndex
      Integer32,
   mscRtgDpnCsTputNextHopLinkGroupsValue
      RowPointer }

mscRtgDpnCsTputNextHopLinkGroupsIndex OBJECT-TYPE
   SYNTAX     Integer32 (0..1)
   ACCESS     not-accessible
   STATUS     mandatory
   DESCRIPTION
     "This variable represents the index for the mscRtgDpnCsTputNextHopLinkGroupsTable."
::= { mscRtgDpnCsTputNextHopLinkGroupsEntry 1 }

mscRtgDpnCsTputNextHopLinkGroupsValue OBJECT-TYPE
   SYNTAX     RowPointer 
   ACCESS     read-only
   STATUS     mandatory
   DESCRIPTION
     "This variable represents an individual value for the
      mscRtgDpnCsTputNextHopLinkGroupsTable."
::= { mscRtgDpnCsTputNextHopLinkGroupsEntry 2 }

mscRtgDpnCsDelayMetricTable OBJECT-TYPE
   SYNTAX     SEQUENCE OF MscRtgDpnCsDelayMetricEntry
   ACCESS     not-accessible
   STATUS     mandatory
   DESCRIPTION
     "*** THIS TABLE CURRENTLY NOT IMPLEMENTED ***

      This attribute indicates the delay metrics of up to two paths to the 
      server supported on a Call Server Resource Module (CSRM). The 
      delay metric associated with a path is computed by the routing 
      system based on the sum of the delays associated with the links in 
      the path to the CSRM supporting the server. It is computed for 
      every possible path to the server and is used by the DpnAddressPlan 
      component for path comparison purposes. A path with a lower 
      metric value is preferable to one with a higher value as it is 
      associated with lower delay facilities. The metrics displayed are 
      those of the paths being used to reach the destination.
      
      Metric values of 2147483647 for both paths means the server is 
      unreachable in the delay class of service. A metric value of 
      2147483647 for the second path only means that there is only one 
      viable delay path to the destination. A value of 0 indicates that no 
      cost is associated with the path to the destination."
::= { mscRtgDpnCs 334 }

mscRtgDpnCsDelayMetricEntry OBJECT-TYPE
   SYNTAX     MscRtgDpnCsDelayMetricEntry
   ACCESS     not-accessible
   STATUS     mandatory
   DESCRIPTION
     "An entry in the mscRtgDpnCsDelayMetricTable."
   INDEX {
      mscRtgIndex,
      mscRtgDpnIndex,
      mscRtgDpnCsIndex,
      mscRtgDpnCsDelayMetricIndex }
::= { mscRtgDpnCsDelayMetricTable 1 }

MscRtgDpnCsDelayMetricEntry ::= SEQUENCE {
   mscRtgDpnCsDelayMetricIndex
      Integer32,
   mscRtgDpnCsDelayMetricValue
      Unsigned32 }

mscRtgDpnCsDelayMetricIndex OBJECT-TYPE
   SYNTAX     Integer32 (0..1)
   ACCESS     not-accessible
   STATUS     mandatory
   DESCRIPTION
     "This variable represents the index for the mscRtgDpnCsDelayMetricTable."
::= { mscRtgDpnCsDelayMetricEntry 1 }

mscRtgDpnCsDelayMetricValue OBJECT-TYPE
   SYNTAX     Unsigned32 (0..2147483647)
   ACCESS     read-only
   STATUS     mandatory
   DESCRIPTION
     "This variable represents an individual value for the
      mscRtgDpnCsDelayMetricTable."
::= { mscRtgDpnCsDelayMetricEntry 2 }

mscRtgDpnCsTputMetricTable OBJECT-TYPE
   SYNTAX     SEQUENCE OF MscRtgDpnCsTputMetricEntry
   ACCESS     not-accessible
   STATUS     mandatory
   DESCRIPTION
     "*** THIS TABLE CURRENTLY NOT IMPLEMENTED ***

      This attribute indicates the throughput metrics of up to two paths to 
      reach the server supported on a Call Server Resource Module 
      (CSRM). The throughput metric associated with a path is computed 
      by the routing system based on the sum of the bandwidth associated 
      with the links in the path to the CSRM supporting the server. It is 
      computed for every possible path to the server and is used by the 
      DpnAddressPlan component for path comparison purposes. A path 
      with a lower metric value is preferable to one with a higher value as 
      it is associated with higher bandwidth facilities. The metrics 
      displayed are those of the paths being used to reach the destination.
      
      Metric values of 2147483647 for both paths means the server is 
      unreachable in the throughput class of service. A metric value of 
      2147483647 for the second path only means that there is only one 
      viable throughput path to the destination. A value of 0 indicates that 
      no cost is associated with the path to the destination."
::= { mscRtgDpnCs 335 }

mscRtgDpnCsTputMetricEntry OBJECT-TYPE
   SYNTAX     MscRtgDpnCsTputMetricEntry
   ACCESS     not-accessible
   STATUS     mandatory
   DESCRIPTION
     "An entry in the mscRtgDpnCsTputMetricTable."
   INDEX {
      mscRtgIndex,
      mscRtgDpnIndex,
      mscRtgDpnCsIndex,
      mscRtgDpnCsTputMetricIndex }
::= { mscRtgDpnCsTputMetricTable 1 }

MscRtgDpnCsTputMetricEntry ::= SEQUENCE {
   mscRtgDpnCsTputMetricIndex
      Integer32,
   mscRtgDpnCsTputMetricValue
      Unsigned32 }

mscRtgDpnCsTputMetricIndex OBJECT-TYPE
   SYNTAX     Integer32 (0..1)
   ACCESS     not-accessible
   STATUS     mandatory
   DESCRIPTION
     "This variable represents the index for the mscRtgDpnCsTputMetricTable."
::= { mscRtgDpnCsTputMetricEntry 1 }

mscRtgDpnCsTputMetricValue OBJECT-TYPE
   SYNTAX     Unsigned32 (0..2147483647)
   ACCESS     read-only
   STATUS     mandatory
   DESCRIPTION
     "This variable represents an individual value for the
      mscRtgDpnCsTputMetricTable."
::= { mscRtgDpnCsTputMetricEntry 2 }

mscRtgDpnCsDelayPathTrafficProportionsTable OBJECT-TYPE
   SYNTAX     SEQUENCE OF MscRtgDpnCsDelayPathTrafficProportionsEntry
   ACCESS     not-accessible
   STATUS     mandatory
   DESCRIPTION
     "*** THIS TABLE CURRENTLY NOT IMPLEMENTED ***

      This attribute indicates the target percentages of the total delay 
      traffic flows to the destination which are sent over each delay path. 
      These percentages are achieved when there is a large number of 
      virtual circuits (VCs)."
::= { mscRtgDpnCs 336 }

mscRtgDpnCsDelayPathTrafficProportionsEntry OBJECT-TYPE
   SYNTAX     MscRtgDpnCsDelayPathTrafficProportionsEntry
   ACCESS     not-accessible
   STATUS     mandatory
   DESCRIPTION
     "An entry in the mscRtgDpnCsDelayPathTrafficProportionsTable."
   INDEX {
      mscRtgIndex,
      mscRtgDpnIndex,
      mscRtgDpnCsIndex,
      mscRtgDpnCsDelayPathTrafficProportionsIndex }
::= { mscRtgDpnCsDelayPathTrafficProportionsTable 1 }

MscRtgDpnCsDelayPathTrafficProportionsEntry ::= SEQUENCE {
   mscRtgDpnCsDelayPathTrafficProportionsIndex
      Integer32,
   mscRtgDpnCsDelayPathTrafficProportionsValue
      Unsigned32 }

mscRtgDpnCsDelayPathTrafficProportionsIndex OBJECT-TYPE
   SYNTAX     Integer32 (0..1)
   ACCESS     not-accessible
   STATUS     mandatory
   DESCRIPTION
     "This variable represents the index for the mscRtgDpnCsDelayPathTrafficProportionsTable."
::= { mscRtgDpnCsDelayPathTrafficProportionsEntry 1 }

mscRtgDpnCsDelayPathTrafficProportionsValue OBJECT-TYPE
   SYNTAX     Unsigned32 (0..100)
   ACCESS     read-only
   STATUS     mandatory
   DESCRIPTION
     "This variable represents an individual value for the
      mscRtgDpnCsDelayPathTrafficProportionsTable."
::= { mscRtgDpnCsDelayPathTrafficProportionsEntry 2 }

mscRtgDpnCsTputPathTrafficProportionsTable OBJECT-TYPE
   SYNTAX     SEQUENCE OF MscRtgDpnCsTputPathTrafficProportionsEntry
   ACCESS     not-accessible
   STATUS     mandatory
   DESCRIPTION
     "*** THIS TABLE CURRENTLY NOT IMPLEMENTED ***

      This attribute indicates the target percentages of the total throughput 
      traffic flows to the destination which are sent over each throughput 
      path. These percentages are achieved when there is a large number 
      of virtual circuits (VCs)."
::= { mscRtgDpnCs 337 }

mscRtgDpnCsTputPathTrafficProportionsEntry OBJECT-TYPE
   SYNTAX     MscRtgDpnCsTputPathTrafficProportionsEntry
   ACCESS     not-accessible
   STATUS     mandatory
   DESCRIPTION
     "An entry in the mscRtgDpnCsTputPathTrafficProportionsTable."
   INDEX {
      mscRtgIndex,
      mscRtgDpnIndex,
      mscRtgDpnCsIndex,
      mscRtgDpnCsTputPathTrafficProportionsIndex }
::= { mscRtgDpnCsTputPathTrafficProportionsTable 1 }

MscRtgDpnCsTputPathTrafficProportionsEntry ::= SEQUENCE {
   mscRtgDpnCsTputPathTrafficProportionsIndex
      Integer32,
   mscRtgDpnCsTputPathTrafficProportionsValue
      Unsigned32 }

mscRtgDpnCsTputPathTrafficProportionsIndex OBJECT-TYPE
   SYNTAX     Integer32 (0..1)
   ACCESS     not-accessible
   STATUS     mandatory
   DESCRIPTION
     "This variable represents the index for the mscRtgDpnCsTputPathTrafficProportionsTable."
::= { mscRtgDpnCsTputPathTrafficProportionsEntry 1 }

mscRtgDpnCsTputPathTrafficProportionsValue OBJECT-TYPE
   SYNTAX     Unsigned32 (0..100)
   ACCESS     read-only
   STATUS     mandatory
   DESCRIPTION
     "This variable represents an individual value for the
      mscRtgDpnCsTputPathTrafficProportionsTable."
::= { mscRtgDpnCsTputPathTrafficProportionsEntry 2 }

-- 
-- *** THIS SUBTREE CURRENTLY NOT IMPLEMENTED ***
-- 

-- Routing Dpn LocalLinkGroups/<neighborNodeName>
-- This component is a dynamic subcomponent of the 
-- DpnAddressPlan. It provides information about the support of 
-- external gateways to RMs and AMs connected to this Passport 
-- node.

mscRtgDpnLg OBJECT IDENTIFIER ::= { mscRtgDpn 5 }



mscRtgDpnLgRowStatusTable OBJECT-TYPE
   SYNTAX     SEQUENCE OF MscRtgDpnLgRowStatusEntry
   ACCESS     not-accessible
   STATUS     mandatory
   DESCRIPTION
     "*** THIS TABLE CURRENTLY NOT IMPLEMENTED ***

      This entry controls the addition and deletion of 
      mscRtgDpnLg components."
::= { mscRtgDpnLg 1 }

mscRtgDpnLgRowStatusEntry OBJECT-TYPE
   SYNTAX     MscRtgDpnLgRowStatusEntry
   ACCESS     not-accessible
   STATUS     mandatory
   DESCRIPTION
     "A single entry in the table represents a single 
      mscRtgDpnLg component."
   INDEX {
      mscRtgIndex,
      mscRtgDpnIndex,
      mscRtgDpnLgIndex }
::= { mscRtgDpnLgRowStatusTable 1 }

MscRtgDpnLgRowStatusEntry ::= SEQUENCE {
   mscRtgDpnLgRowStatus
      RowStatus,
   mscRtgDpnLgComponentName
      DisplayString,
   mscRtgDpnLgStorageType
      StorageType,
   mscRtgDpnLgIndex
      AsciiStringIndex }

mscRtgDpnLgRowStatus OBJECT-TYPE
   SYNTAX     RowStatus 
   ACCESS     read-only
   STATUS     mandatory
   DESCRIPTION
     "This variable is used as the basis for SNMP naming of
      mscRtgDpnLg components.
      These components cannot be added nor deleted."
::= { mscRtgDpnLgRowStatusEntry 1 }

mscRtgDpnLgComponentName OBJECT-TYPE
   SYNTAX     DisplayString 
   ACCESS     read-only
   STATUS     mandatory
   DESCRIPTION
     "This variable provides the component's string name for
      use with the ASCII Console Interface"
::= { mscRtgDpnLgRowStatusEntry 2 }

mscRtgDpnLgStorageType OBJECT-TYPE
   SYNTAX     StorageType 
   ACCESS     read-only
   STATUS     mandatory
   DESCRIPTION
     "This variable represents the storage type value for the
      mscRtgDpnLg tables."
::= { mscRtgDpnLgRowStatusEntry 4 }

mscRtgDpnLgIndex OBJECT-TYPE
   SYNTAX     AsciiStringIndex (SIZE (1..12))
   ACCESS     not-accessible
   STATUS     mandatory
   DESCRIPTION
     "This variable represents the index for the mscRtgDpnLg tables."
::= { mscRtgDpnLgRowStatusEntry 10 }

mscRtgDpnLgOperTable OBJECT-TYPE
   SYNTAX     SEQUENCE OF MscRtgDpnLgOperEntry
   ACCESS     not-accessible
   STATUS     mandatory
   DESCRIPTION
     "*** THIS TABLE CURRENTLY NOT IMPLEMENTED ***

      This group of attributes provides information about the gateways in 
      use to reach Passports, RMs and AMs connected to this Passport 
      node."
::= { mscRtgDpnLg 3 }

mscRtgDpnLgOperEntry OBJECT-TYPE
   SYNTAX     MscRtgDpnLgOperEntry
   ACCESS     not-accessible
   STATUS     mandatory
   DESCRIPTION
     "An entry in the mscRtgDpnLgOperTable."
   INDEX {
      mscRtgIndex,
      mscRtgDpnIndex,
      mscRtgDpnLgIndex }
::= { mscRtgDpnLgOperTable 1 }

MscRtgDpnLgOperEntry ::= SEQUENCE {
   mscRtgDpnLgFarEndType
      INTEGER,
   mscRtgDpnLgFarEndRid
      Unsigned32,
   mscRtgDpnLgFarEndMid
      Unsigned32,
   mscRtgDpnLgDelayMetric
      Unsigned32,
   mscRtgDpnLgTputMetric
      Unsigned32 }

mscRtgDpnLgFarEndType OBJECT-TYPE
   SYNTAX     INTEGER  {
                 em(0),
                 rm(1),
                 am(2) }
   ACCESS     read-only
   STATUS     mandatory
   DESCRIPTION
     "This attribute indicates the type of the far end module (EM, AM or 
      RM)."
::= { mscRtgDpnLgOperEntry 1 }

mscRtgDpnLgFarEndRid OBJECT-TYPE
   SYNTAX     Unsigned32 (1..126)
   ACCESS     read-only
   STATUS     mandatory
   DESCRIPTION
     "This attribute indicates the far end neighbor RID. If the neighbor is 
      an AM then the RID is that of the Passport node."
::= { mscRtgDpnLgOperEntry 2 }

mscRtgDpnLgFarEndMid OBJECT-TYPE
   SYNTAX     Unsigned32 (1..1910)
   ACCESS     read-only
   STATUS     mandatory
   DESCRIPTION
     "This attribute indicates the far end neighbor MID."
::= { mscRtgDpnLgOperEntry 3 }

mscRtgDpnLgDelayMetric OBJECT-TYPE
   SYNTAX     Unsigned32 (1..2147483647)
   ACCESS     read-only
   STATUS     mandatory
   DESCRIPTION
     "This attribute indicates the delay metric calculated for the link 
      group.
      
      If the type of the far end switch is AM, the delay metric is 
      calculated for MID routing, ranging from 1 to 2147483647.
      
      If the type of the far end switch is EM or RM, the delay metric, 
      ranging from 1 to 255, is based on the measured round trip delay of 
      the delay preferred links in the group. A link group with a low 
      metric value is preferable to one with a higher value as it is 
      associated with lower delay facilities."
::= { mscRtgDpnLgOperEntry 4 }

mscRtgDpnLgTputMetric OBJECT-TYPE
   SYNTAX     Unsigned32 (1..2147483647)
   ACCESS     read-only
   STATUS     mandatory
   DESCRIPTION
     "This attribute indicates the throughput metric calculated for the link 
      group.
      
      If the type of the far end switch is AM, the throughput metric is 
      calculated for MID routing, ranging from 1 to 2147483647.
      
      If the type of the far end switch is EM or RM, the throughput 
      metric, ranging from 1 to 255, is based on the sum of the bandwidth 
      available for all links in the group. A link group with a low metric 
      value is preferable to one with a higher value as it is associated with 
      higher bandwidth facilities."
::= { mscRtgDpnLgOperEntry 5 }

-- 
-- *** THIS SUBTREE CURRENTLY NOT IMPLEMENTED ***
-- 

-- Routing Dpn LpStatistics/n 
-- This component provides DPN packet forwarding statistics for the 
-- LP identified by this component instance.

mscRtgDpnLpStats OBJECT IDENTIFIER ::= { mscRtgDpn 6 }



mscRtgDpnLpStatsRowStatusTable OBJECT-TYPE
   SYNTAX     SEQUENCE OF MscRtgDpnLpStatsRowStatusEntry
   ACCESS     not-accessible
   STATUS     mandatory
   DESCRIPTION
     "*** THIS TABLE CURRENTLY NOT IMPLEMENTED ***

      This entry controls the addition and deletion of 
      mscRtgDpnLpStats components."
::= { mscRtgDpnLpStats 1 }

mscRtgDpnLpStatsRowStatusEntry OBJECT-TYPE
   SYNTAX     MscRtgDpnLpStatsRowStatusEntry
   ACCESS     not-accessible
   STATUS     mandatory
   DESCRIPTION
     "A single entry in the table represents a single 
      mscRtgDpnLpStats component."
   INDEX {
      mscRtgIndex,
      mscRtgDpnIndex,
      mscRtgDpnLpStatsIndex }
::= { mscRtgDpnLpStatsRowStatusTable 1 }

MscRtgDpnLpStatsRowStatusEntry ::= SEQUENCE {
   mscRtgDpnLpStatsRowStatus
      RowStatus,
   mscRtgDpnLpStatsComponentName
      DisplayString,
   mscRtgDpnLpStatsStorageType
      StorageType,
   mscRtgDpnLpStatsIndex
      Integer32 }

mscRtgDpnLpStatsRowStatus OBJECT-TYPE
   SYNTAX     RowStatus 
   ACCESS     read-only
   STATUS     mandatory
   DESCRIPTION
     "This variable is used as the basis for SNMP naming of
      mscRtgDpnLpStats components.
      These components cannot be added nor deleted."
::= { mscRtgDpnLpStatsRowStatusEntry 1 }

mscRtgDpnLpStatsComponentName OBJECT-TYPE
   SYNTAX     DisplayString 
   ACCESS     read-only
   STATUS     mandatory
   DESCRIPTION
     "This variable provides the component's string name for
      use with the ASCII Console Interface"
::= { mscRtgDpnLpStatsRowStatusEntry 2 }

mscRtgDpnLpStatsStorageType OBJECT-TYPE
   SYNTAX     StorageType 
   ACCESS     read-only
   STATUS     mandatory
   DESCRIPTION
     "This variable represents the storage type value for the
      mscRtgDpnLpStats tables."
::= { mscRtgDpnLpStatsRowStatusEntry 4 }

mscRtgDpnLpStatsIndex OBJECT-TYPE
   SYNTAX     Integer32 (0..15)
   ACCESS     not-accessible
   STATUS     mandatory
   DESCRIPTION
     "This variable represents the index for the mscRtgDpnLpStats tables."
::= { mscRtgDpnLpStatsRowStatusEntry 10 }

mscRtgDpnLpStatsFwdStatsTable OBJECT-TYPE
   SYNTAX     SEQUENCE OF MscRtgDpnLpStatsFwdStatsEntry
   ACCESS     not-accessible
   STATUS     mandatory
   DESCRIPTION
     "*** THIS TABLE CURRENTLY NOT IMPLEMENTED ***

      This group of attributes provides DPN packet forwarding statistics 
      for this LP. The statistics can be used to monitor the connectionless 
      traffic profile on this LP."
::= { mscRtgDpnLpStats 10 }

mscRtgDpnLpStatsFwdStatsEntry OBJECT-TYPE
   SYNTAX     MscRtgDpnLpStatsFwdStatsEntry
   ACCESS     not-accessible
   STATUS     mandatory
   DESCRIPTION
     "An entry in the mscRtgDpnLpStatsFwdStatsTable."
   INDEX {
      mscRtgIndex,
      mscRtgDpnIndex,
      mscRtgDpnLpStatsIndex }
::= { mscRtgDpnLpStatsFwdStatsTable 1 }

MscRtgDpnLpStatsFwdStatsEntry ::= SEQUENCE {
   mscRtgDpnLpStatsTotalPackets
      PassportCounter64,
   mscRtgDpnLpStatsThroughputPackets
      PassportCounter64,
   mscRtgDpnLpStatsDelayPackets
      PassportCounter64,
   mscRtgDpnLpStatsNormalReliabilityPackets
      PassportCounter64,
   mscRtgDpnLpStatsHighReliabilityPackets
      PassportCounter64,
   mscRtgDpnLpStatsDiscardNoRoute
      PassportCounter64,
   mscRtgDpnLpStatsInterruptingPackets
      PassportCounter64,
   mscRtgDpnLpStatsDiscardLpCongested
      PassportCounter64 }

mscRtgDpnLpStatsTotalPackets OBJECT-TYPE
   SYNTAX     PassportCounter64 
   ACCESS     read-only
   STATUS     mandatory
   DESCRIPTION
     "This attribute counts the total number of delay and throughput 
      packets handled by DPN packet forwarding on this LP. Note that 
      DPRS packets leaving the network at this module are not counted. 
      The counter wraps to zero when the maximum value is exceeded."
::= { mscRtgDpnLpStatsFwdStatsEntry 1 }

mscRtgDpnLpStatsThroughputPackets OBJECT-TYPE
   SYNTAX     PassportCounter64 
   ACCESS     read-only
   STATUS     mandatory
   DESCRIPTION
     "This attribute counts the throughput packets handled by DPN packet 
      forwarding on this LP. Note that DPRS packets leaving the network 
      at this module are not counted. The counter wraps to zero when the 
      maximum value is exceeded."
::= { mscRtgDpnLpStatsFwdStatsEntry 2 }

mscRtgDpnLpStatsDelayPackets OBJECT-TYPE
   SYNTAX     PassportCounter64 
   ACCESS     read-only
   STATUS     mandatory
   DESCRIPTION
     "This attribute counts the delay packets handled by DPN packet 
      forwarding on this LP. Note that DPRS packets leaving the network 
      at this module are not counted. The counter wraps to zero when the 
      maximum value is exceeded."
::= { mscRtgDpnLpStatsFwdStatsEntry 3 }

mscRtgDpnLpStatsNormalReliabilityPackets OBJECT-TYPE
   SYNTAX     PassportCounter64 
   ACCESS     read-only
   STATUS     mandatory
   DESCRIPTION
     "This attribute counts the normal reliability packets handled by DPN 
      packet forwarding on this LP when the forwardingPolicy attribute 
      of Routing DpnAddressPlan is set to loadshare or loadspread. Note 
      that DPRS packets leaving the network at this module are not 
      counted. The counter wraps to zero when the maximum value is 
      exceeded."
::= { mscRtgDpnLpStatsFwdStatsEntry 4 }

mscRtgDpnLpStatsHighReliabilityPackets OBJECT-TYPE
   SYNTAX     PassportCounter64 
   ACCESS     read-only
   STATUS     mandatory
   DESCRIPTION
     "This attribute counts the high reliability packets handled by DPN 
      packet forwarding on this LP when the forwardingPolicy attribute 
      of Routing DpnAddressPlan is set to loadshare or loadspread. Note 
      that DPRS packets leaving the network at this module are not 
      counted. The counter wraps to zero when the maximum value is 
      exceeded."
::= { mscRtgDpnLpStatsFwdStatsEntry 5 }

mscRtgDpnLpStatsDiscardNoRoute OBJECT-TYPE
   SYNTAX     PassportCounter64 
   ACCESS     read-only
   STATUS     mandatory
   DESCRIPTION
     "This attribute counts the packets discarded when DPN packet 
      forwarding has failed to find a route to forward the packets on this 
      LP. Note that DPRS packets leaving the network at this module are 
      not counted. The counter wraps to zero when the maximum value is 
      exceeded."
::= { mscRtgDpnLpStatsFwdStatsEntry 6 }

mscRtgDpnLpStatsInterruptingPackets OBJECT-TYPE
   SYNTAX     PassportCounter64 
   ACCESS     read-only
   STATUS     mandatory
   DESCRIPTION
     "This attribute counts the total number of multimedia packets 
      handled by DPN packet forwarding on this LP. Note that DPRS 
      packets leaving the network at this module are not counted. The 
      counter wraps to zero when the maximum value is exceeded."
::= { mscRtgDpnLpStatsFwdStatsEntry 7 }

mscRtgDpnLpStatsDiscardLpCongested OBJECT-TYPE
   SYNTAX     PassportCounter64 
   ACCESS     read-only
   STATUS     mandatory
   DESCRIPTION
     "This attribute counts the packets that have been discarded by DPN 
      packet forwarding, on the entire module, due to congestion on this 
      LP. This value is the sum of the packets discarded by all LPs due to 
      insufficient shared memory on this one. Note that DPRS packets 
      leaving the network at this module are not counted. The counter 
      wraps to zero when the maximum value is exceeded."
::= { mscRtgDpnLpStatsFwdStatsEntry 8 }


-- Routing Dpn RidFilterInfo/<rid>
-- This component maintains information related to the filtering of 
-- RID reachability information in Routing Table Updates (RTUs) sent 
-- to and received from the instance RID.

mscRtgDpnRidFilter OBJECT IDENTIFIER ::= { mscRtgDpn 7 }



mscRtgDpnRidFilterRowStatusTable OBJECT-TYPE
   SYNTAX     SEQUENCE OF MscRtgDpnRidFilterRowStatusEntry
   ACCESS     not-accessible
   STATUS     mandatory
   DESCRIPTION
     "This entry controls the addition and deletion of 
      mscRtgDpnRidFilter components."
::= { mscRtgDpnRidFilter 1 }

mscRtgDpnRidFilterRowStatusEntry OBJECT-TYPE
   SYNTAX     MscRtgDpnRidFilterRowStatusEntry
   ACCESS     not-accessible
   STATUS     mandatory
   DESCRIPTION
     "A single entry in the table represents a single 
      mscRtgDpnRidFilter component."
   INDEX {
      mscRtgIndex,
      mscRtgDpnIndex,
      mscRtgDpnRidFilterIndex }
::= { mscRtgDpnRidFilterRowStatusTable 1 }

MscRtgDpnRidFilterRowStatusEntry ::= SEQUENCE {
   mscRtgDpnRidFilterRowStatus
      RowStatus,
   mscRtgDpnRidFilterComponentName
      DisplayString,
   mscRtgDpnRidFilterStorageType
      StorageType,
   mscRtgDpnRidFilterIndex
      Integer32 }

mscRtgDpnRidFilterRowStatus OBJECT-TYPE
   SYNTAX     RowStatus 
   ACCESS     read-write
   STATUS     mandatory
   DESCRIPTION
     "This variable is used as the basis for SNMP naming of
      mscRtgDpnRidFilter components.
      These components can be added and deleted."
::= { mscRtgDpnRidFilterRowStatusEntry 1 }

mscRtgDpnRidFilterComponentName OBJECT-TYPE
   SYNTAX     DisplayString 
   ACCESS     read-only
   STATUS     mandatory
   DESCRIPTION
     "This variable provides the component's string name for
      use with the ASCII Console Interface"
::= { mscRtgDpnRidFilterRowStatusEntry 2 }

mscRtgDpnRidFilterStorageType OBJECT-TYPE
   SYNTAX     StorageType 
   ACCESS     read-only
   STATUS     mandatory
   DESCRIPTION
     "This variable represents the storage type value for the
      mscRtgDpnRidFilter tables."
::= { mscRtgDpnRidFilterRowStatusEntry 4 }

mscRtgDpnRidFilterIndex OBJECT-TYPE
   SYNTAX     Integer32 (1..126)
   ACCESS     not-accessible
   STATUS     mandatory
   DESCRIPTION
     "This variable represents the index for the mscRtgDpnRidFilter tables."
::= { mscRtgDpnRidFilterRowStatusEntry 10 }

mscRtgDpnRidFilterImportRidListTable OBJECT-TYPE
   SYNTAX     SEQUENCE OF MscRtgDpnRidFilterImportRidListEntry
   ACCESS     not-accessible
   STATUS     mandatory
   DESCRIPTION
     "This attribute specifies the list of RIDs whose reachability 
      information will be accepted from the instance RID. Information 
      about RIDs which do not appear in this list will be ignored and this 
      node considers those RIDs to be unreachable from the instance 
      RID. Note that this also applies to the instance RID itself, that is, if 
      the instance RID does not appear in the import list, this node 
      considers the instance RID to be unreachable from the instance 
      RID.
      
      By default this list contains all valid RIDs, meaning that 
      information about all RIDs will be accepted from the instance RID. 
      
      When this list is empty, no RID information is accepted from the 
      instance RID, therefore, no RID traffic will be routed to it. A 
      warning is generated when an empty import list is detected.
      
      RID 127 is the Network Services Sharing (NSS) RID, used to 
      identify DPN-100 nodes running call servers which can be used for 
      remote call processing. This RID can be filtered like any other using 
      the import RID list."
::= { mscRtgDpnRidFilter 303 }

mscRtgDpnRidFilterImportRidListEntry OBJECT-TYPE
   SYNTAX     MscRtgDpnRidFilterImportRidListEntry
   ACCESS     not-accessible
   STATUS     mandatory
   DESCRIPTION
     "An entry in the mscRtgDpnRidFilterImportRidListTable."
   INDEX {
      mscRtgIndex,
      mscRtgDpnIndex,
      mscRtgDpnRidFilterIndex,
      mscRtgDpnRidFilterImportRidListValue }
::= { mscRtgDpnRidFilterImportRidListTable 1 }

MscRtgDpnRidFilterImportRidListEntry ::= SEQUENCE {
   mscRtgDpnRidFilterImportRidListValue
      Integer32,
   mscRtgDpnRidFilterImportRidListRowStatus
      RowStatus }

mscRtgDpnRidFilterImportRidListValue OBJECT-TYPE
   SYNTAX     Integer32 (1..127)
   ACCESS     read-write
   STATUS     mandatory
   DESCRIPTION
     "This variable represents both the value and the index for the
      mscRtgDpnRidFilterImportRidListTable."
::= { mscRtgDpnRidFilterImportRidListEntry 1 }

mscRtgDpnRidFilterImportRidListRowStatus OBJECT-TYPE
   SYNTAX     RowStatus 
   ACCESS     write-only
   STATUS     mandatory
   DESCRIPTION
     "This variable is used to control the addition and deletion 
      of individual values of the mscRtgDpnRidFilterImportRidListTable."
::= { mscRtgDpnRidFilterImportRidListEntry 2 }

mscRtgDpnRidFilterExportRidListTable OBJECT-TYPE
   SYNTAX     SEQUENCE OF MscRtgDpnRidFilterExportRidListEntry
   ACCESS     not-accessible
   STATUS     mandatory
   DESCRIPTION
     "This attribute specifies the list of RIDs whose true reachability is 
      advertised to the instance RID. RIDs which do not appear in this list 
      are advertised to the instance RID as being unreachable from this 
      node.
      
      By default, this list contains all valid RIDs, meaning that true 
      reachability information for all RIDs is advertised to the instance 
      RID. 
      
      When this list is empty, all RIDs will be advertised to the instance 
      RID as unreachable, including this node's own RID, therefore the 
      instance RID will not route any RID traffic to this RID. A warning 
      is generated when an empty export list is detected. 
      
      RID 127 is the Network Services Sharing (NSS) RID, used to 
      identify DPN-100 nodes running call servers which can be used for 
      remote call processing. This RID can be filtered like any other using 
      the import RID list."
::= { mscRtgDpnRidFilter 304 }

mscRtgDpnRidFilterExportRidListEntry OBJECT-TYPE
   SYNTAX     MscRtgDpnRidFilterExportRidListEntry
   ACCESS     not-accessible
   STATUS     mandatory
   DESCRIPTION
     "An entry in the mscRtgDpnRidFilterExportRidListTable."
   INDEX {
      mscRtgIndex,
      mscRtgDpnIndex,
      mscRtgDpnRidFilterIndex,
      mscRtgDpnRidFilterExportRidListValue }
::= { mscRtgDpnRidFilterExportRidListTable 1 }

MscRtgDpnRidFilterExportRidListEntry ::= SEQUENCE {
   mscRtgDpnRidFilterExportRidListValue
      Integer32,
   mscRtgDpnRidFilterExportRidListRowStatus
      RowStatus }

mscRtgDpnRidFilterExportRidListValue OBJECT-TYPE
   SYNTAX     Integer32 (1..127)
   ACCESS     read-write
   STATUS     mandatory
   DESCRIPTION
     "This variable represents both the value and the index for the
      mscRtgDpnRidFilterExportRidListTable."
::= { mscRtgDpnRidFilterExportRidListEntry 1 }

mscRtgDpnRidFilterExportRidListRowStatus OBJECT-TYPE
   SYNTAX     RowStatus 
   ACCESS     write-only
   STATUS     mandatory
   DESCRIPTION
     "This variable is used to control the addition and deletion 
      of individual values of the mscRtgDpnRidFilterExportRidListTable."
::= { mscRtgDpnRidFilterExportRidListEntry 2 }


-- Rtg Dpn AutomaticRouteTester
-- This component is a subcomponent of DpnAddressPlan. It provides 
-- the DPN automatic route testing capability by periodically sending 
-- DPN Ping packets to each reachable RID and MID destination in 
-- the DPN routing table. It monitors if these Ping packets are returned 
-- in a reasonable period of time (about 15 seconds), and analyzes the 
-- route information collected in these packets. 
-- 
-- An alarm will be raised if one or more of the following problems 
-- are detected to at least one of the destinations in the DPN routing 
-- table: 
-- (1) "Timeout"
-- After sending three Ping packets (one round-trip-delay Ping packet 
-- and two path Ping packets) to a destination, none of them return 
-- back in a reasonable period of time. This is referred to as a 
-- "timeout" problem to this destination.
-- (2) "Routing Loop"
-- After analyzing the route information collected in the path Ping 
-- packet(s) that have returned in time ( a path Ping packet logs  the 
-- route information (forward direction only) of all the tandem node(s) 
-- this Ping packet has traversed before it reached the destination), a 
-- routing loop is detected if a specific node appears more than once 
-- on the route. This is referred to as a "routing loop" (sometimes 
-- simply "loop") problem to this destination.
-- 
-- Information about each error destination is accessible via a dynamic 
-- sub-component under this component. If the destination is a RID 
-- destination, it will be ErrorRid/x (where x is the RID vlaue of the 
-- RID destination). For MID destination, it will be ErrorMid/y (where 
-- y is the MID value of the MID destination). The maximum number 
-- of error destinations (counting both the RID and the MID 
-- detsinations) that can be simultanuously tracked (and thus appear 
-- here) is 10. 
-- 
-- Please note that ErrorRid/x or ErrorMid/y only exist as long as 
-- there is a problem to this destination. If the problem no longer exist 
-- or this error destination becomes unreachable, the component 
-- (ErrorRid/x or ErrorMid/y) that keeps track of this error destination 
-- will be automatically removed.

mscRtgDpnArt OBJECT IDENTIFIER ::= { mscRtgDpn 9 }



mscRtgDpnArtRowStatusTable OBJECT-TYPE
   SYNTAX     SEQUENCE OF MscRtgDpnArtRowStatusEntry
   ACCESS     not-accessible
   STATUS     mandatory
   DESCRIPTION
     "This entry controls the addition and deletion of 
      mscRtgDpnArt components."
::= { mscRtgDpnArt 1 }

mscRtgDpnArtRowStatusEntry OBJECT-TYPE
   SYNTAX     MscRtgDpnArtRowStatusEntry
   ACCESS     not-accessible
   STATUS     mandatory
   DESCRIPTION
     "A single entry in the table represents a single 
      mscRtgDpnArt component."
   INDEX {
      mscRtgIndex,
      mscRtgDpnIndex,
      mscRtgDpnArtIndex }
::= { mscRtgDpnArtRowStatusTable 1 }

MscRtgDpnArtRowStatusEntry ::= SEQUENCE {
   mscRtgDpnArtRowStatus
      RowStatus,
   mscRtgDpnArtComponentName
      DisplayString,
   mscRtgDpnArtStorageType
      StorageType,
   mscRtgDpnArtIndex
      NonReplicated }

mscRtgDpnArtRowStatus OBJECT-TYPE
   SYNTAX     RowStatus 
   ACCESS     read-only
   STATUS     mandatory
   DESCRIPTION
     "This variable is used as the basis for SNMP naming of
      mscRtgDpnArt components.
      These components cannot be added nor deleted."
::= { mscRtgDpnArtRowStatusEntry 1 }

mscRtgDpnArtComponentName OBJECT-TYPE
   SYNTAX     DisplayString 
   ACCESS     read-only
   STATUS     mandatory
   DESCRIPTION
     "This variable provides the component's string name for
      use with the ASCII Console Interface"
::= { mscRtgDpnArtRowStatusEntry 2 }

mscRtgDpnArtStorageType OBJECT-TYPE
   SYNTAX     StorageType 
   ACCESS     read-only
   STATUS     mandatory
   DESCRIPTION
     "This variable represents the storage type value for the
      mscRtgDpnArt tables."
::= { mscRtgDpnArtRowStatusEntry 4 }

mscRtgDpnArtIndex OBJECT-TYPE
   SYNTAX     NonReplicated 
   ACCESS     not-accessible
   STATUS     mandatory
   DESCRIPTION
     "This variable represents the index for the mscRtgDpnArt tables."
::= { mscRtgDpnArtRowStatusEntry 10 }

mscRtgDpnArtProvTable OBJECT-TYPE
   SYNTAX     SEQUENCE OF MscRtgDpnArtProvEntry
   ACCESS     not-accessible
   STATUS     mandatory
   DESCRIPTION
     "This group of attributes provides information about the option(s) 
      and parameter(s) that the operator can set to control the behavior of 
      automatic route tester."
::= { mscRtgDpnArt 10 }

mscRtgDpnArtProvEntry OBJECT-TYPE
   SYNTAX     MscRtgDpnArtProvEntry
   ACCESS     not-accessible
   STATUS     mandatory
   DESCRIPTION
     "An entry in the mscRtgDpnArtProvTable."
   INDEX {
      mscRtgIndex,
      mscRtgDpnIndex,
      mscRtgDpnArtIndex }
::= { mscRtgDpnArtProvTable 1 }

MscRtgDpnArtProvEntry ::= SEQUENCE {
   mscRtgDpnArtCosUnderTest
      INTEGER,
   mscRtgDpnArtTestInterval
      Unsigned32 }

mscRtgDpnArtCosUnderTest OBJECT-TYPE
   SYNTAX     INTEGER  {
                 none(0),
                 delayCosOnly(1),
                 tputCosOnly(2),
                 delayAndTputCos(3) }
   ACCESS     read-write
   STATUS     mandatory
   DESCRIPTION
     "This attribute specifies the COS type(s) (delay, throughput, delay 
      and throughput) for which the automatic route testing is conducted. 
      
      A description of possible values for this attribute follows:
      none: Do not conduct route testing for any COS type (essentially 
      the automatic route tester is turned off). 
      delayCosOnly: Conduct route testing to each reachable RID and 
      MID destination for delay COS only.
      tputCosOnly: Conduct route testing to each reachable RID and MID 
      destination for throughput COS only.
      delayAndTputCos: Conduct route testing to each reachable RID 
      and MID destination for delay and throughput COSs.
      
      Setting this attribute to 'none' allows the operator to turn off the 
      automatic route tester. Using value 'delayCosOnly' or 
      'tputCosOnly' tells the automated route tester to only work on one 
      COS of the operator's choice. Choosing value 'delayAndTputCos' 
      when both the delay and throughput COSs are to be tested.
      
      The network resources consumption (such as CPU, memory, link 
      bandwidth) of the automatic route tester working on two COSs will 
      roughly be two times as much as working on only one COS. The 
      time to complete a full cycle of route testing to every reachable 
      destination is also expected to be twice as long when working on 
      two COSs."
   DEFVAL     { none }
::= { mscRtgDpnArtProvEntry 1 }

mscRtgDpnArtTestInterval OBJECT-TYPE
   SYNTAX     Unsigned32 (5..900)
   ACCESS     read-write
   STATUS     mandatory
   DESCRIPTION
     "This attribute specifies the time interval between the successive 
      testson different destinations. The automatic route tester 
      periodically tries to test the route to a different reachable destination 
      (RID or MID). In order not to put too heavy a load on the network, 
      it will wait for a period of time equal to this interval before it will 
      start working on another destination.
      
      The smaller the value of this attribute, the more frequently the 
      automatic route tester gets invoked to work on route testing. On one 
      hand, doing so will reduce the amount of time needed to complete a 
      fully cycle of route testing to every reachable destination. One the 
      other hand, this will increase the resource comsumption of the 
      automatic route tester accordingly.
      
      During each testInterval, the automatic route tester will first retry 
      the routes to each error destination, if any, to see if they have 
      recovered. After the retries of all these error destinations, another 
      RID/MID destination from the DPN routing table (not in the error 
      destination list) will be chosen to conduct route testing only if the 
      current number of error destinations is less than 10. If the number of 
      error destinations has reached 10, no other destinations will be 
      chosen and the automatic route tester will focus on retrying only 
      these error destinations at each testInterval. However, if the routes 
      to at least one error destination has recovered or has become 
      unreachable, the number of error destinations will fall below 10, 
      and the selection and conducting of route testing on another 
      destination from the DPN routing table will resume."
   DEFVAL     { 60 }
::= { mscRtgDpnArtProvEntry 2 }

mscRtgDpnArtOperTable OBJECT-TYPE
   SYNTAX     SEQUENCE OF MscRtgDpnArtOperEntry
   ACCESS     not-accessible
   STATUS     mandatory
   DESCRIPTION
     "This group of attributes provides information about the outstanding 
      error destinations discovered by the automatic route tester."
::= { mscRtgDpnArt 11 }

mscRtgDpnArtOperEntry OBJECT-TYPE
   SYNTAX     MscRtgDpnArtOperEntry
   ACCESS     not-accessible
   STATUS     mandatory
   DESCRIPTION
     "An entry in the mscRtgDpnArtOperTable."
   INDEX {
      mscRtgIndex,
      mscRtgDpnIndex,
      mscRtgDpnArtIndex }
::= { mscRtgDpnArtOperTable 1 }

MscRtgDpnArtOperEntry ::= SEQUENCE {
   mscRtgDpnArtNumOfLoopDests
      Unsigned32,
   mscRtgDpnArtNumOfTimeoutDests
      Unsigned32 }

mscRtgDpnArtNumOfLoopDests OBJECT-TYPE
   SYNTAX     Unsigned32 (0..10)
   ACCESS     read-only
   STATUS     mandatory
   DESCRIPTION
     "This attribute indicates the total number of RID and MID 
      destinations to which a routing loop problem has been detected. 
      
      Whenever a new error destination of routing loop type is found, this 
      value is increased by one, and whenever the loop problem to one 
      destination goes away or this destination has become unreachable, 
      this value is decreased by one."
   DEFVAL     { 0 }
::= { mscRtgDpnArtOperEntry 1 }

mscRtgDpnArtNumOfTimeoutDests OBJECT-TYPE
   SYNTAX     Unsigned32 (0..10)
   ACCESS     read-only
   STATUS     mandatory
   DESCRIPTION
     "This attribute indicates the total number of RID and MID 
      destinations to which a timeout problem has been detected. 
      
      Whenever a new error destination of timeout type is found, this 
      value is increased by one, and whenever the timeout problem to one 
      destination goes away or this destination has become unreachable, 
      this value is decreased by one."
   DEFVAL     { 0 }
::= { mscRtgDpnArtOperEntry 2 }

-- 
-- *** THIS SUBTREE CURRENTLY NOT IMPLEMENTED ***
-- 

-- Rtg Dpn Art ErrorRid/*
-- This component provides information about one outstanding 
-- problematic RID destination that has a timeout problem, loop 
-- problem, or both. 
-- 
-- There is one instance of this component per error RID destination.

mscRtgDpnArtErrRid OBJECT IDENTIFIER ::= { mscRtgDpnArt 2 }



mscRtgDpnArtErrRidRowStatusTable OBJECT-TYPE
   SYNTAX     SEQUENCE OF MscRtgDpnArtErrRidRowStatusEntry
   ACCESS     not-accessible
   STATUS     mandatory
   DESCRIPTION
     "*** THIS TABLE CURRENTLY NOT IMPLEMENTED ***

      This entry controls the addition and deletion of 
      mscRtgDpnArtErrRid components."
::= { mscRtgDpnArtErrRid 1 }

mscRtgDpnArtErrRidRowStatusEntry OBJECT-TYPE
   SYNTAX     MscRtgDpnArtErrRidRowStatusEntry
   ACCESS     not-accessible
   STATUS     mandatory
   DESCRIPTION
     "A single entry in the table represents a single 
      mscRtgDpnArtErrRid component."
   INDEX {
      mscRtgIndex,
      mscRtgDpnIndex,
      mscRtgDpnArtIndex,
      mscRtgDpnArtErrRidIndex }
::= { mscRtgDpnArtErrRidRowStatusTable 1 }

MscRtgDpnArtErrRidRowStatusEntry ::= SEQUENCE {
   mscRtgDpnArtErrRidRowStatus
      RowStatus,
   mscRtgDpnArtErrRidComponentName
      DisplayString,
   mscRtgDpnArtErrRidStorageType
      StorageType,
   mscRtgDpnArtErrRidIndex
      Integer32 }

mscRtgDpnArtErrRidRowStatus OBJECT-TYPE
   SYNTAX     RowStatus 
   ACCESS     read-only
   STATUS     mandatory
   DESCRIPTION
     "This variable is used as the basis for SNMP naming of
      mscRtgDpnArtErrRid components.
      These components cannot be added nor deleted."
::= { mscRtgDpnArtErrRidRowStatusEntry 1 }

mscRtgDpnArtErrRidComponentName OBJECT-TYPE
   SYNTAX     DisplayString 
   ACCESS     read-only
   STATUS     mandatory
   DESCRIPTION
     "This variable provides the component's string name for
      use with the ASCII Console Interface"
::= { mscRtgDpnArtErrRidRowStatusEntry 2 }

mscRtgDpnArtErrRidStorageType OBJECT-TYPE
   SYNTAX     StorageType 
   ACCESS     read-only
   STATUS     mandatory
   DESCRIPTION
     "This variable represents the storage type value for the
      mscRtgDpnArtErrRid tables."
::= { mscRtgDpnArtErrRidRowStatusEntry 4 }

mscRtgDpnArtErrRidIndex OBJECT-TYPE
   SYNTAX     Integer32 (1..127)
   ACCESS     not-accessible
   STATUS     mandatory
   DESCRIPTION
     "This variable represents the index for the mscRtgDpnArtErrRid tables."
::= { mscRtgDpnArtErrRidRowStatusEntry 10 }

mscRtgDpnArtErrRidOperTable OBJECT-TYPE
   SYNTAX     SEQUENCE OF MscRtgDpnArtErrRidOperEntry
   ACCESS     not-accessible
   STATUS     mandatory
   DESCRIPTION
     "*** THIS TABLE CURRENTLY NOT IMPLEMENTED ***

      This group of attributes provides information about a single error 
      destination (RID or MID) discovered by the automatic route tester."
::= { mscRtgDpnArtErrRid 10 }

mscRtgDpnArtErrRidOperEntry OBJECT-TYPE
   SYNTAX     MscRtgDpnArtErrRidOperEntry
   ACCESS     not-accessible
   STATUS     mandatory
   DESCRIPTION
     "An entry in the mscRtgDpnArtErrRidOperTable."
   INDEX {
      mscRtgIndex,
      mscRtgDpnIndex,
      mscRtgDpnArtIndex,
      mscRtgDpnArtErrRidIndex }
::= { mscRtgDpnArtErrRidOperTable 1 }

MscRtgDpnArtErrRidOperEntry ::= SEQUENCE {
   mscRtgDpnArtErrRidDelayCosErrType
      INTEGER,
   mscRtgDpnArtErrRidThroughputCosErrType
      INTEGER }

mscRtgDpnArtErrRidDelayCosErrType OBJECT-TYPE
   SYNTAX     INTEGER  {
                 noError(0),
                 timeout(1),
                 loop(2) }
   ACCESS     read-only
   STATUS     mandatory
   DESCRIPTION
     "This attribute indicates the type of error that was found with the 
      route to this destination (on delay COS) by the automatic route 
      tester."
   DEFVAL     { noError }
::= { mscRtgDpnArtErrRidOperEntry 1 }

mscRtgDpnArtErrRidThroughputCosErrType OBJECT-TYPE
   SYNTAX     INTEGER  {
                 noError(0),
                 timeout(1),
                 loop(2) }
   ACCESS     read-only
   STATUS     mandatory
   DESCRIPTION
     "This attribute indicates the type of error that was found with this 
      destination (on throughput COS) by the automatic route tester."
   DEFVAL     { noError }
::= { mscRtgDpnArtErrRidOperEntry 2 }

mscRtgDpnArtErrRidDelayErrPathTable OBJECT-TYPE
   SYNTAX     SEQUENCE OF MscRtgDpnArtErrRidDelayErrPathEntry
   ACCESS     not-accessible
   STATUS     mandatory
   DESCRIPTION
     "*** THIS TABLE CURRENTLY NOT IMPLEMENTED ***

      This attribute provides hop-by-hop route information for a 
      destination to which a routing loop problem (on delay COS) was 
      found. For a timeout problem, this information is not provided."
::= { mscRtgDpnArtErrRid 688 }

mscRtgDpnArtErrRidDelayErrPathEntry OBJECT-TYPE
   SYNTAX     MscRtgDpnArtErrRidDelayErrPathEntry
   ACCESS     not-accessible
   STATUS     mandatory
   DESCRIPTION
     "An entry in the mscRtgDpnArtErrRidDelayErrPathTable."
   INDEX {
      mscRtgIndex,
      mscRtgDpnIndex,
      mscRtgDpnArtIndex,
      mscRtgDpnArtErrRidIndex,
      mscRtgDpnArtErrRidDelayErrPathValue }
::= { mscRtgDpnArtErrRidDelayErrPathTable 1 }

MscRtgDpnArtErrRidDelayErrPathEntry ::= SEQUENCE {
   mscRtgDpnArtErrRidDelayErrPathValue
      AsciiString }

mscRtgDpnArtErrRidDelayErrPathValue OBJECT-TYPE
   SYNTAX     AsciiString (SIZE (0..32))
   ACCESS     read-only
   STATUS     mandatory
   DESCRIPTION
     "This variable represents both the value and the index for the
      mscRtgDpnArtErrRidDelayErrPathTable."
::= { mscRtgDpnArtErrRidDelayErrPathEntry 1 }

mscRtgDpnArtErrRidTputErrPathTable OBJECT-TYPE
   SYNTAX     SEQUENCE OF MscRtgDpnArtErrRidTputErrPathEntry
   ACCESS     not-accessible
   STATUS     mandatory
   DESCRIPTION
     "*** THIS TABLE CURRENTLY NOT IMPLEMENTED ***

      This attribute provides hop-by-hop route information for a 
      destination to which a routing loop problem (on throughput COS) 
      was found. For a timeout problem, this information is not provided."
::= { mscRtgDpnArtErrRid 689 }

mscRtgDpnArtErrRidTputErrPathEntry OBJECT-TYPE
   SYNTAX     MscRtgDpnArtErrRidTputErrPathEntry
   ACCESS     not-accessible
   STATUS     mandatory
   DESCRIPTION
     "An entry in the mscRtgDpnArtErrRidTputErrPathTable."
   INDEX {
      mscRtgIndex,
      mscRtgDpnIndex,
      mscRtgDpnArtIndex,
      mscRtgDpnArtErrRidIndex,
      mscRtgDpnArtErrRidTputErrPathValue }
::= { mscRtgDpnArtErrRidTputErrPathTable 1 }

MscRtgDpnArtErrRidTputErrPathEntry ::= SEQUENCE {
   mscRtgDpnArtErrRidTputErrPathValue
      AsciiString }

mscRtgDpnArtErrRidTputErrPathValue OBJECT-TYPE
   SYNTAX     AsciiString (SIZE (0..32))
   ACCESS     read-only
   STATUS     mandatory
   DESCRIPTION
     "This variable represents both the value and the index for the
      mscRtgDpnArtErrRidTputErrPathTable."
::= { mscRtgDpnArtErrRidTputErrPathEntry 1 }

-- 
-- *** THIS SUBTREE CURRENTLY NOT IMPLEMENTED ***
-- 

-- Rtg Dpn Art ErrorMid/*
-- This component provides information about one outstanding 
-- problematic MID destination that has a timeout problem, loop 
-- problem, or both. 
-- 
-- There is one instance of this component per error MID destination.

mscRtgDpnArtErrMid OBJECT IDENTIFIER ::= { mscRtgDpnArt 3 }



mscRtgDpnArtErrMidRowStatusTable OBJECT-TYPE
   SYNTAX     SEQUENCE OF MscRtgDpnArtErrMidRowStatusEntry
   ACCESS     not-accessible
   STATUS     mandatory
   DESCRIPTION
     "*** THIS TABLE CURRENTLY NOT IMPLEMENTED ***

      This entry controls the addition and deletion of 
      mscRtgDpnArtErrMid components."
::= { mscRtgDpnArtErrMid 1 }

mscRtgDpnArtErrMidRowStatusEntry OBJECT-TYPE
   SYNTAX     MscRtgDpnArtErrMidRowStatusEntry
   ACCESS     not-accessible
   STATUS     mandatory
   DESCRIPTION
     "A single entry in the table represents a single 
      mscRtgDpnArtErrMid component."
   INDEX {
      mscRtgIndex,
      mscRtgDpnIndex,
      mscRtgDpnArtIndex,
      mscRtgDpnArtErrMidIndex }
::= { mscRtgDpnArtErrMidRowStatusTable 1 }

MscRtgDpnArtErrMidRowStatusEntry ::= SEQUENCE {
   mscRtgDpnArtErrMidRowStatus
      RowStatus,
   mscRtgDpnArtErrMidComponentName
      DisplayString,
   mscRtgDpnArtErrMidStorageType
      StorageType,
   mscRtgDpnArtErrMidIndex
      Integer32 }

mscRtgDpnArtErrMidRowStatus OBJECT-TYPE
   SYNTAX     RowStatus 
   ACCESS     read-only
   STATUS     mandatory
   DESCRIPTION
     "This variable is used as the basis for SNMP naming of
      mscRtgDpnArtErrMid components.
      These components cannot be added nor deleted."
::= { mscRtgDpnArtErrMidRowStatusEntry 1 }

mscRtgDpnArtErrMidComponentName OBJECT-TYPE
   SYNTAX     DisplayString 
   ACCESS     read-only
   STATUS     mandatory
   DESCRIPTION
     "This variable provides the component's string name for
      use with the ASCII Console Interface"
::= { mscRtgDpnArtErrMidRowStatusEntry 2 }

mscRtgDpnArtErrMidStorageType OBJECT-TYPE
   SYNTAX     StorageType 
   ACCESS     read-only
   STATUS     mandatory
   DESCRIPTION
     "This variable represents the storage type value for the
      mscRtgDpnArtErrMid tables."
::= { mscRtgDpnArtErrMidRowStatusEntry 4 }

mscRtgDpnArtErrMidIndex OBJECT-TYPE
   SYNTAX     Integer32 (1..2046)
   ACCESS     not-accessible
   STATUS     mandatory
   DESCRIPTION
     "This variable represents the index for the mscRtgDpnArtErrMid tables."
::= { mscRtgDpnArtErrMidRowStatusEntry 10 }

mscRtgDpnArtErrMidOperTable OBJECT-TYPE
   SYNTAX     SEQUENCE OF MscRtgDpnArtErrMidOperEntry
   ACCESS     not-accessible
   STATUS     mandatory
   DESCRIPTION
     "*** THIS TABLE CURRENTLY NOT IMPLEMENTED ***

      This group of attributes provides information about a single error 
      destination (RID or MID) discovered by the automatic route tester."
::= { mscRtgDpnArtErrMid 10 }

mscRtgDpnArtErrMidOperEntry OBJECT-TYPE
   SYNTAX     MscRtgDpnArtErrMidOperEntry
   ACCESS     not-accessible
   STATUS     mandatory
   DESCRIPTION
     "An entry in the mscRtgDpnArtErrMidOperTable."
   INDEX {
      mscRtgIndex,
      mscRtgDpnIndex,
      mscRtgDpnArtIndex,
      mscRtgDpnArtErrMidIndex }
::= { mscRtgDpnArtErrMidOperTable 1 }

MscRtgDpnArtErrMidOperEntry ::= SEQUENCE {
   mscRtgDpnArtErrMidDelayCosErrType
      INTEGER,
   mscRtgDpnArtErrMidThroughputCosErrType
      INTEGER }

mscRtgDpnArtErrMidDelayCosErrType OBJECT-TYPE
   SYNTAX     INTEGER  {
                 noError(0),
                 timeout(1),
                 loop(2) }
   ACCESS     read-only
   STATUS     mandatory
   DESCRIPTION
     "This attribute indicates the type of error that was found with the 
      route to this destination (on delay COS) by the automatic route 
      tester."
   DEFVAL     { noError }
::= { mscRtgDpnArtErrMidOperEntry 1 }

mscRtgDpnArtErrMidThroughputCosErrType OBJECT-TYPE
   SYNTAX     INTEGER  {
                 noError(0),
                 timeout(1),
                 loop(2) }
   ACCESS     read-only
   STATUS     mandatory
   DESCRIPTION
     "This attribute indicates the type of error that was found with this 
      destination (on throughput COS) by the automatic route tester."
   DEFVAL     { noError }
::= { mscRtgDpnArtErrMidOperEntry 2 }

mscRtgDpnArtErrMidDelayErrPathTable OBJECT-TYPE
   SYNTAX     SEQUENCE OF MscRtgDpnArtErrMidDelayErrPathEntry
   ACCESS     not-accessible
   STATUS     mandatory
   DESCRIPTION
     "*** THIS TABLE CURRENTLY NOT IMPLEMENTED ***

      This attribute provides hop-by-hop route information for a 
      destination to which a routing loop problem (on delay COS) was 
      found. For a timeout problem, this information is not provided."
::= { mscRtgDpnArtErrMid 688 }

mscRtgDpnArtErrMidDelayErrPathEntry OBJECT-TYPE
   SYNTAX     MscRtgDpnArtErrMidDelayErrPathEntry
   ACCESS     not-accessible
   STATUS     mandatory
   DESCRIPTION
     "An entry in the mscRtgDpnArtErrMidDelayErrPathTable."
   INDEX {
      mscRtgIndex,
      mscRtgDpnIndex,
      mscRtgDpnArtIndex,
      mscRtgDpnArtErrMidIndex,
      mscRtgDpnArtErrMidDelayErrPathValue }
::= { mscRtgDpnArtErrMidDelayErrPathTable 1 }

MscRtgDpnArtErrMidDelayErrPathEntry ::= SEQUENCE {
   mscRtgDpnArtErrMidDelayErrPathValue
      AsciiString }

mscRtgDpnArtErrMidDelayErrPathValue OBJECT-TYPE
   SYNTAX     AsciiString (SIZE (0..32))
   ACCESS     read-only
   STATUS     mandatory
   DESCRIPTION
     "This variable represents both the value and the index for the
      mscRtgDpnArtErrMidDelayErrPathTable."
::= { mscRtgDpnArtErrMidDelayErrPathEntry 1 }

mscRtgDpnArtErrMidTputErrPathTable OBJECT-TYPE
   SYNTAX     SEQUENCE OF MscRtgDpnArtErrMidTputErrPathEntry
   ACCESS     not-accessible
   STATUS     mandatory
   DESCRIPTION
     "*** THIS TABLE CURRENTLY NOT IMPLEMENTED ***

      This attribute provides hop-by-hop route information for a 
      destination to which a routing loop problem (on throughput COS) 
      was found. For a timeout problem, this information is not provided."
::= { mscRtgDpnArtErrMid 689 }

mscRtgDpnArtErrMidTputErrPathEntry OBJECT-TYPE
   SYNTAX     MscRtgDpnArtErrMidTputErrPathEntry
   ACCESS     not-accessible
   STATUS     mandatory
   DESCRIPTION
     "An entry in the mscRtgDpnArtErrMidTputErrPathTable."
   INDEX {
      mscRtgIndex,
      mscRtgDpnIndex,
      mscRtgDpnArtIndex,
      mscRtgDpnArtErrMidIndex,
      mscRtgDpnArtErrMidTputErrPathValue }
::= { mscRtgDpnArtErrMidTputErrPathTable 1 }

MscRtgDpnArtErrMidTputErrPathEntry ::= SEQUENCE {
   mscRtgDpnArtErrMidTputErrPathValue
      AsciiString }

mscRtgDpnArtErrMidTputErrPathValue OBJECT-TYPE
   SYNTAX     AsciiString (SIZE (0..32))
   ACCESS     read-only
   STATUS     mandatory
   DESCRIPTION
     "This variable represents both the value and the index for the
      mscRtgDpnArtErrMidTputErrPathTable."
::= { mscRtgDpnArtErrMidTputErrPathEntry 1 }




-- 
-- Version and Compliance statements
-- 



-- Object-Group Statement:
-- A list of all current accessible leaf objects.

-- OBJECTS { mscRtgDpnRidFilterImportRidListValue,
--           mscRtgDpnTputMetricRangeBoundary,
--           mscRtgDpnArtErrMidDelayErrPathValue,
--           mscRtgDpnMidSubstituteRid,
--           mscRtgDpnThroughputPackets,
--           mscRtgDpnComponentName,
--           mscRtgDpnArtErrRidComponentName,
--           mscRtgDpnCallServerModuleRidsValue,
--           mscRtgDpnDiscardLpCongested,
--           mscRtgDpnArtCosUnderTest,
--           mscRtgDpnRidFilterStorageType,
--           mscRtgDpnLpStatsInterruptingPackets,
--           mscRtgDpnLgDelayMetric,
--           mscRtgDpnMidDelayNextHopLinkGroupsValue,
--           mscRtgDpnLpStatsHighReliabilityPackets,
--           mscRtgDpnMidTputPathTrafficProportionsValue,
--           mscRtgDpnCsTputMetricValue,
--           mscRtgDpnArtErrMidComponentName,
--           mscRtgDpnLogicalNetworkNumber,
--           mscRtgDpnCsDelayNextHopLinkGroupsValue,
--           mscRtgDpnLpStatsStorageType,
--           mscRtgDpnLgComponentName,
--           mscRtgDpnMidStorageType,
--           mscRtgDpnArtNumOfTimeoutDests,
--           mscRtgDpnCsTputPathTrafficProportionsValue,
--           mscRtgDpnTotalPackets,
--           mscRtgDpnArtStorageType,
--           mscRtgDpnCsStorageType,
--           mscRtgDpnRidDpnTputMetric,
--           mscRtgDpnRidFilterRowStatus,
--           mscRtgDpnRidDelayPathTrafficProportionsValue,
--           mscRtgDpnDelayMetricCutOff,
--           mscRtgDpnLgFarEndRid,
--           mscRtgDpnLpStatsRowStatus,
--           mscRtgDpnInterruptingPackets,
--           mscRtgDpnRidDelayMetricValue,
--           mscRtgDpnHighReliabilityPackets,
--           mscRtgDpnArtErrMidTputErrPathValue,
--           mscRtgDpnArtRowStatus,
--           mscRtgDpnRidMidComponentName,
--           mscRtgDpnCsRowStatus,
--           mscRtgDpnStorageType,
--           mscRtgDpnRidFilterExportRidListRowStatus,
--           mscRtgDpnArtErrRidStorageType,
--           mscRtgDpnRoutingId,
--           mscRtgDpnForwardingPolicy,
--           mscRtgDpnArtErrRidDelayCosErrType,
--           mscRtgDpnRidTputNextHopLinkGroupsValue,
--           mscRtgDpnArtTestInterval,
--           mscRtgDpnLgStorageType,
--           mscRtgDpnArtErrRidTputErrPathValue,
--           mscRtgDpnRowStatus,
--           mscRtgDpnControlPktRx,
--           mscRtgDpnArtErrRidRowStatus,
--           mscRtgDpnRidFilterExportRidListValue,
--           mscRtgDpnDelayMetricRangeBoundary,
--           mscRtgDpnRidComponentName,
--           mscRtgDpnCsDelayPathTrafficProportionsValue,
--           mscRtgDpnLpStatsDelayPackets,
--           mscRtgDpnMidDelayMetricValue,
--           mscRtgDpnLgRowStatus,
--           mscRtgDpnControlBytesTx,
--           mscRtgDpnLpStatsNormalReliabilityPackets,
--           mscRtgDpnVarianceValue,
--           mscRtgDpnMidDelayPathTrafficProportionsValue,
--           mscRtgDpnCsDelayMetricValue,
--           mscRtgDpnRidMidStorageType,
--           mscRtgDpnRidDelayNextHopLinkGroupsValue,
--           mscRtgDpnLgTputMetric,
--           mscRtgDpnModuleId,
--           mscRtgDpnLgFarEndMid,
--           mscRtgDpnArtErrRidDelayErrPathValue,
--           mscRtgDpnSubnetMidsValue,
--           mscRtgDpnMidTputMetricValue,
--           mscRtgDpnRidDpnDelayMetric,
--           mscRtgDpnArtErrRidThroughputCosErrType,
--           mscRtgDpnRidTputMetricValue,
--           mscRtgDpnControlBytesRx,
--           mscRtgDpnArtErrMidStorageType,
--           mscRtgDpnRidMidRowStatus,
--           mscRtgDpnDelayPackets,
--           mscRtgDpnRidTputPathTrafficProportionsValue,
--           mscRtgDpnArtNumOfLoopDests,
--           mscRtgDpnNormalReliabilityPackets,
--           mscRtgDpnMidRowStatus,
--           mscRtgDpnMidTputNextHopLinkGroupsValue,
--           mscRtgDpnArtErrMidThroughputCosErrType,
--           mscRtgDpnLpStatsDiscardNoRoute,
--           mscRtgDpnRidStorageType,
--           mscRtgDpnCsTputNextHopLinkGroupsValue,
--           mscRtgDpnRidFilterComponentName,
--           mscRtgDpnControlPktTx,
--           mscRtgDpnArtErrMidRowStatus,
--           mscRtgDpnLpStatsThroughputPackets,
--           mscRtgDpnLpStatsComponentName,
--           mscRtgDpnMidComponentName,
--           mscRtgDpnLpStatsDiscardLpCongested,
--           mscRtgDpnRidRowStatus,
--           mscRtgDpnArtComponentName,
--           mscRtgDpnLgFarEndType,
--           mscRtgDpnCsComponentName,
--           mscRtgDpnThroughputMetricCutOff,
--           mscRtgDpnRidFilterImportRidListRowStatus,
--           mscRtgDpnDiscardNoRoute,
--           mscRtgDpnArtErrMidDelayCosErrType,
--           mscRtgDpnOutOfSequencePkt,
--           mscRtgDpnLpStatsTotalPackets }
-- STATUS  mandatory
-- DESCRIPTION
--   "A list of all current accessible leaf objects."

dpnRoutingGroup OBJECT IDENTIFIER ::= { dpnRoutingMIB 1 }
dpnRoutingGroupCA OBJECT IDENTIFIER ::= { dpnRoutingGroup 1 }
dpnRoutingGroupCA02 OBJECT IDENTIFIER ::= { dpnRoutingGroupCA 3 }
dpnRoutingGroupCA02A OBJECT IDENTIFIER ::= { dpnRoutingGroupCA02 2 }



-- Agent-Capabilities Statement:

-- PRODUCT-RELEASE "MscPassport Release 1.2 DpnRouting."
-- STATUS          mandatory
-- DESCRIPTION     "Carrier Passport DpnRouting MIB: MIB Version CA02A,
--                  Software Version CA02S9C."
-- SUPPORTS        Nortel-MsCarrier-MscPassport-DpnRoutingMIB
--    INCLUDES     { dpnRoutingGroupCA02A }

dpnRoutingCapabilities OBJECT IDENTIFIER ::= { dpnRoutingMIB 3 }
dpnRoutingCapabilitiesCA OBJECT IDENTIFIER ::= { dpnRoutingCapabilities 1 }
dpnRoutingCapabilitiesCA02 OBJECT IDENTIFIER ::= { dpnRoutingCapabilitiesCA 3 }
dpnRoutingCapabilitiesCA02A OBJECT IDENTIFIER ::= { dpnRoutingCapabilitiesCA02 2 }





END
