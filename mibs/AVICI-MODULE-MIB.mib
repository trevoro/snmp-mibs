AVICI-MODULE-MIB DEFINITIONS ::= BEGIN

IMPORTS
   MODULE-IDENTITY, OBJECT-TYPE, Integer32, TimeTicks, Gauge32, Counter64,
   NOTIFICATION-TYPE
      FROM SNMPv2-SMI
   DisplayString
      FROM SNMPv2-TC
   MODULE-COMPLIANCE, OBJECT-GROUP, NOTIFICATION-GROUP
      FROM SNMPv2-CONF
   aviciBayIndex, aviciSlotIndex
      FROM AVICI-BAY-MIB
   AviciPartNumberType, AviciRevisionType, AviciSerialNumberType,
   AviciProductIdType, AviciHighAvailabilityType 
      FROM AVICI-TC
   aviciMibs
      FROM AVICI-SMI
   aviciSysTrapDescr
      FROM AVICI-SYSTEM-MIB;   

aviciModuleMIB MODULE-IDENTITY
--  Should be: LAST-UPDATED   "200003031812Z"
   LAST-UPDATED   "010316134800Z"
   ORGANIZATION   "Avici Systems, Inc."
   CONTACT-INFO   "
                  Avici Systems, Inc.
                  101 Billerica Avenue
                  North Billerica, MA 01862-1256
 
                  (978) 964-2000
                  (978) 964-2100 (fax)
 
                  snmp@avici.com"
   DESCRIPTION
      "This MIB module specifies those managed objects that monitor and
       control a forwarding module."
   REVISION      "010316134800Z"
   DESCRIPTION
      "Added new aviciModuleIncompatibleSW trap."
   REVISION      "000303181200Z"
   DESCRIPTION
      "Added two new enumerated values to the aviciModuleOperStatus object."
   REVISION      "000523151500Z"
   DESCRIPTION
      "Cleaned up mib."
   REVISION      "990330095500Z"
   DESCRIPTION
      "Created MIB module."
   ::= { aviciMibs 5 }


aviciModuleObjects       OBJECT IDENTIFIER ::= { aviciModuleMIB 1 }

aviciModuleNotifications OBJECT IDENTIFIER ::= { aviciModuleMIB 2 }

aviciModuleNotificationPrefix OBJECT IDENTIFIER ::=
     { aviciModuleNotifications 0 }

aviciServerAccessModuleNotifications OBJECT IDENTIFIER ::= { aviciModuleMIB 4 }

aviciServerAccessModuleNotificationPrefix OBJECT IDENTIFIER ::= 
     { aviciServerAccessModuleNotifications 0 }

--  the Module table
--        
--  This table contains parameters and state variables
--  for modules within the System.

aviciModuleTable    OBJECT-TYPE
        SYNTAX      SEQUENCE OF AviciModuleEntry
        MAX-ACCESS  not-accessible
        STATUS      current
        DESCRIPTION
            "This table contains parameters and state variables
             for all modules in the system."
        ::= { aviciModuleObjects 1 }

aviciModuleEntry    OBJECT-TYPE
        SYNTAX      AviciModuleEntry
        MAX-ACCESS  not-accessible
        STATUS      current
        DESCRIPTION
            "The status and parameter values for a module
             in the TSR bay."
        INDEX       { aviciBayIndex, aviciSlotIndex }
        ::= { aviciModuleTable 1 }
    
AviciModuleEntry ::= SEQUENCE {
         aviciModuleAdminStatus      INTEGER,
         aviciModuleOperStatus       INTEGER,
         aviciModuleUpTime           TimeTicks,
         aviciModuleCurrTemp         Integer32,
         aviciModuleMaxTemp          Gauge32,
         aviciModuleDescr            DisplayString,
         aviciModuleAssySerialNumber AviciSerialNumberType,
         aviciModuleLineSerialNumber AviciSerialNumberType,
         aviciModuleMbSerialNumber   AviciSerialNumberType,
         aviciModuleAssyRevision     AviciRevisionType,
         aviciModuleLineRevision     AviciRevisionType,
         aviciModuleMbRevision       AviciRevisionType,
         aviciModuleSoftwareVersion  DisplayString,
         aviciModuleFirmwareVersion  DisplayString,
         aviciModuleAssyProductId    AviciProductIdType,
         aviciModuleLinePartNumber   AviciPartNumberType,
         aviciModuleMbPartNumber     AviciPartNumberType
    }
    
aviciModuleAdminStatus OBJECT-TYPE
   	SYNTAX INTEGER {                  
       		up (1),                  
        	down (2)
   	}                          
   	MAX-ACCESS   read-write   
   	STATUS       current     
   	DESCRIPTION                          
       		"The administrative state of this module."
   	DEFVAL { down }        
     ::= { aviciModuleEntry 1 }

aviciModuleOperStatus OBJECT-TYPE
        SYNTAX INTEGER {
               up(1),
               down(2),
               unconfigured(3),
               unknown(4),
               testing(5),
               failed(6),
	       misconfigured(7),
	       incompatibleSW(8),
	       upgrading(9)
        }
        MAX-ACCESS   read-only
        STATUS       current
        DESCRIPTION
                "The operating state of the module."
     ::= { aviciModuleEntry 2 }
 
aviciModuleUpTime   OBJECT-TYPE
        SYNTAX      TimeTicks
        MAX-ACCESS  read-only
        STATUS      current
        DESCRIPTION
            "The time in 100ths of seconds since the the
             module booted."
        ::= { aviciModuleEntry 3 }
    
aviciModuleCurrTemp OBJECT-TYPE
        SYNTAX      Integer32
        MAX-ACCESS  read-only
        STATUS      current
        DESCRIPTION
            "The current temperature of the module in degrees C."
        ::= { aviciModuleEntry 4 }
    
aviciModuleMaxTemp  OBJECT-TYPE
        SYNTAX      Gauge32
        MAX-ACCESS  read-only
        STATUS      current
        DESCRIPTION
            "The maximum temperature reported by the module in
             degrees C."
        ::= { aviciModuleEntry 5 }

aviciModuleDescr    OBJECT-TYPE
        SYNTAX      DisplayString (SIZE (0..255))
        MAX-ACCESS  read-only
        STATUS      current
        DESCRIPTION
            "A text string containing a description of the type
             of module card in the slot."
        ::= { aviciModuleEntry 6 }
    
aviciModuleAssySerialNumber   OBJECT-TYPE
        SYNTAX      AviciSerialNumberType
        MAX-ACCESS  read-only
        STATUS      current
        DESCRIPTION
            "The serial number of the module assembly in the slot."
        ::= { aviciModuleEntry 7 }
    
aviciModuleLineSerialNumber   OBJECT-TYPE
        SYNTAX      AviciSerialNumberType
        MAX-ACCESS  read-only
        STATUS      current
        DESCRIPTION
            "The serial number of the line card attached to
             the module in the slot."
        ::= { aviciModuleEntry 8 }

aviciModuleMbSerialNumber     OBJECT-TYPE
        SYNTAX      AviciSerialNumberType
        MAX-ACCESS  read-only
        STATUS      current
        DESCRIPTION
            "The serial number of the mother board in the slot."
        ::= { aviciModuleEntry 9 }    

aviciModuleAssyRevision       OBJECT-TYPE
        SYNTAX      AviciRevisionType
        MAX-ACCESS  read-only
        STATUS      current
        DESCRIPTION
            "The revision number of the module assembly in the slot."
        ::= { aviciModuleEntry 10 }    
    
aviciModuleLineRevision       OBJECT-TYPE
        SYNTAX      AviciRevisionType
        MAX-ACCESS  read-only
        STATUS      current
        DESCRIPTION
            "The revision number of the line card attached
             to the module in the slot."
        ::= { aviciModuleEntry 11 }

aviciModuleMbRevision         OBJECT-TYPE
        SYNTAX      AviciRevisionType
        MAX-ACCESS  read-only
        STATUS      current
        DESCRIPTION
            "The revision number of the mother board in the slot."
        ::= { aviciModuleEntry 12 }    

aviciModuleSoftwareVersion    OBJECT-TYPE
        SYNTAX      DisplayString (SIZE (0..255))
        MAX-ACCESS  read-only
        STATUS      current
        DESCRIPTION
            "The version of the software running on the module in the slot."
        ::= { aviciModuleEntry 13 }  

aviciModuleFirmwareVersion    OBJECT-TYPE
        SYNTAX      DisplayString (SIZE (0..255))
        MAX-ACCESS  read-only
        STATUS      current
        DESCRIPTION
            "The version of the firmware running on the module in the slot."
        ::= { aviciModuleEntry 14 }  

aviciModuleAssyProductId      OBJECT-TYPE
        SYNTAX      AviciProductIdType
        MAX-ACCESS  read-only
        STATUS      current
        DESCRIPTION
            "The product identification number of the module assembly in
             the slot."
        ::= { aviciModuleEntry 15 }      

aviciModuleLinePartNumber     OBJECT-TYPE
        SYNTAX      AviciPartNumberType
        MAX-ACCESS  read-only
        STATUS      current
        DESCRIPTION
            "The part number of the line card attached to the module in
             the slot."
        ::= { aviciModuleEntry 16 }  

aviciModuleMbPartNumber       OBJECT-TYPE
        SYNTAX      AviciPartNumberType
        MAX-ACCESS  read-only
        STATUS      current
        DESCRIPTION
            "The part number of the mother board in the slot."
        ::= { aviciModuleEntry 17 }         
        

--
--  the Module IP table
--

aviciModuleIpTable     OBJECT-TYPE
        SYNTAX      SEQUENCE OF AviciModuleIpEntry
        MAX-ACCESS  not-accessible
        STATUS      current
        DESCRIPTION
                "This table contains the per-module Avici proprietary
                 IP counters."
        ::= { aviciModuleObjects 2 }
    
aviciModuleIpEntry     OBJECT-TYPE
        SYNTAX      AviciModuleIpEntry
        MAX-ACCESS  not-accessible
        STATUS      current
        DESCRIPTION
                "The per module aggregate IP counters."
        INDEX       { aviciBayIndex, aviciSlotIndex }
        ::= { aviciModuleIpTable 1 }
    
AviciModuleIpEntry ::= SEQUENCE {
        aviciModuleIpInReceives      Counter64,
        aviciModuleIpInHdrErrors     Counter64,
        aviciModuleIpInAddrErrors    Counter64,
        aviciModuleIpForwDatagrams   Counter64,
        aviciModuleIpInUnknownProtos Counter64,
        aviciModuleIpInDiscards      Counter64,
        aviciModuleIpInDelivers      Counter64,
        aviciModuleIpOutRequests     Counter64,
        aviciModuleIpOutDiscards     Counter64,
        aviciModuleIpOutNoRoutes     Counter64,
        aviciModuleIpFragOKs         Counter64,
        aviciModuleIpFragFails       Counter64,
        aviciModuleIpFragCreates     Counter64
    }

aviciModuleIpInReceives OBJECT-TYPE
    SYNTAX      Counter64
    MAX-ACCESS  read-only
    STATUS      current
    DESCRIPTION
            "The total number of input datagrams received from
            interfaces, including those received in error."
    ::= { aviciModuleIpEntry 1 }


aviciModuleIpInHdrErrors OBJECT-TYPE
    SYNTAX      Counter64
    MAX-ACCESS  read-only
    STATUS      current
    DESCRIPTION
            "The number of input datagrams discarded due to errors in
            their IP headers, including bad checksums, version number
            mismatch, other format errors, time-to-live exceeded, errors
            discovered in processing their IP options, etc."
    ::= { aviciModuleIpEntry 2 }

aviciModuleIpInAddrErrors OBJECT-TYPE
    SYNTAX      Counter64
    MAX-ACCESS  read-only
    STATUS      current
    DESCRIPTION
            "The number of input datagrams discarded because the IP
            address in their IP header's destination field was not a
            valid address to be received at this entity.  This count
            includes invalid addresses (e.g., 0.0.0.0) and addresses of
            unsupported Classes (e.g., Class E).  For entities which are
            not IP routers and therefore do not forward datagrams, this
            counter includes datagrams discarded because the destination
            address was not a local address."
    ::= { aviciModuleIpEntry 3 }

aviciModuleIpForwDatagrams OBJECT-TYPE
    SYNTAX      Counter64
    MAX-ACCESS  read-only
    STATUS      current
    DESCRIPTION
            "The number of input datagrams for which this entity was not
            their final IP destination, as a result of which an attempt
            was made to find a route to forward them to that final
            destination.  In entities which do not act as IP routers,
            this counter will include only those packets which were
            Source-Routed via this entity, and the Source-Route option
            processing was successful."
    ::= { aviciModuleIpEntry 4 }

aviciModuleIpInUnknownProtos OBJECT-TYPE
    SYNTAX      Counter64
    MAX-ACCESS  read-only
    STATUS      current
    DESCRIPTION
            "The number of locally-addressed datagrams received
            successfully but discarded because of an unknown or
            unsupported protocol."

    ::= { aviciModuleIpEntry 5 }

aviciModuleIpInDiscards OBJECT-TYPE
    SYNTAX      Counter64
    MAX-ACCESS  read-only
    STATUS      current
    DESCRIPTION
            "The number of input IP datagrams for which no problems were
            encountered to prevent their continued processing, but which
            were discarded (e.g., for lack of buffer space).  Note that
            this counter does not include any datagrams discarded while
            awaiting re-assembly."
    ::= { aviciModuleIpEntry 6 }

aviciModuleIpInDelivers OBJECT-TYPE
    SYNTAX      Counter64
    MAX-ACCESS  read-only
    STATUS      current
    DESCRIPTION
            "The total number of input datagrams successfully delivered
            to IP user-protocols (including ICMP)."
    ::= { aviciModuleIpEntry 7 }

aviciModuleIpOutRequests OBJECT-TYPE
    SYNTAX      Counter64
    MAX-ACCESS  read-only
    STATUS      current
    DESCRIPTION
            "The total number of IP datagrams which local IP user-
            protocols (including ICMP) supplied to IP in requests for
            transmission.  Note that this counter does not include any
            datagrams counted in ipForwDatagrams."
    ::= { aviciModuleIpEntry 8 }

aviciModuleIpOutDiscards OBJECT-TYPE
    SYNTAX      Counter64
    MAX-ACCESS  read-only
    STATUS      current
    DESCRIPTION
            "The number of output IP datagrams for which no problem was
            encountered to prevent their transmission to their
            destination, but which were discarded (e.g., for lack of
            buffer space).  Note that this counter would include
            datagrams counted in ipForwDatagrams if any such packets met
            this (discretionary) discard criterion."
    ::= { aviciModuleIpEntry 9 }

aviciModuleIpOutNoRoutes OBJECT-TYPE
    SYNTAX      Counter64
    MAX-ACCESS  read-only
    STATUS      current
    DESCRIPTION
            "The number of IP datagrams discarded because no route could
            be found to transmit them to their destination.  Note that
            this counter includes any packets counted in ipForwDatagrams
            which meet this `no-route' criterion.  Note that this
            includes any datagrams which a host cannot route because all
            of its default routers are down."
    ::= { aviciModuleIpEntry 10 }

aviciModuleIpFragOKs OBJECT-TYPE
    SYNTAX      Counter64
    MAX-ACCESS  read-only
    STATUS      current
    DESCRIPTION
            "The number of IP datagrams that have been successfully
            fragmented at this entity."
    ::= { aviciModuleIpEntry 11 }

aviciModuleIpFragFails OBJECT-TYPE
    SYNTAX      Counter64
    MAX-ACCESS  read-only
    STATUS      current
    DESCRIPTION
            "The number of IP datagrams that have been discarded because
            they needed to be fragmented at this entity but could not
            be, e.g., because their Don't Fragment flag was set."
    ::= { aviciModuleIpEntry 12 }

aviciModuleIpFragCreates OBJECT-TYPE
    SYNTAX      Counter64
    MAX-ACCESS  read-only
    STATUS      current
    DESCRIPTION
            "The number of IP datagram fragments that have been
            generated as a result of fragmentation at this entity."
    ::= { aviciModuleIpEntry 13 }

--
--  the Module ICMP table
--

aviciModuleIcmpTable   OBJECT-TYPE
        SYNTAX      SEQUENCE OF AviciModuleIcmpEntry
        MAX-ACCESS  not-accessible
        STATUS      current
        DESCRIPTION
                "This table contains the per-module Avici proprietary
                 ICMP counters."
        ::= { aviciModuleObjects 3 }
    
aviciModuleIcmpEntry   OBJECT-TYPE
        SYNTAX      AviciModuleIcmpEntry
        MAX-ACCESS  not-accessible
        STATUS      current
        DESCRIPTION
                ""
        INDEX       { aviciBayIndex, aviciSlotIndex}
        ::= { aviciModuleIcmpTable 1 }
    
AviciModuleIcmpEntry ::= SEQUENCE {
        aviciModuleIcmpInMsgs           Counter64,
        aviciModuleIcmpInErrors         Counter64,
        aviciModuleIcmpInDestUnreachs   Counter64,
        aviciModuleIcmpInTimeExcds      Counter64,
        aviciModuleIcmpInParmProbs      Counter64,
        aviciModuleIcmpInSrcQuenchs     Counter64,
        aviciModuleIcmpInRedirects      Counter64,
        aviciModuleIcmpInEchos          Counter64,
        aviciModuleIcmpInEchoReps       Counter64,
        aviciModuleIcmpInTimestamps     Counter64,
        aviciModuleIcmpInTimestampReps  Counter64,
        aviciModuleIcmpInAddrMasks      Counter64,
        aviciModuleIcmpInAddrMaskReps   Counter64,
        aviciModuleIcmpOutMsgs          Counter64,
        aviciModuleIcmpOutErrors        Counter64,
        aviciModuleIcmpOutDestUnreachs  Counter64,
        aviciModuleIcmpOutTimeExcds     Counter64,
        aviciModuleIcmpOutParmProbs     Counter64,
        aviciModuleIcmpOutSrcQuenchs    Counter64,
        aviciModuleIcmpOutRedirects     Counter64,
        aviciModuleIcmpOutEchos         Counter64,
        aviciModuleIcmpOutEchoReps      Counter64,
        aviciModuleIcmpOutTimestamps    Counter64,
        aviciModuleIcmpOutTimestampReps Counter64,
        aviciModuleIcmpOutAddrMasks     Counter64,
        aviciModuleIcmpOutAddrMaskReps  Counter64
    }
aviciModuleIcmpInMsgs OBJECT-TYPE
        SYNTAX      Counter64
        MAX-ACCESS  read-only
        STATUS      current
        DESCRIPTION
            "The total number of ICMP messages which the entity
             received.  Note that this counter includes all those counted
             by aviciModuleIcmpInErrors."
        ::= { aviciModuleIcmpEntry 1 }

aviciModuleIcmpInErrors OBJECT-TYPE
        SYNTAX      Counter64
        MAX-ACCESS  read-only
        STATUS      current
        DESCRIPTION
            "The number of ICMP messages which the entity received but
            determined as having ICMP-specific errors (bad ICMP
            checksums, bad length, etc.)."
        ::= { aviciModuleIcmpEntry 2 }

aviciModuleIcmpInDestUnreachs OBJECT-TYPE
        SYNTAX      Counter64
        MAX-ACCESS  read-only
        STATUS      current
        DESCRIPTION
            "The number of ICMP destination unreachable messages
             received."
        ::= { aviciModuleIcmpEntry 3 }

aviciModuleIcmpInTimeExcds OBJECT-TYPE
        SYNTAX      Counter64
        MAX-ACCESS  read-only
        STATUS      current
        DESCRIPTION
            "The number of ICMP time exceeded messages received."
        ::= { aviciModuleIcmpEntry 4 }

aviciModuleIcmpInParmProbs OBJECT-TYPE
        SYNTAX      Counter64
        MAX-ACCESS  read-only
        STATUS      current
        DESCRIPTION
            "The number of ICMP parameter problem messages received."
        ::= { aviciModuleIcmpEntry 5 }

aviciModuleIcmpInSrcQuenchs OBJECT-TYPE
        SYNTAX      Counter64
        MAX-ACCESS  read-only
        STATUS      current
        DESCRIPTION
            "The number of ICMP source quench messages received."
        ::= { aviciModuleIcmpEntry 6 }

aviciModuleIcmpInRedirects OBJECT-TYPE
        SYNTAX      Counter64
        MAX-ACCESS  read-only
        STATUS      current
        DESCRIPTION
            "The number of ICMP redirect messages received."
        ::= { aviciModuleIcmpEntry 7 }

aviciModuleIcmpInEchos OBJECT-TYPE
        SYNTAX      Counter64
        MAX-ACCESS  read-only
        STATUS      current
        DESCRIPTION
            "The number of ICMP echo request messages received."
        ::= { aviciModuleIcmpEntry 8 }

aviciModuleIcmpInEchoReps OBJECT-TYPE
        SYNTAX      Counter64
        MAX-ACCESS  read-only
        STATUS      current
        DESCRIPTION
            "The number of ICMP echo reply messages received."
        ::= { aviciModuleIcmpEntry 9 }

aviciModuleIcmpInTimestamps OBJECT-TYPE
        SYNTAX      Counter64
        MAX-ACCESS  read-only
        STATUS      current
        DESCRIPTION
            "The number of ICMP timestamp request messages received."
        ::= { aviciModuleIcmpEntry 10 }

aviciModuleIcmpInTimestampReps OBJECT-TYPE
        SYNTAX      Counter64
        MAX-ACCESS  read-only
        STATUS      current
        DESCRIPTION
            "The number of ICMP timestamp reply messages received."
        ::= { aviciModuleIcmpEntry 11 }

aviciModuleIcmpInAddrMasks OBJECT-TYPE
        SYNTAX      Counter64
        MAX-ACCESS  read-only
        STATUS      current
        DESCRIPTION
            "The number of ICMP address mask request messages received."
        ::= { aviciModuleIcmpEntry 12 }

aviciModuleIcmpInAddrMaskReps OBJECT-TYPE
        SYNTAX      Counter64
        MAX-ACCESS  read-only
        STATUS      current
        DESCRIPTION
            "The number of ICMP address mask reply messages received."
        ::= { aviciModuleIcmpEntry 13 }

aviciModuleIcmpOutMsgs OBJECT-TYPE
        SYNTAX      Counter64
        MAX-ACCESS  read-only
        STATUS      current
        DESCRIPTION
            "The total number of ICMP messages which this entity
             attempted to send.  Note that this counter includes all
             those counted by tsrIcmpOutErrors."
        ::= { aviciModuleIcmpEntry 14 }

aviciModuleIcmpOutErrors OBJECT-TYPE
        SYNTAX      Counter64
        MAX-ACCESS  read-only
        STATUS      current
        DESCRIPTION
            "The number of ICMP messages which this entity did not send
             due to problems discovered within ICMP such as a lack of
             buffers.  This value should not include errors discovered
             outside the ICMP layer such as the inability of IP to route
             the resultant datagram.  In some implementations there may
             be no types of error which contribute to this counter's
             value."
        ::= { aviciModuleIcmpEntry 15 }

aviciModuleIcmpOutDestUnreachs OBJECT-TYPE
        SYNTAX      Counter64
        MAX-ACCESS  read-only
        STATUS      current
        DESCRIPTION
            "The number of ICMP destination unreachable messages sent."
        ::= { aviciModuleIcmpEntry 16 }

aviciModuleIcmpOutTimeExcds OBJECT-TYPE
        SYNTAX      Counter64
        MAX-ACCESS  read-only
        STATUS      current
        DESCRIPTION
            "The number of ICMP time exceeded messages sent."
        ::= { aviciModuleIcmpEntry 17 }

aviciModuleIcmpOutParmProbs OBJECT-TYPE
        SYNTAX      Counter64
        MAX-ACCESS  read-only
        STATUS      current
        DESCRIPTION
            "The number of ICMP parameter problem messages sent."
        ::= { aviciModuleIcmpEntry 18 }

aviciModuleIcmpOutSrcQuenchs OBJECT-TYPE
        SYNTAX      Counter64
        MAX-ACCESS  read-only
        STATUS      current
        DESCRIPTION
            "The number of ICMP source quench messages sent."
        ::= { aviciModuleIcmpEntry 19 }

aviciModuleIcmpOutRedirects OBJECT-TYPE
        SYNTAX      Counter64
        MAX-ACCESS  read-only
        STATUS      current
        DESCRIPTION
            "The number of ICMP Redirect messages sent.  For a host,
             this object will always be zero, since hosts do not send
             redirects."
        ::= { aviciModuleIcmpEntry 20 }

aviciModuleIcmpOutEchos OBJECT-TYPE
        SYNTAX      Counter64
        MAX-ACCESS  read-only
        STATUS      current
        DESCRIPTION
            "The number of ICMP echo request messages sent."
        ::= { aviciModuleIcmpEntry 21 }

aviciModuleIcmpOutEchoReps OBJECT-TYPE
        SYNTAX      Counter64
        MAX-ACCESS  read-only
        STATUS      current
        DESCRIPTION
            "The number of ICMP echo reply messages sent."
        ::= { aviciModuleIcmpEntry 22 }

aviciModuleIcmpOutTimestamps OBJECT-TYPE
        SYNTAX      Counter64
        MAX-ACCESS  read-only
        STATUS      current
        DESCRIPTION
            "The number of ICMP timestamp request messages sent."
        ::= { aviciModuleIcmpEntry 23 }

aviciModuleIcmpOutTimestampReps OBJECT-TYPE
        SYNTAX      Counter64
        MAX-ACCESS  read-only
        STATUS      current
        DESCRIPTION
            "The number of ICMP timestamp reply messages sent."
        ::= { aviciModuleIcmpEntry 24 }

aviciModuleIcmpOutAddrMasks OBJECT-TYPE
        SYNTAX      Counter64
        MAX-ACCESS  read-only
        STATUS      current
        DESCRIPTION
            "The number of ICMP address mask request messages sent."
        ::= { aviciModuleIcmpEntry 25 }

aviciModuleIcmpOutAddrMaskReps OBJECT-TYPE
        SYNTAX      Counter64
        MAX-ACCESS  read-only
        STATUS      current
        DESCRIPTION
            "The number of ICMP address mask reply messages sent."
        ::= { aviciModuleIcmpEntry 26 }


--  the Server Access Module table
--        
--  This table contains parameters and state variables
--  for server access modules within the System.

aviciServerAccessModuleTable    OBJECT-TYPE
        SYNTAX      SEQUENCE OF AviciServerAccessModuleEntry
        MAX-ACCESS  not-accessible
        STATUS      current
        DESCRIPTION
            "This table contains parameters and state variables
            for all server access modules in the system."
        ::= { aviciModuleObjects 4 }

aviciServerAccessModuleEntry    OBJECT-TYPE
        SYNTAX      AviciServerAccessModuleEntry
        MAX-ACCESS  not-accessible
        STATUS      current
        DESCRIPTION
            "The status and parameter values for a server
             access module."
        INDEX       { aviciBayIndex, aviciSlotIndex }
        ::= { aviciServerAccessModuleTable 1 }
    
AviciServerAccessModuleEntry ::= SEQUENCE {
        aviciServerAccessModuleType           AviciHighAvailabilityType,
        aviciServerAccessModuleLinkStatus     INTEGER,
        aviciServerAccessModuleNumTransitions Gauge32,
        aviciServerAccessModuleLastTransition TimeTicks
        }

aviciServerAccessModuleType OBJECT-TYPE
        SYNTAX AviciHighAvailabilityType
        MAX-ACCESS  read-only
        STATUS      current
        DESCRIPTION
            "The type of Server Access Module (either primary or secondary)."
        ::= { aviciServerAccessModuleEntry 1 }

aviciServerAccessModuleLinkStatus OBJECT-TYPE
        SYNTAX INTEGER {                  
            up (1),                  
            down (2)
   	}
        MAX-ACCESS  read-only
        STATUS      current
        DESCRIPTION
            "Current state of the link to this Server Access Module as
             seen from the server's point of view."
        ::= { aviciServerAccessModuleEntry 2 }

aviciServerAccessModuleNumTransitions OBJECT-TYPE
        SYNTAX      Gauge32
        MAX-ACCESS  read-only
        STATUS      current
        DESCRIPTION
            "The number of times this Server Access Module has transitioned
             into the primary role."
        ::= { aviciServerAccessModuleEntry 3 }

aviciServerAccessModuleLastTransition OBJECT-TYPE
        SYNTAX      TimeTicks
        MAX-ACCESS  read-only
        STATUS      current
        DESCRIPTION
            "The last time this Server Access Module transitioned
             into the primary role."
        ::= { aviciServerAccessModuleEntry 4 }



--
-- Notifications
--

aviciModuleColdStart  NOTIFICATION-TYPE
        OBJECTS {
                aviciBayIndex,
                aviciSlotIndex,
                aviciSysTrapDescr
		}
	STATUS	current
	DESCRIPTION
            "An aviciModuleColdStart trap indicates that the
             specified module has powered-up."
	::= { aviciModuleNotificationPrefix 1 }

aviciModuleWarmStart  NOTIFICATION-TYPE
        OBJECTS {
                aviciBayIndex,
                aviciSlotIndex,
                aviciSysTrapDescr
                }
        STATUS  current
        DESCRIPTION
            "An aviciModuleWarmStart notification indicates that the
             specified module has restarted."
        ::= { aviciModuleNotificationPrefix 2 }

aviciModuleDown  NOTIFICATION-TYPE
        OBJECTS {
                aviciBayIndex,
                aviciSlotIndex,
                aviciModuleAdminStatus,
                aviciSysTrapDescr
                }
        STATUS  current
        DESCRIPTION
            "The aviciModuleDown notification indicates that a server  
             is no longer communicating with the specified module after
             having established communication."
        ::= { aviciModuleNotificationPrefix 3 }

aviciModuleTemperatureNormal NOTIFICATION-TYPE
        OBJECTS { 
                aviciBayIndex, 
                aviciSlotIndex, 
                aviciModuleCurrTemp,
                aviciSysTrapDescr
                }
        STATUS       current
        DESCRIPTION
            "The moduleTemperatureNormal notification signifies that the
             specified module is now operating within the normal temperature
             range.  The current temperature is reported in the 
             aviciModuleCurrTemp object."
    ::= { aviciModuleNotificationPrefix 4 }

aviciModuleTemperatureMinor NOTIFICATION-TYPE
        OBJECTS {
                aviciBayIndex,
                aviciSlotIndex,
                aviciModuleCurrTemp,
                aviciSysTrapDescr
                }
        STATUS       current
        DESCRIPTION
            "The aviciModuleTemperatureMinor notification signifies that the
             specified module is reporting a temperature above the minor
             temperature threshold but below the major temperature threshold.
             The current module temperature is reported in the
             aviciModuleCurrTemp object.  When the reported temperature drops
             below the minor threshold, the aviciModuleTemperatureNormal
             notification will be sent to clear this fault."
    ::= { aviciModuleNotificationPrefix 5 }

aviciModuleTemperatureMajor NOTIFICATION-TYPE
        OBJECTS {
                aviciBayIndex,
                aviciSlotIndex,
                aviciModuleCurrTemp,
                aviciSysTrapDescr
                }
        STATUS       current
        DESCRIPTION
            "The aviciModuleTemperatureMajor notification signifies that the
             specified module is reporting a temperature above the major
             temperature threshold but below the critical temperature
             threshold.  The current module temperature is reported in the
             aviciModuleCurrTemp object.  When the reported temperature drops
             below the major threshold, the aviciModuleTemperatureMinor
             notification will be sent to clear this fault."
    ::= { aviciModuleNotificationPrefix 6 }

aviciModuleTemperatureCritical NOTIFICATION-TYPE
        OBJECTS {
                aviciBayIndex,
                aviciSlotIndex,
                aviciModuleCurrTemp,
                aviciSysTrapDescr
                }
        STATUS       current
        DESCRIPTION
            "The aviciModuleTemperatureCritical notification signifies that
             the specified module is reporting a temperature above the
             critical temperature threshold.  The current module temperature
             is reported in the aviciModuleCurrTemp object.  When the reported
             temperature drops below the critical threshold, the
             aviciModuleTemperatureMajor notification will be sent to clear
             this fault."
    ::= { aviciModuleNotificationPrefix 7 }


aviciModuleMisconfigured  NOTIFICATION-TYPE
        OBJECTS {
                aviciBayIndex,
                aviciSlotIndex,
                aviciSysTrapDescr
		}
	STATUS	current
	DESCRIPTION
            "An aviciModuleMisconfigured trap indicates when the fabric version
             mismatch, or a module in a multimodule set is not in the proper 
             slot."
	::= { aviciModuleNotificationPrefix 8 }

aviciModuleIncompatibleSW NOTIFICATION-TYPE
        OBJECTS {
                aviciBayIndex,
                aviciSlotIndex,
                aviciSysTrapDescr
                }
        STATUS       current
        DESCRIPTION
            "The aviciModuleIncompatibleSW notification signifies that the module is running a
	     software image that is incompatible with the server image."
        ::= { aviciModuleNotificationPrefix 9 }


aviciServerAccessModuleDown NOTIFICATION-TYPE
        OBJECTS {
                aviciBayIndex,
                aviciSlotIndex,
                aviciSysTrapDescr
                }
        STATUS       current
        DESCRIPTION
            "The aviciServerAccessModuleDown notification signifies that
             a server access module has gone down."
    ::= { aviciServerAccessModuleNotificationPrefix 1 }


aviciServerAccessModuleUp NOTIFICATION-TYPE
        OBJECTS {
                aviciBayIndex,
                aviciSlotIndex,
                aviciSysTrapDescr
                }
        STATUS       current
        DESCRIPTION
            "The aviciServerAccessModuleUp notification signifies that a
             server access module has come up."
    ::= { aviciServerAccessModuleNotificationPrefix 2 }


aviciAllServerAccessModulesDown NOTIFICATION-TYPE
        OBJECTS {
                aviciBayIndex,
                aviciSlotIndex,
                aviciSysTrapDescr
                }
        STATUS       current
        DESCRIPTION
            "The aviciAllServerAccessModulesDown notification signifies that
             all server access modules have gone down."
    ::= { aviciServerAccessModuleNotificationPrefix 3 }


aviciAllServerAccessModulesDownClear NOTIFICATION-TYPE
        OBJECTS {
                aviciBayIndex,
                aviciSlotIndex,
                aviciSysTrapDescr
                }
        STATUS       current
        DESCRIPTION
            "The aviciAllServerAccessModulesDownClear notification signifies
             that at least one server access module has come up."
    ::= { aviciServerAccessModuleNotificationPrefix 4 }


--
-- Conformance Information
--    

aviciModuleMIBConformance OBJECT IDENTIFIER ::= { aviciModuleMIB 3 }
aviciModuleMIBCompliances OBJECT IDENTIFIER ::= { aviciModuleMIBConformance 1 }
aviciModuleMIBGroups OBJECT IDENTIFIER ::= { aviciModuleMIBConformance 2 }

--
-- Compliance Statements
--

aviciModuleMIBCompliance MODULE-COMPLIANCE
        STATUS current
        DESCRIPTION
            "The compliance statement for the aviciModule."
        MODULE
        MANDATORY-GROUPS {
            aviciModuleGroup,
            aviciModuleIpCountersGroup,
            aviciModuleIcmpCountersGroup,
            aviciModuleNotificationGroup,
            aviciServerAccessModuleNotificationGroup
        }
    
        ::= { aviciModuleMIBCompliances 1 } 

aviciModuleGroup OBJECT-GROUP
        OBJECTS {
            aviciModuleAdminStatus,
            aviciModuleOperStatus,
            aviciModuleUpTime,
            aviciModuleCurrTemp,
            aviciModuleMaxTemp,
            aviciModuleDescr,
            aviciModuleAssySerialNumber,
            aviciModuleLineSerialNumber,
            aviciModuleMbSerialNumber,
            aviciModuleAssyRevision,
            aviciModuleLineRevision,
            aviciModuleMbRevision,
            aviciModuleSoftwareVersion,
            aviciModuleFirmwareVersion,
            aviciModuleAssyProductId,
            aviciModuleLinePartNumber,
            aviciModuleMbPartNumber
        }
        STATUS     current
        DESCRIPTION
            "Objects for the module."
        ::= { aviciModuleMIBGroups 1 }

aviciModuleIpCountersGroup OBJECT-GROUP
        OBJECTS {
            aviciModuleIpInReceives,
            aviciModuleIpInHdrErrors,
            aviciModuleIpInAddrErrors,
            aviciModuleIpForwDatagrams,
            aviciModuleIpInUnknownProtos,
            aviciModuleIpInDiscards,
            aviciModuleIpInDelivers,
            aviciModuleIpOutRequests,
            aviciModuleIpOutDiscards,
            aviciModuleIpOutNoRoutes,
            aviciModuleIpFragOKs,
            aviciModuleIpFragFails,
            aviciModuleIpFragCreates
        }
        STATUS     current
        DESCRIPTION
            "Internet Protocol Counter statistics for the module."
        ::= { aviciModuleMIBGroups 2 }

aviciModuleIcmpCountersGroup OBJECT-GROUP
        OBJECTS {
            aviciModuleIcmpInMsgs,
            aviciModuleIcmpInErrors,
            aviciModuleIcmpInDestUnreachs,
            aviciModuleIcmpInTimeExcds,
            aviciModuleIcmpInParmProbs,
            aviciModuleIcmpInSrcQuenchs,
            aviciModuleIcmpInRedirects,
            aviciModuleIcmpInEchos,
            aviciModuleIcmpInEchoReps,
            aviciModuleIcmpInTimestamps,
            aviciModuleIcmpInTimestampReps,
            aviciModuleIcmpInAddrMasks,
            aviciModuleIcmpInAddrMaskReps,
            aviciModuleIcmpOutMsgs,
            aviciModuleIcmpOutErrors,
            aviciModuleIcmpOutDestUnreachs,
            aviciModuleIcmpOutTimeExcds,
            aviciModuleIcmpOutParmProbs,
            aviciModuleIcmpOutSrcQuenchs,
            aviciModuleIcmpOutRedirects,
            aviciModuleIcmpOutEchos,
            aviciModuleIcmpOutEchoReps,
            aviciModuleIcmpOutTimestamps,
            aviciModuleIcmpOutTimestampReps,
            aviciModuleIcmpOutAddrMasks,
            aviciModuleIcmpOutAddrMaskReps
        }
        STATUS     current
        DESCRIPTION
            "Internet Control Message Protocol Counter statistics for the
             module."
        ::= { aviciModuleMIBGroups 3 }

aviciModuleNotificationGroup NOTIFICATION-GROUP
        NOTIFICATIONS {
            aviciModuleColdStart,
            aviciModuleWarmStart,
            aviciModuleDown,
            aviciModuleTemperatureNormal,
            aviciModuleTemperatureMinor,
            aviciModuleTemperatureMajor,
            aviciModuleTemperatureCritical,
	    aviciModuleMisconfigured,
	    aviciModuleIncompatibleSW
        }
        STATUS     current
        DESCRIPTION
            "Notifications for the module."
        ::= { aviciModuleMIBGroups 4 }

aviciServerAccessModuleNotificationGroup NOTIFICATION-GROUP
        NOTIFICATIONS {
            aviciServerAccessModuleDown,
            aviciServerAccessModuleUp,
            aviciAllServerAccessModulesDown,
            aviciAllServerAccessModulesDownClear
        }
        STATUS     current
        DESCRIPTION
            "Notifications for server access modules."
        ::= { aviciModuleMIBGroups 5 }
END
