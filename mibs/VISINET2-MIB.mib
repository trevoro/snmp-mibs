VISINET2-MIB DEFINITIONS ::= BEGIN

IMPORTS
    Counter            FROM RFC1155-SMI
    TimeTicks          FROM RFC1155-SMI
    DisplayString      FROM RFC1213-MIB
	enterprises        FROM RFC1155-SMI
	OBJECT-TYPE FROM SNMPv2-SMI
	TRAP-TYPE FROM RFC-1215;

-- EXPORTS	unisys, unisysOpen;

	unisys      OBJECT IDENTIFIER ::= { enterprises 223 }
	unisysOpen  OBJECT IDENTIFIER ::= { unisys 10 }


-- __________________  ENVIRONMENTAL MONITOR MIB  __________________


-- ****************************************************************************
--
--                Unisys Server Hardware Environmental Monitoring
--                Management Information Base for SNMP Network Management
-- 
--      Copyright 1998 - UNISYS Corporation.
--      All Rights Reserved.
--
--      The information in this document is subject to change without notice.
--     
--      UNISYS CORPORATION SHALL NOT BE LIABLE FOR TECHNICAL OR
--      EDITORIAL ERRORS OR OMISSIONS CONTAINED IN THIS DOCUMENT, NOR FOR
--      INCIDENTAL OR CONSEQUENTIAL DAMAGES RESULTING FROM THE FURNISHING,
--      PERFORMANCE, OR USE OF THIS MATERIAL.
--
-- ****************************************************************************
--
-- ****************************************************************************
--
-- Version 1.0a (Mar 29 1996) of the Server Hardware Environmental Monitoring MIB for Unisys Corp.
-- 
-- The Environmental Monitoring MIB defines three tables, 
--    uemEnvMonitorTable, uemSensorTable and uemSwitchTable.
-- The uemSensorTable uses a generalized approach to report the state of fans, 
-- temperatures and voltages. The uemSwitchTable reports on/off states for things like 
-- open doors and removed covers.  The EnvMonitor table is the parent of the Sensor and 
-- Switch tables. Each row in the Sensor and Switch tables is linked to its parent 
-- row in the EnvMonitor table. The number of rows in each table is dependent on 
-- the number of monitoring devices installed in that specific system. The number 
-- of rows in each table is determined at system startup time and is not expected 
-- to vary during system operation.

-- This MIB is based on the immediate need for monitoring the environmental
-- status of network servers.  The input for this MIB was supplied by the
-- PCD group in San Jose, the Malvern Systems Management group and the 
-- documentation for the first generation Server Hardware Monitor(SHM)
-- devices built by the manufacturer.
-- By utilizing the API provided by the SHM or any comparable interface
-- supplying environmental data on an SNMP host an Object Manager will
-- be able to report this type of hardware environment information
-- defined in this MIB.  As changes occur in the type and quantity of 
-- environmental information supplied by such API specifications this
-- MIB will be updated to reflect those changes.
--
-- ****************************************************************************

    unisysEnvMonitor       OBJECT IDENTIFIER ::= { unisysOpen 6 }
    


-- ****************************************************************************
--
-- This section includes all the simple variables.  This means there can
-- only be one instance of these data objects within the system being
-- monitored.  Tables are defined in later sections and represent objects
-- that may have multiple instances(rows) and that consist of multiple
-- simple attributes(columns).  The TRAP section will also contain some
-- simple variables.
-- ****************************************************************************


    uemAgentRevMajor OBJECT-TYPE
        SYNTAX  INTEGER (1..255)
        ACCESS  read-only
        STATUS  mandatory
        DESCRIPTION
            "Major version of the Unisys Environmental Monitoring Agent."
        ::= { unisysEnvMonitor 2 }

    uemAgentRevMinor OBJECT-TYPE
        SYNTAX  INTEGER (0..255)
        ACCESS  read-only
        STATUS  mandatory
        DESCRIPTION
            "Minor version of the Unisys Environmental Monitoring Agent."
        ::= { unisysEnvMonitor 3 }

    uemMibRevMajor OBJECT-TYPE
        SYNTAX  INTEGER (1..255)
        ACCESS  read-only
        STATUS  mandatory
        DESCRIPTION
            "The Major Revision level of this MIB.
             A change in the major revision level represents a possible
             compatibility problem with older versions of the MIB."
        ::= { unisysEnvMonitor 4 }

    uemMibRevMinor OBJECT-TYPE
        SYNTAX  INTEGER (0..255)
        ACCESS  read-only
        STATUS  mandatory
        DESCRIPTION
            "The minor revision level of this MIB.   A change in the
             minor revision level may represent some minor additional 
             support, changes to documentation or fixes to errors in a
             previous revision.  Backward compatibility should be  
             maintained as long as the major revision level is the same."
        ::= { unisysEnvMonitor 5 }

    uemSystemDescription OBJECT-TYPE
        SYNTAX  DisplayString(SIZE(0..80))
        ACCESS  read-only
        STATUS  mandatory
        DESCRIPTION
             "Text describing this system such as manufacturer and model number."
        ::= { unisysEnvMonitor 7 }

    uemTrapsEnabled OBJECT-TYPE
        SYNTAX  INTEGER -- Boolean
                {
                 true   (1),
                 false  (2)
                }
        ACCESS  read-write
        STATUS  mandatory
        DESCRIPTION
             "All Environmental Monitoring traps can be globally disabled 
              by setting this FALSE."
        ::= { unisysEnvMonitor 8 }

    uemTrapSeverity OBJECT-TYPE
        SYNTAX  INTEGER
        ACCESS  read-only
        STATUS  mandatory
        DESCRIPTION
             "Additional information delivered with sensor and switch trap messages.
              Advanced management applications can make use of this information to
              better evaluate the severity of the situation. This variable is
              only intended for use with traps; no meaning should be assumed by a 
              Manager to the value retrieved through a Get operation on this object."
        ::= { unisysEnvMonitor 9 }

-- ****************************************************************************

    uemEnvMonitorTable OBJECT-TYPE
        SYNTAX SEQUENCE OF UemEnvMonitorTableEntry
        ACCESS not-accessible
        STATUS mandatory
        DESCRIPTION
            "An entry for each Monitor device on this host that is 
             actively reporting environmental data via the SNMP Agent.
             There may ofen only be one row in this table, but there
             must be at least one row."
        ::= { unisysEnvMonitor 16 }

    uemEnvMonitorTableEntry OBJECT-TYPE
        SYNTAX  UemEnvMonitorTableEntry
        ACCESS  not-accessible
        STATUS  mandatory
        INDEX { uemEnvMonIndex }
        ::= { uemEnvMonitorTable 1 }

    UemEnvMonitorTableEntry  ::= SEQUENCE
        { 
          uemEnvMonIndex               INTEGER,
          uemEnvMonLocation            DisplayString,
          uemEnvMonType                INTEGER,
          uemEnvMonFwRevMajor          INTEGER,
          uemEnvMonFwRevMinor          INTEGER,
          uemEnvMonFwRelDate           DisplayString,
          uemEnvMonUpTime              TimeTicks
        }

    uemEnvMonIndex OBJECT-TYPE
        SYNTAX  INTEGER
        ACCESS  read-only
        STATUS  mandatory
        DESCRIPTION
             "A unique value for each hardware monitoring device."
        ::= { uemEnvMonitorTableEntry 1 }

    uemEnvMonLocation OBJECT-TYPE
        SYNTAX  DisplayString(SIZE(0..32))
        ACCESS  read-only
        STATUS  mandatory
        DESCRIPTION
             "The physical location of the Environmental Monitor device in the host hardware.
              e.g. disk drawer 1, DAT drawer... "
        ::= { uemEnvMonitorTableEntry 2 }

    uemEnvMonType OBJECT-TYPE       
        SYNTAX  INTEGER
                {
                 unknown       (1),
                 alrSHM        (2)
                }
        ACCESS  read-only
        STATUS  mandatory
        DESCRIPTION
             "Identifies a specific environmental monitoring device."
        ::= { uemEnvMonitorTableEntry 3 }

    uemEnvMonFwRevMajor OBJECT-TYPE
        SYNTAX  INTEGER (0..255)
        ACCESS  read-only
        STATUS  mandatory
        DESCRIPTION
             "The Environmental Monitor device firmware major version number."
        ::= { uemEnvMonitorTableEntry 5 }

    uemEnvMonFwRevMinor OBJECT-TYPE
        SYNTAX  INTEGER (0..255)
        ACCESS  read-only
        STATUS  mandatory
        DESCRIPTION
             "The Environmental Monitor device firmware minor version number."
        ::= { uemEnvMonitorTableEntry 6 }

    uemEnvMonFwRelDate OBJECT-TYPE
        SYNTAX  DisplayString(SIZE(10))
        ACCESS  read-only
        STATUS  mandatory
        DESCRIPTION
             "The release date of the firmware for this device reported as YYYY-MM-DD."
        ::= { uemEnvMonitorTableEntry 7 }

    uemEnvMonUpTime OBJECT-TYPE
        SYNTAX  TimeTicks
        ACCESS  read-only
        STATUS  mandatory
        DESCRIPTION
             "Length of time since last system power-up or last time the
              SysReset command was issued (which ever is most recent).
              This uptime is relative only to the monitoring device itself."
        ::= { uemEnvMonitorTableEntry 8 }
        
-- ****************************************************************************

    uemSensorTable OBJECT-TYPE
        SYNTAX SEQUENCE OF UemSensorTableEntry
        ACCESS not-accessible
        STATUS mandatory
        DESCRIPTION
          "All fan, temperature and voltage sensors are collected in this table.
           All these devices are similar in that they monitor 5 value ranges: 
               low critical, low warning, normal, high warning, high critical. 
           Notifications (trap messages) are sent whenever the monitored value moves 
           from one value range to another. The guard points defining the 5 monitored 
           regions (or range of values) are read-write allowing remote configuration 
           by an SNMP management console.

           There may be zero or more rows in this table. Each row in the table contains 
           information about a single sensor. One column, uemSensorType, identifies 
           the type of sensor as fan, temp or voltage. Another column, uemSensorStatus, 
           identifies where in the 5 possible ranges the monitored device is currently 
           operating within. Each row is linked to a parent EnvMonitor row to further 
	   identify its location within the server."
        ::= { unisysEnvMonitor 17 }

    uemSensorTableEntry OBJECT-TYPE
        SYNTAX  UemSensorTableEntry
        ACCESS  not-accessible
        STATUS  mandatory
        INDEX { uemSensorIndex }
        ::= { uemSensorTable 1 }

    UemSensorTableEntry  ::= SEQUENCE
        { 
          uemSensorIndex               INTEGER,
          uemSensorEnvMonIndex         INTEGER,
          uemSensorType                INTEGER,
          uemSensorDescription         DisplayString,
          uemSensorStatus              INTEGER,
          uemSensorValue               INTEGER,
          uemSensorNominalValue        INTEGER,
          uemSensorHighCriticalValue   INTEGER,
          uemSensorHighCriticalLabel   DisplayString,
          uemSensorHighWarningValue    INTEGER,
          uemSensorHighWarningLabel    DisplayString,
          uemSensorLowWarningValue     INTEGER,
          uemSensorLowWarningLabel     DisplayString,
          uemSensorLowCriticalValue    INTEGER,
          uemSensorLowCriticalLabel    DisplayString,
          uemSensorEnabled             INTEGER
        }

    uemSensorIndex OBJECT-TYPE
        SYNTAX  INTEGER
        ACCESS  read-only
        STATUS  mandatory
        DESCRIPTION
             "A unique value for each sensor in the monitored system. 
              Note: if there are multiple environmental monitoring cards in a 
              system, all sensors associated with such cards are collected
              in a single uemSensorTable and field uemSensorIndex is guaranteed
              to be unique across all sensors."
        ::= { uemSensorTableEntry 1 }

    uemSensorEnvMonIndex OBJECT-TYPE
        SYNTAX  INTEGER
        ACCESS  read-only
        STATUS  mandatory
        DESCRIPTION
             "A link into the EnvMonitor device table. This identifies which environmental
              device is managing this sensor."
        ::= { uemSensorTableEntry 2 }

    uemSensorType OBJECT-TYPE
        SYNTAX  INTEGER
                {
                 unknown       (1),
                 fan           (2),
                 voltage       (3),
                 temperature   (4)
                }
        ACCESS  read-only
        STATUS  mandatory
        DESCRIPTION
             "The general classification of this sensor."
        ::= { uemSensorTableEntry 3 }

    uemSensorDescription OBJECT-TYPE
        SYNTAX  DisplayString(SIZE(0..80))
        ACCESS  read-only
        STATUS  mandatory
        DESCRIPTION
             "Text describing this sensor."
        ::= { uemSensorTableEntry 4 }

    uemSensorStatus OBJECT-TYPE
        SYNTAX  INTEGER
                {
                 unknown       (1),
                 normal        (2),
                 warning       (3),
                 critical      (4)
                }
        ACCESS  read-only
        STATUS  mandatory
        DESCRIPTION
             "The current state of the sensor."
        ::= { uemSensorTableEntry 5 }

    uemSensorValue OBJECT-TYPE
        SYNTAX  INTEGER
        ACCESS  read-only
        STATUS  mandatory
        DESCRIPTION
             "The current numeric value of the sensor. The interpretation of this 
              value is related to the type of sensor.
              Fan sensor values are reported in rpms (revolutions per minute).
              Voltage sensor values are reported in millivolts. 
              A value of 3300 means 3.3 volts.
              Temperature sensor values are reported as hundreths of Celsius degrees.
              A value of 2500 means 25.0 degrees."
        ::= { uemSensorTableEntry 6 }

    uemSensorNominalValue OBJECT-TYPE
        SYNTAX  INTEGER
        ACCESS  read-write
        STATUS  mandatory
        DESCRIPTION
             "This is the normal value expected to be reported by this sensor in
              a properly operating system."
        ::= { uemSensorTableEntry 7 }

    uemSensorHighCriticalValue OBJECT-TYPE
        SYNTAX  INTEGER
        ACCESS  read-write
        STATUS  mandatory
        DESCRIPTION
             "When the sensor exceeds this value, a critical trap is sent.
              When appropriate, this test point can be disabled by setting 
			  it to the maximum integer value."
        ::= { uemSensorTableEntry 8 }

    uemSensorHighCriticalLabel OBJECT-TYPE
        SYNTAX  DisplayString(SIZE(0..80))
        ACCESS  read-only
        STATUS  mandatory
        DESCRIPTION
             "Text describing this test point."
        ::= { uemSensorTableEntry 9 }

    uemSensorHighWarningValue OBJECT-TYPE
        SYNTAX  INTEGER
        ACCESS  read-write
        STATUS  mandatory
        DESCRIPTION
             "When the sensor value exceeds this value, a warning trap is sent.
              This test point is disabled by setting it to the same value as
              the high critical value."
        ::= { uemSensorTableEntry 10 }

    uemSensorHighWarningLabel OBJECT-TYPE
        SYNTAX  DisplayString(SIZE(0..80))
        ACCESS  read-only
        STATUS  mandatory
        DESCRIPTION
             "Text describing this test point."
        ::= { uemSensorTableEntry 11 }

    uemSensorLowWarningValue OBJECT-TYPE
        SYNTAX  INTEGER
        ACCESS  read-write
        STATUS  mandatory
        DESCRIPTION
             "When the sensor value goes below this value, a warning trap is sent.
              This test point can be disabled by setting it to the same value as
              the low critical point."
        ::= { uemSensorTableEntry 12 }

    uemSensorLowWarningLabel OBJECT-TYPE
        SYNTAX  DisplayString(SIZE(0..80))
        ACCESS  read-only
        STATUS  mandatory
        DESCRIPTION
             "Text describing this test point."
        ::= { uemSensorTableEntry 13 }

    uemSensorLowCriticalValue OBJECT-TYPE
        SYNTAX  INTEGER
        ACCESS  read-write
        STATUS  mandatory
        DESCRIPTION
             "When the sensor goes below this value, a critical trap is sent.
              This test point can be disabled by setting it to zero."
        ::= { uemSensorTableEntry 14 }

    uemSensorLowCriticalLabel OBJECT-TYPE
        SYNTAX  DisplayString(SIZE(0..80))
        ACCESS  read-only
        STATUS  mandatory
        DESCRIPTION
             "Text describing this test point."
        ::= { uemSensorTableEntry 15 }

    uemSensorEnabled OBJECT-TYPE
        SYNTAX  INTEGER -- Boolean
                {
                 true   (1),
                 false  (2)
                }
        ACCESS  read-only
        STATUS  mandatory
        DESCRIPTION
             "If this field is FALSE, the sensor is disabled. No traps will be sent
              from a disabled sensor."
        ::= { uemSensorTableEntry 16 }

-- ****************************************************************************

    uemSwitchTable OBJECT-TYPE
        SYNTAX SEQUENCE OF UemSwitchTableEntry
        ACCESS not-accessible
        STATUS mandatory
        DESCRIPTION
          "An entry for each switch in the monitored system.
           Switches report true/false status and are useful for indicating 
           open doors, unlocked keys, etc. There may be zero or more rows in this table.
           One column, uemSwitchContext, is a displayable string that reports 
           the meaning of the current true/false state of the switch such as 
           'Open', 'Closed', 'Locked', 'Unlocked' etc. Other columns allow access to the 
           actual true/false state and which state is expected in a properly 
           operating system."
        ::= { unisysEnvMonitor 18 }

    uemSwitchTableEntry OBJECT-TYPE
        SYNTAX  UemSwitchTableEntry
        ACCESS  not-accessible
        STATUS  mandatory
        INDEX { uemSwitchIndex }
        ::= { uemSwitchTable 1 }

    UemSwitchTableEntry  ::= SEQUENCE
        { 
          uemSwitchIndex               INTEGER,
          uemSwitchEnvMonIndex         INTEGER,
          uemSwitchDescription         DisplayString,
          uemSwitchContext             DisplayString,
          uemSwitchCurrentState        INTEGER,
          uemSwitchExpectedState       INTEGER,
          uemSwitchEnabled             INTEGER
        }

    uemSwitchIndex OBJECT-TYPE
        SYNTAX  INTEGER
        ACCESS  read-only
        STATUS  mandatory
        DESCRIPTION
             "A unique value for each switch in the monitored system."
        ::= { uemSwitchTableEntry 1 }

    uemSwitchEnvMonIndex OBJECT-TYPE
        SYNTAX  INTEGER
        ACCESS  read-only
        STATUS  mandatory
        DESCRIPTION
             "A link into the EnvMonitor device table. This identifies which environmental
              device is managing this switch."
        ::= { uemSwitchTableEntry 2 }

    uemSwitchDescription OBJECT-TYPE
        SYNTAX  DisplayString(SIZE(0..80))
        ACCESS  read-only
        STATUS  mandatory
        DESCRIPTION
             "A general description of the switch, but not including its current state."
        ::= { uemSwitchTableEntry 3 }

    uemSwitchContext OBJECT-TYPE
        SYNTAX  DisplayString(SIZE(0..80))
        ACCESS  read-only
        STATUS  mandatory
        DESCRIPTION
             "A description of the meaning of the current switch status such as 
              'Open', 'Closed' etc."
        ::= { uemSwitchTableEntry 4 }

    uemSwitchCurrentState OBJECT-TYPE
        SYNTAX  INTEGER -- Boolean
                {
                 true   (1),
                 false  (2)
                }
        ACCESS  read-only
        STATUS  mandatory
        DESCRIPTION
             "The current state of the switch. This variable can be compared with
              uemSwitchExpectedState to determine if the switch is in the unusual
              state."
        ::= { uemSwitchTableEntry 5 }

    uemSwitchExpectedState OBJECT-TYPE
        SYNTAX  INTEGER -- Boolean
                {
                 true   (1),
                 false  (2)
                }
        ACCESS  read-only
        STATUS  mandatory
        DESCRIPTION
             "The normal state expected for this switch in a properly operating system."
        ::= { uemSwitchTableEntry 6 }

    uemSwitchEnabled OBJECT-TYPE
        SYNTAX  INTEGER -- Boolean
                {
                 true   (1),
                 false  (2)
                }
        ACCESS  read-only
        STATUS  mandatory
        DESCRIPTION
             "If this field is FALSE, the switch is disabled. No traps will be sent
              from a disabled switch."
        ::= { uemSwitchTableEntry 7 }

-- ****************************************************************************
--
-- The TRAP definitions.
--
-- Traps are defined for notifying SNMP management stations of change in the 
-- configuration state, sensor state or switch state of environmental monitoring devices.
-- All environmental traps can be globally enabled or disabled via uemTrapsEnabled.
-- When necessary, traps from individual switches and sensors can be disabled
-- via columns in the sensor and switch tables.
-- 
-- ****************************************************************************

    uemTrapConfigurationChange TRAP-TYPE
        ENTERPRISE  unisysEnvMonitor
        DESCRIPTION
             "This trap indicates that configuration changes have been made
              in the Environmental Monitoring subsystem."
        ::= 1
    
    uemTrapSensorCritical TRAP-TYPE
        ENTERPRISE  unisysEnvMonitor
        VARIABLES {
                   uemSensorIndex,
                   uemSensorType,
                   uemSensorDescription,
                   uemSensorStatus,
                   uemSensorValue,
                   uemSensorNominalValue,
                   uemTrapSeverity
                  }
        DESCRIPTION
             "The monitored value of a sensor has crossed the critical threshhold value."
        ::= 2

    uemTrapSensorWarning TRAP-TYPE
        ENTERPRISE  unisysEnvMonitor
        VARIABLES {
                   uemSensorIndex,
                   uemSensorType,
                   uemSensorDescription,
                   uemSensorStatus,
                   uemSensorValue,
                   uemSensorNominalValue,
                   uemTrapSeverity
                  }
        DESCRIPTION
             "The monitored value of a sensor has crossed into the warning range of values.
              Note that this trap can be fired in two situations: both moving from the critical 
              to warning range as well as from normal to warning."
        ::= 3

    uemTrapSensorNormal TRAP-TYPE
        ENTERPRISE  unisysEnvMonitor
        VARIABLES {
                   uemSensorIndex,
                   uemSensorType,
                   uemSensorDescription,
                   uemSensorStatus,
                   uemSensorValue,
                   uemSensorNominalValue,
                   uemTrapSeverity
                  }
        DESCRIPTION
             "The monitored value of a sensor has returned to within the normal range."
        ::= 4

    uemTrapSwitchAlert TRAP-TYPE
        ENTERPRISE  unisysEnvMonitor
        VARIABLES {
                   uemSwitchIndex,
                   uemSwitchDescription,
                   uemSwitchContext,
                   uemTrapSeverity
                  }
        DESCRIPTION
             "The monitored state of a switch has changed to the unexpected state for a 
              normally operating system. The unexpected state is defined to be when
              uemSwitchCurrentState does not equal uemSwitchExpectedState. "
        ::= 5

    uemTrapSwitchNormal TRAP-TYPE
        ENTERPRISE  unisysEnvMonitor
        VARIABLES {
                   uemSwitchIndex,
                   uemSwitchDescription,
                   uemSwitchContext,
                   uemTrapSeverity
                  }
        DESCRIPTION
             "A switch has returned to the normal state expected for a normally operating
              system. The normal state is defined to be when uemSwitchCurrentState equals 
              uemSwitchExpectedState. "
        ::= 6


-- __________________  CONFIGURATION AGENT MIB  __________________

--
-- UNISYS Configuration Agent MIB definition
-- 1997 All rights reserved
-- 

cfgAgent        OBJECT IDENTIFIER ::= { unisysOpen 7 }
 
-- CfgAgent MIB
 
cfgAgentVersion OBJECT-TYPE
	SYNTAX  INTEGER
	ACCESS  read-only
	STATUS  mandatory
	DESCRIPTION
			"The internal version number of this SNMP Extension Agent."
	::= { cfgAgent 1 }

cfgAgentRevision OBJECT-TYPE
	SYNTAX  INTEGER
	ACCESS  read-only
	STATUS  mandatory
	DESCRIPTION
			"The internal revision number of this SNMP Extension Agent."
	::= { cfgAgent 2 }

cfgAgentMIBVersion OBJECT-TYPE
	SYNTAX  INTEGER
	ACCESS  read-only
	STATUS  mandatory
	DESCRIPTION
			"The internal version number of the MIB for this SNMP Extension Agent."
	::= { cfgAgent 3 }

cfgAgentMIBRevision OBJECT-TYPE
	SYNTAX  INTEGER
	ACCESS  read-only
	STATUS  mandatory
	DESCRIPTION
			"The internal revision number of the MIB for this SNMP Extension Agent."
	::= { cfgAgent 4 }


-- __________________________  BIOS DEFINITION DATA  _____________________

cfgAgentBIOSVendor OBJECT-TYPE
	SYNTAX  DisplayString
	ACCESS  read-only
	STATUS  mandatory
	DESCRIPTION
			"A description of the system BIOS vendor."
	::= { cfgAgent 5 }

cfgAgentBIOSVersion OBJECT-TYPE
	SYNTAX  DisplayString
	ACCESS  read-only
	STATUS  mandatory
	DESCRIPTION
			"A description of the version of the system vendor's BIOS."
	::= { cfgAgent 6 }

cfgAgentBIOSDate OBJECT-TYPE
	SYNTAX  DisplayString
	ACCESS  read-only
	STATUS  mandatory
	DESCRIPTION
			"The date that the system BIOS was created."
	::= { cfgAgent 7 }

cfgAgentBIOSsROMInKb OBJECT-TYPE
	SYNTAX  INTEGER
	ACCESS  read-only
	STATUS  mandatory
	DESCRIPTION
			"The size of the BIOS read-only memory in kilobytes."
	::= { cfgAgent 8 }

cfgAgentBIOSBusSupport OBJECT-TYPE
	SYNTAX  DisplayString
	ACCESS  read-only
	STATUS  mandatory
	DESCRIPTION
			"The bus interface(s) supported by the system BIOS."
	::= { cfgAgent 9 }

cfgAgentBIOSAddress OBJECT-TYPE
	SYNTAX  INTEGER
	ACCESS  read-only
	STATUS  mandatory
	DESCRIPTION
			"The memory address used to access the system BIOS."
	::= { cfgAgent 10 }

cfgAgentBIOSInterruptId OBJECT-TYPE
	SYNTAX  INTEGER
	ACCESS  read-only
	STATUS  mandatory
	DESCRIPTION
			"The interrupt ID used to access the system BIOS."
	::= { cfgAgent 11 }


-- __________________________  CPU DEFINITION TABLE  _____________________

cfgAgentnCPUs OBJECT-TYPE
	SYNTAX  INTEGER
	ACCESS  read-only
	STATUS  mandatory
	DESCRIPTION
			"The number of CPUs listed in the subsequent CPUs table."
	::= { cfgAgent 12 }

cfgAgentCPUsTbl OBJECT-TYPE
	SYNTAX  SEQUENCE OF CfgAgentCPUEntry
	ACCESS  not-accessible
	STATUS  mandatory
	DESCRIPTION
			"CPU table consisting of a list of system CPUs."
	::= { cfgAgent 13 }

cfgAgentCPUsTblEntry OBJECT-TYPE
	SYNTAX  CfgAgentCPUEntry
	ACCESS  not-accessible
	STATUS  mandatory
	::= { cfgAgentCPUsTbl 1 }

CfgAgentCPUEntry ::= SEQUENCE
	{
	cfgAgentCPUClass  DisplayString,
	cfgAgentCPUName  DisplayString,
	cfgAgentCPUVendor  DisplayString,
	cfgAgentCPUSpeed  INTEGER,
	cfgAgentCPUsCacheInKb  INTEGER,
	cfgAgentCPUState  INTEGER
	}

cfgAgentCPUClass OBJECT-TYPE
	SYNTAX  DisplayString
	ACCESS  read-only
	STATUS  mandatory
	DESCRIPTION
			"The class of central processor (eg: Intel x86)."
	::= { cfgAgentCPUsTblEntry 1 }

cfgAgentCPUName OBJECT-TYPE
	SYNTAX  DisplayString
	ACCESS  read-only
	STATUS  mandatory
	DESCRIPTION
			"The vendor's name for the CPU (eg: 80486)."
	::= { cfgAgentCPUsTblEntry 2 }

cfgAgentCPUVendor OBJECT-TYPE
	SYNTAX  DisplayString
	ACCESS  read-only
	STATUS  mandatory
	DESCRIPTION
			"The vendor of the CPU chipset (eg: Genuine Intel)."
	::= { cfgAgentCPUsTblEntry 3 }

cfgAgentCPUSpeed OBJECT-TYPE
	SYNTAX  INTEGER
	ACCESS  read-only
	STATUS  mandatory
	DESCRIPTION
			"The approximate operating frequency (in MHz) of the CPU chipset."
	::= { cfgAgentCPUsTblEntry 4 }

cfgAgentCPUsCacheInKb OBJECT-TYPE
	SYNTAX  INTEGER
	ACCESS  read-only
	STATUS  mandatory
	DESCRIPTION
			"The size (in kilobytes) of the CPU operational memory cache."
	::= { cfgAgentCPUsTblEntry 5 }

cfgAgentCPUState OBJECT-TYPE
	SYNTAX  INTEGER  { active(1), disabled(2) }
	ACCESS  read-only
	STATUS  mandatory
	DESCRIPTION
			"The current state of the CPU:  active(1), disabled(2)."
	::= { cfgAgentCPUsTblEntry 6 }


-- __________________________  SYSTEM DEFINITION DATA  ___________________

cfgAgentSysName OBJECT-TYPE
	SYNTAX  DisplayString
	ACCESS  read-only
	STATUS  mandatory
	DESCRIPTION
			"The (network) name of this computer."
	::= { cfgAgent 14 }

cfgAgentSysBoardVersion OBJECT-TYPE
	SYNTAX  DisplayString
	ACCESS  read-only
	STATUS  mandatory
	DESCRIPTION
			"The vendor's board version information."
	::= { cfgAgent 15 }

cfgAgentSysUptimeMilSec OBJECT-TYPE
	SYNTAX  INTEGER
	ACCESS  read-only
	STATUS  mandatory
	DESCRIPTION
			"The length of time that this system has been active (in miliseconds)."
	::= { cfgAgent 16 }

cfgAgentSysOS OBJECT-TYPE
	SYNTAX  DisplayString
	ACCESS  read-only
	STATUS  mandatory
	DESCRIPTION
			"The operating system and its version running on this system."
	::= { cfgAgent 17 }

cfgAgentSysnDMAs OBJECT-TYPE
	SYNTAX  INTEGER
	ACCESS  read-only
	STATUS  mandatory
	DESCRIPTION
			"The number of DMA channels available on this system."
	::= { cfgAgent 18 }


-- __________________________  IRQ DEFINITION TABLE  _____________________

cfgAgentnIRQs OBJECT-TYPE
	SYNTAX  INTEGER
	ACCESS  read-only
	STATUS  mandatory
	DESCRIPTION
			"The number of IRQs listed in the subsequent IRQs table."
	::= { cfgAgent 19 }

cfgAgentIRQsTbl OBJECT-TYPE
	SYNTAX  SEQUENCE OF CfgAgentIRQEntry
	ACCESS  not-accessible
	STATUS  mandatory
	DESCRIPTION
			"IRQ table consisting of a list of IRQs allocated on this system."
	::= { cfgAgent 20 }

cfgAgentIRQsTblEntry OBJECT-TYPE
	SYNTAX  CfgAgentIRQEntry
	ACCESS  not-accessible
	STATUS  mandatory
	::= { cfgAgentIRQsTbl 1 }

CfgAgentIRQEntry ::= SEQUENCE
	{
	cfgAgentIRQ  INTEGER,
	cfgAgentIRQOwner  DisplayString,
	cfgAgentIRQBus  DisplayString,
	cfgAgentIRQClass  DisplayString
	}

cfgAgentIRQ OBJECT-TYPE
	SYNTAX  INTEGER
	ACCESS  read-only
	STATUS  mandatory
	DESCRIPTION
			"The allocated IRQ number."
	::= { cfgAgentIRQsTblEntry 1 }

cfgAgentIRQOwner OBJECT-TYPE
	SYNTAX  DisplayString
	ACCESS  read-only
	STATUS  mandatory
	DESCRIPTION
			"The name of the device/controller that has allocated this IRQ."
	::= { cfgAgentIRQsTblEntry 2 }

cfgAgentIRQBus OBJECT-TYPE
	SYNTAX  DisplayString
	ACCESS  read-only
	STATUS  mandatory
	DESCRIPTION
			"The bus that the IRQ device/controller uses."
	::= { cfgAgentIRQsTblEntry 3 }

cfgAgentIRQClass OBJECT-TYPE
	SYNTAX  DisplayString
	ACCESS  read-only
	STATUS  mandatory
	DESCRIPTION
			"The class of the device/controller that has allocated this IRQ."
	::= { cfgAgentIRQsTblEntry 4 }


-- __________________________  MEMORY DEFINITION DATA  ___________________

cfgAgentMemSizeInMb OBJECT-TYPE
	SYNTAX  INTEGER
	ACCESS  read-only
	STATUS  mandatory
	DESCRIPTION
			"The size of physical memory on the system in megabytes."
	::= { cfgAgent 21 }

cfgAgentMemType OBJECT-TYPE
	SYNTAX  DisplayString
	ACCESS  read-only
	STATUS  mandatory
	DESCRIPTION
			"A description of the type of memory installed on the system."
	::= { cfgAgent 22 }

cfgAgentMemSpeed OBJECT-TYPE
	SYNTAX  INTEGER
	ACCESS  read-only
	STATUS  mandatory
	DESCRIPTION
			"The operating speed (in MHz) of the memory installed on the system."
	::= { cfgAgent 23 }

cfgAgentMemCacheInKb OBJECT-TYPE
	SYNTAX  INTEGER
	ACCESS  read-only
	STATUS  mandatory
	DESCRIPTION
			"The size of the memory hardware cache in kilobytes."
	::= { cfgAgent 24 }

cfgAgentMemBanks OBJECT-TYPE
	SYNTAX  INTEGER
	ACCESS  read-only
	STATUS  mandatory
	DESCRIPTION
			"The number of memory banks on this system."
	::= { cfgAgent 25 }

cfgAgentMemSpeedSupported OBJECT-TYPE
	SYNTAX  INTEGER
	ACCESS  read-only
	STATUS  mandatory
	DESCRIPTION
			"The supported speed (in MHz) of memory installed on the system."
	::= { cfgAgent 26 }


-- __________________________  I/O DEVICE DEFINITION DATA  _______________

cfgAgentIOKbdType OBJECT-TYPE
	SYNTAX  DisplayString
	ACCESS  read-only
	STATUS  mandatory
	DESCRIPTION
			"The type of keyboard in use on the system."
	::= { cfgAgent 27 }

cfgAgentIOMouseType OBJECT-TYPE
	SYNTAX  DisplayString
	ACCESS  read-only
	STATUS  mandatory
	DESCRIPTION
			"The type of mouse in use on the system."
	::= { cfgAgent 28 }

cfgAgentIOVidType OBJECT-TYPE
	SYNTAX  DisplayString
	ACCESS  read-only
	STATUS  mandatory
	DESCRIPTION
			"The type of display monitor in use on the system."
	::= { cfgAgent 29 }


-- __________________________  SERIAL PORT DEFINITION TABLE  _____________

cfgAgentnSerials OBJECT-TYPE
	SYNTAX  INTEGER
	ACCESS  read-only
	STATUS  mandatory
	DESCRIPTION
			"The number of serial ports listed in the subsequent serial ports table."
	::= { cfgAgent 30 }

cfgAgentSerialsTbl OBJECT-TYPE
	SYNTAX  SEQUENCE OF CfgAgentSerialEntry
	ACCESS  not-accessible
	STATUS  mandatory
	DESCRIPTION
			"Serial port table consisting of a list of serial ports."
	::= { cfgAgent 31 }

cfgAgentSerialsTblEntry OBJECT-TYPE
	SYNTAX  CfgAgentSerialEntry
	ACCESS  not-accessible
	STATUS  mandatory
	::= { cfgAgentSerialsTbl 1 }

CfgAgentSerialEntry ::= SEQUENCE
	{
	cfgAgentSerialPort  INTEGER
	}

cfgAgentSerialPort OBJECT-TYPE
	SYNTAX  INTEGER
	ACCESS  read-only
	STATUS  mandatory
	DESCRIPTION
			"The serial I/O port controller's port address."
	::= { cfgAgentSerialsTblEntry 1 }


-- __________________________  PARALLEL PORT DEFINITION TABLE  ___________

cfgAgentnParallels OBJECT-TYPE
	SYNTAX  INTEGER
	ACCESS  read-only
	STATUS  mandatory
	DESCRIPTION
			"The number of parallel ports listed in the subsequent parallel ports table."
	::= { cfgAgent 32 }

cfgAgentParallelsTbl OBJECT-TYPE
	SYNTAX  SEQUENCE OF CfgAgentParallelEntry
	ACCESS  not-accessible
	STATUS  mandatory
	DESCRIPTION
			"Parallel port table consisting of a list of parallel ports."
	::= { cfgAgent 33 }

cfgAgentParallelsTblEntry OBJECT-TYPE
	SYNTAX  CfgAgentParallelEntry
	ACCESS  not-accessible
	STATUS  mandatory
	::= { cfgAgentParallelsTbl 1 }

CfgAgentParallelEntry ::= SEQUENCE
	{
	cfgAgentParallelPort  INTEGER
	}

cfgAgentParallelPort OBJECT-TYPE
	SYNTAX  INTEGER
	ACCESS  read-only
	STATUS  mandatory
	DESCRIPTION
			"The parallel I/O port controller's port address."
	::= { cfgAgentParallelsTblEntry 1 }


-- __________________________  CONTROLLER DEFINITION TABLE  ______________

cfgAgentnControllers OBJECT-TYPE
	SYNTAX  INTEGER
	ACCESS  read-only
	STATUS  mandatory
	DESCRIPTION
			"The number of controllers listed in the subsequent controllers table."
	::= { cfgAgent 34 }

cfgAgentControllersTbl OBJECT-TYPE
	SYNTAX  SEQUENCE OF CfgAgentControllerEntry
	ACCESS  not-accessible
	STATUS  mandatory
	DESCRIPTION
			"Controller table consisting of a list of controllers."
	::= { cfgAgent 35 }

cfgAgentControllersTblEntry OBJECT-TYPE
	SYNTAX  CfgAgentControllerEntry
	ACCESS  not-accessible
	STATUS  mandatory
	::= { cfgAgentControllersTbl 1 }

CfgAgentControllerEntry ::= SEQUENCE
	{
	cfgAgentControllerType  DisplayString,
	cfgAgentControllerName  DisplayString,
	cfgAgentControllerIRQ  INTEGER
	}

cfgAgentControllerType OBJECT-TYPE
	SYNTAX  DisplayString
	ACCESS  read-only
	STATUS  mandatory
	DESCRIPTION
			"The type of device controller."
	::= { cfgAgentControllersTblEntry 1 }

cfgAgentControllerName OBJECT-TYPE
	SYNTAX  DisplayString
	ACCESS  read-only
	STATUS  mandatory
	DESCRIPTION
			"The controller's device name."
	::= { cfgAgentControllersTblEntry 2 }

cfgAgentControllerIRQ OBJECT-TYPE
	SYNTAX  INTEGER
	ACCESS  read-only
	STATUS  mandatory
	DESCRIPTION
			"The IRQ number used by the device controller."
	::= { cfgAgentControllersTblEntry 3 }


-- __________________________  SNMP TRAP DESTINATION TABLE  ______________

cfgAgentnTrapDests OBJECT-TYPE
	SYNTAX  INTEGER
	ACCESS  read-only
	STATUS  mandatory
	DESCRIPTION
			"The number of trap destinations listed in the subsequent trap destinations table."
	::= { cfgAgent 36 }

cfgAgentTrapDestsTbl OBJECT-TYPE
	SYNTAX  SEQUENCE OF CfgAgentTrapDestEntry
	ACCESS  not-accessible
	STATUS  mandatory
	DESCRIPTION
			"Trap destinations table consisting of a list of trap destinations."
	::= { cfgAgent 37 }

cfgAgentTrapDestsTblEntry OBJECT-TYPE
	SYNTAX  CfgAgentTrapDestEntry
	ACCESS  not-accessible
	STATUS  mandatory
	::= { cfgAgentTrapDestsTbl 1 }

CfgAgentTrapDestEntry ::= SEQUENCE
	{
	cfgAgentTrapDestId  DisplayString,
	cfgAgentTrapDestIPAddr  DisplayString
	}

cfgAgentTrapDestId OBJECT-TYPE
	SYNTAX  DisplayString
	ACCESS  read-only
	STATUS  mandatory
	DESCRIPTION
			"The identifier of this trap destination."
	::= { cfgAgentTrapDestsTblEntry 1 }

cfgAgentTrapDestIPAddr OBJECT-TYPE
	SYNTAX  DisplayString
	ACCESS  read-write
	STATUS  mandatory
	DESCRIPTION
			"The IP address of this trap destination."
	::= { cfgAgentTrapDestsTblEntry 2 }


-- __________________  NETWORK AGENT MIB  __________________

--
-- UNISYS Network Agent MIB definition
-- 1997 All rights reserved
-- 

netAgent        OBJECT IDENTIFIER ::= { unisysOpen 8 }
 
-- NetAgent MIB
 
netAgentVersion OBJECT-TYPE
	SYNTAX  INTEGER
	ACCESS  read-only
	STATUS  mandatory
	DESCRIPTION
			"The internal version number of this SNMP Extension Agent."
	::= { netAgent 1 }

netAgentRevision OBJECT-TYPE
	SYNTAX  INTEGER
	ACCESS  read-only
	STATUS  mandatory
	DESCRIPTION
			"The internal revision number of this SNMP Extension Agent."
	::= { netAgent 2 }

netAgentMIBVersion OBJECT-TYPE
	SYNTAX  INTEGER
	ACCESS  read-only
	STATUS  mandatory
	DESCRIPTION
			"The internal version number of the MIB for this SNMP Extension Agent."
	::= { netAgent 3 }

netAgentMIBRevision OBJECT-TYPE
	SYNTAX  INTEGER
	ACCESS  read-only
	STATUS  mandatory
	DESCRIPTION
			"The internal revision number of the MIB for this SNMP Extension Agent."
	::= { netAgent 4 }

netAgentMachineName OBJECT-TYPE
	SYNTAX  DisplayString
	ACCESS  read-only
	STATUS  mandatory
	DESCRIPTION
			"The network (NetBIOS) name of this computer."
	::= { netAgent 5 }

netAgentLogonServer OBJECT-TYPE
	SYNTAX  DisplayString
	ACCESS  read-only
	STATUS  mandatory
	DESCRIPTION
			"The network domain name that this computer is connected to."
	::= { netAgent 6 }


-- __________________________  NIC DEFINITION TABLE  _____________________

netAgentnNICs OBJECT-TYPE
	SYNTAX  INTEGER
	ACCESS  read-only
	STATUS  mandatory
	DESCRIPTION
			"The number of network interface cards (NIC) listed in the subsequent NIC table."
	::= { netAgent 7 }

netAgentNICsTbl OBJECT-TYPE
	SYNTAX  SEQUENCE OF NetAgentNICEntry
	ACCESS  not-accessible
	STATUS  mandatory
	DESCRIPTION
			"Network interface cards (NIC) table consisting of a list of installed system NICs."
	::= { netAgent 8 }

netAgentNICTblEntry OBJECT-TYPE
	SYNTAX  NetAgentNICEntry
	ACCESS  not-accessible
	STATUS  mandatory
	::= { netAgentNICsTbl 1 }

NetAgentNICEntry ::= SEQUENCE
	{
	netAgentVendorID  DisplayString,
	netAgentMACAddress  DisplayString,
	netAgentFirmwareVersion  INTEGER,
	netAgentFirmwareRevision  INTEGER,
	netAgentControllerType  DisplayString,
	netAgentControllerPort  INTEGER,
	netAgentControllerIRQ  INTEGER,
	netAgentControllerBaseIO  INTEGER,
	netAgentDataSent  INTEGER,
	netAgentDataReceived  INTEGER,
	netAgentNICDriver  DisplayString,
	netAgentDriverName  DisplayString
	}

netAgentVendorID OBJECT-TYPE
	SYNTAX  DisplayString
	ACCESS  read-only
	STATUS  mandatory
	DESCRIPTION
			"The manufacturer's internal network adapter card identification string."
	::= { netAgentNICTblEntry 1 }

netAgentMACAddress OBJECT-TYPE
	SYNTAX  DisplayString
	ACCESS  read-only
	STATUS  mandatory
	DESCRIPTION
			"The network adapter card's unique network address."
	::= { netAgentNICTblEntry 2 }

netAgentFirmwareVersion OBJECT-TYPE
	SYNTAX  INTEGER
	ACCESS  read-only
	STATUS  mandatory
	DESCRIPTION
			"The manufacturer's network adapter card firmware version."
	::= { netAgentNICTblEntry 3 }

netAgentFirmwareRevision OBJECT-TYPE
	SYNTAX  INTEGER
	ACCESS  read-only
	STATUS  mandatory
	DESCRIPTION
			"The manufacturer's network adapter card firmware revision."
	::= { netAgentNICTblEntry 4 }

netAgentControllerType OBJECT-TYPE
	SYNTAX  DisplayString
	ACCESS  read-only
	STATUS  mandatory
	DESCRIPTION
			"The type of PC bus connector used by this network adapter card."
	::= { netAgentNICTblEntry 5 }

netAgentControllerPort OBJECT-TYPE
	SYNTAX  INTEGER
	ACCESS  read-only
	STATUS  mandatory
	DESCRIPTION
			"The controller port number/address used by this network adapter card."
	::= { netAgentNICTblEntry 6 }

netAgentControllerIRQ OBJECT-TYPE
	SYNTAX  INTEGER
	ACCESS  read-only
	STATUS  mandatory
	DESCRIPTION
			"The controller IRQ number used by this network adapter card."
	::= { netAgentNICTblEntry 7 }

netAgentControllerBaseIO OBJECT-TYPE
	SYNTAX  INTEGER
	ACCESS  read-only
	STATUS  mandatory
	DESCRIPTION
			"The controller base IO address used by this network adapter card."
	::= { netAgentNICTblEntry 8 }

netAgentDataSent OBJECT-TYPE
	SYNTAX  INTEGER
	ACCESS  read-only
	STATUS  mandatory
	DESCRIPTION
			"The number of network packets sent by this computer."
	::= { netAgentNICTblEntry 9 }

netAgentDataReceived OBJECT-TYPE
	SYNTAX  INTEGER
	ACCESS  read-only
	STATUS  mandatory
	DESCRIPTION
			"The number of network packets received by this computer."
	::= { netAgentNICTblEntry 10 }

netAgentNICDriver OBJECT-TYPE
	SYNTAX  DisplayString
	ACCESS  read-only
	STATUS  mandatory
	DESCRIPTION
			"The network adapter card's driver specification."
	::= { netAgentNICTblEntry 11 }

netAgentDriverName OBJECT-TYPE
	SYNTAX  DisplayString
	ACCESS  read-only
	STATUS  mandatory
	DESCRIPTION
			"The network adapter card's driver name."
	::= { netAgentNICTblEntry 12 }


-- __________________  SOFTWARE AGENT MIB  __________________

--
-- UNISYS Software Agent MIB definition
-- 1997 All rights reserved
-- 

sftAgent        OBJECT IDENTIFIER ::= { unisysOpen 9 }
 
-- sftAgent MIB
 
sftAgentVersion OBJECT-TYPE
	SYNTAX  INTEGER
	ACCESS  read-only
	STATUS  mandatory
	DESCRIPTION
			"The internal version number of this SNMP Extension Agent."
	::= { sftAgent 1 }

sftAgentRevision OBJECT-TYPE
	SYNTAX  INTEGER
	ACCESS  read-only
	STATUS  mandatory
	DESCRIPTION
			"The internal revision number of this SNMP Extension Agent."
	::= { sftAgent 2 }

sftAgentMIBVersion OBJECT-TYPE
	SYNTAX  INTEGER
	ACCESS  read-only
	STATUS  mandatory
	DESCRIPTION
			"The internal version number of the MIB for this SNMP Extension Agent."
	::= { sftAgent 3 }

sftAgentMIBRevision OBJECT-TYPE
	SYNTAX  INTEGER
	ACCESS  read-only
	STATUS  mandatory
	DESCRIPTION
			"The internal revision number of the MIB for this SNMP Extension Agent."
	::= { sftAgent 4 }


-- __________________________  PACKAGE DEFINITION TABLE  _________________

sftAgentnPackages OBJECT-TYPE
	SYNTAX  INTEGER
	ACCESS  read-only
	STATUS  mandatory
	DESCRIPTION
			"The number of Packages listed in the subsequent Packages table."
	::= { sftAgent 5 }

sftAgentPackagesTbl OBJECT-TYPE
	SYNTAX  SEQUENCE OF SftAgentPackageEntry
	ACCESS  not-accessible
	STATUS  mandatory
	DESCRIPTION
			"Package table consisting of a list of uninstallable packages."
	::= { sftAgent 6 }

sftAgentPackagesTblEntry OBJECT-TYPE
	SYNTAX  SftAgentPackageEntry
	ACCESS  not-accessible
	STATUS  mandatory
	::= { sftAgentPackagesTbl 1 }

SftAgentPackageEntry ::= SEQUENCE
	{
	sftAgentPackage  DisplayString
	}

sftAgentPackage OBJECT-TYPE
	SYNTAX  DisplayString
	ACCESS  read-only
	STATUS  mandatory
	DESCRIPTION
			"The name of the package that can be uninstalled."
	::= { sftAgentPackagesTblEntry 1 }


-- __________________________  SERVICE DEFINITION TABLE  _________________

sftAgentnServices OBJECT-TYPE
	SYNTAX  INTEGER
	ACCESS  read-only
	STATUS  mandatory
	DESCRIPTION
			"The number of Services listed in the subsequent Services table."
	::= { sftAgent 7 }

sftAgentServicesTbl OBJECT-TYPE
	SYNTAX  SEQUENCE OF SftAgentServiceEntry
	ACCESS  not-accessible
	STATUS  mandatory
	DESCRIPTION
			"Service table consisting of a list of installed system services."
	::= { sftAgent 8 }

sftAgentServicesTblEntry OBJECT-TYPE
	SYNTAX  SftAgentServiceEntry
	ACCESS  not-accessible
	STATUS  mandatory
	::= { sftAgentServicesTbl 1 }

SftAgentServiceEntry ::= SEQUENCE
	{
	sftAgentService  DisplayString,
	sftAgentServiceStartup  INTEGER
	}

sftAgentService OBJECT-TYPE
	SYNTAX  DisplayString
	ACCESS  read-only
	STATUS  mandatory
	DESCRIPTION
			"The name of the service that has been installed."
	::= { sftAgentServicesTblEntry 1 }

sftAgentServiceStartup OBJECT-TYPE
	SYNTAX  INTEGER { boot(0), system(1), auto(2), manual(3), disabled(4) }
	ACCESS  read-only
	STATUS  mandatory
	DESCRIPTION
			"The service startup mode: boot(0), system(1), auto(2), manual(3), disabled(4)."
	::= { sftAgentServicesTblEntry 2 }


-- __________________________  DEVICE DEFINITION TABLE  __________________

sftAgentnDevices OBJECT-TYPE
	SYNTAX  INTEGER
	ACCESS  read-only
	STATUS  mandatory
	DESCRIPTION
			"The number of Devices listed in the subsequent Devices table."
	::= { sftAgent 9 }

sftAgentDevicesTbl OBJECT-TYPE
	SYNTAX  SEQUENCE OF SftAgentDeviceEntry
	ACCESS  not-accessible
	STATUS  mandatory
	DESCRIPTION
			"Device table consisting of a list of installed system devices."
	::= { sftAgent 10 }

sftAgentDevicesTblEntry OBJECT-TYPE
	SYNTAX  SftAgentDeviceEntry
	ACCESS  not-accessible
	STATUS  mandatory
	::= { sftAgentDevicesTbl 1 }

SftAgentDeviceEntry ::= SEQUENCE
	{
	sftAgentDevice  DisplayString,
	sftAgentDeviceStartup  INTEGER
	}

sftAgentDevice OBJECT-TYPE
	SYNTAX  DisplayString
	ACCESS  read-only
	STATUS  mandatory
	DESCRIPTION
			"The name of the device that has been installed."
	::= { sftAgentDevicesTblEntry 1 }

sftAgentDeviceStartup OBJECT-TYPE
	SYNTAX  INTEGER { boot(0), system(1), auto(2), manual(3), disabled(4) }
	ACCESS  read-only
	STATUS  mandatory
	DESCRIPTION
			"The device startup mode: boot(0), system(1), auto(2), manual(3), disabled(4)."
	::= { sftAgentDevicesTblEntry 2 }


-- __________________  STORAGE AGENT MIB  __________________

--
-- UNISYS Storage Agent MIB definition
-- 1997 All rights reserved
-- 
 
strAgent        OBJECT IDENTIFIER ::= { unisysOpen 10 }
 
-- StrAgent MIB
 
strAgentVersion OBJECT-TYPE
	SYNTAX  INTEGER
	ACCESS  read-only
	STATUS  mandatory
	DESCRIPTION
			"The internal version number of this SNMP Extension Agent."
	::= { strAgent 1 }

strAgentRevision OBJECT-TYPE
	SYNTAX  INTEGER
	ACCESS  read-only
	STATUS  mandatory
	DESCRIPTION
			"The internal revision number of this SNMP Extension Agent."
	::= { strAgent 2 }

strAgentMIBVersion OBJECT-TYPE
	SYNTAX  INTEGER
	ACCESS  read-only
	STATUS  mandatory
	DESCRIPTION
			"The internal version number of the MIB for this SNMP Extension Agent."
	::= { strAgent 3 }

strAgentMIBRevision OBJECT-TYPE
	SYNTAX  INTEGER
	ACCESS  read-only
	STATUS  mandatory
	DESCRIPTION
			"The internal revision number of the MIB for this SNMP Extension Agent."
	::= { strAgent 4 }


-- __________________________  CONTROLLER DEFINITION TABLE  ______________

strAgentnControllers OBJECT-TYPE
	SYNTAX  INTEGER
	ACCESS  read-only
	STATUS  mandatory
	DESCRIPTION
			"The number of disk controllers listed in the subsequent Controllers table."
	::= { strAgent 5 }

strAgentControllersTbl OBJECT-TYPE
	SYNTAX  SEQUENCE OF StrAgentControllerEntry
	ACCESS  not-accessible
	STATUS  mandatory
	DESCRIPTION
			"Controller table consisting of a list of uninstallable Controllers."
	::= { strAgent 6 }

strAgentControllersTblEntry OBJECT-TYPE
	SYNTAX  StrAgentControllerEntry
	ACCESS  not-accessible
	STATUS  mandatory
	::= { strAgentControllersTbl 1 }

StrAgentControllerEntry ::= SEQUENCE
	{
	strAgentCtlrType  DisplayString,
	strAgentCtlrVendor  DisplayString,
	strAgentCtlrFirmware  DisplayString,
	strAgentCtlrSerialNo  DisplayString,
	strAgentCtlrDMA  INTEGER,
	strAgentCtlrIRQ  INTEGER,
	strAgentCtlrAddress  INTEGER,
	strAgentCtlrIOPort  INTEGER
	}

strAgentCtlrType OBJECT-TYPE
	SYNTAX  DisplayString
	ACCESS  read-only
	STATUS  mandatory
	DESCRIPTION
			"The type of the controller:  SCSI or IDE."
	::= { strAgentControllersTblEntry 1 }

strAgentCtlrVendor OBJECT-TYPE
	SYNTAX  DisplayString
	ACCESS  read-only
	STATUS  mandatory
	DESCRIPTION
			"The name of the controller's vendor."
	::= { strAgentControllersTblEntry 2 }

strAgentCtlrFirmware OBJECT-TYPE
	SYNTAX  DisplayString
	ACCESS  read-only
	STATUS  mandatory
	DESCRIPTION
			"The description of the controller's firmware version."
	::= { strAgentControllersTblEntry 3 }

strAgentCtlrSerialNo OBJECT-TYPE
	SYNTAX  DisplayString
	ACCESS  read-only
	STATUS  mandatory
	DESCRIPTION
			"The name of the Controller that can be uninstalled."
	::= { strAgentControllersTblEntry 4 }

strAgentCtlrDMA OBJECT-TYPE
	SYNTAX  INTEGER
	ACCESS  read-only
	STATUS  mandatory
	DESCRIPTION
			"The DMA number used by the controller."
	::= { strAgentControllersTblEntry 5 }

strAgentCtlrIRQ OBJECT-TYPE
	SYNTAX  INTEGER
	ACCESS  read-only
	STATUS  mandatory
	DESCRIPTION
			"The IRQ number used by the controller."
	::= { strAgentControllersTblEntry 6 }

strAgentCtlrAddress OBJECT-TYPE
	SYNTAX  INTEGER
	ACCESS  read-only
	STATUS  mandatory
	DESCRIPTION
			"The memory address used by the controller."
	::= { strAgentControllersTblEntry 7 }

strAgentCtlrIOPort OBJECT-TYPE
	SYNTAX  INTEGER
	ACCESS  read-only
	STATUS  mandatory
	DESCRIPTION
			"The I/O port number used by the controller."
	::= { strAgentControllersTblEntry 8 }


-- __________________________  DISK DEFINITION TABLE  ____________________

strAgentnDisks OBJECT-TYPE
	SYNTAX  INTEGER
	ACCESS  read-only
	STATUS  mandatory
	DESCRIPTION
			"The number of Disks listed in the subsequent Disks table."
	::= { strAgent 7 }

strAgentDisksTbl OBJECT-TYPE
	SYNTAX  SEQUENCE OF StrAgentDiskEntry
	ACCESS  not-accessible
	STATUS  mandatory
	DESCRIPTION
			"Disk table consisting of a list of installed system disks."
	::= { strAgent 8 }

strAgentDisksTblEntry OBJECT-TYPE
	SYNTAX  StrAgentDiskEntry
	ACCESS  not-accessible
	STATUS  mandatory
	::= { strAgentDisksTbl 1 }

StrAgentDiskEntry ::= SEQUENCE
	{
	strAgentDiskVendor  DisplayString,
	strAgentDiskDescription  DisplayString,
	strAgentDiskFirmware  DisplayString,
	strAgentDiskPort  INTEGER,
	strAgentDiskBus  INTEGER,
	strAgentDiskLUN  INTEGER,
	strAgentDiskID  INTEGER,
	strAgentDiskSerialNo  DisplayString,
	strAgentDisknSectors  INTEGER,
	strAgentDiskDriveLetters  DisplayString,
	strAgentDiskSizeInMb  INTEGER,
	strAgentDiskState  INTEGER,
	strAgentDiskXfersPerSec  INTEGER,
	strAgentDiskSmartCond  INTEGER
	}

strAgentDiskVendor OBJECT-TYPE
	SYNTAX  DisplayString
	ACCESS  read-only
	STATUS  mandatory
	DESCRIPTION
			"The vendor of this disk device."
	::= { strAgentDisksTblEntry 1 }

strAgentDiskDescription OBJECT-TYPE
	SYNTAX  DisplayString
	ACCESS  read-only
	STATUS  mandatory
	DESCRIPTION
			"A description of the type of device."
	::= { strAgentDisksTblEntry 2 }

strAgentDiskFirmware OBJECT-TYPE
	SYNTAX  DisplayString
	ACCESS  read-only
	STATUS  mandatory
	DESCRIPTION
			"The description of the device's firmware version."
	::= { strAgentDisksTblEntry 3 }

strAgentDiskPort OBJECT-TYPE
	SYNTAX  INTEGER
	ACCESS  read-only
	STATUS  mandatory
	DESCRIPTION
			"The SCSI port this device is attached to."
	::= { strAgentDisksTblEntry 4 }

strAgentDiskBus OBJECT-TYPE
	SYNTAX  INTEGER
	ACCESS  read-only
	STATUS  mandatory
	DESCRIPTION
			"The SCSI bus number on the SCSI port that this device is attached to."
	::= { strAgentDisksTblEntry 5 }

strAgentDiskLUN OBJECT-TYPE
	SYNTAX  INTEGER
	ACCESS  read-only
	STATUS  mandatory
	DESCRIPTION
			"This SCSI device's logical unit number (LUN)."
	::= { strAgentDisksTblEntry 6 }

strAgentDiskID OBJECT-TYPE
	SYNTAX  INTEGER
	ACCESS  read-only
	STATUS  mandatory
	DESCRIPTION
			"This SCSI device's SCSI ID."
	::= { strAgentDisksTblEntry 7 }

strAgentDiskSerialNo OBJECT-TYPE
	SYNTAX  DisplayString
	ACCESS  read-only
	STATUS  mandatory
	DESCRIPTION
			"The vendor's serial number for the device."
	::= { strAgentDisksTblEntry 8 }

strAgentDisknSectors OBJECT-TYPE
	SYNTAX  INTEGER
	ACCESS  read-only
	STATUS  mandatory
	DESCRIPTION
			"The number of sectors (512b) that this device can store."
	::= { strAgentDisksTblEntry 9 }

strAgentDiskDriveLetters OBJECT-TYPE
	SYNTAX  DisplayString
	ACCESS  read-only
	STATUS  mandatory
	DESCRIPTION
			"A list of the drive letters that have storage on this device."
	::= { strAgentDisksTblEntry 10 }

strAgentDiskSizeInMb OBJECT-TYPE
	SYNTAX  INTEGER
	ACCESS  read-only
	STATUS  mandatory
	DESCRIPTION
			"The capacity (in megabytes) of this device."
	::= { strAgentDisksTblEntry 11 }

strAgentDiskState OBJECT-TYPE
	SYNTAX  INTEGER { accessable(1), offline(2) }
	ACCESS  read-only
	STATUS  mandatory
	DESCRIPTION
			"The operational state of the device: accessable(1), off-line(2)."
	::= { strAgentDisksTblEntry 12 }

strAgentDiskXfersPerSec OBJECT-TYPE
	SYNTAX  INTEGER
	ACCESS  read-only
	STATUS  mandatory
	DESCRIPTION
			"the number of disk transfers per second reported by this device."
	::= { strAgentDisksTblEntry 13 }

strAgentDiskSmartCond OBJECT-TYPE
	SYNTAX  INTEGER { unknown(0), safe(1), degraded(2) }
	ACCESS  read-only
	STATUS  mandatory
	DESCRIPTION
			"The SMART condition of the device: unknown(0), safe(1), degraded(2)."
	::= { strAgentDisksTblEntry 14 }


-- __________________________  FLOPPY DEFINITION TABLE  __________________

strAgentnFloppies OBJECT-TYPE
	SYNTAX  INTEGER
	ACCESS  read-only
	STATUS  mandatory
	DESCRIPTION
			"The number of floppy drives listed in the subsequent Floppies table."
	::= { strAgent 9 }

strAgentFloppyTbl OBJECT-TYPE
	SYNTAX  SEQUENCE OF StrAgentFloppyEntry
	ACCESS  not-accessible
	STATUS  mandatory
	DESCRIPTION
			"Floppy table consisting of a list of floppy devices."
	::= { strAgent 10 }

strAgentFloppyTblEntry OBJECT-TYPE
	SYNTAX  StrAgentFloppyEntry
	ACCESS  not-accessible
	STATUS  mandatory
	::= { strAgentFloppyTbl 1 }

StrAgentFloppyEntry ::= SEQUENCE
	{
	strAgentFlopVendor  DisplayString,
	strAgentFlopDescription  DisplayString,
	strAgentFlopFirmware  DisplayString,
	strAgentFlopSerialNo  DisplayString
	}

strAgentFlopVendor OBJECT-TYPE
	SYNTAX  DisplayString
	ACCESS  read-only
	STATUS  mandatory
	DESCRIPTION
			"The vendor information for this floppy drive."
	::= { strAgentFloppyTblEntry 1 }

strAgentFlopDescription OBJECT-TYPE
	SYNTAX  DisplayString
	ACCESS  read-only
	STATUS  mandatory
	DESCRIPTION
			"The vendor's description of this floppy drive."
	::= { strAgentFloppyTblEntry 2 }

strAgentFlopFirmware OBJECT-TYPE
	SYNTAX  DisplayString
	ACCESS  read-only
	STATUS  mandatory
	DESCRIPTION
			"The description and version information from this floppy drive's firmware"
	::= { strAgentFloppyTblEntry 3 }

strAgentFlopSerialNo OBJECT-TYPE
	SYNTAX  DisplayString
	ACCESS  read-only
	STATUS  mandatory
	DESCRIPTION
			"The serial number of this floppy drive."
	::= { strAgentFloppyTblEntry 4 }


-- __________________________  VOLUME DEFINITION TABLE  __________________

strAgentnVolumes OBJECT-TYPE
	SYNTAX  INTEGER
	ACCESS  read-only
	STATUS  mandatory
	DESCRIPTION
			"The number of volumes listed in the subsequent Volumes table."
	::= { strAgent 11 }

strAgentVolumesTbl OBJECT-TYPE
	SYNTAX  SEQUENCE OF StrAgentVolumeEntry
	ACCESS  not-accessible
	STATUS  mandatory
	DESCRIPTION
			"Volume table consisting of a list of installed storage volumes."
	::= { strAgent 12 }

strAgentVolumesTblEntry OBJECT-TYPE
	SYNTAX  StrAgentVolumeEntry
	ACCESS  not-accessible
	STATUS  mandatory
	::= { strAgentVolumesTbl 1 }

StrAgentVolumeEntry ::= SEQUENCE
	{
	strAgentVolDriveLetter  DisplayString,
	strAgentVolDriveLabel  DisplayString,
	strAgentVolFileSystemType  DisplayString,
	strAgentVolCapacityInMb  INTEGER,
	strAgentVolClusterSize  INTEGER,
	strAgentVolPercentUsed  INTEGER
	}

strAgentVolDriveLetter OBJECT-TYPE
	SYNTAX  DisplayString
	ACCESS  read-only
	STATUS  mandatory
	DESCRIPTION
			"The drive letter that allows access to this storage volume."
	::= { strAgentVolumesTblEntry 1 }

strAgentVolDriveLabel OBJECT-TYPE
	SYNTAX  DisplayString
	ACCESS  read-only
	STATUS  mandatory
	DESCRIPTION
			"The label assigned to this volume (for display purposes)."
	::= { strAgentVolumesTblEntry 2 }

strAgentVolFileSystemType OBJECT-TYPE
	SYNTAX  DisplayString
	ACCESS  read-only
	STATUS  mandatory
	DESCRIPTION
			"The type of file system configured for this volume (eg: FAT, NTFS)."
	::= { strAgentVolumesTblEntry 3 }

strAgentVolCapacityInMb OBJECT-TYPE
	SYNTAX  INTEGER
	ACCESS  read-only
	STATUS  mandatory
	DESCRIPTION
			"The size (in megabytes) of this storage volume."
	::= { strAgentVolumesTblEntry 4 }

strAgentVolClusterSize OBJECT-TYPE
	SYNTAX  INTEGER
	ACCESS  read-only
	STATUS  mandatory
	DESCRIPTION
			"The size of each cluster (storage unit) in sectors (512 bytes)."
	::= { strAgentVolumesTblEntry 5 }

strAgentVolPercentUsed OBJECT-TYPE
	SYNTAX  INTEGER
	ACCESS  read-only
	STATUS  mandatory
	DESCRIPTION
			"The percent of volume storage space used (monitored by the agent)."
	::= { strAgentVolumesTblEntry 6 }


-- __________________________  THRESHHOLD DEFINITION DATA  _______________

strAgentStateThreshhold OBJECT-TYPE
	SYNTAX  INTEGER
	ACCESS  read-write
	STATUS  mandatory
	DESCRIPTION
			"Indicates whether a drive that goes off-line should cause an alert.  (1 = yes)"
	::= { strAgent 13 }

strAgentSpaceThreshhold OBJECT-TYPE
	SYNTAX  INTEGER
	ACCESS  read-write
	STATUS  mandatory
	DESCRIPTION
			"Indicates the maximum disk consumption (%) allowed before an alert is issued."
	::= { strAgent 14 }


-- __________________________  TRAP DEFINITIONS  _________________________

strAgentIndex OBJECT-TYPE
	SYNTAX  INTEGER
	ACCESS  not-accessible
	STATUS  mandatory
	DESCRIPTION
			"Indicates the number (starting from 1) of the unit reported in an alert message."
	::= { strAgent 99 }

strAgentStateTrap TRAP-TYPE
	ENTERPRISE strAgent
	VARIABLES {
	           strAgentDiskState,
	           strAgentIndex
	          }
	DESCRIPTION
			"The disk drive is no longer accessable (off-line)."
	::= 1

strAgentSpaceTrap TRAP-TYPE
	ENTERPRISE strAgent
	VARIABLES {
	           strAgentVolPercentUsed,
	           strAgentIndex
	          }
	DESCRIPTION
			"The space used on the volume has exceeded the indicated threshhold."
	::= 2

strAgentSmartTrap TRAP-TYPE
	ENTERPRISE strAgent
	VARIABLES {
	           strAgentDiskSmartCond,
	           strAgentIndex
	          }
	DESCRIPTION
			"The condition of the disk drive has degraded.  It should be archived and replaced immediately to avoid data loss due to failure."
	::= 3

strAgentStateOkTrap TRAP-TYPE
	ENTERPRISE strAgent
	VARIABLES {
	           strAgentDiskState,
	           strAgentIndex
	          }
	DESCRIPTION
			"The disk drive is again accessable (on-line)."
	::= 11

strAgentSpaceOkTrap TRAP-TYPE
	ENTERPRISE strAgent
	VARIABLES {
	           strAgentVolPercentUsed,
	           strAgentIndex
	          }
	DESCRIPTION
			"The space used on the volume has returned to an acceptable level."
	::= 12

strAgentSmartOKTrap TRAP-TYPE
	ENTERPRISE strAgent
	VARIABLES {
	           strAgentDiskSmartCond,
	           strAgentIndex
	          }
	DESCRIPTION
			"The degraded condition of the disk drive has cleared.  Continue to monitor this drive's performance to ensure the integrity of its data."
	::= 13


-- __________________  SYSTEM STATISTICS AGENT MIB  __________________

--
-- UNISYS System Agent MIB definition
-- 1997 All rights reserved
-- 

sysAgent        OBJECT IDENTIFIER ::= { unisysOpen 11 }
 
-- sysAgent MIB
 
sysAgentVersion OBJECT-TYPE
	SYNTAX  INTEGER
	ACCESS  read-only
	STATUS  mandatory
	DESCRIPTION
			"The internal version number of this SNMP Extension Agent."
	::= { sysAgent 1 }

sysAgentRevision OBJECT-TYPE
	SYNTAX  INTEGER
	ACCESS  read-only
	STATUS  mandatory
	DESCRIPTION
			"The internal revision number of this SNMP Extension Agent."
	::= { sysAgent 2 }

sysAgentMIBVersion OBJECT-TYPE
	SYNTAX  INTEGER
	ACCESS  read-only
	STATUS  mandatory
	DESCRIPTION
			"The internal version number of the MIB for this SNMP Extension Agent."
	::= { sysAgent 3 }

sysAgentMIBRevision OBJECT-TYPE
	SYNTAX  INTEGER
	ACCESS  read-only
	STATUS  mandatory
	DESCRIPTION
			"The internal revision number of the MIB for this SNMP Extension Agent."
	::= { sysAgent 4 }

sysAgentCPUCyclesUsed OBJECT-TYPE
	SYNTAX  INTEGER
	ACCESS  read-only
	STATUS  mandatory
	DESCRIPTION
			"The percentage of CPU cycles used."
	::= { sysAgent 5 }

sysAgentPCICyclesUsed OBJECT-TYPE
	SYNTAX  INTEGER
	ACCESS  read-only
	STATUS  mandatory
	DESCRIPTION
			"The percentage of PCI bus cycles used."
	::= { sysAgent 6 }

sysAgentInterrupts OBJECT-TYPE
	SYNTAX  INTEGER
	ACCESS  read-only
	STATUS  mandatory
	DESCRIPTION
			"The number of interrupts processed per second."
	::= { sysAgent 7 }

sysAgentMemorySize OBJECT-TYPE
	SYNTAX  INTEGER
	ACCESS  read-only
	STATUS  mandatory
	DESCRIPTION
			"The size of memory in bytes."
	::= { sysAgent 8 }

sysAgentMemoryUsed OBJECT-TYPE
	SYNTAX  INTEGER
	ACCESS  read-only
	STATUS  mandatory
	DESCRIPTION
			"The percentage of memory in use."
	::= { sysAgent 9 }

sysAgentPageFaults OBJECT-TYPE
	SYNTAX  INTEGER
	ACCESS  read-only
	STATUS  mandatory
	DESCRIPTION
			"The number of page faults per second."
	::= { sysAgent 10 }

sysAgentPageFaultThreshhold OBJECT-TYPE
	SYNTAX  INTEGER
	ACCESS  read-write
	STATUS  mandatory
	DESCRIPTION
			"The minimum number of page faults per second that will generate an alert."
	::= { sysAgent 11 }

sysAgentMemoryThreshhold OBJECT-TYPE
	SYNTAX  INTEGER
	ACCESS  read-write
	STATUS  mandatory
	DESCRIPTION
			"The minimum amount of memory consumption that will generate an alert."
	::= { sysAgent 12 }


-- __________________________  TRAP DEFINITIONS  _________________________

sysAgentIndex OBJECT-TYPE
	SYNTAX  INTEGER
	ACCESS  not-accessible
	STATUS  mandatory
	DESCRIPTION
			"Indicates the number (starting from 1) of the unit reported in an alert message.  (Not used in this agent.)"
	::= { sysAgent 99 }

sysAgentMemTrap TRAP-TYPE
	ENTERPRISE sysAgent
	VARIABLES {
	           sysAgentMemoryUsed,
	           sysAgentIndex
	          }
	DESCRIPTION
			"The percentage of memory in use has exceeded the indicated threshhold."
	::= 1

sysAgentPageTrap TRAP-TYPE
	ENTERPRISE sysAgent
	VARIABLES {
	           sysAgentPageFaults,
	           sysAgentIndex
	          }
	DESCRIPTION
			"The number of page faults has exceeded the indicated threshhold."
	::= 2

sysAgentMemOkTrap TRAP-TYPE
	ENTERPRISE sysAgent
	VARIABLES {
	           sysAgentMemoryUsed,
	           sysAgentIndex
	          }
	DESCRIPTION
			"The percentage of memory in use has returned to an accecptable level."
	::= 11

sysAgentPageOkTrap TRAP-TYPE
	ENTERPRISE sysAgent
	VARIABLES {
	           sysAgentPageFaults,
	           sysAgentIndex
	          }
	DESCRIPTION
			"The number of page faults has returned to an accecptable level."
	::= 12


-- __________________  NETWORK AGENT MIB  __________________

--
-- UNISYS Environmental Monitoring Agent MIB definition for Laguna hardware
-- 1997 All rights reserved
-- 

ecmAgent        OBJECT IDENTIFIER ::= { unisysOpen 12 }
 
-- EcmAgent MIB
 
ecmAgentVersion OBJECT-TYPE
	SYNTAX  INTEGER
	ACCESS  read-only
	STATUS  mandatory
	DESCRIPTION
			"The internal version number of this SNMP Extension Agent."
	::= { ecmAgent 1 }

ecmAgentRevision OBJECT-TYPE
	SYNTAX  INTEGER
	ACCESS  read-only
	STATUS  mandatory
	DESCRIPTION
			"The internal revision number of this SNMP Extension Agent."
	::= { ecmAgent 2 }

ecmAgentMIBVersion OBJECT-TYPE
	SYNTAX  INTEGER
	ACCESS  read-only
	STATUS  mandatory
	DESCRIPTION
			"The internal version number of the MIB for this SNMP Extension Agent."
	::= { ecmAgent 3 }

ecmAgentMIBRevision OBJECT-TYPE
	SYNTAX  INTEGER
	ACCESS  read-only
	STATUS  mandatory
	DESCRIPTION
			"The internal revision number of the MIB for this SNMP Extension Agent."
	::= { ecmAgent 4 }

ecmAgentFirmwareVersion OBJECT-TYPE
	SYNTAX  INTEGER
	ACCESS  read-only
	STATUS  mandatory
	DESCRIPTION
			"The manufacturer's environmental monitoring hardware firmware version."
	::= { ecmAgent 5 }

-- __________________________  FAN DEFINITION TABLE  _____________________

ecmAgentnFans OBJECT-TYPE
	SYNTAX  INTEGER
	ACCESS  read-only
	STATUS  mandatory
	DESCRIPTION
			"The number of fans listed in the subsequent Fan table."
	::= { ecmAgent 6 }

ecmAgentFansTbl OBJECT-TYPE
	SYNTAX  SEQUENCE OF EcmAgentFanEntry
	ACCESS  not-accessible
	STATUS  mandatory
	DESCRIPTION
			"Fan table consisting of a list of installed system fans."
	::= { ecmAgent 7 }

ecmAgentFanTblEntry OBJECT-TYPE
	SYNTAX  EcmAgentFanEntry
	ACCESS  not-accessible
	STATUS  mandatory
	::= { ecmAgentFansTbl 1 }

EcmAgentFanEntry ::= SEQUENCE
	{
	ecmAgentFanPresent INTEGER,
	ecmAgentFanState INTEGER
	}

ecmAgentFanPresent OBJECT-TYPE
	SYNTAX  INTEGER
	ACCESS  read-only
	STATUS  mandatory
	DESCRIPTION
			"Indicates that this fan is present on the system (1 = yes, 2 = no)."
	::= { ecmAgentFanTblEntry 1 }

ecmAgentFanState OBJECT-TYPE
	SYNTAX  INTEGER
	ACCESS  read-only
	STATUS  mandatory
	DESCRIPTION
			"Indicates that this fan is operational (1 = yes, 2 = no)."
	::= { ecmAgentFanTblEntry 2 }

-- __________________________  POWER DEFINITION TABLE  ___________________

ecmAgentnPowers OBJECT-TYPE
	SYNTAX  INTEGER
	ACCESS  read-only
	STATUS  mandatory
	DESCRIPTION
			"The number of power supplies listed in the subsequent Power supply table."
	::= { ecmAgent 8 }

ecmAgentPowersTbl OBJECT-TYPE
	SYNTAX  SEQUENCE OF EcmAgentPowerEntry
	ACCESS  not-accessible
	STATUS  mandatory
	DESCRIPTION
			"Power table consisting of a list of installed system power supplies."
	::= { ecmAgent 9 }

ecmAgentPowerTblEntry OBJECT-TYPE
	SYNTAX  EcmAgentPowerEntry
	ACCESS  not-accessible
	STATUS  mandatory
	::= { ecmAgentPowersTbl 1 }

EcmAgentPowerEntry ::= SEQUENCE
	{
	ecmAgentPowerPresent INTEGER,
	ecmAgentPowerState INTEGER
	}

ecmAgentPowerPresent OBJECT-TYPE
	SYNTAX  INTEGER
	ACCESS  read-only
	STATUS  mandatory
	DESCRIPTION
			"Indicates that this power supply is present on the system (1 = yes, 2 = no)."
	::= { ecmAgentPowerTblEntry 1 }

ecmAgentPowerState OBJECT-TYPE
	SYNTAX  INTEGER
	ACCESS  read-only
	STATUS  mandatory
	DESCRIPTION
			"Indicates that this power supply is operational (1 = yes, 2 = no)."
	::= { ecmAgentPowerTblEntry 2 }

-- __________________________  VOLT DEFINITION TABLE  ____________________

ecmAgentnVolts OBJECT-TYPE
	SYNTAX  INTEGER
	ACCESS  read-only
	STATUS  mandatory
	DESCRIPTION
			"The number of Volts listed in the subsequent Volt table."
	::= { ecmAgent 10 }

ecmAgentVoltsTbl OBJECT-TYPE
	SYNTAX  SEQUENCE OF EcmAgentVoltEntry
	ACCESS  not-accessible
	STATUS  mandatory
	DESCRIPTION
			"Volt table consisting of a list of installed system Volts."
	::= { ecmAgent 11 }

ecmAgentVoltTblEntry OBJECT-TYPE
	SYNTAX  EcmAgentVoltEntry
	ACCESS  not-accessible
	STATUS  mandatory
	::= { ecmAgentVoltsTbl 1 }

EcmAgentVoltEntry ::= SEQUENCE
	{
	ecmAgentVoltage INTEGER,
	ecmAgentVoltLowFail INTEGER,
	ecmAgentVoltLowWarn INTEGER,
	ecmAgentVoltHighWarn INTEGER,
	ecmAgentVoltHighFail INTEGER,
	ecmAgentVoltState INTEGER
	}

ecmAgentVoltage OBJECT-TYPE
	SYNTAX  INTEGER
	ACCESS  read-only
	STATUS  mandatory
	DESCRIPTION
			"The current voltage reading at this voltage level."
	::= { ecmAgentVoltTblEntry 1 }

ecmAgentVoltLowFail OBJECT-TYPE
	SYNTAX  INTEGER
	ACCESS  read-only
	STATUS  mandatory
	DESCRIPTION
			"The low failure limit for the voltage threshold value."
	::= { ecmAgentVoltTblEntry 2 }

ecmAgentVoltLowWarn OBJECT-TYPE
	SYNTAX  INTEGER
	ACCESS  read-only
	STATUS  mandatory
	DESCRIPTION
			"The low warning limit for the voltage threshold value."
	::= { ecmAgentVoltTblEntry 3 }

ecmAgentVoltHighWarn OBJECT-TYPE
	SYNTAX  INTEGER
	ACCESS  read-only
	STATUS  mandatory
	DESCRIPTION
			"The high warning limit for the voltage threshold value."
	::= { ecmAgentVoltTblEntry 4 }

ecmAgentVoltHighFail OBJECT-TYPE
	SYNTAX  INTEGER
	ACCESS  read-only
	STATUS  mandatory
	DESCRIPTION
			"The high failure limit for the voltage threshold value."
	::= { ecmAgentVoltTblEntry 5 }

ecmAgentVoltState OBJECT-TYPE
	SYNTAX  INTEGER
	ACCESS  read-only
	STATUS  mandatory
	DESCRIPTION
			"The relative state of the voltage level (1 = low failure, 2 = low warning, 3 = normal, 4 = high warning, 5 = high failure)."
	::= { ecmAgentVoltTblEntry 6 }

-- __________________________  TEMP DEFINITION TABLE  ____________________

ecmAgentnTemps OBJECT-TYPE
	SYNTAX  INTEGER
	ACCESS  read-only
	STATUS  mandatory
	DESCRIPTION
			"The number of Temps listed in the subsequent Temp table."
	::= { ecmAgent 12 }

ecmAgentTempsTbl OBJECT-TYPE
	SYNTAX  SEQUENCE OF EcmAgentTempEntry
	ACCESS  not-accessible
	STATUS  mandatory
	DESCRIPTION
			"Temp table consisting of a list of installed system Temps."
	::= { ecmAgent 13 }

ecmAgentTempTblEntry OBJECT-TYPE
	SYNTAX  EcmAgentTempEntry
	ACCESS  not-accessible
	STATUS  mandatory
	::= { ecmAgentTempsTbl 1 }

EcmAgentTempEntry ::= SEQUENCE
	{
	ecmAgentTemperature INTEGER,
	ecmAgentTempLowFail INTEGER,
	ecmAgentTempLowWarn INTEGER,
	ecmAgentTempHighWarn INTEGER,
	ecmAgentTempHighFail INTEGER,
	ecmAgentTempState INTEGER
	}

ecmAgentTemperature OBJECT-TYPE
	SYNTAX  INTEGER
	ACCESS  read-only
	STATUS  mandatory
	DESCRIPTION
			"The current temperature reading at this temperature level."
	::= { ecmAgentTempTblEntry 1 }

ecmAgentTempLowFail OBJECT-TYPE
	SYNTAX  INTEGER
	ACCESS  read-only
	STATUS  mandatory
	DESCRIPTION
			"The low failure limit for the temperature threshold value."
	::= { ecmAgentTempTblEntry 2 }

ecmAgentTempLowWarn OBJECT-TYPE
	SYNTAX  INTEGER
	ACCESS  read-only
	STATUS  mandatory
	DESCRIPTION
			"The low warning limit for the temperature threshold value."
	::= { ecmAgentTempTblEntry 3 }

ecmAgentTempHighWarn OBJECT-TYPE
	SYNTAX  INTEGER
	ACCESS  read-only
	STATUS  mandatory
	DESCRIPTION
			"The high warning limit for the temperature threshold value."
	::= { ecmAgentTempTblEntry 4 }

ecmAgentTempHighFail OBJECT-TYPE
	SYNTAX  INTEGER
	ACCESS  read-only
	STATUS  mandatory
	DESCRIPTION
			"The high failure limit for the temperature threshold value."
	::= { ecmAgentTempTblEntry 5 }

ecmAgentTempState OBJECT-TYPE
	SYNTAX  INTEGER
	ACCESS  read-only
	STATUS  mandatory
	DESCRIPTION
			"The relative state of the temperature level (1 = low failure, 2 = low warning, 3 = normal, 4 = high warning, 5 = high failure)."
	::= { ecmAgentTempTblEntry 6 }

-- __________________________  CPU DEFINITION TABLE  _____________________

ecmAgentnCPUs OBJECT-TYPE
	SYNTAX  INTEGER
	ACCESS  read-only
	STATUS  mandatory
	DESCRIPTION
			"The number of CPUs listed in the subsequent CPU table."
	::= { ecmAgent 14 }

ecmAgentCPUsTbl OBJECT-TYPE
	SYNTAX  SEQUENCE OF EcmAgentCPUEntry
	ACCESS  not-accessible
	STATUS  mandatory
	DESCRIPTION
			"CPU table consisting of a list of installed system CPUs."
	::= { ecmAgent 15 }

ecmAgentCPUTblEntry OBJECT-TYPE
	SYNTAX  EcmAgentCPUEntry
	ACCESS  not-accessible
	STATUS  mandatory
	::= { ecmAgentCPUsTbl 1 }

EcmAgentCPUEntry ::= SEQUENCE
	{
	ecmAgentCPUUsage INTEGER
	}

ecmAgentCPUUsage OBJECT-TYPE
	SYNTAX  INTEGER
	ACCESS  read-only
	STATUS  mandatory
	DESCRIPTION
			"The percentage of CPU cycles used during the last sample period."
	::= { ecmAgentCPUTblEntry 4 }


-- __________________________  TRAP DEFINITIONS  _________________________

ecmAgentIndex OBJECT-TYPE
	SYNTAX  INTEGER
	ACCESS  not-accessible
	STATUS  mandatory
	DESCRIPTION
			"Indicates the number (starting from 1) of the unit reported in an alert message."
	::= { ecmAgent 99 }

ecmAgentFanTrap TRAP-TYPE
	ENTERPRISE ecmAgent
	VARIABLES {
	           ecmAgentFanState,
	           ecmAgentIndex
	          }
	DESCRIPTION
			"The indicated fan is no longer operational."
	::= 1

ecmAgentPowerTrap TRAP-TYPE
	ENTERPRISE ecmAgent
	VARIABLES {
	           ecmAgentPowerState,
	           ecmAgentIndex
	          }
	DESCRIPTION
			"The indicated power supply is no longer operational."
	::= 2

ecmAgentFanOKTrap TRAP-TYPE
	ENTERPRISE ecmAgent
	VARIABLES {
	           ecmAgentFanState,
	           ecmAgentIndex
	          }
	DESCRIPTION
			"The indicated fan is again operational."
	::= 11

ecmAgentPowerOKTrap TRAP-TYPE
	ENTERPRISE ecmAgent
	VARIABLES {
	           ecmAgentPowerState,
	           ecmAgentIndex
	          }
	DESCRIPTION
			"The indicated power supply is again operational."
	::= 12

ecmAgentVoltCritTrap TRAP-TYPE
	ENTERPRISE ecmAgent
	VARIABLES {
	           ecmAgentVoltState,
	           ecmAgentIndex
	          }
	DESCRIPTION
			"The indicated voltage level has exceeded a critical threshold."
	::= 3

ecmAgentVoltWarnTrap TRAP-TYPE
	ENTERPRISE ecmAgent
	VARIABLES {
	           ecmAgentVoltState,
	           ecmAgentIndex
	          }
	DESCRIPTION
			"The indicated voltage level is in the warning range of values."
	::= 4

ecmAgentVoltNormTrap TRAP-TYPE
	ENTERPRISE ecmAgent
	VARIABLES {
	           ecmAgentVoltState,
	           ecmAgentIndex
	          }
	DESCRIPTION
			"The indicated voltage level has returned to an acceptable level."
	::= 5

ecmAgentTempCritTrap TRAP-TYPE
	ENTERPRISE ecmAgent
	VARIABLES {
	           ecmAgentTempState,
	           ecmAgentIndex
	          }
	DESCRIPTION
			"The indicated temperature level has exceeded a critical threshold."
	::= 6

ecmAgentTempWarnTrap TRAP-TYPE
	ENTERPRISE ecmAgent
	VARIABLES {
	           ecmAgentTempState,
	           ecmAgentIndex
	          }
	DESCRIPTION
			"The indicated temperature level is in the warning range of values."
	::= 7

ecmAgentTempNormTrap TRAP-TYPE
	ENTERPRISE ecmAgent
	VARIABLES {
	           ecmAgentTempState,
	           ecmAgentIndex
	          }
	DESCRIPTION
			"The indicated temperature level has returned to an acceptable level."
	::= 8


-- __________________  DMI EVENT AGENT MIB  __________________

--
-- UNISYS DMI Event SNMP Agent MIB definition
-- 1997 All rights reserved
-- 

evtAgent        OBJECT IDENTIFIER ::= { unisysOpen 999 }
 
-- EvtAgent MIB
 
evtAgentVersion OBJECT-TYPE
	SYNTAX  INTEGER
	ACCESS  read-only
	STATUS  mandatory
	DESCRIPTION
			"The internal version number of this SNMP Extension Agent."
	::= { evtAgent 1 }

evtAgentRevision OBJECT-TYPE
	SYNTAX  INTEGER
	ACCESS  read-only
	STATUS  mandatory
	DESCRIPTION
			"The internal revision number of this SNMP Extension Agent."
	::= { evtAgent 2 }

evtAgentMIBVersion OBJECT-TYPE
	SYNTAX  INTEGER
	ACCESS  read-only
	STATUS  mandatory
	DESCRIPTION
			"The internal version number of the MIB for this SNMP Extension Agent."
	::= { evtAgent 3 }

evtAgentMIBRevision OBJECT-TYPE
	SYNTAX  INTEGER
	ACCESS  read-only
	STATUS  mandatory
	DESCRIPTION
			"The internal revision number of the MIB for this SNMP Extension Agent."
	::= { evtAgent 4 }


evtAgentnEventsQueued OBJECT-TYPE
	SYNTAX  INTEGER
	ACCESS  read-only
	STATUS  mandatory
	DESCRIPTION
			"The number of "
	::= { evtAgent 5 }

evtAgentnEventsReceived OBJECT-TYPE
	SYNTAX  INTEGER
	ACCESS  read-only
	STATUS  mandatory
	DESCRIPTION
			"The number of "
	::= { evtAgent 6 }


-- __________________________  TRAP DEFINITIONS  _________________________

--
--  The following values are common to every DMI event reported as a SNMP trap

evtAgentIPAddress OBJECT-TYPE
	SYNTAX  INTEGER
	ACCESS  not-accessible
	STATUS  mandatory
	DESCRIPTION
			"Indicates the IP address of the node that reported the DMI event."
	::= { evtAgent 1000 }

evtAgentSeverity OBJECT-TYPE
	SYNTAX  INTEGER
	ACCESS  not-accessible
	STATUS  mandatory
	DESCRIPTION
			"Indicates the VisiNet-II severity value of the event."
	::= { evtAgent 1001 }

evtAgentClass OBJECT-TYPE
	SYNTAX  INTEGER
	ACCESS  not-accessible
	STATUS  mandatory
	DESCRIPTION
			"Indicates the DMI event class description."
	::= { evtAgent 1002 }

--
--  The following is the list of DMI groups that report events

dmiVirusAgent   OBJECT IDENTIFIER ::= { evtAgent 2001 }
dmiMemoryAgent  OBJECT IDENTIFIER ::= { evtAgent 2003 }
dmiGDIAgent     OBJECT IDENTIFIER ::= { evtAgent 2005 }
dmiDiskAgent    OBJECT IDENTIFIER ::= { evtAgent 2007 }
dmiSMARTAgent   OBJECT IDENTIFIER ::= { evtAgent 2009 }
dmiParityAgent  OBJECT IDENTIFIER ::= { evtAgent 2015 }
dmiPOSTAgent    OBJECT IDENTIFIER ::= { evtAgent 2017 }

--
--  What remains is the comprehensive list of events reported as traps.

dmiVirusDetected TRAP-TYPE
	ENTERPRISE dmiVirusAgent
	VARIABLES {
	           evtAgentIPAddress,
	           evtAgentSeverity,
	           evtAgentClass
	          }
	DESCRIPTION
			"The DMI agent detected a virus during system initialization."
	::= 1

dmiVirtualMemoryOK TRAP-TYPE
	ENTERPRISE dmiMemoryAgent
	VARIABLES {
	           evtAgentIPAddress,
	           evtAgentSeverity,
	           evtAgentClass
	          }
	DESCRIPTION
			"The available virtual memory on the system is acceptable."
	::= 0

dmiVirtualMemoryLow TRAP-TYPE
	ENTERPRISE dmiMemoryAgent
	VARIABLES {
	           evtAgentIPAddress,
	           evtAgentSeverity,
	           evtAgentClass
	          }
	DESCRIPTION
			"The available virtual memory on the system is running low."
	::= 1

dmiVirtualMemoryOut TRAP-TYPE
	ENTERPRISE dmiMemoryAgent
	VARIABLES {
	           evtAgentIPAddress,
	           evtAgentSeverity,
	           evtAgentClass
	          }
	DESCRIPTION
			"The available virtual memory on the system is running out."
	::= 2

dmiGDIResourceOK TRAP-TYPE
	ENTERPRISE dmiGDIAgent
	VARIABLES {
	           evtAgentIPAddress,
	           evtAgentSeverity,
	           evtAgentClass
	          }
	DESCRIPTION
			"The available graphics resources on the system are acceptable."
	::= 0

dmiGDIResourceLow TRAP-TYPE
	ENTERPRISE dmiGDIAgent
	VARIABLES {
	           evtAgentIPAddress,
	           evtAgentSeverity,
	           evtAgentClass
	          }
	DESCRIPTION
			"The available graphics resources on the system are running low."
	::= 1

dmiGDIResourceOut TRAP-TYPE
	ENTERPRISE dmiGDIAgent
	VARIABLES {
	           evtAgentIPAddress,
	           evtAgentSeverity,
	           evtAgentClass
	          }
	DESCRIPTION
			"The available graphics resources on the system are running out."
	::= 2

dmiDiskSpaceOK TRAP-TYPE
	ENTERPRISE dmiDiskAgent
	VARIABLES {
	           evtAgentIPAddress,
	           evtAgentSeverity,
	           evtAgentClass
	          }
	DESCRIPTION
			"The available disk space on the system is acceptable."
	::= 0

dmiDiskSpaceLow TRAP-TYPE
	ENTERPRISE dmiDiskAgent
	VARIABLES {
	           evtAgentIPAddress,
	           evtAgentSeverity,
	           evtAgentClass
	          }
	DESCRIPTION
			"The available disk space on the system is running low."
	::= 1

dmiDiskSpaceOut TRAP-TYPE
	ENTERPRISE dmiDiskAgent
	VARIABLES {
	           evtAgentIPAddress,
	           evtAgentSeverity,
	           evtAgentClass
	          }
	DESCRIPTION
			"The available disk space on the system is running out."
	::= 2

dmiSMARTFailing TRAP-TYPE
	ENTERPRISE dmiSMARTAgent
	VARIABLES {
	           evtAgentIPAddress,
	           evtAgentSeverity,
	           evtAgentClass
	          }
	DESCRIPTION
			"The operating condition of a S.M.A.R.T. drive has degraded.  Archive and replace the drive to avoid subsequent data loss."
	::= 1

dmiSMARTNowOK TRAP-TYPE
	ENTERPRISE dmiSMARTAgent
	VARIABLES {
	           evtAgentIPAddress,
	           evtAgentSeverity,
	           evtAgentClass
	          }
	DESCRIPTION
			"The condition of a S.M.A.R.T. drive has returned to acceptable tolerances.  Continue to monitor closely the condition of the drive."
	::= 2

dmiParityCorrection TRAP-TYPE
	ENTERPRISE dmiParityAgent
	VARIABLES {
	           evtAgentIPAddress,
	           evtAgentSeverity,
	           evtAgentClass
	          }
	DESCRIPTION
			"The DMI agent detected a correctable memory parity error."
	::= 1

dmiParityFailure TRAP-TYPE
	ENTERPRISE dmiParityAgent
	VARIABLES {
	           evtAgentIPAddress,
	           evtAgentSeverity,
	           evtAgentClass
	          }
	DESCRIPTION
			"The DMI agent detected an uncorrectable memory parity error."
	::= 2

dmiPOSTError TRAP-TYPE
	ENTERPRISE dmiPOSTAgent
	VARIABLES {
	           evtAgentIPAddress,
	           evtAgentSeverity,
	           evtAgentClass
	          }
	DESCRIPTION
			"The DMI agent reported a P.O.S.T. error."
	::= 1

END
